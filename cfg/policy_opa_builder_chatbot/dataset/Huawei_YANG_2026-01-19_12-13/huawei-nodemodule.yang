module huawei-nodemodule {
 yang-version 1.1;
 namespace "urn:rdns:com:huawei:oammodel:huawei-nodemodule";
 prefix nodemodule;
 import huawei-ne {
 prefix ne;
 }
 import ietf-inet-types {
 prefix inet;
 }
 import ietf-interfaces {
 prefix if;
 }
 import ietf-ip {
 prefix ip;
 }
 import huawei-yang-types {
 prefix hwat;
 }
 import ietf-yang-types {
 prefix yang;
 }
 description
 "Auto-generated modular YANG for huawei-nodemodule" ;
 revision "2026-01-19" {
 description "Auto-generated abstract group module (aggregated lists from relations.xml). Generated at 2026-01-19 12:13.";
 }
 augment "/ne:NE" {
 container NodeModule {
  description "Abstract group container injected between NE and its direct child.";
  container attributes {
    leaf neName {
     type string;
     mandatory false;
    }
    leaf productversion {
     type string;
     mandatory false;
    }
  }
 }
 }
 augment "/ne:NE/nodemodule:NodeModule/NODE" {
  list AAL2NODE {
   max-elements 5;
   key "ADDR";
   leaf ADDR {
    type leafref {
     path "../attributes/ADDR";
     require-instance true;
    }
   }
   container attributes {
    uses AAL2NODE-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list AAL2PATH {
   max-elements 64;
   key "PATHID";
   leaf PATHID {
    type leafref {
     path "../attributes/PATHID";
     require-instance true;
    }
   }
   container attributes {
    uses AAL2PATH-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list ACL {
   max-elements 1040;
   key "ACLID";
   leaf ACLID {
    type leafref {
     path "../attributes/ACLID";
     require-instance true;
    }
   }
   container attributes {
    uses ACL-attributes;
    leaf modifier {
     type hwat:modifier_AMD;
     mandatory false;
    }
    leaf remark {
     type string;
     mandatory false;
    }
    leaf template {
     type string;
     mandatory false;
    }
   }
  }
 }
 augment "/ne:NE/nodemodule:NodeModule/NODE/ACL" {
  list ACLRULE {
   max-elements 2024;
   key "ACLID";
   leaf ACLID {
    type leafref {
     path "../attributes/ACLID";
     require-instance true;
    }
   }
   container attributes {
    uses ACLRULE-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EQUIPMENT" {
  list ALDCONNINFO {
   max-elements 128;
   key "CONNID";
   leaf CONNID {
    type leafref {
     path "../attributes/CONNID";
     require-instance true;
    }
   }
   container attributes {
    uses ALDCONNINFO-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EQUIPMENT/NGALD" {
  list ALDDEVICEDATA {
   max-elements 12;
   key "DEVICENO";
   leaf DEVICENO {
    type leafref {
     path "../attributes/DEVICENO";
     require-instance true;
    }
   }
   container attributes {
    uses ALDDEVICEDATA-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EQUIPMENT/NGALD" {
  list ALDSUBUNIT {
   max-elements 65;
   key "DEVICENO";
   leaf DEVICENO {
    type leafref {
     path "../attributes/DEVICENO";
     require-instance true;
    }
   }
   container attributes {
    uses ALDSUBUNIT-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list APPCERT {
   max-elements 3;
   key "APPCERT";
   leaf APPCERT {
    type leafref {
     path "../attributes/APPCERT";
     require-instance true;
    }
   }
   container attributes {
    uses APPCERT-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list BACKTUNNEL {
   max-elements 15;
   key "PORTID";
   leaf PORTID {
    type leafref {
     path "../attributes/PORTID";
     require-instance true;
    }
   }
   container attributes {
    uses BACKTUNNEL-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list BASEBANDEQM {
   max-elements 36;
   key "BASEBANDEQMID";
   leaf BASEBANDEQMID {
    type leafref {
     path "../attributes/BASEBANDEQMID";
     require-instance true;
    }
   }
   container attributes {
    uses BASEBANDEQM-attributes;
    leaf modifier {
     type hwat:modifier_AMD;
     mandatory false;
    }
    leaf remark {
     type string;
     mandatory false;
    }
    leaf template {
     type string;
     mandatory false;
    }
   }
  }
 }
 augment "/ne:NE/nodemodule:NodeModule/NODE/BASEBANDEQM" {
  list BASEBANDEQMBOARDREF {
   max-elements 12;
   key "BASEBANDEQMID BASEBANDEQMTYPE";
   leaf BASEBANDEQMID {
    type leafref {
     path "../attributes/BASEBANDEQMID";
     require-instance true;
    }
   }
   leaf BASEBANDEQMTYPE {
    type leafref {
     path "../attributes/BASEBANDEQMTYPE";
     require-instance true;
    }
   }
   container attributes {
    uses BASEBANDEQMBOARDREF-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list BFD {
   max-elements 96;
   key "KEYCHAINID";
   leaf KEYCHAINID {
    type leafref {
     path "../attributes/KEYCHAINID";
     require-instance true;
    }
   }
   container attributes {
    uses BFD-attributes;
    leaf modifier {
     type hwat:modifier_AMD;
     mandatory false;
    }
    leaf remark {
     type string;
     mandatory false;
    }
    leaf template {
     type string;
     mandatory false;
    }
   }
  }
 }
 augment "/ne:NE/nodemodule:NodeModule/NODE/BFDKEYCHAIN" {
  list BFDKEY {
   max-elements 3;
   key "KEYCHAINID";
   leaf KEYCHAINID {
    type leafref {
     path "../attributes/KEYCHAINID";
     require-instance true;
    }
   }
   container attributes {
    uses BFDKEY-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list BFDKEYCHAIN {
   max-elements 1;
   key "KEYCHAINID";
   leaf KEYCHAINID {
    type leafref {
     path "../attributes/KEYCHAINID";
     require-instance true;
    }
   }
   container attributes {
    uses BFDKEYCHAIN-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list BFDSESSION {
   max-elements 96;
   key "KEYCHAINID";
   leaf KEYCHAINID {
    type leafref {
     path "../attributes/KEYCHAINID";
     require-instance true;
    }
   }
   container attributes {
    uses BFDSESSION-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list CA {
   max-elements 6;
   key "POLICYID";
   leaf POLICYID {
    type leafref {
     path "../attributes/POLICYID";
     require-instance true;
    }
   }
   container attributes {
    uses CA-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list CERTCFG {
   max-elements 1;
   key "IKECHECKSW";
   leaf IKECHECKSW {
    type leafref {
     path "../attributes/IKECHECKSW";
     require-instance true;
    }
   }
   container attributes {
    uses CERTCFG-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list CERTCHKTSK {
   max-elements 1;
   key "ALMRNG";
   leaf ALMRNG {
    type leafref {
     path "../attributes/ALMRNG";
     require-instance true;
    }
   }
   container attributes {
    uses CERTCHKTSK-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list CERTDEPLOY {
   max-elements 1;
   key "CN";
   leaf CN {
    type leafref {
     path "../attributes/CN";
     require-instance true;
    }
   }
   container attributes {
    uses CERTDEPLOY-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list CERTMK {
   max-elements 20;
   key "CANAME";
   leaf CANAME {
    type leafref {
     path "../attributes/CANAME";
     require-instance true;
    }
   }
   container attributes {
    uses CERTMK-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list CERTREQ {
   max-elements 1;
   key "COMMNAME";
   leaf COMMNAME {
    type leafref {
     path "../attributes/COMMNAME";
     require-instance true;
    }
   }
   container attributes {
    uses CERTREQ-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list CPBEARER {
   max-elements 2625;
   key "CPBEARID";
   leaf CPBEARID {
    type leafref {
     path "../attributes/CPBEARID";
     require-instance true;
    }
   }
   container attributes {
    uses CPBEARER-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list CRL {
   max-elements 20;
   key "CERTNAME";
   leaf CERTNAME {
    type leafref {
     path "../attributes/CERTNAME";
     require-instance true;
    }
   }
   container attributes {
    uses CRL-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list CRLPOLICY {
   max-elements 1;
   key "CRLPOLICY";
   leaf CRLPOLICY {
    type leafref {
     path "../attributes/CRLPOLICY";
     require-instance true;
    }
   }
   container attributes {
    uses CRLPOLICY-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list CRLTSK {
   max-elements 6;
   key "TSKID";
   leaf TSKID {
    type leafref {
     path "../attributes/TSKID";
     require-instance true;
    }
   }
   container attributes {
    uses CRLTSK-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list DEVIP {
   max-elements 128;
   key "VRFIDX";
   leaf VRFIDX {
    type leafref {
     path "../attributes/VRFIDX";
     require-instance true;
    }
   }
   container attributes {
    uses DEVIP-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list DFUMLCLIENT {
   max-elements 2;
   key "UID";
   leaf UID {
    type leafref {
     path "../attributes/UID";
     require-instance true;
    }
   }
   container attributes {
    uses DFUMLCLIENT-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list DHCPRELAYSWITCH {
   max-elements 1;
   key "ES";
   leaf ES {
    type leafref {
     path "../attributes/ES";
     require-instance true;
    }
   }
   container attributes {
    uses DHCPRELAYSWITCH-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list DHCPSVRIP {
   max-elements 2;
   key "VRFIDX";
   leaf VRFIDX {
    type leafref {
     path "../attributes/VRFIDX";
     require-instance true;
    }
   }
   container attributes {
    uses DHCPSVRIP-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list DHCPSVRIP6 {
   max-elements 4;
   key "VRFIDX";
   leaf VRFIDX {
    type leafref {
     path "../attributes/VRFIDX";
     require-instance true;
    }
   }
   container attributes {
    uses DHCPSVRIP6-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list DHCPSW {
   max-elements 1;
   key "DELAYSW";
   leaf DELAYSW {
    type leafref {
     path "../attributes/DELAYSW";
     require-instance true;
    }
   }
   container attributes {
    uses DHCPSW-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list DIFPRI {
   max-elements 1;
   key "IPCLKPRI";
   leaf IPCLKPRI {
    type leafref {
     path "../attributes/IPCLKPRI";
     require-instance true;
    }
   }
   container attributes {
    uses DIFPRI-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list DLFLOWCTRLPARA {
   max-elements 144;
   key "BEAR";
   leaf BEAR {
    type leafref {
     path "../attributes/BEAR";
     require-instance true;
    }
   }
   container attributes {
    uses DLFLOWCTRLPARA-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list DSCP2PCPMAP {
   max-elements 16;
   key "DSCP2PCPMAPID";
   leaf DSCP2PCPMAPID {
    type leafref {
     path "../attributes/DSCP2PCPMAPID";
     require-instance true;
    }
   }
   container attributes {
    uses DSCP2PCPMAP-attributes;
    leaf modifier {
     type hwat:modifier_AMD;
     mandatory false;
    }
    leaf remark {
     type string;
     mandatory false;
    }
    leaf template {
     type string;
     mandatory false;
    }
   }
  }
 }
 augment "/ne:NE/nodemodule:NodeModule/NODE/DSCP2PCPMAP" {
  list DSCP2PCPREF {
   max-elements 64;
   key "DSCP2PCPMAPID";
   leaf DSCP2PCPMAPID {
    type leafref {
     path "../attributes/DSCP2PCPMAPID";
     require-instance true;
    }
   }
   container attributes {
    uses DSCP2PCPREF-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list DSCP2QUEMAP {
   max-elements 16;
   key "DSCP2QUEMAPID";
   leaf DSCP2QUEMAPID {
    type leafref {
     path "../attributes/DSCP2QUEMAPID";
     require-instance true;
    }
   }
   container attributes {
    uses DSCP2QUEMAP-attributes;
    leaf modifier {
     type hwat:modifier_AMD;
     mandatory false;
    }
    leaf remark {
     type string;
     mandatory false;
    }
    leaf template {
     type string;
     mandatory false;
    }
   }
  }
 }
 augment "/ne:NE/nodemodule:NodeModule/NODE/DSCP2QUEMAP" {
  list DSCP2QUEREF {
   max-elements 64;
   key "DSCP2QUEMAPID";
   leaf DSCP2QUEMAPID {
    type leafref {
     path "../attributes/DSCP2QUEMAPID";
     require-instance true;
    }
   }
   container attributes {
    uses DSCP2QUEREF-attributes;
    leaf modifier {
     type hwat:modifier_AMD;
     mandatory false;
    }
    leaf remark {
     type string;
     mandatory false;
    }
    leaf template {
     type string;
     mandatory false;
    }
   }
  }
 }
 augment "/ne:NE/nodemodule:NodeModule/NODE/VRF" {
  list DSCPMAP {
   max-elements 64;
   key "VRFIDX";
   leaf VRFIDX {
    type leafref {
     path "../attributes/VRFIDX";
     require-instance true;
    }
   }
   container attributes {
    uses DSCPMAP-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list DTLSPOLICY {
   max-elements 1;
   key "DTLSPOLICYID";
   leaf DTLSPOLICYID {
    type leafref {
     path "../attributes/DTLSPOLICYID";
     require-instance true;
    }
   }
   container attributes {
    uses DTLSPOLICY-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list E1T1 {
   max-elements 64;
   key "CLKM";
   leaf CLKM {
    type leafref {
     path "../attributes/CLKM";
     require-instance true;
    }
   }
   container attributes {
    uses E1T1-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list E1T1BEAR {
   max-elements 8;
   key "CN";
   leaf CN {
    type leafref {
     path "../attributes/CN";
     require-instance true;
    }
   }
   container attributes {
    uses E1T1BEAR-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list EP2IPRSCGRP {
   max-elements 456;
   key "MAPID";
   leaf MAPID {
    type leafref {
     path "../attributes/MAPID";
     require-instance true;
    }
   }
   container attributes {
    uses EP2IPRSCGRP-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list EP2RSCGRP {
   max-elements 456;
   key "RSCGRPID";
   leaf RSCGRPID {
    type leafref {
     path "../attributes/RSCGRPID";
     require-instance true;
    }
   }
   container attributes {
    uses EP2RSCGRP-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list EPGROUP {
   max-elements 74;
   key "EPGROUPID";
   leaf EPGROUPID {
    type leafref {
     path "../attributes/EPGROUPID";
     require-instance true;
    }
   }
   container attributes {
    uses EPGROUP-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list EQUIPMENT {
   max-elements 1;
   key "ODIID";
   leaf ODIID {
    type leafref {
     path "../attributes/ODIID";
     require-instance true;
    }
   }
   container attributes {
    uses EQUIPMENT-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list ETHCIPORT {
   max-elements 14;
   key "PORTID";
   leaf PORTID {
    type leafref {
     path "../attributes/PORTID";
     require-instance true;
    }
   }
   container attributes {
    uses ETHCIPORT-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list ETHPORT {
   max-elements 48;
   key "PORTID";
   leaf PORTID {
    type leafref {
     path "../attributes/PORTID";
     require-instance true;
    }
   }
   container attributes {
    uses ETHPORT-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list ETHTRK {
   max-elements 24;
   key "ARPPROXY";
   leaf ARPPROXY {
    type leafref {
     path "../attributes/ARPPROXY";
     require-instance true;
    }
   }
   container attributes {
    uses ETHTRK-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list ETHTRUNK {
   max-elements 24;
   key "PORTID";
   leaf PORTID {
    type leafref {
     path "../attributes/PORTID";
     require-instance true;
    }
   }
   container attributes {
    uses ETHTRUNK-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list FLEXIP4 {
   max-elements 2;
   key "FLEXIP4ID";
   leaf FLEXIP4ID {
    type leafref {
     path "../attributes/FLEXIP4ID";
     require-instance true;
    }
   }
   container attributes {
    uses FLEXIP4-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list FLOODDEFEND {
   max-elements 9;
   key "ALMSW";
   leaf ALMSW {
    type leafref {
     path "../attributes/ALMSW";
     require-instance true;
    }
   }
   container attributes {
    uses FLOODDEFEND-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list FRAATM {
   max-elements 64;
   key "CN";
   leaf CN {
    type leafref {
     path "../attributes/CN";
     require-instance true;
    }
   }
   container attributes {
    uses FRAATM-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list GEPMODELPARA {
   max-elements 1;
   key "DIRECTIPSECAUTOSETUPMODE";
   leaf DIRECTIPSECAUTOSETUPMODE {
    type leafref {
     path "../attributes/DIRECTIPSECAUTOSETUPMODE";
     require-instance true;
    }
   }
   container attributes {
    uses GEPMODELPARA-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list GMPIPADDR {
   max-elements 10;
   key "GMPIPADDRID";
   leaf GMPIPADDRID {
    type leafref {
     path "../attributes/GMPIPADDRID";
     require-instance true;
    }
   }
   container attributes {
    uses GMPIPADDR-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EPGROUP" {
  list GMPIPADDRREF {
   max-elements 6;
   key "EPGROUPID";
   leaf EPGROUPID {
    type leafref {
     path "../attributes/EPGROUPID";
     require-instance true;
    }
   }
   container attributes {
    uses GMPIPADDRREF-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EQUIPMENT" {
  list GNSS {
   max-elements 2;
   key "AGL";
   leaf AGL {
    type leafref {
     path "../attributes/AGL";
     require-instance true;
    }
   }
   container attributes {
    uses GNSS-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list GPM {
   max-elements 20;
   key "GPMID";
   leaf GPMID {
    type leafref {
     path "../attributes/GPMID";
     require-instance true;
    }
   }
   container attributes {
    uses GPM-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list GTPU {
   max-elements 1;
   key "DLGTPUSNCHKSW";
   leaf DLGTPUSNCHKSW {
    type leafref {
     path "../attributes/DLGTPUSNCHKSW";
     require-instance true;
    }
   }
   container attributes {
    uses GTPU-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list GTRANSPARA {
   max-elements 1;
   key "VLANID";
   leaf VLANID {
    type leafref {
     path "../attributes/VLANID";
     require-instance true;
    }
   }
   container attributes {
    uses GTRANSPARA-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list GTRANSPARAGW {
   max-elements 1;
   key "ARPAGINGTIME";
   leaf ARPAGINGTIME {
    type leafref {
     path "../attributes/ARPAGINGTIME";
     require-instance true;
    }
   }
   container attributes {
    uses GTRANSPARAGW-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list GUPTRANSPARA {
   max-elements 1;
   key "UPFLTSRVADMSW";
   leaf UPFLTSRVADMSW {
    type leafref {
     path "../attributes/UPFLTSRVADMSW";
     require-instance true;
    }
   }
   container attributes {
    uses GUPTRANSPARA-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list ICMPV6 {
   max-elements 1;
   key "ERRMSGSW";
   leaf ERRMSGSW {
    type leafref {
     path "../attributes/ERRMSGSW";
     require-instance true;
    }
   }
   container attributes {
    uses ICMPV6-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list IFIP {
   max-elements 128;
   key "VRFIDX";
   leaf VRFIDX {
    type leafref {
     path "../attributes/VRFIDX";
     require-instance true;
    }
   }
   container attributes {
    uses IFIP-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list IKECFG {
   max-elements 1;
   key "DSCP";
   leaf DSCP {
    type leafref {
     path "../attributes/DSCP";
     require-instance true;
    }
   }
   container attributes {
    uses IKECFG-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list IKEPEER {
   max-elements 1032;
   key "PROPID";
   leaf PROPID {
    type leafref {
     path "../attributes/PROPID";
     require-instance true;
    }
   }
   container attributes {
    uses IKEPEER-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list IKEPROPOSAL {
   max-elements 99;
   key "PROPID";
   leaf PROPID {
    type leafref {
     path "../attributes/PROPID";
     require-instance true;
    }
   }
   container attributes {
    uses IKEPROPOSAL-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list IMAGRP {
   max-elements 32;
   key "CLKM";
   leaf CLKM {
    type leafref {
     path "../attributes/CLKM";
     require-instance true;
    }
   }
   container attributes {
    uses IMAGRP-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list IMALNK {
   max-elements 64;
   key "CN";
   leaf CN {
    type leafref {
     path "../attributes/CN";
     require-instance true;
    }
   }
   container attributes {
    uses IMALNK-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list INTERFACE {
   max-elements 2308;
   key "ITFID";
   leaf ITFID {
    type leafref {
     path "../attributes/ITFID";
     require-instance true;
    }
   }
   container attributes {
    uses INTERFACE-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list INTERFACEPARA6 {
   max-elements 300;
   key "ITFID";
   leaf ITFID {
    type leafref {
     path "../attributes/ITFID";
     require-instance true;
    }
   }
   container attributes {
    uses INTERFACEPARA6-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list IP2IPRSCGRP {
   max-elements 256;
   key "IP2IPRSCGRPID";
   leaf IP2IPRSCGRPID {
    type leafref {
     path "../attributes/IP2IPRSCGRPID";
     require-instance true;
    }
   }
   container attributes {
    uses IP2IPRSCGRP-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list IP2RSCGRP {
   max-elements 128;
   key "RSCGRPID";
   leaf RSCGRPID {
    type leafref {
     path "../attributes/RSCGRPID";
     require-instance true;
    }
   }
   container attributes {
    uses IP2RSCGRP-attributes;
    leaf modifier {
     type hwat:modifier_AMD;
     mandatory false;
    }
    leaf remark {
     type string;
     mandatory false;
    }
    leaf template {
     type string;
     mandatory false;
    }
   }
  }
 }
 augment "/ne:NE/nodemodule:NodeModule/NODE/INTERFACE" {
  list IPADDR4 {
   max-elements 128;
   key "ITFID";
   leaf ITFID {
    type leafref {
     path "../attributes/ITFID";
     require-instance true;
    }
   }
   container attributes {
    uses IPADDR4-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list IPADDR6 {
   max-elements 64;
   key "IPADDR6ID";
   leaf IPADDR6ID {
    type leafref {
     path "../attributes/IPADDR6ID";
     require-instance true;
    }
   }
   container attributes {
    uses IPADDR6-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EQUIPMENT" {
  list IPCLKLNK {
   max-elements 2;
   key "PTPVLANID";
   leaf PTPVLANID {
    type leafref {
     path "../attributes/PTPVLANID";
     require-instance true;
    }
   }
   container attributes {
    uses IPCLKLNK-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list IPDLFLOWCTRLPARA {
   max-elements 144;
   key "PORTID";
   leaf PORTID {
    type leafref {
     path "../attributes/PORTID";
     require-instance true;
    }
   }
   container attributes {
    uses IPDLFLOWCTRLPARA-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list IPGPM {
   max-elements 20;
   key "IPGPMID";
   leaf IPGPMID {
    type leafref {
     path "../attributes/IPGPMID";
     require-instance true;
    }
   }
   container attributes {
    uses IPGPM-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list IPGUARD {
   max-elements 1;
   key "ARPLRNSTRICTPOLICY";
   leaf ARPLRNSTRICTPOLICY {
    type leafref {
     path "../attributes/ARPLRNSTRICTPOLICY";
     require-instance true;
    }
   }
   container attributes {
    uses IPGUARD-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list IPPATH {
   max-elements 320;
   key "PATHID";
   leaf PATHID {
    type leafref {
     path "../attributes/PATHID";
     require-instance true;
    }
   }
   container attributes {
    uses IPPATH-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list IPPMSESSION {
   max-elements 500;
   key "PATHID";
   leaf PATHID {
    type leafref {
     path "../attributes/PATHID";
     require-instance true;
    }
   }
   container attributes {
    uses IPPMSESSION-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list IPROUTE4 {
   max-elements 150;
   key "PORTID";
   leaf PORTID {
    type leafref {
     path "../attributes/PORTID";
     require-instance true;
    }
   }
   container attributes {
    uses IPROUTE4-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list IPROUTE6 {
   max-elements 640;
   key "ITFID";
   leaf ITFID {
    type leafref {
     path "../attributes/ITFID";
     require-instance true;
    }
   }
   container attributes {
    uses IPROUTE6-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list IPRSCGRP {
   max-elements 464;
   key "IPRSCGRPID";
   leaf IPRSCGRPID {
    type leafref {
     path "../attributes/IPRSCGRPID";
     require-instance true;
    }
   }
   container attributes {
    uses IPRSCGRP-attributes;
    leaf modifier {
     type hwat:modifier_AMD;
     mandatory false;
    }
    leaf remark {
     type string;
     mandatory false;
    }
    leaf template {
     type string;
     mandatory false;
    }
   }
  }
 }
 augment "/ne:NE/nodemodule:NodeModule/NODE/IPRSCGRP" {
  list IPRSCGRPALG {
   max-elements 1;
   key "IPRSCGRPID";
   leaf IPRSCGRPID {
    type leafref {
     path "../attributes/IPRSCGRPID";
     require-instance true;
    }
   }
   container attributes {
    uses IPRSCGRPALG-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list IPRT {
   max-elements 150;
   key "IFNO";
   leaf IFNO {
    type leafref {
     path "../attributes/IFNO";
     require-instance true;
    }
   }
   container attributes {
    uses IPRT-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list IPSECBIND {
   max-elements 12;
   key "CN";
   leaf CN {
    type leafref {
     path "../attributes/CN";
     require-instance true;
    }
   }
   container attributes {
    uses IPSECBIND-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list IPSECBINDITF {
   max-elements 2056;
   key "IPSECBINDITFID";
   leaf IPSECBINDITFID {
    type leafref {
     path "../attributes/IPSECBINDITFID";
     require-instance true;
    }
   }
   container attributes {
    uses IPSECBINDITF-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list IPSECPOLICY {
   max-elements 1032;
   key "ACLID";
   leaf ACLID {
    type leafref {
     path "../attributes/ACLID";
     require-instance true;
    }
   }
   container attributes {
    uses IPSECPOLICY-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list IPSECPROPOSAL {
   max-elements 99;
   key "OLD_PROPNAME";
   leaf OLD_PROPNAME {
    type leafref {
     path "../attributes/OLD_PROPNAME";
     require-instance true;
    }
   }
   container attributes {
    uses IPSECPROPOSAL-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list IPULFLOWCTRLPARA {
   max-elements 144;
   key "PORTID";
   leaf PORTID {
    type leafref {
     path "../attributes/PORTID";
     require-instance true;
    }
   }
   container attributes {
    uses IPULFLOWCTRLPARA-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list LOCALETHPORT {
   max-elements 1;
   key "ALMSW";
   leaf ALMSW {
    type leafref {
     path "../attributes/ALMSW";
     require-instance true;
    }
   }
   container attributes {
    uses LOCALETHPORT-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EQUIPMENT" {
  list LOCATION {
   max-elements 128;
   key "LOCATIONID";
   leaf LOCATIONID {
    type leafref {
     path "../attributes/LOCATIONID";
     require-instance true;
    }
   }
   container attributes {
    uses LOCATION-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list LOOPBACK {
   max-elements 128;
   key "PORTID";
   leaf PORTID {
    type leafref {
     path "../attributes/PORTID";
     require-instance true;
    }
   }
   container attributes {
    uses LOOPBACK-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EPGROUP" {
  list LOOSESCTPPEERREF {
   max-elements 768;
   key "EPGROUPID";
   leaf EPGROUPID {
    type leafref {
     path "../attributes/EPGROUPID";
     require-instance true;
    }
   }
   container attributes {
    uses LOOSESCTPPEERREF-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EPGROUP" {
  list LOOSEUPPEERREF {
   max-elements 1024;
   key "EPGROUPID";
   leaf EPGROUPID {
    type leafref {
     path "../attributes/EPGROUPID";
     require-instance true;
    }
   }
   container attributes {
    uses LOOSEUPPEERREF-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list LR {
   max-elements 80;
   key "CBS";
   leaf CBS {
    type leafref {
     path "../attributes/CBS";
     require-instance true;
    }
   }
   container attributes {
    uses LR-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list MPGRP {
   max-elements 32;
   key "PORTID";
   leaf PORTID {
    type leafref {
     path "../attributes/PORTID";
     require-instance true;
    }
   }
   container attributes {
    uses MPGRP-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list MPLNK {
   max-elements 128;
   key "ACFC";
   leaf ACFC {
    type leafref {
     path "../attributes/ACFC";
     require-instance true;
    }
   }
   container attributes {
    uses MPLNK-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list ND {
   max-elements 1;
   key "NDREACHABLETIME";
   leaf NDREACHABLETIME {
    type leafref {
     path "../attributes/NDREACHABLETIME";
     require-instance true;
    }
   }
   container attributes {
    uses ND-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EQUIPMENT" {
  list NGALD {
   max-elements 712;
   key "INSTALLERID";
   leaf INSTALLERID {
    type leafref {
     path "../attributes/INSTALLERID";
     require-instance true;
    }
   }
   container attributes {
    uses NGALD-attributes;
    leaf modifier {
     type hwat:modifier_AMD;
     mandatory false;
    }
    leaf remark {
     type string;
     mandatory false;
    }
    leaf template {
     type string;
     mandatory false;
    }
   }
  }
 }
 augment "/ne:NE/nodemodule:NodeModule" {
  list NODE {
   max-elements 1;
   key "NODEID";
   leaf NODEID {
    type leafref {
     path "../attributes/NODEID";
     require-instance true;
    }
   }
   container attributes {
    uses NODE-attributes;
    leaf modifier {
     type hwat:modifier_M;
     mandatory false;
    }
    leaf remark {
     type string;
     mandatory false;
    }
    leaf template {
     type string;
     mandatory false;
    }
   }
  }
 }
 augment "/ne:NE/nodemodule:NodeModule/NODE/SYSTEMOM" {
  list NTPCP {
   max-elements 4;
   key "KEYID";
   leaf KEYID {
    type leafref {
     path "../attributes/KEYID";
     require-instance true;
    }
   }
   container attributes {
    uses NTPCP-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list OMCH {
   max-elements 2;
   key "RSCGRPID";
   leaf RSCGRPID {
    type leafref {
     path "../attributes/RSCGRPID";
     require-instance true;
    }
   }
   container attributes {
    uses OMCH-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list PACKETFILTER {
   max-elements 4;
   key "ACLID";
   leaf ACLID {
    type leafref {
     path "../attributes/ACLID";
     require-instance true;
    }
   }
   container attributes {
    uses PACKETFILTER-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list PACKETFILTERING {
   max-elements 60;
   key "PACKETFILTERINGID";
   leaf PACKETFILTERINGID {
    type leafref {
     path "../attributes/PACKETFILTERINGID";
     require-instance true;
    }
   }
   container attributes {
    uses PACKETFILTERING-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list PLRTHRESHOLD {
   max-elements 1;
   key "PLRAT";
   leaf PLRAT {
    type leafref {
     path "../attributes/PLRAT";
     require-instance true;
    }
   }
   container attributes {
    uses PLRTHRESHOLD-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list PMTUCFG {
   max-elements 1;
   key "PORTNO";
   leaf PORTNO {
    type leafref {
     path "../attributes/PORTNO";
     require-instance true;
    }
   }
   container attributes {
    uses PMTUCFG-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list PORTLR {
   max-elements 80;
   key "PORTLRID";
   leaf PORTLRID {
    type leafref {
     path "../attributes/PORTLRID";
     require-instance true;
    }
   }
   container attributes {
    uses PORTLR-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list PORTSECURITY {
   max-elements 96;
   key "CN";
   leaf CN {
    type leafref {
     path "../attributes/CN";
     require-instance true;
    }
   }
   container attributes {
    uses PORTSECURITY-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list PPPLNK {
   max-elements 128;
   key "PORTID";
   leaf PORTID {
    type leafref {
     path "../attributes/PORTID";
     require-instance true;
    }
   }
   container attributes {
    uses PPPLNK-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EQUIPMENT" {
  list RAE {
   max-elements 72;
   key "DEVICENO";
   leaf DEVICENO {
    type leafref {
     path "../attributes/DEVICENO";
     require-instance true;
    }
   }
   container attributes {
    uses RAE-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EQUIPMENT" {
  list RAS {
   max-elements 35;
   key "DEVICENO";
   leaf DEVICENO {
    type leafref {
     path "../attributes/DEVICENO";
     require-instance true;
    }
   }
   container attributes {
    uses RAS-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EQUIPMENT" {
  list RCSSERVER {
   max-elements 1;
   key "RCSSERVERNO";
   leaf RCSSERVERNO {
    type leafref {
     path "../attributes/RCSSERVERNO";
     require-instance true;
    }
   }
   container attributes {
    uses RCSSERVER-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EQUIPMENT" {
  list RET {
   max-elements 512;
   key "DEVICENO";
   leaf DEVICENO {
    type leafref {
     path "../attributes/DEVICENO";
     require-instance true;
    }
   }
   container attributes {
    uses RET-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EQUIPMENT/RET/RETSUBUNIT" {
  list RETDEVICEDATA {
   max-elements 1;
   key "DEVICENO SUBUNITNO";
   leaf DEVICENO {
    type leafref {
     path "../attributes/DEVICENO";
     require-instance true;
    }
   }
   leaf SUBUNITNO {
    type leafref {
     path "../attributes/SUBUNITNO";
     require-instance true;
    }
   }
   container attributes {
    uses RETDEVICEDATA-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EQUIPMENT/RET" {
  list RETSUBUNIT {
   max-elements 8;
   key "DEVICENO";
   leaf DEVICENO {
    type leafref {
     path "../attributes/DEVICENO";
     require-instance true;
    }
   }
   container attributes {
    uses RETSUBUNIT-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EQUIPMENT" {
  list RFPATH {
   max-elements 128;
   key "RFPATHID";
   leaf RFPATHID {
    type leafref {
     path "../attributes/RFPATHID";
     require-instance true;
    }
   }
   container attributes {
    uses RFPATH-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list RSCGRP {
   max-elements 464;
   key "RSCGRPID";
   leaf RSCGRPID {
    type leafref {
     path "../attributes/RSCGRPID";
     require-instance true;
    }
   }
   container attributes {
    uses RSCGRP-attributes;
    leaf modifier {
     type hwat:modifier_AMD;
     mandatory false;
    }
    leaf remark {
     type string;
     mandatory false;
    }
    leaf template {
     type string;
     mandatory false;
    }
   }
  }
 }
 augment "/ne:NE/nodemodule:NodeModule/NODE/RSCGRP" {
  list RSCGRPALG {
   max-elements 1;
   key "CN SRN SN BEAR SBT RSCGRPID PT PN";
   leaf CN {
    type leafref {
     path "../attributes/CN";
     require-instance true;
    }
   }
   leaf SRN {
    type leafref {
     path "../attributes/SRN";
     require-instance true;
    }
   }
   leaf SN {
    type leafref {
     path "../attributes/SN";
     require-instance true;
    }
   }
   leaf BEAR {
    type leafref {
     path "../attributes/BEAR";
     require-instance true;
    }
   }
   leaf SBT {
    type leafref {
     path "../attributes/SBT";
     require-instance true;
    }
   }
   leaf RSCGRPID {
    type leafref {
     path "../attributes/RSCGRPID";
     require-instance true;
    }
   }
   leaf PT {
    type leafref {
     path "../attributes/PT";
     require-instance true;
    }
   }
   leaf PN {
    type leafref {
     path "../attributes/PN";
     require-instance true;
    }
   }
   container attributes {
    uses RSCGRPALG-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EQUIPMENT" {
  list RVD {
   max-elements 35;
   key "DEVICENO";
   leaf DEVICENO {
    type leafref {
     path "../attributes/DEVICENO";
     require-instance true;
    }
   }
   container attributes {
    uses RVD-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EQUIPMENT/RVD/RVDSUBUNIT" {
  list RVDDEVICEDATA {
   max-elements 1;
   key "DEVICENO SUBUNITNO";
   leaf DEVICENO {
    type leafref {
     path "../attributes/DEVICENO";
     require-instance true;
    }
   }
   leaf SUBUNITNO {
    type leafref {
     path "../attributes/SUBUNITNO";
     require-instance true;
    }
   }
   container attributes {
    uses RVDDEVICEDATA-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EQUIPMENT/RVD" {
  list RVDSUBUNIT {
   max-elements 8;
   key "DEVICENO";
   leaf DEVICENO {
    type leafref {
     path "../attributes/DEVICENO";
     require-instance true;
    }
   }
   container attributes {
    uses RVDSUBUNIT-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list SAALLNK {
   max-elements 64;
   key "RSCGRPID";
   leaf RSCGRPID {
    type leafref {
     path "../attributes/RSCGRPID";
     require-instance true;
    }
   }
   container attributes {
    uses SAALLNK-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EQUIPMENT" {
  list SASU {
   max-elements 35;
   key "DEVICENO";
   leaf DEVICENO {
    type leafref {
     path "../attributes/DEVICENO";
     require-instance true;
    }
   }
   container attributes {
    uses SASU-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list SCTPHOST {
   max-elements 24;
   key "SCTPHOSTID";
   leaf SCTPHOSTID {
    type leafref {
     path "../attributes/SCTPHOSTID";
     require-instance true;
    }
   }
   container attributes {
    uses SCTPHOST-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EPGROUP" {
  list SCTPHOSTREF {
   max-elements 2;
   key "EPGROUPID";
   leaf EPGROUPID {
    type leafref {
     path "../attributes/EPGROUPID";
     require-instance true;
    }
   }
   container attributes {
    uses SCTPHOSTREF-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list SCTPLNK {
   max-elements 2577;
   key "DTLSPOLICYID";
   leaf DTLSPOLICYID {
    type leafref {
     path "../attributes/DTLSPOLICYID";
     require-instance true;
    }
   }
   container attributes {
    uses SCTPLNK-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list SCTPPEER {
   max-elements 2577;
   key "SCTPPEERID";
   leaf SCTPPEERID {
    type leafref {
     path "../attributes/SCTPPEERID";
     require-instance true;
    }
   }
   container attributes {
    uses SCTPPEER-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EPGROUP" {
  list SCTPPEERREF {
   max-elements 768;
   key "EPGROUPID";
   leaf EPGROUPID {
    type leafref {
     path "../attributes/EPGROUPID";
     require-instance true;
    }
   }
   container attributes {
    uses SCTPPEERREF-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list SECTOR {
   max-elements 102;
   key "SECTORID";
   leaf SECTORID {
    type leafref {
     path "../attributes/SECTORID";
     require-instance true;
    }
   }
   container attributes {
    uses SECTOR-attributes;
    leaf modifier {
     type hwat:modifier_AMD;
     mandatory false;
    }
    leaf remark {
     type string;
     mandatory false;
    }
    leaf template {
     type string;
     mandatory false;
    }
   }
  }
 }
 augment "/ne:NE/nodemodule:NodeModule/NODE/SECTOR" {
  list SECTORANTENNAREF {
   max-elements 1536;
   key "SECTORID";
   leaf SECTORID {
    type leafref {
     path "../attributes/SECTORID";
     require-instance true;
    }
   }
   container attributes {
    uses SECTORANTENNAREF-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list SECTOREQM {
   max-elements 102;
   key "SECTOREQMID";
   leaf SECTOREQMID {
    type leafref {
     path "../attributes/SECTOREQMID";
     require-instance true;
    }
   }
   container attributes {
    uses SECTOREQM-attributes;
    leaf modifier {
     type hwat:modifier_AMD;
     mandatory false;
    }
    leaf remark {
     type string;
     mandatory false;
    }
    leaf template {
     type string;
     mandatory false;
    }
   }
  }
 }
 augment "/ne:NE/nodemodule:NodeModule/NODE/SECTOREQM" {
  list SECTOREQMANTENNAREF {
   max-elements 1536;
   key "SECTOREQMID";
   leaf SECTOREQMID {
    type leafref {
     path "../attributes/SECTOREQMID";
     require-instance true;
    }
   }
   container attributes {
    uses SECTOREQMANTENNAREF-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list SECURITYHOST {
   max-elements 32;
   key "SECURITYHOSTID";
   leaf SECURITYHOSTID {
    type leafref {
     path "../attributes/SECURITYHOSTID";
     require-instance true;
    }
   }
   container attributes {
    uses SECURITYHOST-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list SECURITYPEER {
   max-elements 512;
   key "SECURITYPEERID";
   leaf SECURITYPEERID {
    type leafref {
     path "../attributes/SECURITYPEERID";
     require-instance true;
    }
   }
   container attributes {
    uses SECURITYPEER-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list SECURITYTEMPLATE {
   max-elements 32;
   key "SECURITYTEMPLATEID";
   leaf SECURITYTEMPLATEID {
    type leafref {
     path "../attributes/SECURITYTEMPLATEID";
     require-instance true;
    }
   }
   container attributes {
    uses SECURITYTEMPLATE-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list SSL {
   max-elements 1;
   key "PID";
   leaf PID {
    type leafref {
     path "../attributes/PID";
     require-instance true;
    }
   }
   container attributes {
    uses SSL-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EQUIPMENT" {
  list STAGGEREDPOWERRECORD {
   max-elements 144;
   key "RECORDID";
   leaf RECORDID {
    type leafref {
     path "../attributes/RECORDID";
     require-instance true;
    }
   }
   container attributes {
    uses STAGGEREDPOWERRECORD-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list SUBNETVLAN {
   max-elements 128;
   key "VLANID";
   leaf VLANID {
    type leafref {
     path "../attributes/VLANID";
     require-instance true;
    }
   }
   container attributes {
    uses SUBNETVLAN-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list SYSTEMOM {
   max-elements 1;
   key "CFGSECLEV";
   leaf CFGSECLEV {
    type leafref {
     path "../attributes/CFGSECLEV";
     require-instance true;
    }
   }
   container attributes {
    uses SYSTEMOM-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list TACALG {
   max-elements 1;
   key "EMCTACPSW";
   leaf EMCTACPSW {
    type leafref {
     path "../attributes/EMCTACPSW";
     require-instance true;
    }
   }
   container attributes {
    uses TACALG-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EQUIPMENT" {
  list TASM {
   max-elements 1;
   key "SRCNO";
   leaf SRCNO {
    type leafref {
     path "../attributes/SRCNO";
     require-instance true;
    }
   }
   container attributes {
    uses TASM-attributes;
    leaf modifier {
     type hwat:modifier_AMD;
     mandatory false;
    }
    leaf remark {
     type string;
     mandatory false;
    }
    leaf template {
     type string;
     mandatory false;
    }
   }
  }
 }
 augment "/ne:NE/nodemodule:NodeModule/NODE/SYSTEMOM" {
  list TIMESRC {
   max-elements 1;
   key "AUTOSWITCH";
   leaf AUTOSWITCH {
    type leafref {
     path "../attributes/AUTOSWITCH";
     require-instance true;
    }
   }
   container attributes {
    uses TIMESRC-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EQUIPMENT" {
  list TMA {
   max-elements 35;
   key "DEVICENO";
   leaf DEVICENO {
    type leafref {
     path "../attributes/DEVICENO";
     require-instance true;
    }
   }
   container attributes {
    uses TMA-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list TOLCALG {
   max-elements 1;
   key "TRMDLOLCRELTH";
   leaf TRMDLOLCRELTH {
    type leafref {
     path "../attributes/TRMDLOLCRELTH";
     require-instance true;
    }
   }
   container attributes {
    uses TOLCALG-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list TRANSFUNCTIONSW {
   max-elements 1;
   key "DLLIMITSW";
   leaf DLLIMITSW {
    type leafref {
     path "../attributes/DLLIMITSW";
     require-instance true;
    }
   }
   container attributes {
    uses TRANSFUNCTIONSW-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list TREELNKPVC {
   max-elements 96;
   key "NO";
   leaf NO {
    type leafref {
     path "../attributes/NO";
     require-instance true;
    }
   }
   container attributes {
    uses TREELNKPVC-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list TRUSTCERT {
   max-elements 20;
   key "CERTNAME";
   leaf CERTNAME {
    type leafref {
     path "../attributes/CERTNAME";
     require-instance true;
    }
   }
   container attributes {
    uses TRUSTCERT-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list TSCROSS {
   max-elements 16;
   key "NO";
   leaf NO {
    type leafref {
     path "../attributes/NO";
     require-instance true;
    }
   }
   container attributes {
    uses TSCROSS-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list TUNNEL {
   max-elements 15;
   key "TUNNELID";
   leaf TUNNELID {
    type leafref {
     path "../attributes/TUNNELID";
     require-instance true;
    }
   }
   container attributes {
    uses TUNNEL-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list TUNNELITF {
   max-elements 1032;
   key "PORTID";
   leaf PORTID {
    type leafref {
     path "../attributes/PORTID";
     require-instance true;
    }
   }
   container attributes {
    uses TUNNELITF-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list TWAMPCLIENT {
   max-elements 24;
   key "CLIENTID";
   leaf CLIENTID {
    type leafref {
     path "../attributes/CLIENTID";
     require-instance true;
    }
   }
   container attributes {
    uses TWAMPCLIENT-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list TWAMPRESPONDER {
   max-elements 16;
   key "RESPONDERID";
   leaf RESPONDERID {
    type leafref {
     path "../attributes/RESPONDERID";
     require-instance true;
    }
   }
   container attributes {
    uses TWAMPRESPONDER-attributes;
    leaf modifier {
     type hwat:modifier_AMD;
     mandatory false;
    }
    leaf remark {
     type string;
     mandatory false;
    }
    leaf template {
     type string;
     mandatory false;
    }
   }
  }
 }
 augment "/ne:NE/nodemodule:NodeModule/NODE/TWAMPCLIENT" {
  list TWAMPSENDER {
   max-elements 16;
   key "CLIENTID";
   leaf CLIENTID {
    type leafref {
     path "../attributes/CLIENTID";
     require-instance true;
    }
   }
   container attributes {
    uses TWAMPSENDER-attributes;
    leaf modifier {
     type hwat:modifier_AMD;
     mandatory false;
    }
    leaf remark {
     type string;
     mandatory false;
    }
    leaf template {
     type string;
     mandatory false;
    }
   }
  }
 }
 augment "/ne:NE/nodemodule:NodeModule/NODE/SYSTEMOM" {
  list TZ {
   max-elements 1;
   key "DST";
   leaf DST {
    type leafref {
     path "../attributes/DST";
     require-instance true;
    }
   }
   container attributes {
    uses TZ-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list UDPSESSION {
   max-elements 2;
   key "UDPSESSIONGRPID";
   leaf UDPSESSIONGRPID {
    type leafref {
     path "../attributes/UDPSESSIONGRPID";
     require-instance true;
    }
   }
   container attributes {
    uses UDPSESSION-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list UDT {
   max-elements 87;
   key "UDTPARAGRPID";
   leaf UDTPARAGRPID {
    type leafref {
     path "../attributes/UDTPARAGRPID";
     require-instance true;
    }
   }
   container attributes {
    uses UDT-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list UDTPARAGRP {
   max-elements 49;
   key "UDTPARAGRPID";
   leaf UDTPARAGRPID {
    type leafref {
     path "../attributes/UDTPARAGRPID";
     require-instance true;
    }
   }
   container attributes {
    uses UDTPARAGRP-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list ULFLOWCTRLPARA {
   max-elements 144;
   key "BEAR";
   leaf BEAR {
    type leafref {
     path "../attributes/BEAR";
     require-instance true;
    }
   }
   container attributes {
    uses ULFLOWCTRLPARA-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list UNILNK {
   max-elements 64;
   key "CN";
   leaf CN {
    type leafref {
     path "../attributes/CN";
     require-instance true;
    }
   }
   container attributes {
    uses UNILNK-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list USERPLANEHOST {
   max-elements 32;
   key "UPHOSTID";
   leaf UPHOSTID {
    type leafref {
     path "../attributes/UPHOSTID";
     require-instance true;
    }
   }
   container attributes {
    uses USERPLANEHOST-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EPGROUP" {
  list USERPLANEHOSTREF {
   max-elements 12;
   key "EPGROUPID";
   leaf EPGROUPID {
    type leafref {
     path "../attributes/EPGROUPID";
     require-instance true;
    }
   }
   container attributes {
    uses USERPLANEHOSTREF-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list USERPLANEPEER {
   max-elements 3300;
   key "REMOTEID";
   leaf REMOTEID {
    type leafref {
     path "../attributes/REMOTEID";
     require-instance true;
    }
   }
   container attributes {
    uses USERPLANEPEER-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EPGROUP" {
  list USERPLANEPEERREF {
   max-elements 1024;
   key "EPGROUPID";
   leaf EPGROUPID {
    type leafref {
     path "../attributes/EPGROUPID";
     require-instance true;
    }
   }
   container attributes {
    uses USERPLANEPEERREF-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list VETHPORT {
   max-elements 16;
   key "VBIID";
   leaf VBIID {
    type leafref {
     path "../attributes/VBIID";
     require-instance true;
    }
   }
   container attributes {
    uses VETHPORT-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list VLANCLASS {
   max-elements 272;
   key "VLANID";
   leaf VLANID {
    type leafref {
     path "../attributes/VLANID";
     require-instance true;
    }
   }
   container attributes {
    uses VLANCLASS-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list VLANMAP {
   max-elements 48;
   key "VLANID";
   leaf VLANID {
    type leafref {
     path "../attributes/VLANID";
     require-instance true;
    }
   }
   container attributes {
    uses VLANMAP-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EQUIPMENT" {
  list VRET {
   max-elements 72;
   key "DEVICENO";
   leaf DEVICENO {
    type leafref {
     path "../attributes/DEVICENO";
     require-instance true;
    }
   }
   container attributes {
    uses VRET-attributes;
    leaf modifier {
     type hwat:modifier_AMD;
     mandatory false;
    }
    leaf remark {
     type string;
     mandatory false;
    }
    leaf template {
     type string;
     mandatory false;
    }
   }
  }
 }
 augment "/ne:NE/nodemodule:NodeModule/NODE/EQUIPMENT/VRET" {
  list VRETSUBUNIT {
   max-elements 8;
   key "DEVICENO";
   leaf DEVICENO {
    type leafref {
     path "../attributes/DEVICENO";
     require-instance true;
    }
   }
   container attributes {
    uses VRETSUBUNIT-attributes;
    leaf modifier {
     type hwat:modifier_AMD;
     mandatory false;
    }
    leaf remark {
     type string;
     mandatory false;
    }
    leaf template {
     type string;
     mandatory false;
    }
   }
  }
 }
 augment "/ne:NE/nodemodule:NodeModule/NODE" {
  list VRF {
   max-elements 32;
   key "IPSECVPNID";
   leaf IPSECVPNID {
    type leafref {
     path "../attributes/IPSECVPNID";
     require-instance true;
    }
   }
   container attributes {
    uses VRF-attributes;
    leaf modifier {
     type hwat:modifier_AMD;
     mandatory false;
    }
    leaf remark {
     type string;
     mandatory false;
    }
    leaf template {
     type string;
     mandatory false;
    }
   }
  }
 }
 augment "/if:interfaces/if:interface/ip:ipv4" {
  container aclrule-ipv4 {
   container attributes {
    uses ACLRULE-attributes;
   }
  }
 }
 augment "/if:interfaces/if:interface/ip:ipv4" {
  container bfd-ipv4 {
   container attributes {
    uses BFD-attributes;
   }
  }
 }
 augment "/if:interfaces/if:interface/ip:ipv6" {
  container bfd-ipv6 {
   container attributes {
    uses BFD-attributes;
   }
  }
 }
 augment "/if:interfaces/if:interface/ip:ipv4" {
  container bfdsession-ipv4 {
   container attributes {
    uses BFDSESSION-attributes;
   }
  }
 }
 augment "/if:interfaces/if:interface/ip:ipv4" {
  container ca-ipv4 {
   container attributes {
    uses CA-attributes;
   }
  }
 }
 augment "/if:interfaces/if:interface/ip:ipv6" {
  container ca-ipv6 {
   container attributes {
    uses CA-attributes;
   }
  }
 }
 augment "/if:interfaces/if:interface/ip:ipv4" {
  container certreq-ipv4 {
   container attributes {
    uses CERTREQ-attributes;
   }
  }
 }
 augment "/if:interfaces/if:interface/ip:ipv6" {
  container certreq-ipv6 {
   container attributes {
    uses CERTREQ-attributes;
   }
  }
 }
 augment "/if:interfaces/if:interface/ip:ipv4" {
  container crltsk-ipv4 {
   container attributes {
    uses CRLTSK-attributes;
   }
  }
 }
 augment "/if:interfaces/if:interface/ip:ipv6" {
  container crltsk-ipv6 {
   container attributes {
    uses CRLTSK-attributes;
   }
  }
 }
 augment "/if:interfaces/if:interface/ip:ipv4" {
  container devip-ipv4 {
   container attributes {
    uses DEVIP-attributes;
   }
  }
 }
 augment "/if:interfaces/if:interface/ip:ipv4" {
  container dfumlclient-ipv4 {
   container attributes {
    uses DFUMLCLIENT-attributes;
   }
  }
 }
 augment "/if:interfaces/if:interface/ip:ipv4" {
  container dhcpsvrip-ipv4 {
   container attributes {
    uses DHCPSVRIP-attributes;
   }
  }
 }
 augment "/if:interfaces/if:interface/ip:ipv6" {
  container dhcpsvrip6-ipv6 {
   container attributes {
    uses DHCPSVRIP6-attributes;
   }
  }
 }
 augment "/if:interfaces/if:interface/ip:ipv4" {
  container gmpipaddr-ipv4 {
   container attributes {
    uses GMPIPADDR-attributes;
   }
  }
 }
 augment "/if:interfaces/if:interface/ip:ipv4" {
  container ifip-ipv4 {
   container attributes {
    uses IFIP-attributes;
   }
  }
 }
 augment "/if:interfaces/if:interface/ip:ipv4" {
  container ikepeer-ipv4 {
   container attributes {
    uses IKEPEER-attributes;
   }
  }
 }
 augment "/if:interfaces/if:interface/ip:ipv4" {
  container ip2iprscgrp-ipv4 {
   container attributes {
    uses IP2IPRSCGRP-attributes;
   }
  }
 }
 augment "/if:interfaces/if:interface/ip:ipv6" {
  container ip2iprscgrp-ipv6 {
   container attributes {
    uses IP2IPRSCGRP-attributes;
   }
  }
 }
 augment "/if:interfaces/if:interface/ip:ipv4" {
  container ip2rscgrp-ipv4 {
   container attributes {
    uses IP2RSCGRP-attributes;
   }
  }
 }
 augment "/if:interfaces/if:interface/ip:ipv4" {
  container ipaddr4-ipv4 {
   container attributes {
    uses IPADDR4-attributes;
   }
  }
 }
 augment "/if:interfaces/if:interface/ip:ipv6" {
  container ipaddr6-ipv6 {
   container attributes {
    uses IPADDR6-attributes;
   }
  }
 }
 augment "/if:interfaces/if:interface/ip:ipv4" {
  container ipclklnk-ipv4 {
   container attributes {
    uses IPCLKLNK-attributes;
   }
  }
 }
 augment "/if:interfaces/if:interface/ip:ipv6" {
  container ipclklnk-ipv6 {
   container attributes {
    uses IPCLKLNK-attributes;
   }
  }
 }
 augment "/if:interfaces/if:interface" {
  container attributes {
   uses IPCLKLNK-attributes;
  }
 }
 augment "/if:interfaces/if:interface/ip:ipv4" {
  container ippath-ipv4 {
   container attributes {
    uses IPPATH-attributes;
   }
  }
 }
 augment "/if:interfaces/if:interface/ip:ipv4" {
  container ippmsession-ipv4 {
   container attributes {
    uses IPPMSESSION-attributes;
   }
  }
 }
 augment "/if:interfaces/if:interface/ip:ipv6" {
  container ippmsession-ipv6 {
   container attributes {
    uses IPPMSESSION-attributes;
   }
  }
 }
 augment "/if:interfaces/if:interface/ip:ipv4" {
  container iproute4-ipv4 {
   container attributes {
    uses IPROUTE4-attributes;
   }
  }
 }
 augment "/if:interfaces/if:interface/ip:ipv6" {
  container iproute6-ipv6 {
   container attributes {
    uses IPROUTE6-attributes;
   }
  }
 }
 augment "/if:interfaces/if:interface/ip:ipv4" {
  container iprt-ipv4 {
   container attributes {
    uses IPRT-attributes;
   }
  }
 }
 augment "/if:interfaces/if:interface/ip:ipv4" {
  container mpgrp-ipv4 {
   container attributes {
    uses MPGRP-attributes;
   }
  }
 }
 augment "/if:interfaces/if:interface/ip:ipv4" {
  container ntpcp-ipv4 {
   container attributes {
    uses NTPCP-attributes;
   }
  }
 }
 augment "/if:interfaces/if:interface/ip:ipv6" {
  container ntpcp-ipv6 {
   container attributes {
    uses NTPCP-attributes;
   }
  }
 }
 augment "/if:interfaces/if:interface/ip:ipv4" {
  container omch-ipv4 {
   container attributes {
    uses OMCH-attributes;
   }
  }
 }
 augment "/if:interfaces/if:interface/ip:ipv6" {
  container omch-ipv6 {
   container attributes {
    uses OMCH-attributes;
   }
  }
 }
 augment "/if:interfaces/if:interface/ip:ipv4" {
  container ppplnk-ipv4 {
   container attributes {
    uses PPPLNK-attributes;
   }
  }
 }
 augment "/if:interfaces/if:interface/ip:ipv4" {
  container sctphost-ipv4 {
   container attributes {
    uses SCTPHOST-attributes;
   }
  }
 }
 augment "/if:interfaces/if:interface/ip:ipv6" {
  container sctphost-ipv6 {
   container attributes {
    uses SCTPHOST-attributes;
   }
  }
 }
 augment "/if:interfaces/if:interface/ip:ipv4" {
  container sctplnk-ipv4 {
   container attributes {
    uses SCTPLNK-attributes;
   }
  }
 }
 augment "/if:interfaces/if:interface/ip:ipv6" {
  container sctplnk-ipv6 {
   container attributes {
    uses SCTPLNK-attributes;
   }
  }
 }
 augment "/if:interfaces/if:interface/ip:ipv4" {
  container sctppeer-ipv4 {
   container attributes {
    uses SCTPPEER-attributes;
   }
  }
 }
 augment "/if:interfaces/if:interface/ip:ipv6" {
  container sctppeer-ipv6 {
   container attributes {
    uses SCTPPEER-attributes;
   }
  }
 }
 augment "/if:interfaces/if:interface/ip:ipv4" {
  container securityhost-ipv4 {
   container attributes {
    uses SECURITYHOST-attributes;
   }
  }
 }
 augment "/if:interfaces/if:interface/ip:ipv6" {
  container securityhost-ipv6 {
   container attributes {
    uses SECURITYHOST-attributes;
   }
  }
 }
 augment "/if:interfaces/if:interface/ip:ipv4" {
  container securitypeer-ipv4 {
   container attributes {
    uses SECURITYPEER-attributes;
   }
  }
 }
 augment "/if:interfaces/if:interface/ip:ipv6" {
  container securitypeer-ipv6 {
   container attributes {
    uses SECURITYPEER-attributes;
   }
  }
 }
 augment "/if:interfaces/if:interface/ip:ipv4" {
  container subnetvlan-ipv4 {
   container attributes {
    uses SUBNETVLAN-attributes;
   }
  }
 }
 augment "/if:interfaces/if:interface/ip:ipv4" {
  container tunnelitf-ipv4 {
   container attributes {
    uses TUNNELITF-attributes;
   }
  }
 }
 augment "/if:interfaces/if:interface/ip:ipv6" {
  container tunnelitf-ipv6 {
   container attributes {
    uses TUNNELITF-attributes;
   }
  }
 }
 augment "/if:interfaces/if:interface/ip:ipv4" {
  container twampclient-ipv4 {
   container attributes {
    uses TWAMPCLIENT-attributes;
   }
  }
 }
 augment "/if:interfaces/if:interface/ip:ipv6" {
  container twampclient-ipv6 {
   container attributes {
    uses TWAMPCLIENT-attributes;
   }
  }
 }
 augment "/if:interfaces/if:interface/ip:ipv4" {
  container twampresponder-ipv4 {
   container attributes {
    uses TWAMPRESPONDER-attributes;
   }
  }
 }
 augment "/if:interfaces/if:interface/ip:ipv6" {
  container twampresponder-ipv6 {
   container attributes {
    uses TWAMPRESPONDER-attributes;
   }
  }
 }
 augment "/if:interfaces/if:interface/ip:ipv4" {
  container udpsession-ipv4 {
   container attributes {
    uses UDPSESSION-attributes;
   }
  }
 }
 augment "/if:interfaces/if:interface/ip:ipv4" {
  container userplanehost-ipv4 {
   container attributes {
    uses USERPLANEHOST-attributes;
   }
  }
 }
 augment "/if:interfaces/if:interface/ip:ipv6" {
  container userplanehost-ipv6 {
   container attributes {
    uses USERPLANEHOST-attributes;
   }
  }
 }
 augment "/if:interfaces/if:interface/ip:ipv4" {
  container userplanepeer-ipv4 {
   container attributes {
    uses USERPLANEPEER-attributes;
   }
  }
 }
 augment "/if:interfaces/if:interface/ip:ipv6" {
  container userplanepeer-ipv6 {
   container attributes {
    uses USERPLANEPEER-attributes;
   }
  }
 }
 augment "/if:interfaces/if:interface/ip:ipv4" {
  container vlanmap-ipv4 {
   container attributes {
    uses VLANMAP-attributes;
   }
  }
 }
 grouping AAL2NODE-attributes {
 leaf ADDR {
  type string {
   length "1..42";
  }
  mandatory false;
 }
 leaf OLD_BELONG {
  type enumeration {
   enum val--1;
   enum val-0;
   enum val-1;
  }
  mandatory false;
 }
 leaf BELONG {
  type enumeration {
   enum val--1;
   enum val-0;
   enum val-1;
  }
  mandatory false;
 }
 leaf OLD_FLAG {
  type enumeration {
   enum val--1;
   enum val-0;
   enum val-1;
  }
  mandatory false;
 }
 leaf FLAG {
  type enumeration {
   enum val--1;
   enum val-0;
   enum val-1;
  }
  mandatory false;
 }
 leaf LN {
  type uint8 {
   range "0..63";
  }
  mandatory false;
 }
 leaf OLD_NT {
  type enumeration {
   enum val--1;
   enum val-0;
   enum val-1;
  }
  mandatory false;
 }
 leaf NT {
  type enumeration {
   enum val--1;
   enum val-0;
   enum val-1;
  }
  mandatory false;
 }
 }
 grouping AAL2PATH-attributes {
 leaf OLD_ANI {
  type union {
   type int8 {
    range "-1..31";
   }
  }
  mandatory false;
 }
 leaf ANI {
  type union {
   type int8 {
    range "-1..31";
   }
  }
  mandatory false;
 }
 leaf CDVT {
  type uint32 {
   range "1024..13300000";
  }
  mandatory false;
 }
 leaf CN {
  type uint8 {
   range "0..7";
  }
  mandatory false;
 }
 leaf JNRSCGRP {
  type boolean;
  mandatory false;
 }
 leaf MBS {
  type uint16 {
   range "3..10000";
  }
  mandatory false;
 }
 leaf MCR {
  type uint16 {
   range "30..49526";
  }
  mandatory false;
 }
 leaf OLD_NT {
  type enumeration {
   enum val--1;
   enum val-0;
   enum val-1;
   enum val-2;
  }
  mandatory false;
 }
 leaf NT {
  type enumeration {
   enum val--1;
   enum val-0;
   enum val-1;
   enum val-2;
  }
  mandatory false;
 }
 leaf OLD_PATHID {
  type union {
   type int64 {
    range "-1..4294967295";
   }
  }
  mandatory false;
 }
 leaf PATHID {
  type union {
   type int64 {
    range "-1..4294967295";
   }
  }
  mandatory false;
 }
 leaf PCR {
  type uint16 {
   range "30..49529";
  }
  mandatory false;
 }
 leaf PN {
  type uint8 {
   range "0..7";
  }
  mandatory false;
 }
 leaf PT {
  type enumeration {
   enum val-0;
   enum val-1;
   enum val-5;
  }
  mandatory false;
 }
 leaf RCR {
  type uint32 {
   range "30..129717";
  }
  mandatory false;
 }
 leaf RSCGRPID {
  type uint8 {
   range "0..15";
  }
  mandatory false;
 }
 leaf RU {
  type boolean;
  mandatory false;
 }
 leaf SBT {
  type enumeration {
   enum val-0;
   enum val-3;
   enum val-4;
  }
  mandatory false;
 }
 leaf SCR {
  type uint16 {
   range "30..49526";
  }
  mandatory false;
 }
 leaf SN {
  type uint8 {
   range "0..7";
  }
  mandatory false;
 }
 leaf SRN {
  type uint8 {
   range "0..1";
  }
  mandatory false;
 }
 leaf ST {
  type enumeration {
   enum val-0;
   enum val-1;
   enum val-2;
   enum val-3;
   enum val-4;
  }
  mandatory false;
 }
 leaf USERLABEL {
  type string {
   length "0..255";
  }
  mandatory false;
 }
 leaf VCI {
  type uint16 {
   range "32..511";
  }
  mandatory false;
 }
 leaf VPI {
  type uint8 {
   range "0..255";
  }
  mandatory false;
 }
 }
 grouping ACL-attributes {
 leaf ACLDESC {
  type string {
   length "0..127";
  }
  mandatory false;
 }
 leaf OLD_ACLID {
  type union {
   type int16 {
    range "-1..9999";
   }
  }
  mandatory false;
 }
 leaf ACLID {
  type union {
   type int16 {
    range "-1..9999";
   }
  }
  mandatory false;
 }
 leaf CTRLMODE {
  type boolean;
  mandatory false;
 }
 }
 grouping ACLRULE-attributes {
 leaf OLD_ACLID {
  type union {
   type int16 {
    range "-1..9999";
   }
  }
  mandatory false;
 }
 leaf ACLID {
  type union {
   type int16 {
    range "-1..9999";
   }
  }
  mandatory false;
 }
 leaf ACTION {
  type boolean;
  mandatory false;
 }
 leaf CTRLMODE {
  type boolean;
  mandatory false;
 }
 leaf DIP {
  type inet:ipv4-address;
  mandatory false;
 }
 leaf DMPT {
  type boolean;
  mandatory false;
 }
 leaf DOP {
  type enumeration {
   enum val-1;
   enum val-2;
   enum val-3;
   enum val-4;
   enum val-5;
  }
  mandatory false;
 }
 leaf DPT1 {
  type uint16 {
   range "0..65535";
  }
  mandatory false;
 }
 leaf DPT2 {
  type uint16 {
   range "0..65535";
  }
  mandatory false;
 }
 leaf DSCP {
  type uint8 {
   range "0..63";
  }
  mandatory false;
 }
 leaf DWC {
  type inet:ipv4-address;
  mandatory false;
 }
 leaf MDSCP {
  type boolean;
  mandatory false;
 }
 leaf PT {
  type enumeration {
   enum val-0;
   enum val-1;
   enum val-6;
   enum val-17;
   enum val-132;
  }
  mandatory false;
 }
 leaf OLD_RULEID {
  type union {
   type int32 {
    range "-1..89999";
   }
  }
  mandatory false;
 }
 leaf RULEID {
  type union {
   type int32 {
    range "-1..89999";
   }
  }
  mandatory false;
 }
 leaf SIP {
  type inet:ipv4-address;
  mandatory false;
 }
 leaf SMPT {
  type boolean;
  mandatory false;
 }
 leaf SOP {
  type enumeration {
   enum val-1;
   enum val-2;
   enum val-3;
   enum val-4;
   enum val-5;
  }
  mandatory false;
 }
 leaf SPT1 {
  type uint16 {
   range "0..65535";
  }
  mandatory false;
 }
 leaf SPT2 {
  type uint16 {
   range "0..65535";
  }
  mandatory false;
 }
 leaf SWC {
  type inet:ipv4-address;
  mandatory false;
 }
 leaf USERLABEL {
  type string {
   length "0..48";
  }
  mandatory false;
 }
 leaf VLANID1 {
  type uint16 {
   range "1..4094";
  }
  mandatory false;
 }
 leaf VLANID2 {
  type uint16 {
   range "1..4094";
  }
  mandatory false;
 }
 leaf VLANIDOP {
  type enumeration {
   enum val-0;
   enum val-1;
   enum val-2;
  }
  mandatory false;
 }
 }
 grouping ALDCONNINFO-attributes {
 leaf ALDPORTNO {
  type uint8 {
   range "1..255";
  }
  mandatory false;
 }
 leaf OLD_CONNID {
  type union {
   type int32 {
    range "-1..65535";
   }
  }
  mandatory false;
 }
 leaf CONNID {
  type union {
   type int32 {
    range "-1..65535";
   }
  }
  mandatory false;
 }
 leaf CONNTYPE {
  type boolean;
  mandatory false;
 }
 leaf DEVICENO {
  type uint16 {
   range "0..1023";
  }
  mandatory false;
 }
 leaf RFPATHID {
  type uint16 {
   range "0..65535";
  }
  mandatory false;
 }
 leaf SUBUNITNO {
  type union {
   type uint8 {
    range "1..255";
   }
  }
  mandatory false;
 }
 }
 grouping ALDDEVICEDATA-attributes {
 leaf ALTITUDE {
  type union {
   type int32 {
    range "-327670..4000000";
   }
  }
  mandatory false;
 }
 leaf BAND1 {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-48;
   enum val-49;
   enum val-50;
   enum val-51;
   enum val-52;
   enum val-65;
   enum val-66;
   enum val-67;
   enum val-68;
   enum val-69;
   enum val-70;
   enum val-71;
   enum val-72;
   enum val-73;
   enum val-74;
   enum val-75;
   enum val-76;
   enum val-85;
  }
  mandatory false;
 }
 leaf BAND2 {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-48;
   enum val-49;
   enum val-50;
   enum val-51;
   enum val-52;
   enum val-65;
   enum val-66;
   enum val-67;
   enum val-68;
   enum val-69;
   enum val-70;
   enum val-71;
   enum val-72;
   enum val-73;
   enum val-74;
   enum val-75;
   enum val-76;
   enum val-85;
  }
  mandatory false;
 }
 leaf BAND3 {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-48;
   enum val-49;
   enum val-50;
   enum val-51;
   enum val-52;
   enum val-65;
   enum val-66;
   enum val-67;
   enum val-68;
   enum val-69;
   enum val-70;
   enum val-71;
   enum val-72;
   enum val-73;
   enum val-74;
   enum val-75;
   enum val-76;
   enum val-85;
  }
  mandatory false;
 }
 leaf BAND4 {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-48;
   enum val-49;
   enum val-50;
   enum val-51;
   enum val-52;
   enum val-65;
   enum val-66;
   enum val-67;
   enum val-68;
   enum val-69;
   enum val-70;
   enum val-71;
   enum val-72;
   enum val-73;
   enum val-74;
   enum val-75;
   enum val-76;
   enum val-85;
  }
  mandatory false;
 }
 leaf BEAMWIDTH1 {
  type uint16 {
   range "0..359";
  }
  mandatory false;
 }
 leaf BEAMWIDTH2 {
  type uint16 {
   range "0..359";
  }
  mandatory false;
 }
 leaf BEAMWIDTH3 {
  type uint16 {
   range "0..359";
  }
  mandatory false;
 }
 leaf BEAMWIDTH4 {
  type uint16 {
   range "0..359";
  }
  mandatory false;
 }
 leaf BEARING {
  type union {
   type uint32 {
    range "0..4294967295";
   }
  }
  mandatory false;
 }
 leaf BSID {
  type string {
   length "0..32";
  }
  mandatory false;
 }
 leaf DATE {
  type string {
   length "0..6";
  }
  mandatory false;
 }
 leaf DEVICENO {
  type union {
   type int16 {
    range "-1..1023";
   }
  }
  mandatory false;
 }
 leaf GAIN1 {
  type uint8 {
   range "0..255";
  }
  mandatory false;
 }
 leaf GAIN2 {
  type uint8 {
   range "0..255";
  }
  mandatory false;
 }
 leaf GAIN3 {
  type uint8 {
   range "0..255";
  }
  mandatory false;
 }
 leaf GAIN4 {
  type uint8 {
   range "0..255";
  }
  mandatory false;
 }
 leaf INSTALLERID {
  type string {
   length "0..5";
  }
  mandatory false;
 }
 leaf LATITUDEDEGFORMAT {
  type union {
   type int32 {
    range "-90000000..2147483647";
   }
  }
  mandatory false;
 }
 leaf LONGITUDEDEGFORMAT {
  type union {
   type int32 {
    range "-180000000..2147483647";
   }
  }
  mandatory false;
 }
 leaf MODELNO {
  type string {
   length "0..15";
  }
  mandatory false;
 }
 leaf SECTORID {
  type string {
   length "0..32";
  }
  mandatory false;
 }
 leaf SERIALNO {
  type string {
   length "0..17";
  }
  mandatory false;
 }
 leaf SUBTYPE {
  type enumeration {
   enum val-0;
   enum val-1;
   enum val-2;
   enum val-3;
   enum val-4;
   enum val-5;
  }
  mandatory false;
 }
 leaf SUBUNITNO {
  type union {
   type int8 {
    range "-1..12";
   }
  }
  mandatory false;
 }
 leaf TILT {
  type union {
   type int32 {
    range "-900..2147483647";
   }
  }
  mandatory false;
 }
 }
 grouping ALDSUBUNIT-attributes {
 leaf AER {
  type uint8 {
   range "0..100";
  }
  mandatory false;
 }
 leaf ANTENNAARRAYTYPE {
  type enumeration {
   enum val-0;
   enum val-1;
   enum val-2;
   enum val-3;
  }
  mandatory false;
 }
 leaf ANTENNAFORM {
  type boolean;
  mandatory false;
 }
 leaf AUTHORITYPOLICY {
  type enumeration {
   enum val-0;
   enum val-1;
   enum val-2;
   enum val-3;
  }
  mandatory false;
 }
 leaf AZIMUTH {
  type union {
   type int16 {
    range "-1800..32767";
   }
  }
  mandatory false;
 }
 leaf OLD_DEVICENO {
  type union {
   type int16 {
    range "-1..1023";
   }
  }
  mandatory false;
 }
 leaf DEVICENO {
  type union {
   type int16 {
    range "-1..1023";
   }
  }
  mandatory false;
 }
 leaf GAIN {
  type uint16 {
   range "0..65535";
  }
  mandatory false;
 }
 leaf HORIZONTALBW {
  type union {
   type int16 {
    range "-1800..32767";
   }
  }
  mandatory false;
 }
 leaf MECHINCALTILT {
  type union {
   type int32 {
    range "-900..2147483647";
   }
  }
  mandatory false;
 }
 leaf MECHNICALBEARING {
  type union {
   type uint32 {
    range "0..4294967295";
   }
  }
  mandatory false;
 }
 leaf MODE {
  type enumeration {
   enum val-0;
   enum val-1;
   enum val-255;
  }
  mandatory false;
 }
 leaf POSITIONWITHINSECTOR {
  type string {
   length "0..32";
  }
  mandatory false;
 }
 leaf SDAMODE {
  type enumeration {
   enum val-0;
   enum val-1;
   enum val-255;
  }
  mandatory false;
 }
 leaf SECTORID {
  type string {
   length "0..32";
  }
  mandatory false;
 }
 leaf SUBNAME {
  type string {
   length "0..83";
  }
  mandatory false;
 }
 leaf SUBTYPE {
  type enumeration {
   enum val-0;
   enum val-1;
   enum val-2;
   enum val-3;
   enum val-4;
   enum val-5;
  }
  mandatory false;
 }
 leaf OLD_SUBUNITNO {
  type union {
   type int8 {
    range "-1..65";
   }
  }
  mandatory false;
 }
 leaf SUBUNITNO {
  type union {
   type int8 {
    range "-1..65";
   }
  }
  mandatory false;
 }
 leaf TARGETCONTROLPORT {
  type union {
   type uint32 {
    range "1..4294967295";
   }
  }
  mandatory false;
 }
 leaf TILT {
  type union {
   type int16 {
    range "-300..32767";
   }
  }
  mandatory false;
 }
 leaf VBEAMWIDTH {
  type uint16 {
   range "0..3599";
  }
  mandatory false;
 }
 }
 grouping APPCERT-attributes {
 leaf APPCERT {
  type string {
   length "1..64";
  }
  mandatory false;
 }
 leaf APPTYPE {
  type enumeration {
   enum val--1;
   enum val-0;
   enum val-1;
   enum val-2;
  }
  mandatory false;
 }
 leaf RRUCERTREQSW {
  type boolean;
  mandatory false;
 }
 }
 grouping BACKTUNNEL-attributes {
 leaf DCN {
  type uint8 {
   range "0..7";
  }
  mandatory false;
 }
 leaf DSN {
  type uint8 {
   range "0..7";
  }
  mandatory false;
 }
 leaf DSRN {
  type uint8 {
   range "0..1";
  }
  mandatory false;
 }
 leaf OLD_PORTID {
  type union {
   type int8 {
    range "-1..14";
   }
  }
  mandatory false;
 }
 leaf PORTID {
  type union {
   type int8 {
    range "-1..14";
   }
  }
  mandatory false;
 }
 leaf SCN {
  type uint8 {
   range "0..7";
  }
  mandatory false;
 }
 leaf SSN {
  type uint8 {
   range "0..7";
  }
  mandatory false;
 }
 leaf SSRN {
  type uint8 {
   range "0..1";
  }
  mandatory false;
 }
 leaf TUNNELNO {
  type uint8 {
   range "0..7";
  }
  mandatory false;
 }
 leaf TUNNELTYPE {
  type boolean;
  mandatory false;
 }
 }
 grouping BASEBANDEQM-attributes {
 leaf OLD_BASEBANDEQMID {
  type union {
   type int8 {
    range "-1..23";
   }
  }
  mandatory false;
 }
 leaf BASEBANDEQMID {
  type union {
   type int8 {
    range "-1..23";
   }
  }
  mandatory false;
 }
 leaf OLD_BASEBANDEQMTYPE {
  type enumeration {
   enum val--1;
   enum val-0;
   enum val-1;
   enum val-2;
  }
  mandatory false;
 }
 leaf BASEBANDEQMTYPE {
  type enumeration {
   enum val--1;
   enum val-0;
   enum val-1;
   enum val-2;
  }
  mandatory false;
 }
 leaf UMTSDEMMODE {
  type enumeration {
   enum val-0;
   enum val-1;
   enum val-3;
   enum val-4;
   enum val-5;
  }
  mandatory false;
 }
 }
 grouping BASEBANDEQMBOARDREF-attributes {
 leaf BASEBANDEQMID {
  type union {
   type int8 {
    range "-1..23";
   }
  }
  mandatory false;
 }
 leaf BASEBANDEQMTYPE {
  type enumeration {
   enum val--1;
   enum val-0;
   enum val-1;
   enum val-2;
  }
  mandatory false;
 }
 leaf CN {
  type union {
   type int8 {
    range "-1..7";
   }
  }
  mandatory false;
 }
 leaf SN {
  type union {
   type int8 {
    range "-1..6";
   }
  }
  mandatory false;
 }
 leaf SRN {
  type union {
   type int8 {
    range "-1..1";
   }
  }
  mandatory false;
 }
 }
 grouping BFD-attributes {
 leaf BFDAUTHSW {
  type boolean;
  mandatory false;
 }
 leaf BFDAUTHTYPE {
  type enumeration {
   enum val-0;
   enum val-1;
   enum val-2;
   enum val-3;
  }
  mandatory false;
 }
 leaf OLD_BFDSN {
  type union {
   type int16 {
    range "-1..195";
   }
  }
  mandatory false;
 }
 leaf BFDSN {
  type union {
   type int16 {
    range "-1..195";
   }
  }
  mandatory false;
 }
 leaf CATLOG {
  type boolean;
  mandatory false;
 }
 leaf DM {
  type uint8 {
   range "3..10";
  }
  mandatory false;
 }
 leaf DSCP {
  type uint8 {
   range "0..63";
  }
  mandatory false;
 }
 leaf DSTIP {
  type inet:ipv4-address;
  mandatory false;
 }
 leaf DSTIPV6 {
  type inet:ipv6-address;
  mandatory false;
 }
 leaf HT {
  type boolean;
  mandatory false;
 }
 leaf IPVERSION {
  type boolean;
  mandatory false;
 }
 leaf KEYCHAINID {
  type uint8 {
   range "0..255";
  }
  mandatory false;
 }
 leaf MINRI {
  type uint16 {
   range "10..1000";
  }
  mandatory false;
 }
 leaf MINTI {
  type uint16 {
   range "10..1000";
  }
  mandatory false;
 }
 leaf MYDISCREAMINATOR {
  type uint16 {
   range "1..500";
  }
  mandatory false;
 }
 leaf MYDSCRMGENMODE {
  type enumeration {
   enum val-0;
   enum val-1;
   enum val-2;
  }
  mandatory false;
 }
 leaf SRCIP {
  type inet:ipv4-address;
  mandatory false;
 }
 leaf SRCIPV6 {
  type inet:ipv6-address;
  mandatory false;
 }
 leaf VER {
  type boolean;
  mandatory false;
 }
 leaf VRFIDX {
  type uint8 {
   range "0..31";
  }
  mandatory false;
 }
 }
 grouping BFDKEY-attributes {
 leaf KEY {
  type string {
   length "1..20";
  }
  mandatory false;
 }
 leaf OLD_KEYCHAINID {
  type union {
   type int16 {
    range "-1..255";
   }
  }
  mandatory false;
 }
 leaf KEYCHAINID {
  type union {
   type int16 {
    range "-1..255";
   }
  }
  mandatory false;
 }
 leaf OLD_KEYID {
  type union {
   type int16 {
    range "-1..255";
   }
  }
  mandatory false;
 }
 leaf KEYID {
  type union {
   type int16 {
    range "-1..255";
   }
  }
  mandatory false;
 }
 }
 grouping BFDKEYCHAIN-attributes {
 leaf KEYCHAINDESC {
  type string {
   length "0..127";
  }
  mandatory false;
 }
 leaf OLD_KEYCHAINID {
  type union {
   type int16 {
    range "-1..255";
   }
  }
  mandatory false;
 }
 leaf KEYCHAINID {
  type union {
   type int16 {
    range "-1..255";
   }
  }
  mandatory false;
 }
 }
 grouping BFDSESSION-attributes {
 leaf BFDAUTHSW {
  type boolean;
  mandatory false;
 }
 leaf BFDAUTHTYPE {
  type enumeration {
   enum val-0;
   enum val-1;
   enum val-2;
   enum val-3;
  }
  mandatory false;
 }
 leaf OLD_BFDSN {
  type union {
   type int8 {
    range "-1..95";
   }
  }
  mandatory false;
 }
 leaf BFDSN {
  type union {
   type int8 {
    range "-1..95";
   }
  }
  mandatory false;
 }
 leaf CATLOG {
  type boolean;
  mandatory false;
 }
 leaf OLD_CN {
  type union {
   type int8 {
    range "-1..7";
   }
  }
  mandatory false;
 }
 leaf CN {
  type union {
   type int8 {
    range "-1..7";
   }
  }
  mandatory false;
 }
 leaf DM {
  type uint8 {
   range "3..10";
  }
  mandatory false;
 }
 leaf DSCP {
  type uint8 {
   range "0..63";
  }
  mandatory false;
 }
 leaf DSTIP {
  type inet:ipv4-address;
  mandatory false;
 }
 leaf HT {
  type boolean;
  mandatory false;
 }
 leaf KEYCHAINID {
  type uint8 {
   range "0..255";
  }
  mandatory false;
 }
 leaf MINRI {
  type uint16 {
   range "10..1000";
  }
  mandatory false;
 }
 leaf MINTI {
  type uint16 {
   range "10..1000";
  }
  mandatory false;
 }
 leaf MYDSCRMGENMODE {
  type enumeration {
   enum val-0;
   enum val-1;
   enum val-2;
  }
  mandatory false;
 }
 leaf OLD_SN {
  type union {
   type int8 {
    range "-1..7";
   }
  }
  mandatory false;
 }
 leaf SN {
  type union {
   type int8 {
    range "-1..7";
   }
  }
  mandatory false;
 }
 leaf SRCIP {
  type inet:ipv4-address;
  mandatory false;
 }
 leaf OLD_SRN {
  type union {
   type int8 {
    range "-1..1";
   }
  }
  mandatory false;
 }
 leaf SRN {
  type union {
   type int8 {
    range "-1..1";
   }
  }
  mandatory false;
 }
 leaf VER {
  type boolean;
  mandatory false;
 }
 leaf VRFIDX {
  type uint8 {
   range "0..7";
  }
  mandatory false;
 }
 }
 grouping CA-attributes {
 leaf OLD_CANAME {
  type string {
   length "1..127";
  }
  mandatory false;
 }
 leaf CANAME {
  type string {
   length "1..127";
  }
  mandatory false;
 }
 leaf CERTNAME {
  type string {
   length "0..64";
  }
  mandatory false;
 }
 leaf CERTREQSIGNALG {
  type enumeration {
   enum val-0;
   enum val-2;
   enum val-3;
   enum val-4;
  }
  mandatory false;
 }
 leaf CERTREQSW {
  type boolean;
  mandatory false;
 }
 leaf COMMNAME {
  type boolean;
  mandatory false;
 }
 leaf COUNTRY {
  type string;
  mandatory false;
 }
 leaf ECCCURVE {
  type enumeration {
   enum val-0;
   enum val-1;
   enum val-2;
   enum val-4;
  }
  mandatory false;
 }
 leaf INITREQSIP {
  type inet:ipv4-address;
  mandatory false;
 }
 leaf INITREQSIP6 {
  type inet:ipv6-address;
  mandatory false;
 }
 leaf INITREQURL {
  type string {
   length "1..128";
  }
  mandatory false;
 }
 leaf IPVERSION {
  type boolean;
  mandatory false;
 }
 leaf KEYSIZE {
  type enumeration {
   enum val-0;
   enum val-1;
   enum val-2;
   enum val-3;
  }
  mandatory false;
 }
 leaf KEYTYPE {
  type boolean;
  mandatory false;
 }
 leaf KEYUSAGE {
  type string;
  mandatory false;
 }
 leaf LOCALIP {
  type inet:ipv4-address;
  mandatory false;
 }
 leaf LOCALIP6 {
  type inet:ipv6-address;
  mandatory false;
 }
 leaf LOCALITY {
  type string {
   length "0..128";
  }
  mandatory false;
 }
 leaf LOCALNAME {
  type string {
   length "0..128";
  }
  mandatory false;
 }
 leaf MODE {
  type enumeration {
   enum val-0;
   enum val-1;
   enum val-2;
  }
  mandatory false;
 }
 leaf OCSPURL {
  type string {
   length "0..128";
  }
  mandatory false;
 }
 leaf ORG {
  type string {
   length "0..64";
  }
  mandatory false;
 }
 leaf ORGUNIT {
  type string {
   length "0..64";
  }
  mandatory false;
 }
 leaf POLICYID {
  type uint8 {
   range "0..16";
  }
  mandatory false;
 }
 leaf RANAME {
  type string {
   length "0..127";
  }
  mandatory false;
 }
 leaf REQVRFIDX {
  type uint8 {
   range "0..31";
  }
  mandatory false;
 }
 leaf SIGNALG {
  type enumeration {
   enum val-0;
   enum val-2;
   enum val-3;
   enum val-4;
  }
  mandatory false;
 }
 leaf SLVINITREQSIP {
  type inet:ipv4-address;
  mandatory false;
 }
 leaf SLVINITREQSIP6 {
  type inet:ipv6-address;
  mandatory false;
 }
 leaf SLVINITREQURL {
  type string {
   length "0..128";
  }
  mandatory false;
 }
 leaf SLVUPDSIP {
  type inet:ipv4-address;
  mandatory false;
 }
 leaf SLVUPDSIP6 {
  type inet:ipv6-address;
  mandatory false;
 }
 leaf SLVURL {
  type string {
   length "0..128";
  }
  mandatory false;
 }
 leaf STATEPROVINCENAME {
  type string {
   length "0..128";
  }
  mandatory false;
 }
 leaf TLSSECCSSW {
  type boolean;
  mandatory false;
 }
 leaf TRUSTGROUPID {
  type union {
   type uint16 {
    range "0..65535";
   }
  }
  mandatory false;
 }
 leaf UPDSIP {
  type inet:ipv4-address;
  mandatory false;
 }
 leaf UPDSIP6 {
  type inet:ipv6-address;
  mandatory false;
 }
 leaf UPDVRFIDX {
  type uint8 {
   range "0..31";
  }
  mandatory false;
 }
 leaf URL {
  type string {
   length "1..128";
  }
  mandatory false;
 }
 leaf USERADDINFO {
  type string {
   length "0..32";
  }
  mandatory false;
 }
 leaf VENDORCERT {
  type boolean;
  mandatory false;
 }
 }
 grouping CERTCFG-attributes {
 leaf IKECHECKSW {
  type boolean;
  mandatory false;
 }
 }
 grouping CERTCHKTSK-attributes {
 leaf ALMRNG {
  type uint8 {
   range "7..180";
  }
  mandatory false;
 }
 leaf AUTOREAPPLYSW {
  type boolean;
  mandatory false;
 }
 leaf PERIOD {
  type uint8 {
   range "1..15";
  }
  mandatory false;
 }
 leaf UPDATEMETHOD {
  type enumeration {
   enum val-1;
   enum val-2;
  }
  mandatory false;
 }
 leaf VENDORALMRNG {
  type uint8 {
   range "7..180";
  }
  mandatory false;
 }
 leaf VENDORCERTCHKSW {
  type boolean;
  mandatory false;
 }
 }
 grouping CERTDEPLOY-attributes {
 leaf CN {
  type uint8 {
   range "0..7";
  }
  mandatory false;
 }
 leaf DEPLOYTYPE {
  type boolean;
  mandatory false;
 }
 leaf SN {
  type uint8 {
   range "0..7";
  }
  mandatory false;
 }
 leaf SRN {
  type uint8 {
   range "0..1";
  }
  mandatory false;
 }
 }
 grouping CERTMK-attributes {
 leaf OLD_APPCERT {
  type string {
   length "1..64";
  }
  mandatory false;
 }
 leaf APPCERT {
  type string {
   length "1..64";
  }
  mandatory false;
 }
 leaf CANAME {
  type string {
   length "1..127";
  }
  mandatory false;
 }
 leaf CASW {
  type boolean;
  mandatory false;
 }
 leaf KEYSOURCE {
  type boolean;
  mandatory false;
 }
 leaf RELATEDCERT {
  type string {
   length "1..64";
  }
  mandatory false;
 }
 }
 grouping CERTREQ-attributes {
 leaf COMMNAME {
  type boolean;
  mandatory false;
 }
 leaf COUNTRY {
  type string;
  mandatory false;
 }
 leaf ECCCURVE {
  type enumeration {
   enum val-0;
   enum val-1;
   enum val-2;
   enum val-4;
  }
  mandatory false;
 }
 leaf KEYSIZE {
  type enumeration {
   enum val-0;
   enum val-1;
   enum val-2;
   enum val-3;
  }
  mandatory false;
 }
 leaf KEYTYPE {
  type boolean;
  mandatory false;
 }
 leaf KEYUSAGE {
  type string;
  mandatory false;
 }
 leaf LOCALIP {
  type inet:ipv4-address;
  mandatory false;
 }
 leaf LOCALIP6 {
  type inet:ipv6-address;
  mandatory false;
 }
 leaf LOCALITY {
  type string {
   length "0..128";
  }
  mandatory false;
 }
 leaf LOCALNAME {
  type string {
   length "0..128";
  }
  mandatory false;
 }
 leaf ORG {
  type string {
   length "0..64";
  }
  mandatory false;
 }
 leaf ORGUNIT {
  type string {
   length "0..64";
  }
  mandatory false;
 }
 leaf SIGNALG {
  type enumeration {
   enum val-0;
   enum val-2;
   enum val-3;
   enum val-4;
  }
  mandatory false;
 }
 leaf STATEPROVINCENAME {
  type string {
   length "0..128";
  }
  mandatory false;
 }
 leaf USERADDINFO {
  type string {
   length "0..32";
  }
  mandatory false;
 }
 }
 grouping CPBEARER-attributes {
 leaf AUTOCFGFLAG {
  type boolean;
  mandatory false;
 }
 leaf BEARTYPE {
  type boolean;
  mandatory false;
 }
 leaf OLD_CPBEARID {
  type union {
   type int32 {
    range "-1..79999";
   }
  }
  mandatory false;
 }
 leaf CPBEARID {
  type union {
   type int32 {
    range "-1..79999";
   }
  }
  mandatory false;
 }
 leaf CTRLMODE {
  type boolean;
  mandatory false;
 }
 leaf OLD_FLAG {
  type enumeration {
   enum val--1;
   enum val-0;
   enum val-1;
  }
  mandatory false;
 }
 leaf FLAG {
  type enumeration {
   enum val--1;
   enum val-0;
   enum val-1;
  }
  mandatory false;
 }
 leaf LINKNO {
  type union {
   type uint32 {
    range "0..79999";
   }
  }
  mandatory false;
 }
 }
 grouping CRL-attributes {
 leaf OLD_CERTNAME {
  type string {
   length "1..64";
  }
  mandatory false;
 }
 leaf CERTNAME {
  type string {
   length "1..64";
  }
  mandatory false;
 }
 }
 grouping CRLPOLICY-attributes {
 leaf CRLPOLICY {
  type enumeration {
   enum val-0;
   enum val-1;
   enum val-2;
  }
  mandatory false;
 }
 }
 grouping CRLTSK-attributes {
 leaf AUTHPEER {
  type boolean;
  mandatory false;
 }
 leaf CERTNAME {
  type string {
   length "0..64";
  }
  mandatory false;
 }
 leaf CONNMODE {
  type boolean;
  mandatory false;
 }
 leaf CRLGETMETHOD {
  type boolean;
  mandatory false;
 }
 leaf FILENAME {
  type string {
   length "1..128";
  }
  mandatory false;
 }
 leaf IP {
  type inet:ipv4-address;
  mandatory false;
 }
 leaf IP6 {
  type inet:ipv6-address;
  mandatory false;
 }
 leaf IPVERSION {
  type boolean;
  mandatory false;
 }
 leaf ISCRLTIME {
  type boolean;
  mandatory false;
 }
 leaf MINDHLEN {
  type enumeration {
   enum val-0;
   enum val-512;
   enum val-1024;
   enum val-2048;
   enum val-3072;
   enum val-4096;
  }
  mandatory false;
 }
 leaf PERIOD {
  type uint8 {
   range "8..240";
  }
  mandatory false;
 }
 leaf POLICYID {
  type uint8 {
   range "0..16";
  }
  mandatory false;
 }
 leaf PORT {
  type uint16 {
   range "0..65535";
  }
  mandatory false;
 }
 leaf PWD {
  type string {
   length "0..64";
  }
  mandatory false;
 }
 leaf SEARCHDN {
  type string {
   length "0..255";
  }
  mandatory false;
 }
 leaf SIP {
  type inet:ipv4-address;
  mandatory false;
 }
 leaf SIP6 {
  type inet:ipv6-address;
  mandatory false;
 }
 leaf SLVIP {
  type inet:ipv4-address;
  mandatory false;
 }
 leaf SLVIP6 {
  type inet:ipv6-address;
  mandatory false;
 }
 leaf SLVPORT {
  type uint16 {
   range "0..65535";
  }
  mandatory false;
 }
 leaf SLVPWD {
  type string {
   length "0..64";
  }
  mandatory false;
 }
 leaf SLVSIP {
  type inet:ipv4-address;
  mandatory false;
 }
 leaf SLVSIP6 {
  type inet:ipv6-address;
  mandatory false;
 }
 leaf SLVUSR {
  type string {
   length "0..255";
  }
  mandatory false;
 }
 leaf TLSSECCSSW {
  type boolean;
  mandatory false;
 }
 leaf TRUSTGROUPID {
  type union {
   type uint16 {
    range "0..65535";
   }
  }
  mandatory false;
 }
 leaf OLD_TSKID {
  type union {
   type int8 {
    range "-1..5";
   }
  }
  mandatory false;
 }
 leaf TSKID {
  type union {
   type int8 {
    range "-1..5";
   }
  }
  mandatory false;
 }
 leaf USR {
  type string {
   length "0..255";
  }
  mandatory false;
 }
 leaf VRFIDX {
  type uint8 {
   range "0..31";
  }
  mandatory false;
 }
 }
 grouping DEVIP-attributes {
 leaf BORROWIFIP {
  type boolean;
  mandatory false;
 }
 leaf OLD_CN {
  type union {
   type int8 {
    range "-1..7";
   }
  }
  mandatory false;
 }
 leaf CN {
  type union {
   type int8 {
    range "-1..7";
   }
  }
  mandatory false;
 }
 leaf CTRLMODE {
  type boolean;
  mandatory false;
 }
 leaf OLD_IP {
  type inet:ipv4-address;
  mandatory false;
 }
 leaf IP {
  type inet:ipv4-address;
  mandatory false;
 }
 leaf MASK {
  type inet:ipv4-address;
  mandatory false;
 }
 leaf OLD_PN {
  type union {
   type int8 {
    range "-1..63";
   }
  }
  mandatory false;
 }
 leaf PN {
  type union {
   type int8 {
    range "-1..63";
   }
  }
  mandatory false;
 }
 leaf OLD_PT {
  type enumeration {
   enum val--1;
   enum val-0;
   enum val-2;
   enum val-3;
   enum val-4;
   enum val-6;
   enum val-9;
   enum val-16;
  }
  mandatory false;
 }
 leaf PT {
  type enumeration {
   enum val--1;
   enum val-0;
   enum val-2;
   enum val-3;
   enum val-4;
   enum val-6;
   enum val-9;
   enum val-16;
  }
  mandatory false;
 }
 leaf OLD_SBT {
  type enumeration {
   enum val--1;
   enum val-0;
   enum val-3;
   enum val-4;
   enum val-5;
  }
  mandatory false;
 }
 leaf SBT {
  type enumeration {
   enum val--1;
   enum val-0;
   enum val-3;
   enum val-4;
   enum val-5;
  }
  mandatory false;
 }
 leaf OLD_SN {
  type union {
   type int8 {
    range "-1..7";
   }
  }
  mandatory false;
 }
 leaf SN {
  type union {
   type int8 {
    range "-1..7";
   }
  }
  mandatory false;
 }
 leaf OLD_SRN {
  type union {
   type int8 {
    range "-1..1";
   }
  }
  mandatory false;
 }
 leaf SRN {
  type union {
   type int8 {
    range "-1..1";
   }
  }
  mandatory false;
 }
 leaf USERLABEL {
  type string {
   length "0..255";
  }
  mandatory false;
 }
 leaf OLD_VRFIDX {
  type union {
   type int8 {
    range "-1..7";
   }
  }
  mandatory false;
 }
 leaf VRFIDX {
  type union {
   type int8 {
    range "-1..7";
   }
  }
  mandatory false;
 }
 }
 grouping DFUMLCLIENT-attributes {
 leaf OLD_CLIENTID {
  type union {
   type int16 {
    range "-1..255";
   }
  }
  mandatory false;
 }
 leaf CLIENTID {
  type union {
   type int16 {
    range "-1..255";
   }
  }
  mandatory false;
 }
 leaf CLIENTIPV4 {
  type inet:ipv4-address;
  mandatory false;
 }
 leaf IPVERSION {
  type boolean;
  mandatory false;
 }
 leaf UID {
  type uint8 {
   range "0..255";
  }
  mandatory false;
 }
 leaf USERLABEL {
  type string {
   length "0..255";
  }
  mandatory false;
 }
 leaf VRFIDX {
  type uint8 {
   range "0..31";
  }
  mandatory false;
 }
 }
 grouping DHCPRELAYSWITCH-attributes {
 leaf ES {
  type boolean;
  mandatory false;
 }
 }
 grouping DHCPSVRIP-attributes {
 leaf DHCPRELAYIP {
  type inet:ipv4-address;
  mandatory false;
 }
 leaf DHCPRELAYIPSW {
  type boolean;
  mandatory false;
 }
 leaf OLD_DHCPSVRIP {
  type inet:ipv4-address;
  mandatory false;
 }
 leaf DHCPSVRIP {
  type inet:ipv4-address;
  mandatory false;
 }
 leaf VRFIDX {
  type uint8 {
   range "0..31";
  }
  mandatory false;
 }
 }
 grouping DHCPSVRIP6-attributes {
 leaf DHCPRELAYIP {
  type inet:ipv6-address;
  mandatory false;
 }
 leaf DHCPRELAYIPSW {
  type boolean;
  mandatory false;
 }
 leaf OLD_DHCPSVRIP {
  type inet:ipv6-address;
  mandatory false;
 }
 leaf DHCPSVRIP {
  type inet:ipv6-address;
  mandatory false;
 }
 leaf VRFIDX {
  type uint8 {
   range "0..31";
  }
  mandatory false;
 }
 }
 grouping DHCPSW-attributes {
 leaf DELAYSW {
  type boolean;
  mandatory false;
 }
 leaf SWITCH {
  type boolean;
  mandatory false;
 }
 leaf TEMPIPPNPSW {
  type boolean;
  mandatory false;
 }
 leaf VLANSCANSW {
  type boolean;
  mandatory false;
 }
 }
 grouping DIFPRI-attributes {
 leaf IPCLKPRI {
  type uint8 {
   range "0..63";
  }
  mandatory false;
 }
 leaf OMHIGHPRI {
  type uint8 {
   range "0..63";
  }
  mandatory false;
 }
 leaf OMLOWPRI {
  type uint8 {
   range "0..63";
  }
  mandatory false;
 }
 leaf PRIRULE {
  type boolean;
  mandatory false;
 }
 leaf SIGPRI {
  type uint8 {
   range "0..63";
  }
  mandatory false;
 }
 }
 grouping DLFLOWCTRLPARA-attributes {
 leaf OLD_BEAR {
  type enumeration {
   enum val--1;
   enum val-0;
   enum val-1;
  }
  mandatory false;
 }
 leaf BEAR {
  type enumeration {
   enum val--1;
   enum val-0;
   enum val-1;
  }
  mandatory false;
 }
 leaf BWPRTSWITCH {
  type boolean;
  mandatory false;
 }
 leaf OLD_CN {
  type union {
   type int8 {
    range "-1..7";
   }
  }
  mandatory false;
 }
 leaf CN {
  type union {
   type int8 {
    range "-1..7";
   }
  }
  mandatory false;
 }
 leaf DLFLOWCTRLENHSW {
  type boolean;
  mandatory false;
 }
 leaf DLIUBBWMINPRORATIO {
  type uint8 {
   range "0..100";
  }
  mandatory false;
 }
 leaf DLIUBMINBW {
  type uint32 {
   range "0..1000000";
  }
  mandatory false;
 }
 leaf DR {
  type uint16 {
   range "0..1000";
  }
  mandatory false;
 }
 leaf FAIRRATIO {
  type uint8 {
   range "0..100";
  }
  mandatory false;
 }
 leaf FAIRSWITCH {
  type boolean;
  mandatory false;
 }
 leaf ITM {
  type boolean;
  mandatory false;
 }
 leaf OLD_PN {
  type union {
   type int8 {
    range "-1..15";
   }
  }
  mandatory false;
 }
 leaf PN {
  type union {
   type int8 {
    range "-1..15";
   }
  }
  mandatory false;
 }
 leaf OLD_PT {
  type enumeration {
   enum val--1;
   enum val-0;
   enum val-1;
   enum val-5;
   enum val-6;
   enum val-10;
   enum val-12;
   enum val-13;
   enum val-14;
   enum val-15;
  }
  mandatory false;
 }
 leaf PT {
  type enumeration {
   enum val--1;
   enum val-0;
   enum val-1;
   enum val-5;
   enum val-6;
   enum val-10;
   enum val-12;
   enum val-13;
   enum val-14;
   enum val-15;
  }
  mandatory false;
 }
 leaf OLD_SBT {
  type enumeration {
   enum val--1;
   enum val-0;
   enum val-3;
   enum val-4;
   enum val-5;
  }
  mandatory false;
 }
 leaf SBT {
  type enumeration {
   enum val--1;
   enum val-0;
   enum val-3;
   enum val-4;
   enum val-5;
  }
  mandatory false;
 }
 leaf OLD_SN {
  type union {
   type int8 {
    range "-1..7";
   }
  }
  mandatory false;
 }
 leaf SN {
  type union {
   type int8 {
    range "-1..7";
   }
  }
  mandatory false;
 }
 leaf OLD_SRN {
  type union {
   type int8 {
    range "-1..1";
   }
  }
  mandatory false;
 }
 leaf SRN {
  type union {
   type int8 {
    range "-1..1";
   }
  }
  mandatory false;
 }
 leaf SWITCH {
  type enumeration {
   enum val-0;
   enum val-1;
   enum val-2;
   enum val-3;
  }
  mandatory false;
 }
 leaf TD {
  type uint8 {
   range "0..100";
  }
  mandatory false;
 }
 }
 grouping DSCP2PCPMAP-attributes {
 leaf DEFAULTPCP {
  type uint8 {
   range "0..7";
  }
  mandatory false;
 }
 leaf OLD_DSCP2PCPMAPID {
  type union {
   type int8 {
    range "-1..15";
   }
  }
  mandatory false;
 }
 leaf DSCP2PCPMAPID {
  type union {
   type int8 {
    range "-1..15";
   }
  }
  mandatory false;
 }
 leaf USERLABEL {
  type string {
   length "0..255";
  }
  mandatory false;
 }
 }
 grouping DSCP2PCPREF-attributes {
 leaf DSCP {
  type union {
   type int8 {
    range "-1..63";
   }
  }
  mandatory false;
 }
 leaf DSCP2PCPMAPID {
  type union {
   type int8 {
    range "-1..15";
   }
  }
  mandatory false;
 }
 leaf PCP {
  type union {
   type int8 {
    range "-1..7";
   }
  }
  mandatory false;
 }
 }
 grouping DSCP2QUEMAP-attributes {
 leaf DEFAULTQUE {
  type uint8 {
   range "0..6";
  }
  mandatory false;
 }
 leaf OLD_DSCP2QUEMAPID {
  type union {
   type int8 {
    range "-1..15";
   }
  }
  mandatory false;
 }
 leaf DSCP2QUEMAPID {
  type union {
   type int8 {
    range "-1..15";
   }
  }
  mandatory false;
 }
 leaf USERLABEL {
  type string {
   length "0..255";
  }
  mandatory false;
 }
 }
 grouping DSCP2QUEREF-attributes {
 leaf DSCP {
  type union {
   type int8 {
    range "-1..63";
   }
  }
  mandatory false;
 }
 leaf DSCP2QUEMAPID {
  type union {
   type int8 {
    range "-1..15";
   }
  }
  mandatory false;
 }
 leaf QUE {
  type union {
   type int8 {
    range "-1..6";
   }
  }
  mandatory false;
 }
 }
 grouping DSCPMAP-attributes {
 leaf OLD_DSCP {
  type union {
   type int8 {
    range "-1..63";
   }
  }
  mandatory false;
 }
 leaf DSCP {
  type union {
   type int8 {
    range "-1..63";
   }
  }
  mandatory false;
 }
 leaf VLANPRIO {
  type uint8 {
   range "0..7";
  }
  mandatory false;
 }
 leaf OLD_VRFIDX {
  type union {
   type int8 {
    range "-1..7";
   }
  }
  mandatory false;
 }
 leaf VRFIDX {
  type union {
   type int8 {
    range "-1..7";
   }
  }
  mandatory false;
 }
 }
 grouping DTLSPOLICY-attributes {
 leaf CIPHERSUITE {
  type inet:ip-address;
  mandatory false;
 }
 leaf OLD_DTLSPOLICYID {
  type enumeration {
   enum val--1;
   enum val-0;
  }
  mandatory false;
 }
 leaf DTLSPOLICYID {
  type enumeration {
   enum val--1;
   enum val-0;
  }
  mandatory false;
 }
 }
 grouping E1T1-attributes {
 leaf CLKM {
  type boolean;
  mandatory false;
 }
 leaf OLD_CN {
  type union {
   type int8 {
    range "-1..7";
   }
  }
  mandatory false;
 }
 leaf CN {
  type union {
   type int8 {
    range "-1..7";
   }
  }
  mandatory false;
 }
 leaf DSTSN {
  type uint8 {
   range "0..7";
  }
  mandatory false;
 }
 leaf FRAME {
  type enumeration {
   enum val-0;
   enum val-1;
   enum val-2;
   enum val-3;
   enum val-5;
  }
  mandatory false;
 }
 leaf LNCODE {
  type enumeration {
   enum val-0;
   enum val-1;
   enum val-2;
  }
  mandatory false;
 }
 leaf OLD_PN {
  type union {
   type int16 {
    range "-1..255";
   }
  }
  mandatory false;
 }
 leaf PN {
  type union {
   type int16 {
    range "-1..255";
   }
  }
  mandatory false;
 }
 leaf PS {
  type boolean;
  mandatory false;
 }
 leaf OLD_SBT {
  type enumeration {
   enum val--1;
   enum val-0;
   enum val-3;
   enum val-4;
  }
  mandatory false;
 }
 leaf SBT {
  type enumeration {
   enum val--1;
   enum val-0;
   enum val-3;
   enum val-4;
  }
  mandatory false;
 }
 leaf OLD_SN {
  type union {
   type int8 {
    range "-1..7";
   }
  }
  mandatory false;
 }
 leaf SN {
  type union {
   type int8 {
    range "-1..7";
   }
  }
  mandatory false;
 }
 leaf OLD_SRN {
  type union {
   type int8 {
    range "-1..1";
   }
  }
  mandatory false;
 }
 leaf SRN {
  type union {
   type int8 {
    range "-1..1";
   }
  }
  mandatory false;
 }
 leaf WORKMODE {
  type enumeration {
   enum val-0;
   enum val-1;
   enum val-2;
  }
  mandatory false;
 }
 }
 grouping E1T1BEAR-attributes {
 leaf CN {
  type union {
   type int8 {
    range "-1..7";
   }
  }
  mandatory false;
 }
 leaf MODE {
  type boolean;
  mandatory false;
 }
 leaf SN {
  type union {
   type int8 {
    range "-1..7";
   }
  }
  mandatory false;
 }
 leaf SRN {
  type union {
   type int8 {
    range "-1..1";
   }
  }
  mandatory false;
 }
 }
 grouping EP2IPRSCGRP-attributes {
 leaf ENDPOINTID {
  type union {
   type uint32 {
    range "0..79999";
   }
  }
  mandatory false;
 }
 leaf IPRSCGRPID {
  type uint32 {
   range "0..150014";
  }
  mandatory false;
 }
 leaf OLD_MAPID {
  type union {
   type int16 {
    range "-1..455";
   }
  }
  mandatory false;
 }
 leaf MAPID {
  type union {
   type int16 {
    range "-1..455";
   }
  }
  mandatory false;
 }
 leaf MT {
  type boolean;
  mandatory false;
 }
 leaf USERLABEL {
  type string {
   length "0..256";
  }
  mandatory false;
 }
 }
 grouping EP2RSCGRP-attributes {
 leaf OLD_BEAR {
  type enumeration {
   enum val--1;
   enum val-1;
  }
  mandatory false;
 }
 leaf BEAR {
  type enumeration {
   enum val--1;
   enum val-1;
  }
  mandatory false;
 }
 leaf OLD_CN {
  type union {
   type int8 {
    range "-1..7";
   }
  }
  mandatory false;
 }
 leaf CN {
  type union {
   type int8 {
    range "-1..7";
   }
  }
  mandatory false;
 }
 leaf OLD_ENDPOINTID {
  type union {
   type int32 {
    range "-1..79999";
   }
  }
  mandatory false;
 }
 leaf ENDPOINTID {
  type union {
   type int32 {
    range "-1..79999";
   }
  }
  mandatory false;
 }
 leaf OLD_MT {
  type enumeration {
   enum val--1;
   enum val-0;
   enum val-1;
  }
  mandatory false;
 }
 leaf MT {
  type enumeration {
   enum val--1;
   enum val-0;
   enum val-1;
  }
  mandatory false;
 }
 leaf OLD_PN {
  type union {
   type int8 {
    range "-1..15";
   }
  }
  mandatory false;
 }
 leaf PN {
  type union {
   type int8 {
    range "-1..15";
   }
  }
  mandatory false;
 }
 leaf OLD_PT {
  type enumeration {
   enum val--1;
   enum val-0;
   enum val-2;
   enum val-3;
   enum val-4;
   enum val-8;
  }
  mandatory false;
 }
 leaf PT {
  type enumeration {
   enum val--1;
   enum val-0;
   enum val-2;
   enum val-3;
   enum val-4;
   enum val-8;
  }
  mandatory false;
 }
 leaf OLD_RSCGRPID {
  type union {
   type int8 {
    range "-1..15";
   }
  }
  mandatory false;
 }
 leaf RSCGRPID {
  type union {
   type int8 {
    range "-1..15";
   }
  }
  mandatory false;
 }
 leaf OLD_SBT {
  type enumeration {
   enum val--1;
   enum val-0;
   enum val-3;
   enum val-4;
   enum val-5;
  }
  mandatory false;
 }
 leaf SBT {
  type enumeration {
   enum val--1;
   enum val-0;
   enum val-3;
   enum val-4;
   enum val-5;
  }
  mandatory false;
 }
 leaf OLD_SN {
  type union {
   type int8 {
    range "-1..7";
   }
  }
  mandatory false;
 }
 leaf SN {
  type union {
   type int8 {
    range "-1..7";
   }
  }
  mandatory false;
 }
 leaf OLD_SRN {
  type union {
   type int8 {
    range "-1..1";
   }
  }
  mandatory false;
 }
 leaf SRN {
  type union {
   type int8 {
    range "-1..1";
   }
  }
  mandatory false;
 }
 leaf USERLABEL {
  type string {
   length "0..256";
  }
  mandatory false;
 }
 }
 grouping EPGROUP-attributes {
 leaf APPTYPE {
  type enumeration {
   enum val-3;
   enum val-10;
   enum val-255;
  }
  mandatory false;
 }
 leaf AUTOCFGFLAG {
  type boolean;
  mandatory false;
 }
 leaf CTRLMODE {
  type boolean;
  mandatory false;
 }
 leaf ENBINTERFACE {
  type string;
  mandatory false;
 }
 leaf OLD_EPGROUPID {
  type union {
   type int32 {
    range "-1..65535";
   }
  }
  mandatory false;
 }
 leaf EPGROUPID {
  type union {
   type int32 {
    range "-1..65535";
   }
  }
  mandatory false;
 }
 leaf GNBINTERFACE {
  type string;
  mandatory false;
 }
 leaf IPPMDSCP {
  type uint8 {
   range "0..63";
  }
  mandatory false;
 }
 leaf IPPMSWITCH {
  type boolean;
  mandatory false;
 }
 leaf IPV6VRFIDX {
  type uint8 {
   range "0..31";
  }
  mandatory false;
 }
 leaf IPVERPREFERENCE {
  type boolean;
  mandatory false;
 }
 leaf LNKPFMSW {
  type boolean;
  mandatory false;
 }
 leaf PACKETFILTERSWITCH {
  type boolean;
  mandatory false;
 }
 leaf PACKETFILTERSWITCH6 {
  type boolean;
  mandatory false;
 }
 leaf STATICCHK {
  type boolean;
  mandatory false;
 }
 leaf TYPEFLAG {
  type boolean;
  mandatory false;
 }
 leaf USERLABEL {
  type string {
   length "0..256";
  }
  mandatory false;
 }
 leaf VRFIDX {
  type uint8 {
   range "0..31";
  }
  mandatory false;
 }
 }
 grouping EQUIPMENT-attributes {
 leaf ALDCFGMODE {
  type boolean;
  mandatory false;
 }
 leaf APST {
  type union {
   type uint16 {
    range "390..65535";
   }
  }
  mandatory false;
 }
 leaf AUTOCPRIRESDEFRAGSW {
  type enumeration {
   enum val-0;
   enum val-1;
   enum val-2;
  }
  mandatory false;
 }
 leaf BATIMS {
  type boolean;
  mandatory false;
 }
 leaf BBPDORMSFPCHKSW {
  type boolean;
  mandatory false;
 }
 leaf CPRIMUXEXTSW {
  type boolean;
  mandatory false;
 }
 leaf DCALMSW {
  type boolean;
  mandatory false;
 }
 leaf DCUSDRENHSW {
  type boolean;
  mandatory false;
 }
 leaf DVAH {
  type uint16 {
   range "390..556";
  }
  mandatory false;
 }
 leaf DVAL {
  type uint16 {
   range "390..600";
  }
  mandatory false;
 }
 leaf DVAS {
  type boolean;
  mandatory false;
 }
 leaf ECPRIIBENHSW {
  type boolean;
  mandatory false;
 }
 leaf EQMDOROPTFEATSW {
  type string;
  mandatory false;
 }
 leaf EQMOPTFEATSW {
  type string;
  mandatory false;
 }
 leaf EQUIPMENTTY {
  type enumeration {
   enum val-0;
   enum val-1;
   enum val-2;
   enum val-3;
   enum val-4;
   enum val-5;
   enum val-6;
   enum val-8;
   enum val-12;
   enum val-13;
   enum val-14;
   enum val-21;
   enum val-22;
   enum val-23;
   enum val-24;
   enum val-25;
  }
  mandatory false;
 }
 leaf ESN {
  type string {
   length "0..23";
  }
  mandatory false;
 }
 leaf HWFLTSELFHEALSW {
  type string;
  mandatory false;
 }
 leaf HWTAGMNGSW {
  type enumeration {
   enum val-0;
   enum val-1;
   enum val-2;
  }
  mandatory false;
 }
 leaf IMDSRTMODE {
  type enumeration {
   enum val-0;
   enum val-1;
   enum val-2;
  }
  mandatory false;
 }
 leaf INTERSUBRACKCLKALIGNMODE {
  type boolean;
  mandatory false;
 }
 leaf MAXRAMDORMANCYWAITTIME {
  type uint8 {
   range "0..30";
  }
  mandatory false;
 }
 leaf NPST {
  type union {
   type uint16 {
    range "390..65535";
   }
  }
  mandatory false;
 }
 leaf ODIID {
  type uint8 {
   range "0..254";
  }
  mandatory false;
 }
 leaf OMCONNENHSWCTLTIME {
  type uint8 {
   range "6..20";
  }
  mandatory false;
 }
 leaf PAE {
  type boolean;
  mandatory false;
 }
 leaf PROTOCOL {
  type boolean;
  mandatory false;
 }
 leaf PSUFP {
  type boolean;
  mandatory false;
 }
 leaf PWRFAILOMCONNENHSW {
  type boolean;
  mandatory false;
 }
 leaf PWRSVGPOLICYID {
  type uint8 {
   range "0..24";
  }
  mandatory false;
 }
 leaf RFPWRABNORMALPROTECTSW {
  type boolean;
  mandatory false;
 }
 leaf RFPWRTSLOGSW {
  type boolean;
  mandatory false;
 }
 leaf SDBBLSD {
  type boolean;
  mandatory false;
 }
 leaf SDRCONNSW {
  type enumeration {
   enum val-0;
   enum val-1;
   enum val-2;
  }
  mandatory false;
 }
 leaf SIMULOADDURATION {
  type uint8 {
   range "3..5";
  }
  mandatory false;
 }
 leaf SIMULOADRATE {
  type uint8 {
   range "10..100";
  }
  mandatory false;
 }
 leaf SMARTTRX {
  type boolean;
  mandatory false;
 }
 leaf SPCEM {
  type boolean;
  mandatory false;
 }
 leaf STAGGEREDDISCHARGESTOPTHLD {
  type uint8 {
   range "50..100";
  }
  mandatory false;
 }
 leaf STAGGEREDPOWERSWITCH {
  type boolean;
  mandatory false;
 }
 leaf SYSCLKDETECTSENS {
  type enumeration {
   enum val-0;
   enum val-1;
   enum val-2;
  }
  mandatory false;
 }
 leaf TESTENDTIME {
  type union {
   type uint8 {
    range "0..255";
   }
  }
  mandatory false;
 }
 leaf TESTPERIOD {
  type uint8 {
   range "1..7";
  }
  mandatory false;
 }
 leaf TESTSTARTTIME {
  type union {
   type uint8 {
    range "0..255";
   }
  }
  mandatory false;
 }
 leaf TGBKD {
  type uint16 {
   range "30..600";
  }
  mandatory false;
 }
 leaf TIMINGDORMCOMPSTARTTIME {
  type hwat:HH_MM_SS_Time;
  mandatory false;
 }
 leaf TIMINGDORMCOMPSTOPTIME {
  type hwat:HH_MM_SS_Time;
  mandatory false;
 }
 }
 grouping ETHCIPORT-attributes {
 leaf OLD_CN {
  type union {
   type int8 {
    range "-1..7";
   }
  }
  mandatory false;
 }
 leaf CN {
  type union {
   type int8 {
    range "-1..7";
   }
  }
  mandatory false;
 }
 leaf MTU {
  type uint16 {
   range "46..2000";
  }
  mandatory false;
 }
 leaf OLD_PN {
  type union {
   type int8 {
    range "-1..0";
   }
  }
  mandatory false;
 }
 leaf PN {
  type union {
   type int8 {
    range "-1..0";
   }
  }
  mandatory false;
 }
 leaf PORTID {
  type union {
   type uint32 {
    range "0..4294967295";
   }
  }
  mandatory false;
 }
 leaf OLD_SBT {
  type enumeration {
   enum val--1;
   enum val-0;
  }
  mandatory false;
 }
 leaf SBT {
  type enumeration {
   enum val--1;
   enum val-0;
  }
  mandatory false;
 }
 leaf OLD_SN {
  type union {
   type int8 {
    range "-1..7";
   }
  }
  mandatory false;
 }
 leaf SN {
  type union {
   type int8 {
    range "-1..7";
   }
  }
  mandatory false;
 }
 leaf OLD_SRN {
  type union {
   type int8 {
    range "-1..1";
   }
  }
  mandatory false;
 }
 leaf SRN {
  type union {
   type int8 {
    range "-1..1";
   }
  }
  mandatory false;
 }
 }
 grouping ETHPORT-attributes {
 leaf ARPPROXY {
  type boolean;
  mandatory false;
 }
 leaf AUTOCFGFLAG {
  type boolean;
  mandatory false;
 }
 leaf OLD_CN {
  type union {
   type int8 {
    range "-1..7";
   }
  }
  mandatory false;
 }
 leaf CN {
  type union {
   type int8 {
    range "-1..7";
   }
  }
  mandatory false;
 }
 leaf DUPLEX {
  type enumeration {
   enum val-1;
   enum val-2;
   enum val-255;
  }
  mandatory false;
 }
 leaf FC {
  type boolean;
  mandatory false;
 }
 leaf FECMODE {
  type boolean;
  mandatory false;
 }
 leaf FERAT {
  type uint8 {
   range "0..100";
  }
  mandatory false;
 }
 leaf FERDT {
  type uint8 {
   range "0..100";
  }
  mandatory false;
 }
 leaf FIBERSPEEDMATCH {
  type boolean;
  mandatory false;
 }
 leaf MTU {
  type uint16 {
   range "46..9296";
  }
  mandatory false;
 }
 leaf PA {
  type enumeration {
   enum val-0;
   enum val-1;
   enum val-2;
   enum val-255;
  }
  mandatory false;
 }
 leaf OLD_PN {
  type union {
   type int8 {
    range "-1..5";
   }
  }
  mandatory false;
 }
 leaf PN {
  type union {
   type int8 {
    range "-1..5";
   }
  }
  mandatory false;
 }
 leaf PORTID {
  type union {
   type uint32 {
    range "0..4294967295";
   }
  }
  mandatory false;
 }
 leaf RXBCPKTALMCLRTHD {
  type uint16 {
   range "50..6000";
  }
  mandatory false;
 }
 leaf RXBCPKTALMOCRTHD {
  type uint16 {
   range "50..6000";
  }
  mandatory false;
 }
 leaf OLD_SBT {
  type enumeration {
   enum val--1;
   enum val-0;
   enum val-5;
  }
  mandatory false;
 }
 leaf SBT {
  type enumeration {
   enum val--1;
   enum val-0;
   enum val-5;
  }
  mandatory false;
 }
 leaf OLD_SN {
  type union {
   type int8 {
    range "-1..7";
   }
  }
  mandatory false;
 }
 leaf SN {
  type union {
   type int8 {
    range "-1..7";
   }
  }
  mandatory false;
 }
 leaf SPEED {
  type enumeration {
   enum val-0;
   enum val-1;
   enum val-2;
   enum val-3;
   enum val-5;
   enum val-6;
   enum val-7;
   enum val-8;
   enum val-9;
   enum val-255;
  }
  mandatory false;
 }
 leaf OLD_SRN {
  type union {
   type int8 {
    range "-1..1";
   }
  }
  mandatory false;
 }
 leaf SRN {
  type union {
   type int8 {
    range "-1..1";
   }
  }
  mandatory false;
 }
 leaf USERLABEL {
  type string {
   length "0..255";
  }
  mandatory false;
 }
 }
 grouping ETHTRK-attributes {
 leaf ARPPROXY {
  type boolean;
  mandatory false;
 }
 leaf OLD_CN {
  type union {
   type int8 {
    range "-1..7";
   }
  }
  mandatory false;
 }
 leaf CN {
  type union {
   type int8 {
    range "-1..7";
   }
  }
  mandatory false;
 }
 leaf LACP {
  type boolean;
  mandatory false;
 }
 leaf MTU {
  type uint16 {
   range "46..9296";
  }
  mandatory false;
 }
 leaf OLD_SBT {
  type enumeration {
   enum val--1;
   enum val-0;
   enum val-5;
  }
  mandatory false;
 }
 leaf SBT {
  type enumeration {
   enum val--1;
   enum val-0;
   enum val-5;
  }
  mandatory false;
 }
 leaf OLD_SN {
  type union {
   type int8 {
    range "-1..7";
   }
  }
  mandatory false;
 }
 leaf SN {
  type union {
   type int8 {
    range "-1..7";
   }
  }
  mandatory false;
 }
 leaf OLD_SRN {
  type union {
   type int8 {
    range "-1..1";
   }
  }
  mandatory false;
 }
 leaf SRN {
  type union {
   type int8 {
    range "-1..1";
   }
  }
  mandatory false;
 }
 leaf OLD_TN {
  type union {
   type int8 {
    range "-1..2";
   }
  }
  mandatory false;
 }
 leaf TN {
  type union {
   type int8 {
    range "-1..2";
   }
  }
  mandatory false;
 }
 }
 grouping ETHTRUNK-attributes {
 leaf LACP {
  type boolean;
  mandatory false;
 }
 leaf OLD_PORTID {
  type union {
   type int8 {
    range "-1..23";
   }
  }
  mandatory false;
 }
 leaf PORTID {
  type union {
   type int8 {
    range "-1..23";
   }
  }
  mandatory false;
 }
 }
 grouping FLEXIP4-attributes {
 leaf OLD_FLEXIP4ID {
  type union {
   type int8 {
    range "-1..127";
   }
  }
  mandatory false;
 }
 leaf FLEXIP4ID {
  type union {
   type int8 {
    range "-1..127";
   }
  }
  mandatory false;
 }
 leaf ITFID {
  type uint16 {
   range "0..1499";
  }
  mandatory false;
 }
 leaf USERLABEL {
  type string {
   length "0..255";
  }
  mandatory false;
 }
 leaf VRFIDX {
  type uint8 {
   range "1..31";
  }
  mandatory false;
 }
 }
 grouping FLOODDEFEND-attributes {
 leaf ALMSW {
  type boolean;
  mandatory false;
 }
 leaf DFDSW {
  type boolean;
  mandatory false;
 }
 leaf DFDTHD {
  type uint16 {
   range "1..20736";
  }
  mandatory false;
 }
 leaf OLD_FLDTYPE {
  type enumeration {
   enum val--1;
   enum val-0;
   enum val-1;
   enum val-2;
   enum val-3;
   enum val-4;
   enum val-6;
   enum val-7;
   enum val-8;
   enum val-9;
   enum val-10;
   enum val-11;
   enum val-12;
   enum val-13;
   enum val-14;
   enum val-17;
  }
  mandatory false;
 }
 leaf FLDTYPE {
  type enumeration {
   enum val--1;
   enum val-0;
   enum val-1;
   enum val-2;
   enum val-3;
   enum val-4;
   enum val-6;
   enum val-7;
   enum val-8;
   enum val-9;
   enum val-10;
   enum val-11;
   enum val-12;
   enum val-13;
   enum val-14;
   enum val-17;
  }
  mandatory false;
 }
 }
 grouping FRAATM-attributes {
 leaf OLD_CN {
  type union {
   type int8 {
    range "-1..7";
   }
  }
  mandatory false;
 }
 leaf CN {
  type union {
   type int8 {
    range "-1..7";
   }
  }
  mandatory false;
 }
 leaf OLD_FRAATM {
  type union {
   type int8 {
    range "-1..7";
   }
  }
  mandatory false;
 }
 leaf FRAATM {
  type union {
   type int8 {
    range "-1..7";
   }
  }
  mandatory false;
 }
 leaf PN {
  type uint8 {
   range "0..3";
  }
  mandatory false;
 }
 leaf OLD_SBT {
  type enumeration {
   enum val--1;
   enum val-0;
   enum val-3;
   enum val-4;
  }
  mandatory false;
 }
 leaf SBT {
  type enumeration {
   enum val--1;
   enum val-0;
   enum val-3;
   enum val-4;
  }
  mandatory false;
 }
 leaf SCRAM {
  type boolean;
  mandatory false;
 }
 leaf OLD_SN {
  type union {
   type int8 {
    range "-1..7";
   }
  }
  mandatory false;
 }
 leaf SN {
  type union {
   type int8 {
    range "-1..7";
   }
  }
  mandatory false;
 }
 leaf OLD_SRN {
  type union {
   type int8 {
    range "-1..1";
   }
  }
  mandatory false;
 }
 leaf SRN {
  type union {
   type int8 {
    range "-1..1";
   }
  }
  mandatory false;
 }
 leaf TSN {
  type string;
  mandatory false;
 }
 }
 grouping GEPMODELPARA-attributes {
 leaf DIRECTIPSECAUTOSETUPMODE {
  type boolean;
  mandatory false;
 }
 leaf DIRIPSECAUTODELSW {
  type boolean;
  mandatory false;
 }
 leaf DIRIPSECAUTODELTIMER {
  type uint16 {
   range "0..50400";
  }
  mandatory false;
 }
 leaf DIRIPSECUPDATESW {
  type boolean;
  mandatory false;
 }
 leaf STATICCHKMODE {
  type boolean;
  mandatory false;
 }
 leaf UPAUTODELSW {
  type boolean;
  mandatory false;
 }
 }
 grouping GMPIPADDR-attributes {
 leaf OLD_GMPIPADDRID {
  type union {
   type int8 {
    range "-1..9";
   }
  }
  mandatory false;
 }
 leaf GMPIPADDRID {
  type union {
   type int8 {
    range "-1..9";
   }
  }
  mandatory false;
 }
 leaf IPVERSION {
  type boolean;
  mandatory false;
 }
 leaf ITFID {
  type uint16 {
   range "0..1499";
  }
  mandatory false;
 }
 leaf LOCIPV4 {
  type inet:ipv4-address;
  mandatory false;
 }
 leaf VRFIDX {
  type uint8 {
   range "0..31";
  }
  mandatory false;
 }
 }
 grouping GMPIPADDRREF-attributes {
 leaf EPGROUPID {
  type union {
   type int32 {
    range "-1..65535";
   }
  }
  mandatory false;
 }
 leaf GMPIPADDRID {
  type union {
   type int8 {
    range "-1..9";
   }
  }
  mandatory false;
 }
 }
 grouping GNSS-attributes {
 leaf AGL {
  type uint8 {
   range "0..89";
  }
  mandatory false;
 }
 leaf ALT {
  type int16 {
   range "-1000..10000";
  }
  mandatory false;
 }
 leaf ANTMODE {
  type enumeration {
   enum val-0;
   enum val-1;
   enum val-2;
  }
  mandatory false;
 }
 leaf CABLE_LEN {
  type uint16 {
   range "0..8000";
  }
  mandatory false;
 }
 leaf CN {
  type uint8 {
   range "0..15";
  }
  mandatory false;
 }
 leaf DETECTENHSW {
  type boolean;
  mandatory false;
 }
 leaf DURATION {
  type uint16 {
   range "1..2880";
  }
  mandatory false;
 }
 leaf OLD_GN {
  type union {
   type int8 {
    range "-1..17";
   }
  }
  mandatory false;
 }
 leaf GN {
  type union {
   type int8 {
    range "-1..17";
   }
  }
  mandatory false;
 }
 leaf LAT {
  type int32 {
   range "-90000000..90000000";
  }
  mandatory false;
 }
 leaf LONG {
  type int32 {
   range "-180000000..180000000";
  }
  mandatory false;
 }
 leaf MODE {
  type enumeration {
   enum val-0;
   enum val-1;
   enum val-2;
   enum val-3;
   enum val-4;
   enum val-6;
   enum val-7;
   enum val-8;
   enum val-9;
   enum val-10;
  }
  mandatory false;
 }
 leaf POSCHECKSW {
  type boolean;
  mandatory false;
 }
 leaf PRECISION {
  type uint8 {
   range "1..100";
  }
  mandatory false;
 }
 leaf PRI {
  type uint8 {
   range "1..4";
  }
  mandatory false;
 }
 leaf PRIMARYMODE {
  type boolean;
  mandatory false;
 }
 leaf PRIMODESBDUR {
  type enumeration {
   enum val-0;
   enum val-1;
   enum val-2;
   enum val-3;
   enum val-4;
   enum val-5;
   enum val-6;
  }
  mandatory false;
 }
 leaf SN {
  type uint8 {
   range "0..7";
  }
  mandatory false;
 }
 leaf SRN {
  type union {
   type uint8 {
    range "0..254";
   }
  }
  mandatory false;
 }
 leaf WPOS {
  type enumeration {
   enum val-0;
   enum val-1;
   enum val-2;
   enum val-3;
  }
  mandatory false;
 }
 }
 grouping GPM-attributes {
 leaf CN {
  type uint8 {
   range "0..7";
  }
  mandatory false;
 }
 leaf DDM {
  type boolean;
  mandatory false;
 }
 leaf DETECTOBJECT {
  type boolean;
  mandatory false;
 }
 leaf DIR {
  type boolean;
  mandatory false;
 }
 leaf OLD_GPMID {
  type union {
   type int32 {
    range "-1..65535";
   }
  }
  mandatory false;
 }
 leaf GPMID {
  type union {
   type int32 {
    range "-1..65535";
   }
  }
  mandatory false;
 }
 leaf PN {
  type uint8 {
   range "0..15";
  }
  mandatory false;
 }
 leaf PT {
  type enumeration {
   enum val-0;
   enum val-2;
   enum val-3;
   enum val-4;
   enum val-6;
   enum val-8;
  }
  mandatory false;
 }
 leaf RSCGRPID {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-127;
  }
  mandatory false;
 }
 leaf SBT {
  type enumeration {
   enum val-0;
   enum val-3;
   enum val-4;
   enum val-5;
  }
  mandatory false;
 }
 leaf SN {
  type uint8 {
   range "0..7";
  }
  mandatory false;
 }
 leaf SRN {
  type uint8 {
   range "0..1";
  }
  mandatory false;
 }
 }
 grouping GTPU-attributes {
 leaf DLGTPUSNCHKSW {
  type boolean;
  mandatory false;
 }
 leaf DSCP {
  type uint8 {
   range "0..63";
  }
  mandatory false;
 }
 leaf STATICCHK {
  type boolean;
  mandatory false;
 }
 leaf TIMEOUTCNT {
  type uint8 {
   range "3..6";
  }
  mandatory false;
 }
 leaf TIMEOUTTH {
  type uint16 {
   range "5000..60000";
  }
  mandatory false;
 }
 leaf ULGTPUSNPADSW {
  type boolean;
  mandatory false;
 }
 }
 grouping GTRANSPARA-attributes {
 leaf ARPAGINGTIME {
  type uint8 {
   range "5..120";
  }
  mandatory false;
 }
 leaf BYPASSSWITCH {
  type boolean;
  mandatory false;
 }
 leaf CPLBSW {
  type boolean;
  mandatory false;
 }
 leaf CPLISTENINGMODE {
  type boolean;
  mandatory false;
 }
 leaf DIRECTIPSECPRIMATCHSW {
  type boolean;
  mandatory false;
 }
 leaf DNSPRD {
  type uint16 {
   range "0..1000";
  }
  mandatory false;
 }
 leaf EPCFGMODE {
  type string;
  mandatory false;
 }
 leaf EPOBJAUTOCFGSW {
  type boolean;
  mandatory false;
 }
 leaf FORWARDMODE {
  type boolean;
  mandatory false;
 }
 leaf IPERRFRMALMAT {
  type uint8 {
   range "0..100";
  }
  mandatory false;
 }
 leaf IPERRFRMALMDT {
  type uint8 {
   range "0..100";
  }
  mandatory false;
 }
 leaf IPERRFRMSW {
  type boolean;
  mandatory false;
 }
 leaf LPSCHSW {
  type boolean;
  mandatory false;
 }
 leaf MODE {
  type enumeration {
   enum val-1;
   enum val-2;
  }
  mandatory false;
 }
 leaf MODELSELECT {
  type boolean;
  mandatory false;
 }
 leaf MONITORPOLICY {
  type enumeration {
   enum val-1;
   enum val-2;
   enum val-3;
   enum val-4;
   enum val-5;
  }
  mandatory false;
 }
 leaf OAMTYPE {
  type boolean;
  mandatory false;
 }
 leaf OMCHSBWAITTIME {
  type uint16 {
   range "1..600";
  }
  mandatory false;
 }
 leaf OMCHSWITCHBACK {
  type boolean;
  mandatory false;
 }
 leaf ONLYOMIP {
  type boolean;
  mandatory false;
 }
 leaf PWD {
  type string {
   length "1..19";
  }
  mandatory false;
 }
 leaf RATECFGTYPE {
  type boolean;
  mandatory false;
 }
 leaf SAMEPORTFORWARDSW {
  type boolean;
  mandatory false;
 }
 leaf SBTIME {
  type uint16 {
   range "0..1200";
  }
  mandatory false;
 }
 leaf SCTPRTRPTSW {
  type boolean;
  mandatory false;
 }
 leaf STATUS {
  type boolean;
  mandatory false;
 }
 leaf TRANSCFGMODE {
  type boolean;
  mandatory false;
 }
 leaf ULFLOWCTRLDECOUPSW {
  type boolean;
  mandatory false;
 }
 leaf VLANID {
  type uint16 {
   range "1..4094";
  }
  mandatory false;
 }
 }
 grouping GTRANSPARAGW-attributes {
 leaf ARPAGINGTIME {
  type uint8 {
   range "5..120";
  }
  mandatory false;
 }
 leaf FORWARDMODE {
  type boolean;
  mandatory false;
 }
 leaf IPCLKPRI {
  type uint8 {
   range "0..63";
  }
  mandatory false;
 }
 leaf IPERRFRMALMAT {
  type uint8 {
   range "0..100";
  }
  mandatory false;
 }
 leaf IPERRFRMALMDT {
  type uint8 {
   range "0..100";
  }
  mandatory false;
 }
 leaf IPERRFRMSW {
  type boolean;
  mandatory false;
 }
 leaf LPSCHSW {
  type boolean;
  mandatory false;
 }
 leaf MODE {
  type enumeration {
   enum val-1;
   enum val-2;
  }
  mandatory false;
 }
 leaf MONITORPOLICY {
  type enumeration {
   enum val-1;
   enum val-2;
   enum val-3;
   enum val-4;
   enum val-5;
  }
  mandatory false;
 }
 leaf OAMTYPE {
  type boolean;
  mandatory false;
 }
 leaf PORTDLCACSW {
  type boolean;
  mandatory false;
 }
 leaf PORTDLOBSW {
  type boolean;
  mandatory false;
 }
 leaf PORTULCACSW {
  type boolean;
  mandatory false;
 }
 leaf PORTULOBSW {
  type boolean;
  mandatory false;
 }
 leaf PRIRULE {
  type boolean;
  mandatory false;
 }
 leaf RATECFGTYPE {
  type boolean;
  mandatory false;
 }
 leaf SAMEPORTFORWARDSW {
  type boolean;
  mandatory false;
 }
 leaf SBTIME {
  type uint16 {
   range "0..1200";
  }
  mandatory false;
 }
 }
 grouping GUPTRANSPARA-attributes {
 leaf UPFLTSRVADMSW {
  type boolean;
  mandatory false;
 }
 leaf UPSRVALMSW {
  type string;
  mandatory false;
 }
 leaf UPSTATFASW {
  type boolean;
  mandatory false;
 }
 }
 grouping ICMPV6-attributes {
 leaf ERRMSGSW {
  type string;
  mandatory false;
 }
 }
 grouping IFIP-attributes {
 leaf OLD_CN {
  type union {
   type int8 {
    range "-1..7";
   }
  }
  mandatory false;
 }
 leaf CN {
  type union {
   type int8 {
    range "-1..7";
   }
  }
  mandatory false;
 }
 leaf OLD_IP {
  type inet:ipv4-address;
  mandatory false;
 }
 leaf IP {
  type inet:ipv4-address;
  mandatory false;
 }
 leaf MASK {
  type inet:ipv4-address;
  mandatory false;
 }
 leaf OLD_PN {
  type union {
   type int8 {
    range "-1..63";
   }
  }
  mandatory false;
 }
 leaf PN {
  type union {
   type int8 {
    range "-1..63";
   }
  }
  mandatory false;
 }
 leaf OLD_PT {
  type enumeration {
   enum val--1;
   enum val-0;
   enum val-2;
   enum val-3;
   enum val-4;
   enum val-9;
   enum val-16;
  }
  mandatory false;
 }
 leaf PT {
  type enumeration {
   enum val--1;
   enum val-0;
   enum val-2;
   enum val-3;
   enum val-4;
   enum val-9;
   enum val-16;
  }
  mandatory false;
 }
 leaf OLD_SBT {
  type enumeration {
   enum val--1;
   enum val-0;
   enum val-3;
   enum val-4;
   enum val-5;
  }
  mandatory false;
 }
 leaf SBT {
  type enumeration {
   enum val--1;
   enum val-0;
   enum val-3;
   enum val-4;
   enum val-5;
  }
  mandatory false;
 }
 leaf OLD_SN {
  type union {
   type int8 {
    range "-1..7";
   }
  }
  mandatory false;
 }
 leaf SN {
  type union {
   type int8 {
    range "-1..7";
   }
  }
  mandatory false;
 }
 leaf OLD_SRN {
  type union {
   type int8 {
    range "-1..1";
   }
  }
  mandatory false;
 }
 leaf SRN {
  type union {
   type int8 {
    range "-1..1";
   }
  }
  mandatory false;
 }
 leaf USERLABEL {
  type string {
   length "0..255";
  }
  mandatory false;
 }
 leaf OLD_VRFIDX {
  type union {
   type int8 {
    range "-1..7";
   }
  }
  mandatory false;
 }
 leaf VRFIDX {
  type union {
   type int8 {
    range "-1..7";
   }
  }
  mandatory false;
 }
 }
 grouping IKECFG-attributes {
 leaf DSCP {
  type uint8 {
   range "0..63";
  }
  mandatory false;
 }
 leaf ESPSPIPREFIX {
  type uint32 {
   range "0..4194303";
  }
  mandatory false;
 }
 leaf ESPSPIPREFIXLEN {
  type union {
   type uint8 {
    range "0..22";
   }
  }
  mandatory false;
 }
 leaf IKEKLI {
  type union {
   type uint16 {
    range "0..28800";
   }
  }
  mandatory false;
 }
 leaf IKEKLT {
  type union {
   type uint16 {
    range "0..28800";
   }
  }
  mandatory false;
 }
 leaf IKELNM {
  type string {
   length "0..31";
  }
  mandatory false;
 }
 leaf IPSECBINDMODE {
  type boolean;
  mandatory false;
 }
 leaf IPSECCFGMODE {
  type boolean;
  mandatory false;
 }
 leaf IPSECSBRANDTIME {
  type uint8 {
   range "0..120";
  }
  mandatory false;
 }
 leaf IPSECSBWAITTIME {
  type uint8 {
   range "2..15";
  }
  mandatory false;
 }
 leaf IPSECSORANDTIME {
  type uint8 {
   range "0..120";
  }
  mandatory false;
 }
 leaf IPSECSOWAITTIME {
  type uint8 {
   range "0..15";
  }
  mandatory false;
 }
 leaf IPSECSWITCHBACK {
  type enumeration {
   enum val-0;
   enum val-1;
   enum val-2;
   enum val-3;
  }
  mandatory false;
 }
 leaf NATKLI {
  type uint16 {
   range "5..300";
  }
  mandatory false;
 }
 leaf SMSWITCH {
  type boolean;
  mandatory false;
 }
 }
 grouping IKEPEER-attributes {
 leaf CERTNAME {
  type string {
   length "1..64";
  }
  mandatory false;
 }
 leaf CERTSOURCE {
  type boolean;
  mandatory false;
 }
 leaf CRLPOLICY {
  type enumeration {
   enum val-0;
   enum val-1;
   enum val-2;
  }
  mandatory false;
 }
 leaf CTRLMODE {
  type boolean;
  mandatory false;
 }
 leaf DPD {
  type enumeration {
   enum val-0;
   enum val-2;
  }
  mandatory false;
 }
 leaf DPDIDLETIME {
  type uint16 {
   range "3..3600";
  }
  mandatory false;
 }
 leaf DPDRETRI {
  type uint8 {
   range "3..30";
  }
  mandatory false;
 }
 leaf DPDRETRN {
  type uint8 {
   range "3..10";
  }
  mandatory false;
 }
 leaf ENCCERTNAME {
  type string {
   length "0..64";
  }
  mandatory false;
 }
 leaf EXCHMODE {
  type enumeration {
   enum val-2;
   enum val-4;
  }
  mandatory false;
 }
 leaf IDTYPE {
  type enumeration {
   enum val-1;
   enum val-2;
   enum val-5;
   enum val-9;
  }
  mandatory false;
 }
 leaf IKEV2FRGMTU {
  type uint16 {
   range "576..3000";
  }
  mandatory false;
 }
 leaf IKEV2FRGSW {
  type boolean;
  mandatory false;
 }
 leaf IKEVERSION {
  type enumeration {
   enum val-1;
   enum val-2;
  }
  mandatory false;
 }
 leaf IPSECPREFRGSW {
  type boolean;
  mandatory false;
 }
 leaf IPVERSION {
  type enumeration {
   enum val-0;
   enum val-1;
   enum val-2;
  }
  mandatory false;
 }
 leaf LOCALIP {
  type inet:ipv4-address;
  mandatory false;
 }
 leaf MASTERPEERNAME {
  type string {
   length "1..15";
  }
  mandatory false;
 }
 leaf MTU {
  type uint16 {
   range "46..9296";
  }
  mandatory false;
 }
 leaf MULTIVPNSWITCH {
  type boolean;
  mandatory false;
 }
 leaf NATTRAV {
  type boolean;
  mandatory false;
 }
 leaf OCSPSW {
  type boolean;
  mandatory false;
 }
 leaf OLD_PEERNAME {
  type string {
   length "1..15";
  }
  mandatory false;
 }
 leaf PEERNAME {
  type string {
   length "1..15";
  }
  mandatory false;
 }
 leaf PKEY {
  type string {
   length "0..127";
  }
  mandatory false;
 }
 leaf PRIORITY {
  type uint8 {
   range "1..7";
  }
  mandatory false;
 }
 leaf PROPID {
  type uint8 {
   range "1..99";
  }
  mandatory false;
 }
 leaf REDIRECTSW {
  type boolean;
  mandatory false;
 }
 leaf REDUNDANCYFLAG {
  type enumeration {
   enum val-0;
   enum val-1;
   enum val-2;
  }
  mandatory false;
 }
 leaf REMOTEIP {
  type inet:ipv4-address;
  mandatory false;
 }
 leaf REMOTENAME {
  type string {
   length "0..31";
  }
  mandatory false;
 }
 leaf TRUSTGROUPID {
  type union {
   type uint16 {
    range "0..65535";
   }
  }
  mandatory false;
 }
 leaf VRFIDX {
  type uint8 {
   range "0..31";
  }
  mandatory false;
 }
 }
 grouping IKEPROPOSAL-attributes {
 leaf AUTHALG {
  type enumeration {
   enum val-4;
   enum val-5;
   enum val-6;
   enum val-7;
   enum val-8;
   enum val-20;
  }
  mandatory false;
 }
 leaf AUTHMETH {
  type enumeration {
   enum val-8;
   enum val-10;
   enum val-12;
  }
  mandatory false;
 }
 leaf DHGRP {
  type enumeration {
   enum val-6;
   enum val-7;
   enum val-14;
   enum val-15;
   enum val-19;
   enum val-20;
   enum val-31;
  }
  mandatory false;
 }
 leaf DURATION {
  type uint32 {
   range "60..604800";
  }
  mandatory false;
 }
 leaf ENCALG {
  type enumeration {
   enum val-2;
   enum val-3;
   enum val-11;
   enum val-12;
   enum val-13;
   enum val-14;
   enum val-15;
   enum val-129;
  }
  mandatory false;
 }
 leaf PRFALG {
  type enumeration {
   enum val-14;
   enum val-15;
   enum val-18;
   enum val-19;
   enum val-20;
  }
  mandatory false;
 }
 leaf OLD_PROPID {
  type union {
   type int8 {
    range "-1..99";
   }
  }
  mandatory false;
 }
 leaf PROPID {
  type union {
   type int8 {
    range "-1..99";
   }
  }
  mandatory false;
 }
 leaf REAUTHLT {
  type uint32 {
   range "300..604800";
  }
  mandatory false;
 }
 leaf REAUTHSW {
  type boolean;
  mandatory false;
 }
 leaf RSAPADDING {
  type boolean;
  mandatory false;
 }
 leaf RSASIGHASHALG {
  type enumeration {
   enum val-3;
   enum val-14;
   enum val-15;
  }
  mandatory false;
 }
 }
 grouping IMAGRP-attributes {
 leaf CLKM {
  type enumeration {
   enum val-1;
   enum val-2;
  }
  mandatory false;
 }
 leaf OLD_CN {
  type union {
   type int8 {
    range "-1..7";
   }
  }
  mandatory false;
 }
 leaf CN {
  type union {
   type int8 {
    range "-1..7";
   }
  }
  mandatory false;
 }
 leaf DELAY {
  type uint8 {
   range "4..100";
  }
  mandatory false;
 }
 leaf FRMLEN {
  type enumeration {
   enum val-0;
   enum val-1;
   enum val-2;
   enum val-3;
  }
  mandatory false;
 }
 leaf OLD_IMAGRPN {
  type union {
   type int8 {
    range "-1..3";
   }
  }
  mandatory false;
 }
 leaf IMAGRPN {
  type union {
   type int8 {
    range "-1..3";
   }
  }
  mandatory false;
 }
 leaf MINLNK {
  type uint8 {
   range "1..8";
  }
  mandatory false;
 }
 leaf OLD_SBT {
  type enumeration {
   enum val--1;
   enum val-0;
   enum val-3;
  }
  mandatory false;
 }
 leaf SBT {
  type enumeration {
   enum val--1;
   enum val-0;
   enum val-3;
  }
  mandatory false;
 }
 leaf SCRAM {
  type boolean;
  mandatory false;
 }
 leaf OLD_SN {
  type union {
   type int8 {
    range "-1..7";
   }
  }
  mandatory false;
 }
 leaf SN {
  type union {
   type int8 {
    range "-1..7";
   }
  }
  mandatory false;
 }
 leaf OLD_SRN {
  type union {
   type int8 {
    range "-1..1";
   }
  }
  mandatory false;
 }
 leaf SRN {
  type union {
   type int8 {
    range "-1..1";
   }
  }
  mandatory false;
 }
 leaf TS16 {
  type boolean;
  mandatory false;
 }
 leaf VER {
  type enumeration {
   enum val-1;
   enum val-3;
  }
  mandatory false;
 }
 }
 grouping IMALNK-attributes {
 leaf CN {
  type union {
   type int8 {
    range "-1..7";
   }
  }
  mandatory false;
 }
 leaf IMAGRPN {
  type uint8 {
   range "0..3";
  }
  mandatory false;
 }
 leaf IMAGRPSBT {
  type enumeration {
   enum val-0;
   enum val-3;
  }
  mandatory false;
 }
 leaf IMALNKN {
  type union {
   type int8 {
    range "-1..7";
   }
  }
  mandatory false;
 }
 leaf SBT {
  type enumeration {
   enum val--1;
   enum val-0;
   enum val-3;
   enum val-4;
  }
  mandatory false;
 }
 leaf SN {
  type union {
   type int8 {
    range "-1..7";
   }
  }
  mandatory false;
 }
 leaf SRN {
  type union {
   type int8 {
    range "-1..1";
   }
  }
  mandatory false;
 }
 }
 grouping INTERFACE-attributes {
 leaf ARPPROXY {
  type boolean;
  mandatory false;
 }
 leaf CTRLMODE {
  type boolean;
  mandatory false;
 }
 leaf DSCP2PCPMAPID {
  type uint8 {
   range "0..15";
  }
  mandatory false;
 }
 leaf DSCP2QUEMAPID {
  type uint8 {
   range "0..15";
  }
  mandatory false;
 }
 leaf IPV6SW {
  type boolean;
  mandatory false;
 }
 leaf OLD_ITFID {
  type union {
   type int16 {
    range "-1..19999";
   }
  }
  mandatory false;
 }
 leaf ITFID {
  type union {
   type int16 {
    range "-1..19999";
   }
  }
  mandatory false;
 }
 leaf ITFTYPE {
  type enumeration {
   enum val-0;
   enum val-1;
   enum val-2;
  }
  mandatory false;
 }
 leaf MTU4 {
  type uint16 {
   range "46..9296";
  }
  mandatory false;
 }
 leaf MTU6 {
  type uint16 {
   range "1280..9296";
  }
  mandatory false;
 }
 leaf PORTID {
  type uint32 {
   range "0..99999";
  }
  mandatory false;
 }
 leaf PT {
  type enumeration {
   enum val-0;
   enum val-2;
   enum val-3;
   enum val-4;
   enum val-6;
   enum val-8;
   enum val-14;
   enum val-15;
   enum val-16;
   enum val-19;
  }
  mandatory false;
 }
 leaf TAGGED {
  type boolean;
  mandatory false;
 }
 leaf USERLABEL {
  type string {
   length "0..255";
  }
  mandatory false;
 }
 leaf VLANID {
  type uint16 {
   range "1..4094";
  }
  mandatory false;
 }
 leaf VRFIDX {
  type uint8 {
   range "0..31";
  }
  mandatory false;
 }
 }
 grouping INTERFACEPARA6-attributes {
 leaf DHCPRELAYSW {
  type boolean;
  mandatory false;
 }
 leaf ITFID {
  type union {
   type int16 {
    range "-1..1499";
   }
  }
  mandatory false;
 }
 leaf NDPROXY {
  type boolean;
  mandatory false;
 }
 leaf SENDDELTA {
  type uint16 {
   range "0..1000";
  }
  mandatory false;
 }
 leaf SENDDRIFT {
  type uint8 {
   range "0..100";
  }
  mandatory false;
 }
 leaf SENDFUZZFACTOR {
  type uint16 {
   range "0..1000";
  }
  mandatory false;
 }
 leaf SENDSW {
  type boolean;
  mandatory false;
 }
 }
 grouping IP2IPRSCGRP-attributes {
 leaf DSTIPV4 {
  type inet:ipv4-address;
  mandatory false;
 }
 leaf DSTIPV6 {
  type inet:ipv6-address;
  mandatory false;
 }
 leaf DSTMASK {
  type inet:ipv4-address;
  mandatory false;
 }
 leaf OLD_IP2IPRSCGRPID {
  type union {
   type int16 {
    range "-1..255";
   }
  }
  mandatory false;
 }
 leaf IP2IPRSCGRPID {
  type union {
   type int16 {
    range "-1..255";
   }
  }
  mandatory false;
 }
 leaf IPRSCGRPID {
  type uint32 {
   range "0..150014";
  }
  mandatory false;
 }
 leaf IPVERSION {
  type boolean;
  mandatory false;
 }
 leaf PFXLEN {
  type uint8 {
   range "1..128";
  }
  mandatory false;
 }
 leaf VRFIDX {
  type uint8 {
   range "0..31";
  }
  mandatory false;
 }
 }
 grouping IP2RSCGRP-attributes {
 leaf BEAR {
  type boolean;
  mandatory false;
 }
 leaf CN {
  type uint8 {
   range "0..7";
  }
  mandatory false;
 }
 leaf DSTIP {
  type inet:ipv4-address;
  mandatory false;
 }
 leaf DSTMASK {
  type inet:ipv4-address;
  mandatory false;
 }
 leaf OLD_MAPIDX {
  type union {
   type int8 {
    range "-1..127";
   }
  }
  mandatory false;
 }
 leaf MAPIDX {
  type union {
   type int8 {
    range "-1..127";
   }
  }
  mandatory false;
 }
 leaf PN {
  type uint8 {
   range "0..15";
  }
  mandatory false;
 }
 leaf PT {
  type enumeration {
   enum val-0;
   enum val-2;
   enum val-3;
   enum val-4;
   enum val-8;
  }
  mandatory false;
 }
 leaf RSCGRPID {
  type uint8 {
   range "0..15";
  }
  mandatory false;
 }
 leaf SBT {
  type enumeration {
   enum val-0;
   enum val-3;
   enum val-4;
   enum val-5;
  }
  mandatory false;
 }
 leaf SN {
  type uint8 {
   range "0..7";
  }
  mandatory false;
 }
 leaf SRN {
  type uint8 {
   range "0..1";
  }
  mandatory false;
 }
 leaf VRFIDX {
  type uint8 {
   range "0..7";
  }
  mandatory false;
 }
 }
 grouping IPADDR4-attributes {
 leaf OLD_IP {
  type inet:ipv4-address;
  mandatory false;
 }
 leaf IP {
  type inet:ipv4-address;
  mandatory false;
 }
 leaf OLD_ITFID {
  type union {
   type int16 {
    range "-1..1499";
   }
  }
  mandatory false;
 }
 leaf ITFID {
  type union {
   type int16 {
    range "-1..1499";
   }
  }
  mandatory false;
 }
 leaf MASK {
  type inet:ipv4-address;
  mandatory false;
 }
 leaf USERLABEL {
  type string {
   length "0..255";
  }
  mandatory false;
 }
 leaf VRFIDX {
  type uint8 {
   range "0..31";
  }
  mandatory false;
 }
 }
 grouping IPADDR6-attributes {
 leaf OLD_IPADDR6ID {
  type string {
   length "1..15";
  }
  mandatory false;
 }
 leaf IPADDR6ID {
  type string {
   length "1..15";
  }
  mandatory false;
 }
 leaf IPV6 {
  type inet:ipv6-address;
  mandatory false;
 }
 leaf ITFID {
  type uint16 {
   range "0..1499";
  }
  mandatory false;
 }
 leaf PFXLEN {
  type uint8 {
   range "1..128";
  }
  mandatory false;
 }
 leaf USERLABEL {
  type string {
   length "0..255";
  }
  mandatory false;
 }
 leaf VRFIDX {
  type uint8 {
   range "0..31";
  }
  mandatory false;
 }
 }
 grouping IPCLKLNK-attributes {
 leaf ANNFREQ {
  type enumeration {
   enum val-0;
   enum val-1;
   enum val-2;
   enum val-3;
   enum val-4;
   enum val-5;
   enum val-6;
   enum val-7;
  }
  mandatory false;
 }
 leaf AUTOCMPSTSW {
  type boolean;
  mandatory false;
 }
 leaf CIP {
  type inet:ipv4-address;
  mandatory false;
 }
 leaf CIPV6 {
  type inet:ipv6-address;
  mandatory false;
 }
 leaf CLASS0 {
  type uint8 {
   range "0..255";
  }
  mandatory false;
 }
 leaf CLASS1 {
  type uint8 {
   range "0..255";
  }
  mandatory false;
 }
 leaf CLASS2 {
  type uint8 {
   range "0..255";
  }
  mandatory false;
 }
 leaf CLASS3 {
  type uint8 {
   range "0..255";
  }
  mandatory false;
 }
 leaf CLASSENHHOSW {
  type boolean;
  mandatory false;
 }
 leaf CLASSIDENTIFY {
  type boolean;
  mandatory false;
 }
 leaf CLKMAC {
  type yang:mac-address;
  mandatory false;
 }
 leaf CLKSRVDESCRI {
  type string {
   length "0..63";
  }
  mandatory false;
 }
 leaf CMPST {
  type int32 {
   range "-1000000..1000000";
  }
  mandatory false;
 }
 leaf CMPSTINTERVAL {
  type uint16 {
   range "10..300";
  }
  mandatory false;
 }
 leaf CN {
  type uint8 {
   range "0..7";
  }
  mandatory false;
 }
 leaf CNM {
  type enumeration {
   enum val-0;
   enum val-1;
   enum val-2;
  }
  mandatory false;
 }
 leaf CNTNETTYPE {
  type boolean;
  mandatory false;
 }
 leaf CSSPSW {
  type boolean;
  mandatory false;
 }
 leaf DELAYFREQ {
  type enumeration {
   enum val-0;
   enum val-1;
   enum val-2;
   enum val-3;
   enum val-4;
   enum val-5;
   enum val-6;
   enum val-7;
   enum val-8;
   enum val-9;
   enum val-10;
   enum val-11;
  }
  mandatory false;
 }
 leaf DELAYTYPE {
  type boolean;
  mandatory false;
 }
 leaf DEVTYPE {
  type boolean;
  mandatory false;
 }
 leaf DM {
  type uint8 {
   range "0..255";
  }
  mandatory false;
 }
 leaf DSTMLTMACTYPE {
  type boolean;
  mandatory false;
 }
 leaf ICPT {
  type boolean;
  mandatory false;
 }
 leaf IPMODE {
  type boolean;
  mandatory false;
 }
 leaf IPSYNCMODE {
  type enumeration {
   enum val-0;
   enum val-1;
   enum val-4;
  }
  mandatory false;
 }
 leaf OLD_LN {
  type union {
   type int8 {
    range "-1..3";
   }
  }
  mandatory false;
 }
 leaf LN {
  type union {
   type int8 {
    range "-1..3";
   }
  }
  mandatory false;
 }
 leaf MACMODE {
  type boolean;
  mandatory false;
 }
 leaf MASTERPRIO {
  type uint8 {
   range "0..255";
  }
  mandatory false;
 }
 leaf MINSTEPSW {
  type boolean;
  mandatory false;
 }
 leaf NEGDURATION {
  type uint16 {
   range "60..1000";
  }
  mandatory false;
 }
 leaf PDELAYREQFREQ {
  type enumeration {
   enum val-3;
   enum val-4;
   enum val-5;
   enum val-6;
   enum val-7;
   enum val-8;
  }
  mandatory false;
 }
 leaf PREHOPIP {
  type inet:ipv4-address;
  mandatory false;
 }
 leaf PRI {
  type uint8 {
   range "1..4";
  }
  mandatory false;
 }
 leaf PRIORITY1 {
  type uint8 {
   range "0..255";
  }
  mandatory false;
 }
 leaf PRIORITY2 {
  type uint8 {
   range "0..255";
  }
  mandatory false;
 }
 leaf PROFILETYPE {
  type enumeration {
   enum val-0;
   enum val-1;
   enum val-2;
   enum val-3;
   enum val-4;
  }
  mandatory false;
 }
 leaf PTPVLANID {
  type uint16 {
   range "1..4094";
  }
  mandatory false;
 }
 leaf PTPVLANMODE {
  type enumeration {
   enum val-0;
   enum val-1;
   enum val-2;
  }
  mandatory false;
 }
 leaf SIP {
  type inet:ipv4-address;
  mandatory false;
 }
 leaf SIPV6 {
  type inet:ipv6-address;
  mandatory false;
 }
 leaf SN {
  type uint8 {
   range "0..7";
  }
  mandatory false;
 }
 leaf SRN {
  type uint8 {
   range "0..1";
  }
  mandatory false;
 }
 leaf SYNCFREQ {
  type enumeration {
   enum val-0;
   enum val-1;
   enum val-2;
   enum val-3;
   enum val-4;
   enum val-5;
   enum val-6;
   enum val-7;
   enum val-8;
   enum val-9;
   enum val-10;
   enum val-11;
  }
  mandatory false;
 }
 leaf VRFIDX {
  type uint8 {
   range "0..31";
  }
  mandatory false;
 }
 }
 grouping IPDLFLOWCTRLPARA-attributes {
 leaf BWPRTSWITCH {
  type boolean;
  mandatory false;
 }
 leaf DLFLOWCTRLENHSW {
  type boolean;
  mandatory false;
 }
 leaf DLIUBBWMINPRORATIO {
  type uint8 {
   range "0..100";
  }
  mandatory false;
 }
 leaf DLIUBMINBW {
  type uint32 {
   range "0..1000000";
  }
  mandatory false;
 }
 leaf DR {
  type uint16 {
   range "0..1000";
  }
  mandatory false;
 }
 leaf FAIRRATIO {
  type uint8 {
   range "0..100";
  }
  mandatory false;
 }
 leaf FAIRSWITCH {
  type boolean;
  mandatory false;
 }
 leaf OLD_IPDLFLOWCTRALGID {
  type union {
   type int16 {
    range "-1..143";
   }
  }
  mandatory false;
 }
 leaf IPDLFLOWCTRALGID {
  type union {
   type int16 {
    range "-1..143";
   }
  }
  mandatory false;
 }
 leaf ITM {
  type boolean;
  mandatory false;
 }
 leaf PORTID {
  type uint32 {
   range "0..99999";
  }
  mandatory false;
 }
 leaf PT {
  type enumeration {
   enum val-6;
   enum val-10;
   enum val-12;
   enum val-13;
   enum val-14;
   enum val-15;
  }
  mandatory false;
 }
 leaf SWITCH {
  type enumeration {
   enum val-0;
   enum val-1;
   enum val-2;
   enum val-3;
  }
  mandatory false;
 }
 leaf TD {
  type uint8 {
   range "0..100";
  }
  mandatory false;
 }
 }
 grouping IPGPM-attributes {
 leaf DDM {
  type boolean;
  mandatory false;
 }
 leaf DETECTOBJECT {
  type boolean;
  mandatory false;
 }
 leaf DIR {
  type boolean;
  mandatory false;
 }
 leaf OLD_IPGPMID {
  type union {
   type int32 {
    range "-1..65535";
   }
  }
  mandatory false;
 }
 leaf IPGPMID {
  type union {
   type int32 {
    range "-1..65535";
   }
  }
  mandatory false;
 }
 leaf IPRSCGRPID {
  type uint32 {
   range "0..150014";
  }
  mandatory false;
 }
 leaf PORTID {
  type uint32 {
   range "0..99999";
  }
  mandatory false;
 }
 leaf PT {
  type boolean;
  mandatory false;
 }
 }
 grouping IPGUARD-attributes {
 leaf ARPLRNSTRICTPOLICY {
  type boolean;
  mandatory false;
 }
 leaf ARPLRNSTRICTSW {
  type boolean;
  mandatory false;
 }
 leaf ARPSPOOFALMTHD {
  type uint16 {
   range "10..1000";
  }
  mandatory false;
 }
 leaf ARPSPOOFCHKSW {
  type boolean;
  mandatory false;
 }
 leaf INVALIDPKTALMTHD {
  type uint32 {
   range "20..200000";
  }
  mandatory false;
 }
 leaf INVALIDPKTCHKSW {
  type boolean;
  mandatory false;
 }
 leaf IPSECREPLAYALMTHD {
  type uint32 {
   range "1..100000";
  }
  mandatory false;
 }
 leaf IPSECREPLAYCHKSW {
  type boolean;
  mandatory false;
 }
 leaf MAXREDIRECTS {
  type uint8 {
   range "1..15";
  }
  mandatory false;
 }
 leaf NDSPOOFALMTHD {
  type uint16 {
   range "10..1000";
  }
  mandatory false;
 }
 leaf NDSPOOFCHKSW {
  type boolean;
  mandatory false;
 }
 leaf PORTSCANCAPLIST {
  type string {
   length "1..59";
  }
  mandatory false;
 }
 leaf PORTSCANCAPSW {
  type boolean;
  mandatory false;
 }
 leaf REDIRECTDOSCHKSW {
  type boolean;
  mandatory false;
 }
 }
 grouping IPPATH-attributes {
 leaf BPT {
  type enumeration {
   enum val-0;
   enum val-2;
   enum val-3;
   enum val-4;
   enum val-6;
   enum val-8;
  }
  mandatory false;
 }
 leaf CN {
  type uint8 {
   range "0..7";
  }
  mandatory false;
 }
 leaf DESCRI {
  type string {
   length "0..47";
  }
  mandatory false;
 }
 leaf DSCP {
  type uint8 {
   range "0..63";
  }
  mandatory false;
 }
 leaf FRAMELEN {
  type uint16 {
   range "100..1031";
  }
  mandatory false;
 }
 leaf IPMUXSWITCH {
  type boolean;
  mandatory false;
 }
 leaf IPRSCGRPID {
  type uint32 {
   range "0..150014";
  }
  mandatory false;
 }
 leaf JNIPRSCGRP {
  type boolean;
  mandatory false;
 }
 leaf JNRSCGRP {
  type boolean;
  mandatory false;
 }
 leaf LOCALIP {
  type inet:ipv4-address;
  mandatory false;
 }
 leaf OLD_PATHID {
  type union {
   type int32 {
    range "-1..65535";
   }
  }
  mandatory false;
 }
 leaf PATHID {
  type union {
   type int32 {
    range "-1..65535";
   }
  }
  mandatory false;
 }
 leaf PATHTYPE {
  type boolean;
  mandatory false;
 }
 leaf PEERIP {
  type inet:ipv4-address;
  mandatory false;
 }
 leaf PN {
  type uint8 {
   range "0..35";
  }
  mandatory false;
 }
 leaf PORTID {
  type uint32 {
   range "0..99999";
  }
  mandatory false;
 }
 leaf PT {
  type enumeration {
   enum val-0;
   enum val-2;
   enum val-3;
   enum val-4;
   enum val-6;
   enum val-8;
  }
  mandatory false;
 }
 leaf QT {
  type boolean;
  mandatory false;
 }
 leaf RSCGRPID {
  type uint8 {
   range "0..15";
  }
  mandatory false;
 }
 leaf SBT {
  type enumeration {
   enum val-0;
   enum val-3;
   enum val-4;
   enum val-5;
  }
  mandatory false;
 }
 leaf SN {
  type uint8 {
   range "0..7";
  }
  mandatory false;
 }
 leaf SRN {
  type uint8 {
   range "0..1";
  }
  mandatory false;
 }
 leaf STATICCHK {
  type enumeration {
   enum val-0;
   enum val-1;
   enum val-2;
  }
  mandatory false;
 }
 leaf SUBFRAMELEN {
  type uint16 {
   range "1..1023";
  }
  mandatory false;
 }
 leaf TIMER {
  type uint8 {
   range "1..20";
  }
  mandatory false;
 }
 leaf TRANSCFGMODE {
  type boolean;
  mandatory false;
 }
 leaf VRFIDX {
  type uint8 {
   range "0..31";
  }
  mandatory false;
 }
 }
 grouping IPPMSESSION-attributes {
 leaf ASSOCIATEUPPATHPLR {
  type boolean;
  mandatory false;
 }
 leaf BINDPATH {
  type boolean;
  mandatory false;
 }
 leaf CTRLMODE {
  type boolean;
  mandatory false;
 }
 leaf DIR {
  type enumeration {
   enum val-1;
   enum val-2;
  }
  mandatory false;
 }
 leaf IPPMDSCP {
  type uint8 {
   range "0..63";
  }
  mandatory false;
 }
 leaf OLD_IPPMSN {
  type union {
   type int32 {
    range "-1..79999";
   }
  }
  mandatory false;
 }
 leaf IPPMSN {
  type union {
   type int32 {
    range "-1..79999";
   }
  }
  mandatory false;
 }
 leaf IPPMTYPE {
  type enumeration {
   enum val-0;
   enum val-2;
  }
  mandatory false;
 }
 leaf IPVERSION {
  type boolean;
  mandatory false;
 }
 leaf LOCALIP {
  type inet:ipv4-address;
  mandatory false;
 }
 leaf LOCALIPV6 {
  type inet:ipv6-address;
  mandatory false;
 }
 leaf PATHID {
  type uint16 {
   range "0..65535";
  }
  mandatory false;
 }
 leaf PEERIP {
  type inet:ipv4-address;
  mandatory false;
 }
 leaf PEERIPV6 {
  type inet:ipv6-address;
  mandatory false;
 }
 leaf VRFIDX {
  type uint8 {
   range "0..31";
  }
  mandatory false;
 }
 }
 grouping IPROUTE4-attributes {
 leaf DSTIP {
  type inet:ipv4-address;
  mandatory false;
 }
 leaf DSTMASK {
  type inet:ipv4-address;
  mandatory false;
 }
 leaf MTU {
  type uint16 {
   range "46..9296";
  }
  mandatory false;
 }
 leaf MTUSWITCH {
  type boolean;
  mandatory false;
 }
 leaf NEXTHOP {
  type inet:ipv4-address;
  mandatory false;
 }
 leaf PEERIP {
  type inet:ipv4-address;
  mandatory false;
 }
 leaf PORTID {
  type uint16 {
   range "0..1499";
  }
  mandatory false;
 }
 leaf PREF {
  type uint8 {
   range "1..255";
  }
  mandatory false;
 }
 leaf PT {
  type enumeration {
   enum val-0;
   enum val-2;
   enum val-8;
   enum val-10;
   enum val-12;
   enum val-18;
  }
  mandatory false;
 }
 leaf OLD_RTIDX {
  type union {
   type int16 {
    range "-1..149";
   }
  }
  mandatory false;
 }
 leaf RTIDX {
  type union {
   type int16 {
    range "-1..149";
   }
  }
  mandatory false;
 }
 leaf RTTYPE {
  type boolean;
  mandatory false;
 }
 leaf USERLABEL {
  type string {
   length "0..255";
  }
  mandatory false;
 }
 leaf VRFIDX {
  type uint8 {
   range "0..31";
  }
  mandatory false;
 }
 }
 grouping IPROUTE6-attributes {
 leaf DSTIP {
  type inet:ipv6-address;
  mandatory false;
 }
 leaf ITFID {
  type uint16 {
   range "0..1499";
  }
  mandatory false;
 }
 leaf NEXTHOP {
  type inet:ipv6-address;
  mandatory false;
 }
 leaf PFXLEN {
  type uint8 {
   range "0..128";
  }
  mandatory false;
 }
 leaf PREF {
  type uint8 {
   range "1..255";
  }
  mandatory false;
 }
 leaf OLD_RTIDX {
  type union {
   type int8 {
    range "-1..127";
   }
  }
  mandatory false;
 }
 leaf RTIDX {
  type union {
   type int8 {
    range "-1..127";
   }
  }
  mandatory false;
 }
 leaf RTTYPE {
  type boolean;
  mandatory false;
 }
 leaf USERLABEL {
  type string {
   length "0..255";
  }
  mandatory false;
 }
 leaf VRFIDX {
  type uint8 {
   range "0..31";
  }
  mandatory false;
 }
 }
 grouping IPRSCGRP-attributes {
 leaf OLD_IPRSCGRPID {
  type union {
   type int32 {
    range "-1..150014";
   }
  }
  mandatory false;
 }
 leaf IPRSCGRPID {
  type union {
   type int32 {
    range "-1..150014";
   }
  }
  mandatory false;
 }
 leaf OID {
  type uint8 {
   range "0..5";
  }
  mandatory false;
 }
 leaf PORTID {
  type uint16 {
   range "0..9999";
  }
  mandatory false;
 }
 leaf PT {
  type enumeration {
   enum val-6;
   enum val-8;
   enum val-9;
   enum val-10;
   enum val-15;
  }
  mandatory false;
 }
 leaf RSCGRPNO {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-126;
   enum val-127;
  }
  mandatory false;
 }
 leaf RU {
  type boolean;
  mandatory false;
 }
 leaf RXBW {
  type uint32 {
   range "32..100000000";
  }
  mandatory false;
 }
 leaf RXCIR {
  type uint32 {
   range "64..100000000";
  }
  mandatory false;
 }
 leaf RXPIR {
  type uint32 {
   range "64..100000000";
  }
  mandatory false;
 }
 leaf TXBW {
  type uint32 {
   range "32..100000000";
  }
  mandatory false;
 }
 leaf TXCBS {
  type uint32 {
   range "64..100000000";
  }
  mandatory false;
 }
 leaf TXCIR {
  type uint32 {
   range "64..100000000";
  }
  mandatory false;
 }
 leaf TXEBS {
  type uint32 {
   range "64..100000000";
  }
  mandatory false;
 }
 leaf TXPBS {
  type uint32 {
   range "64..100000000";
  }
  mandatory false;
 }
 leaf TXPIR {
  type uint32 {
   range "64..100000000";
  }
  mandatory false;
 }
 leaf USERLABEL {
  type string {
   length "0..255";
  }
  mandatory false;
 }
 leaf WEIGHT {
  type uint8 {
   range "1..100";
  }
  mandatory false;
 }
 }
 grouping IPRSCGRPALG-attributes {
 leaf CCTTH {
  type uint16 {
   range "0..500";
  }
  mandatory false;
 }
 leaf CTTH {
  type uint16 {
   range "0..500";
  }
  mandatory false;
 }
 leaf DDTH {
  type uint16 {
   range "0..10000";
  }
  mandatory false;
 }
 leaf DROPPKTNUM {
  type uint16 {
   range "0..8192";
  }
  mandatory false;
 }
 leaf IPRSCGRPID {
  type union {
   type int32 {
    range "-1..150014";
   }
  }
  mandatory false;
 }
 leaf PLRDTH {
  type uint16 {
   range "0..1000";
  }
  mandatory false;
 }
 leaf PQN {
  type uint8 {
   range "0..6";
  }
  mandatory false;
 }
 leaf RXBWAMIN {
  type uint32 {
   range "64..100000000";
  }
  mandatory false;
 }
 leaf RXBWASW {
  type boolean;
  mandatory false;
 }
 leaf RXRSVBW {
  type uint32 {
   range "0..100000000";
  }
  mandatory false;
 }
 leaf TCSW {
  type boolean;
  mandatory false;
 }
 leaf TXBWAMIN {
  type uint32 {
   range "64..100000000";
  }
  mandatory false;
 }
 leaf TXBWASW {
  type boolean;
  mandatory false;
 }
 leaf TXRSVBW {
  type uint32 {
   range "0..100000000";
  }
  mandatory false;
 }
 leaf TXSSW {
  type boolean;
  mandatory false;
 }
 }
 grouping IPRT-attributes {
 leaf CN {
  type uint8 {
   range "0..7";
  }
  mandatory false;
 }
 leaf DESCRI {
  type string {
   length "0..47";
  }
  mandatory false;
 }
 leaf DSTIP {
  type inet:ipv4-address;
  mandatory false;
 }
 leaf DSTMASK {
  type inet:ipv4-address;
  mandatory false;
 }
 leaf IFNO {
  type uint8 {
   range "0..15";
  }
  mandatory false;
 }
 leaf IFT {
  type enumeration {
   enum val-0;
   enum val-2;
   enum val-8;
   enum val-10;
   enum val-12;
  }
  mandatory false;
 }
 leaf MTU {
  type uint16 {
   range "46..9296";
  }
  mandatory false;
 }
 leaf MTUSWITCH {
  type boolean;
  mandatory false;
 }
 leaf NEXTHOP {
  type inet:ipv4-address;
  mandatory false;
 }
 leaf PEERIP {
  type inet:ipv4-address;
  mandatory false;
 }
 leaf PREF {
  type uint8 {
   range "1..255";
  }
  mandatory false;
 }
 leaf OLD_RTIDX {
  type union {
   type int16 {
    range "-1..149";
   }
  }
  mandatory false;
 }
 leaf RTIDX {
  type union {
   type int16 {
    range "-1..149";
   }
  }
  mandatory false;
 }
 leaf RTTYPE {
  type boolean;
  mandatory false;
 }
 leaf SBT {
  type enumeration {
   enum val-0;
   enum val-3;
   enum val-4;
   enum val-5;
  }
  mandatory false;
 }
 leaf SN {
  type uint8 {
   range "0..7";
  }
  mandatory false;
 }
 leaf SRN {
  type uint8 {
   range "0..1";
  }
  mandatory false;
 }
 leaf VRFIDX {
  type uint8 {
   range "0..7";
  }
  mandatory false;
 }
 }
 grouping IPSECBIND-attributes {
 leaf OLD_CN {
  type union {
   type int8 {
    range "-1..7";
   }
  }
  mandatory false;
 }
 leaf CN {
  type union {
   type int8 {
    range "-1..7";
   }
  }
  mandatory false;
 }
 leaf CTRLMODE {
  type boolean;
  mandatory false;
 }
 leaf OLD_PN {
  type union {
   type int8 {
    range "-1..5";
   }
  }
  mandatory false;
 }
 leaf PN {
  type union {
   type int8 {
    range "-1..5";
   }
  }
  mandatory false;
 }
 leaf OLD_PT {
  type enumeration {
   enum val--1;
   enum val-3;
   enum val-4;
   enum val-16;
  }
  mandatory false;
 }
 leaf PT {
  type enumeration {
   enum val--1;
   enum val-3;
   enum val-4;
   enum val-16;
  }
  mandatory false;
 }
 leaf OLD_SBT {
  type enumeration {
   enum val--1;
   enum val-0;
   enum val-5;
  }
  mandatory false;
 }
 leaf SBT {
  type enumeration {
   enum val--1;
   enum val-0;
   enum val-5;
  }
  mandatory false;
 }
 leaf OLD_SN {
  type union {
   type int8 {
    range "-1..7";
   }
  }
  mandatory false;
 }
 leaf SN {
  type union {
   type int8 {
    range "-1..7";
   }
  }
  mandatory false;
 }
 leaf OLD_SPGN {
  type string {
   length "1..15";
  }
  mandatory false;
 }
 leaf SPGN {
  type string {
   length "1..15";
  }
  mandatory false;
 }
 leaf OLD_SRN {
  type union {
   type int8 {
    range "-1..1";
   }
  }
  mandatory false;
 }
 leaf SRN {
  type union {
   type int8 {
    range "-1..1";
   }
  }
  mandatory false;
 }
 }
 grouping IPSECBINDITF-attributes {
 leaf CTRLMODE {
  type boolean;
  mandatory false;
 }
 leaf OLD_IPSECBINDITFID {
  type union {
   type int16 {
    range "-1..19999";
   }
  }
  mandatory false;
 }
 leaf IPSECBINDITFID {
  type union {
   type int16 {
    range "-1..19999";
   }
  }
  mandatory false;
 }
 leaf ITFID {
  type union {
   type uint16 {
    range "0..19999";
   }
  }
  mandatory false;
 }
 leaf SPGN {
  type string {
   length "1..15";
  }
  mandatory false;
 }
 }
 grouping IPSECPOLICY-attributes {
 leaf ACL2ID {
  type uint16 {
   range "3000..3999";
  }
  mandatory false;
 }
 leaf ACLID {
  type union {
   type uint16 {
    range "3000..9999";
   }
  }
  mandatory false;
 }
 leaf ACLTYPE {
  type enumeration {
   enum val-0;
   enum val-1;
   enum val-2;
  }
  mandatory false;
 }
 leaf CTRLMODE {
  type boolean;
  mandatory false;
 }
 leaf LTCFG {
  type boolean;
  mandatory false;
 }
 leaf LTKB {
  type union {
   type uint32 {
    range "0..4294967295";
   }
  }
  mandatory false;
 }
 leaf LTS {
  type uint32 {
   range "30..604800";
  }
  mandatory false;
 }
 leaf NARROWDOWNSW {
  type boolean;
  mandatory false;
 }
 leaf PEERNAME {
  type string {
   length "1..15";
  }
  mandatory false;
 }
 leaf PFS {
  type enumeration {
   enum val-0;
   enum val-1;
   enum val-2;
   enum val-14;
   enum val-15;
   enum val-19;
   enum val-20;
   enum val-31;
  }
  mandatory false;
 }
 leaf PROPNAME {
  type string {
   length "1..15";
  }
  mandatory false;
 }
 leaf REPLAYWND {
  type enumeration {
   enum val-0;
   enum val-1;
   enum val-2;
   enum val-128;
   enum val-256;
   enum val-512;
   enum val-1024;
   enum val-2048;
   enum val-4096;
  }
  mandatory false;
 }
 leaf OLD_SPGN {
  type string {
   length "1..15";
  }
  mandatory false;
 }
 leaf SPGN {
  type string {
   length "1..15";
  }
  mandatory false;
 }
 leaf OLD_SPSN {
  type union {
   type int16 {
    range "-1..20000";
   }
  }
  mandatory false;
 }
 leaf SPSN {
  type union {
   type int16 {
    range "-1..20000";
   }
  }
  mandatory false;
 }
 }
 grouping IPSECPROPOSAL-attributes {
 leaf AHAUTHALG {
  type enumeration {
   enum val-1;
   enum val-2;
   enum val-5;
   enum val-12;
  }
  mandatory false;
 }
 leaf ENCAPMODE {
  type boolean;
  mandatory false;
 }
 leaf ESPAUTHALG {
  type enumeration {
   enum val-0;
   enum val-1;
   enum val-2;
   enum val-5;
   enum val-12;
   enum val-20;
  }
  mandatory false;
 }
 leaf ESPENCALG {
  type enumeration {
   enum val-0;
   enum val-1;
   enum val-2;
   enum val-6;
   enum val-7;
   enum val-8;
   enum val-9;
   enum val-10;
   enum val-11;
   enum val-12;
   enum val-127;
  }
  mandatory false;
 }
 leaf ESPESNSW {
  type boolean;
  mandatory false;
 }
 leaf OLD_PROPNAME {
  type string {
   length "1..15";
  }
  mandatory false;
 }
 leaf PROPNAME {
  type string {
   length "1..15";
  }
  mandatory false;
 }
 leaf TRANMODE {
  type enumeration {
   enum val-0;
   enum val-1;
   enum val-2;
  }
  mandatory false;
 }
 }
 grouping IPULFLOWCTRLPARA-attributes {
 leaf BWPRTSWITCH {
  type boolean;
  mandatory false;
 }
 leaf OLD_IPULFLOWCTRALGID {
  type union {
   type int16 {
    range "-1..143";
   }
  }
  mandatory false;
 }
 leaf IPULFLOWCTRALGID {
  type union {
   type int16 {
    range "-1..143";
   }
  }
  mandatory false;
 }
 leaf PORTID {
  type uint32 {
   range "0..99999";
  }
  mandatory false;
 }
 leaf PT {
  type enumeration {
   enum val-6;
   enum val-10;
   enum val-12;
   enum val-13;
   enum val-14;
   enum val-15;
  }
  mandatory false;
 }
 leaf TNLCONGCTRLENHSW {
  type boolean;
  mandatory false;
 }
 leaf TNLCONGCTRLSWITCH {
  type boolean;
  mandatory false;
 }
 leaf ULIUBMINBW {
  type uint32 {
   range "0..1000000";
  }
  mandatory false;
 }
 }
 grouping LOCALETHPORT-attributes {
 leaf ALMSW {
  type boolean;
  mandatory false;
 }
 leaf GRATUITOUSARPSW {
  type boolean;
  mandatory false;
 }
 leaf IP6SW {
  type boolean;
  mandatory false;
 }
 leaf SWITCH {
  type boolean;
  mandatory false;
 }
 }
 grouping LOCATION-attributes {
 leaf ADDRESS {
  type string {
   length "0..128";
  }
  mandatory false;
 }
 leaf ALTITUDE {
  type int16 {
   range "-32767..32767";
  }
  mandatory false;
 }
 leaf CITY {
  type string {
   length "0..64";
  }
  mandatory false;
 }
 leaf CONTACT {
  type string {
   length "0..64";
  }
  mandatory false;
 }
 leaf GCDF {
  type boolean;
  mandatory false;
 }
 leaf HEIGHT {
  type uint16 {
   range "0..32767";
  }
  mandatory false;
 }
 leaf LATITUDEDEGFORMAT {
  type int32 {
   range "-90000000..90000000";
  }
  mandatory false;
 }
 leaf LATITUDESECFORMAT {
  type string {
   length "0..64";
  }
  mandatory false;
 }
 leaf LOCATIONID {
  type uint16 {
   range "0..65535";
  }
  mandatory false;
 }
 leaf OLD_LOCATIONNAME {
  type string {
   length "1..128";
  }
  mandatory false;
 }
 leaf LOCATIONNAME {
  type string {
   length "1..128";
  }
  mandatory false;
 }
 leaf LOCATIONTYPE {
  type enumeration {
   enum val-0;
   enum val-1;
   enum val-2;
  }
  mandatory false;
 }
 leaf LONGITUDEDEGFORMAT {
  type int32 {
   range "-180000000..180000000";
  }
  mandatory false;
 }
 leaf LONGITUDESECFORMAT {
  type string {
   length "0..64";
  }
  mandatory false;
 }
 leaf MODE {
  type boolean;
  mandatory false;
 }
 leaf OFFICE {
  type string {
   length "0..64";
  }
  mandatory false;
 }
 leaf POSITIONINGMETHOD {
  type boolean;
  mandatory false;
 }
 leaf PRECISE {
  type uint16 {
   range "0..1000";
  }
  mandatory false;
 }
 leaf PS {
  type enumeration {
   enum val-0;
   enum val-1;
   enum val-4;
   enum val-5;
   enum val-6;
   enum val-8;
   enum val-9;
   enum val-10;
   enum val-255;
  }
  mandatory false;
 }
 leaf RANGE {
  type uint32 {
   range "1..100000";
  }
  mandatory false;
 }
 leaf REGION {
  type string {
   length "0..64";
  }
  mandatory false;
 }
 leaf TELEPHONE {
  type string {
   length "0..64";
  }
  mandatory false;
 }
 leaf USERLABEL {
  type string {
   length "0..256";
  }
  mandatory false;
 }
 }
 grouping LOOPBACK-attributes {
 leaf CN {
  type uint8 {
   range "0..7";
  }
  mandatory false;
 }
 leaf OLD_PORTID {
  type union {
   type int32 {
    range "-1..99999";
   }
  }
  mandatory false;
 }
 leaf PORTID {
  type union {
   type int32 {
    range "-1..99999";
   }
  }
  mandatory false;
 }
 leaf SN {
  type uint8 {
   range "0..7";
  }
  mandatory false;
 }
 leaf SRN {
  type uint8 {
   range "0..1";
  }
  mandatory false;
 }
 leaf USERLABEL {
  type string {
   length "0..255";
  }
  mandatory false;
 }
 }
 grouping LOOSESCTPPEERREF-attributes {
 leaf EPGROUPID {
  type union {
   type int32 {
    range "-1..65535";
   }
  }
  mandatory false;
 }
 leaf SCTPPEERID {
  type union {
   type int32 {
    range "-1..79999";
   }
  }
  mandatory false;
 }
 }
 grouping LOOSEUPPEERREF-attributes {
 leaf EPGROUPID {
  type union {
   type int32 {
    range "-1..65535";
   }
  }
  mandatory false;
 }
 leaf UPPEERID {
  type union {
   type int32 {
    range "-1..79999";
   }
  }
  mandatory false;
 }
 }
 grouping LR-attributes {
 leaf CBS {
  type uint32 {
   range "32..100000000";
  }
  mandatory false;
 }
 leaf CIR {
  type uint32 {
   range "32..100000000";
  }
  mandatory false;
 }
 leaf OLD_CN {
  type union {
   type int8 {
    range "-1..7";
   }
  }
  mandatory false;
 }
 leaf CN {
  type union {
   type int8 {
    range "-1..7";
   }
  }
  mandatory false;
 }
 leaf DLCIR {
  type uint32 {
   range "32..100000000";
  }
  mandatory false;
 }
 leaf EBS {
  type uint32 {
   range "0..100000000";
  }
  mandatory false;
 }
 leaf LRSW {
  type boolean;
  mandatory false;
 }
 leaf OLD_PN {
  type union {
   type int8 {
    range "-1..14";
   }
  }
  mandatory false;
 }
 leaf PN {
  type union {
   type int8 {
    range "-1..14";
   }
  }
  mandatory false;
 }
 leaf OLD_PT {
  type enumeration {
   enum val--1;
   enum val-2;
   enum val-3;
   enum val-4;
   enum val-8;
  }
  mandatory false;
 }
 leaf PT {
  type enumeration {
   enum val--1;
   enum val-2;
   enum val-3;
   enum val-4;
   enum val-8;
  }
  mandatory false;
 }
 leaf OLD_SBT {
  type enumeration {
   enum val--1;
   enum val-0;
   enum val-3;
   enum val-4;
   enum val-5;
  }
  mandatory false;
 }
 leaf SBT {
  type enumeration {
   enum val--1;
   enum val-0;
   enum val-3;
   enum val-4;
   enum val-5;
  }
  mandatory false;
 }
 leaf OLD_SN {
  type union {
   type int8 {
    range "-1..7";
   }
  }
  mandatory false;
 }
 leaf SN {
  type union {
   type int8 {
    range "-1..7";
   }
  }
  mandatory false;
 }
 leaf OLD_SRN {
  type union {
   type int8 {
    range "-1..1";
   }
  }
  mandatory false;
 }
 leaf SRN {
  type union {
   type int8 {
    range "-1..1";
   }
  }
  mandatory false;
 }
 }
 grouping MPGRP-attributes {
 leaf AUTH {
  type enumeration {
   enum val-0;
   enum val-1;
   enum val-2;
  }
  mandatory false;
 }
 leaf OLD_CN {
  type union {
   type int8 {
    range "-1..7";
   }
  }
  mandatory false;
 }
 leaf CN {
  type union {
   type int8 {
    range "-1..7";
   }
  }
  mandatory false;
 }
 leaf FRAGSIZE {
  type uint16 {
   range "128..1500";
  }
  mandatory false;
 }
 leaf IPHC {
  type boolean;
  mandatory false;
 }
 leaf IPHCSUBOPT {
  type boolean;
  mandatory false;
 }
 leaf IPMASK {
  type inet:ipv4-address;
  mandatory false;
 }
 leaf LOCALIP {
  type inet:ipv4-address;
  mandatory false;
 }
 leaf MAXMFLEN {
  type uint16 {
   range "3..1500";
  }
  mandatory false;
 }
 leaf MAXSFLEN {
  type uint16 {
   range "1..512";
  }
  mandatory false;
 }
 leaf MCCLASS {
  type union {
   type uint8 {
    range "4..8";
   }
  }
  mandatory false;
 }
 leaf MCPPP {
  type boolean;
  mandatory false;
 }
 leaf MHO {
  type boolean;
  mandatory false;
 }
 leaf MPDAAT {
  type uint16 {
   range "0..1000";
  }
  mandatory false;
 }
 leaf MPDADT {
  type uint16 {
   range "0..1000";
  }
  mandatory false;
 }
 leaf OLD_MPGRPN {
  type union {
   type int8 {
    range "-1..3";
   }
  }
  mandatory false;
 }
 leaf MPGRPN {
  type union {
   type int8 {
    range "-1..3";
   }
  }
  mandatory false;
 }
 leaf MUXCP {
  type boolean;
  mandatory false;
 }
 leaf MUXTIME {
  type uint16 {
   range "1..1000";
  }
  mandatory false;
 }
 leaf PEERIP {
  type inet:ipv4-address;
  mandatory false;
 }
 leaf PORTID {
  type union {
   type uint32 {
    range "0..4294967295";
   }
  }
  mandatory false;
 }
 leaf PWD {
  type string {
   length "1..19";
  }
  mandatory false;
 }
 leaf OLD_SBT {
  type enumeration {
   enum val--1;
   enum val-0;
   enum val-3;
  }
  mandatory false;
 }
 leaf SBT {
  type enumeration {
   enum val--1;
   enum val-0;
   enum val-3;
  }
  mandatory false;
 }
 leaf OLD_SN {
  type union {
   type int8 {
    range "-1..7";
   }
  }
  mandatory false;
 }
 leaf SN {
  type union {
   type int8 {
    range "-1..7";
   }
  }
  mandatory false;
 }
 leaf OLD_SRN {
  type union {
   type int8 {
    range "-1..1";
   }
  }
  mandatory false;
 }
 leaf SRN {
  type union {
   type int8 {
    range "-1..1";
   }
  }
  mandatory false;
 }
 leaf UN {
  type string {
   length "1..67";
  }
  mandatory false;
 }
 }
 grouping MPLNK-attributes {
 leaf ACFC {
  type boolean;
  mandatory false;
 }
 leaf OLD_CN {
  type union {
   type int8 {
    range "-1..7";
   }
  }
  mandatory false;
 }
 leaf CN {
  type union {
   type int8 {
    range "-1..7";
   }
  }
  mandatory false;
 }
 leaf E1T1PN {
  type uint8 {
   range "0..7";
  }
  mandatory false;
 }
 leaf E1T1SBT {
  type enumeration {
   enum val-0;
   enum val-3;
   enum val-4;
  }
  mandatory false;
 }
 leaf E1T1SN {
  type uint8 {
   range "0..7";
  }
  mandatory false;
 }
 leaf E1T1SRN {
  type uint8 {
   range "0..1";
  }
  mandatory false;
 }
 leaf MPGRPN {
  type uint8 {
   range "0..3";
  }
  mandatory false;
 }
 leaf MPGRPSBT {
  type enumeration {
   enum val-0;
   enum val-3;
  }
  mandatory false;
 }
 leaf MRU {
  type uint16 {
   range "128..1500";
  }
  mandatory false;
 }
 leaf PFC {
  type boolean;
  mandatory false;
 }
 leaf OLD_PPPLNKN {
  type union {
   type int8 {
    range "-1..15";
   }
  }
  mandatory false;
 }
 leaf PPPLNKN {
  type union {
   type int8 {
    range "-1..15";
   }
  }
  mandatory false;
 }
 leaf RESTARTTMR {
  type uint16 {
   range "1..65535";
  }
  mandatory false;
 }
 leaf OLD_SBT {
  type enumeration {
   enum val--1;
   enum val-0;
   enum val-3;
   enum val-4;
  }
  mandatory false;
 }
 leaf SBT {
  type enumeration {
   enum val--1;
   enum val-0;
   enum val-3;
   enum val-4;
  }
  mandatory false;
 }
 leaf OLD_SN {
  type union {
   type int8 {
    range "-1..7";
   }
  }
  mandatory false;
 }
 leaf SN {
  type union {
   type int8 {
    range "-1..7";
   }
  }
  mandatory false;
 }
 leaf OLD_SRN {
  type union {
   type int8 {
    range "-1..1";
   }
  }
  mandatory false;
 }
 leaf SRN {
  type union {
   type int8 {
    range "-1..1";
   }
  }
  mandatory false;
 }
 leaf TSN {
  type string;
  mandatory false;
 }
 }
 grouping ND-attributes {
 leaf NDREACHABLETIME {
  type uint32 {
   range "5000..3600000";
  }
  mandatory false;
 }
 }
 grouping NGALD-attributes {
 leaf ALDTYPE {
  type enumeration {
   enum val-1;
   enum val-2;
   enum val-17;
   enum val-32;
   enum val-49;
   enum val-64;
   enum val-65;
   enum val-254;
  }
  mandatory false;
 }
 leaf BASESTATIONID {
  type string {
   length "0..32";
  }
  mandatory false;
 }
 leaf CTRLCN {
  type uint8 {
   range "0..62";
  }
  mandatory false;
 }
 leaf CTRLSN {
  type uint8 {
   range "0..8";
  }
  mandatory false;
 }
 leaf CTRLSRN {
  type union {
   type uint8 {
    range "4..254";
   }
  }
  mandatory false;
 }
 leaf DEVICENAME {
  type string {
   length "0..83";
  }
  mandatory false;
 }
 leaf DEVICENO {
  type union {
   type int16 {
    range "-1..1023";
   }
  }
  mandatory false;
 }
 leaf INSTALLERID {
  type string {
   length "0..32";
  }
  mandatory false;
 }
 leaf MALDSETUPPERM {
  type enumeration {
   enum val-0;
   enum val-1;
   enum val-2;
  }
  mandatory false;
 }
 leaf MALDSWDLDPERM {
  type enumeration {
   enum val-0;
   enum val-1;
   enum val-2;
   enum val-3;
  }
  mandatory false;
 }
 leaf POLARTYPE {
  type enumeration {
   enum val-1;
   enum val-2;
  }
  mandatory false;
 }
 leaf SCENARIO {
  type enumeration {
   enum val-1;
   enum val-2;
   enum val-3;
  }
  mandatory false;
 }
 leaf SERIALNO {
  type string {
   length "0..36";
  }
  mandatory false;
 }
 leaf SUBUNITNUM {
  type uint8 {
   range "0..12";
  }
  mandatory false;
 }
 leaf TARGETCONTROLPORT {
  type union {
   type uint32 {
    range "1..4294967295";
   }
  }
  mandatory false;
 }
 leaf TMATYPE {
  type boolean;
  mandatory false;
 }
 leaf VENDORCODE {
  type string {
   length "0..2";
  }
  mandatory false;
 }
 }
 grouping NODE-attributes {
 leaf TEMPLATENAME {
  type string;
  mandatory false;
 }
 leaf HWPATTERN {
  type string;
  mandatory false;
 }
 leaf CONNTYPE {
  type string;
  mandatory false;
 }
 leaf CONNINFO {
  type string;
  mandatory false;
 }
 leaf APPHOTPATCHVERSION {
  type string {
   length "0..64";
  }
  mandatory false;
 }
 leaf APPVERSION {
  type string {
   length "0..64";
  }
  mandatory false;
 }
 leaf ESNSUFFIX {
  type boolean;
  mandatory false;
 }
 leaf HOTPATCHVERSION {
  type string {
   length "0..64";
  }
  mandatory false;
 }
 leaf INTERFACEID {
  type string {
   length "0..128";
  }
  mandatory false;
 }
 leaf LMTVERSION {
  type string {
   length "0..128";
  }
  mandatory false;
 }
 leaf LTEMODE {
  type boolean;
  mandatory false;
 }
 leaf NODEID {
  type uint8 {
   range "0..64";
  }
  mandatory false;
 }
 leaf NODENAME {
  type string {
   length "1..128";
  }
  mandatory false;
 }
 leaf PRODUCTTYPE {
  type enumeration {
   enum val-125;
   enum val-126;
   enum val-127;
   enum val-128;
   enum val-129;
   enum val-135;
   enum val-214;
   enum val-256;
   enum val-257;
  }
  mandatory false;
 }
 leaf PRODUCTVERSION {
  type string {
   length "0..128";
  }
  mandatory false;
 }
 leaf SWVERSION {
  type string {
   length "0..64";
  }
  mandatory false;
 }
 leaf USERLABEL {
  type string {
   length "0..256";
  }
  mandatory false;
 }
 leaf WM {
  type boolean;
  mandatory false;
 }
 leaf WMEXTENSION {
  type boolean;
  mandatory false;
 }
 }
 grouping NTPCP-attributes {
 leaf AUTHMODE {
  type enumeration {
   enum val-0;
   enum val-1;
   enum val-2;
   enum val-3;
   enum val-4;
   enum val-5;
   enum val-6;
   enum val-7;
  }
  mandatory false;
 }
 leaf OLD_IP {
  type inet:ipv4-address;
  mandatory false;
 }
 leaf IP {
  type inet:ipv4-address;
  mandatory false;
 }
 leaf OLD_IPV6 {
  type inet:ipv6-address;
  mandatory false;
 }
 leaf IPV6 {
  type inet:ipv6-address;
  mandatory false;
 }
 leaf KEY {
  type string {
   length "1..31";
  }
  mandatory false;
 }
 leaf KEYID {
  type uint32 {
   range "1..4294967295";
  }
  mandatory false;
 }
 leaf MASTERFLAG {
  type boolean;
  mandatory false;
 }
 leaf OLD_MODE {
  type enumeration {
   enum val--1;
   enum val-0;
   enum val-1;
  }
  mandatory false;
 }
 leaf MODE {
  type enumeration {
   enum val--1;
   enum val-0;
   enum val-1;
  }
  mandatory false;
 }
 leaf PORT {
  type union {
   type uint16 {
    range "123..65534";
   }
  }
  mandatory false;
 }
 leaf SYNCCYCLE {
  type uint32 {
   range "1..525600";
  }
  mandatory false;
 }
 }
 grouping OMCH-attributes {
 leaf BEAR {
  type enumeration {
   enum val-0;
   enum val-1;
   enum val-2;
  }
  mandatory false;
 }
 leaf BINDSECONDARYRT {
  type boolean;
  mandatory false;
 }
 leaf BRT {
  type boolean;
  mandatory false;
 }
 leaf CHECKTYPE {
  type enumeration {
   enum val-0;
   enum val-1;
   enum val-2;
   enum val-3;
  }
  mandatory false;
 }
 leaf CN {
  type uint8 {
   range "0..7";
  }
  mandatory false;
 }
 leaf OLD_FLAG {
  type enumeration {
   enum val--1;
   enum val-0;
   enum val-1;
  }
  mandatory false;
 }
 leaf FLAG {
  type enumeration {
   enum val--1;
   enum val-0;
   enum val-1;
  }
  mandatory false;
 }
 leaf IP {
  type inet:ipv4-address;
  mandatory false;
 }
 leaf IP6 {
  type inet:ipv6-address;
  mandatory false;
 }
 leaf JNRSCGRP {
  type boolean;
  mandatory false;
 }
 leaf MASK {
  type inet:ipv4-address;
  mandatory false;
 }
 leaf MCR {
  type uint16 {
   range "30..37262";
  }
  mandatory false;
 }
 leaf OMIP {
  type inet:ipv4-address;
  mandatory false;
 }
 leaf OMIPMASK {
  type inet:ipv4-address;
  mandatory false;
 }
 leaf OMIPSWITCH {
  type boolean;
  mandatory false;
 }
 leaf PCR {
  type uint16 {
   range "30..37265";
  }
  mandatory false;
 }
 leaf PEERIP {
  type inet:ipv4-address;
  mandatory false;
 }
 leaf PEERIP6 {
  type inet:ipv6-address;
  mandatory false;
 }
 leaf PEERIP6PFXLEN {
  type uint8 {
   range "1..128";
  }
  mandatory false;
 }
 leaf PEERMASK {
  type inet:ipv4-address;
  mandatory false;
 }
 leaf PN {
  type uint8 {
   range "0..7";
  }
  mandatory false;
 }
 leaf PT {
  type enumeration {
   enum val-0;
   enum val-1;
   enum val-5;
  }
  mandatory false;
 }
 leaf RSCGRPID {
  type uint8 {
   range "0..15";
  }
  mandatory false;
 }
 leaf RTIDX {
  type uint8 {
   range "0..149";
  }
  mandatory false;
 }
 leaf RU {
  type boolean;
  mandatory false;
 }
 leaf SBT {
  type enumeration {
   enum val-0;
   enum val-3;
   enum val-4;
  }
  mandatory false;
 }
 leaf SCR {
  type uint16 {
   range "30..37262";
  }
  mandatory false;
 }
 leaf SECONDARYRTIDX {
  type uint8 {
   range "0..149";
  }
  mandatory false;
 }
 leaf SN {
  type uint8 {
   range "0..7";
  }
  mandatory false;
 }
 leaf SRN {
  type uint8 {
   range "0..1";
  }
  mandatory false;
 }
 leaf ST {
  type enumeration {
   enum val-0;
   enum val-1;
   enum val-2;
   enum val-3;
   enum val-4;
  }
  mandatory false;
 }
 leaf UDPSESSIONGRPID {
  type uint8 {
   range "0..1";
  }
  mandatory false;
 }
 leaf UDPSN {
  type uint16 {
   range "0..65535";
  }
  mandatory false;
 }
 leaf USERLABEL {
  type string {
   length "0..255";
  }
  mandatory false;
 }
 leaf VCI {
  type uint16 {
   range "32..511";
  }
  mandatory false;
 }
 leaf VPI {
  type uint8 {
   range "0..255";
  }
  mandatory false;
 }
 leaf VRFIDX {
  type uint8 {
   range "0..31";
  }
  mandatory false;
 }
 }
 grouping PACKETFILTER-attributes {
 leaf ACLAUTOSWITCH {
  type boolean;
  mandatory false;
 }
 leaf ACLID {
  type uint16 {
   range "3000..3999";
  }
  mandatory false;
 }
 leaf ACLID2 {
  type uint16 {
   range "4000..4999";
  }
  mandatory false;
 }
 leaf OLD_CN {
  type union {
   type int8 {
    range "-1..7";
   }
  }
  mandatory false;
 }
 leaf CN {
  type union {
   type int8 {
    range "-1..7";
   }
  }
  mandatory false;
 }
 leaf FM {
  type enumeration {
   enum val-0;
   enum val-1;
   enum val-2;
  }
  mandatory false;
 }
 leaf MB {
  type boolean;
  mandatory false;
 }
 leaf OMPEERIPLIMITSW {
  type boolean;
  mandatory false;
 }
 leaf OLD_PN {
  type union {
   type int8 {
    range "-1..63";
   }
  }
  mandatory false;
 }
 leaf PN {
  type union {
   type int8 {
    range "-1..63";
   }
  }
  mandatory false;
 }
 leaf OLD_PT {
  type enumeration {
   enum val--1;
   enum val-3;
   enum val-4;
   enum val-8;
   enum val-9;
   enum val-16;
  }
  mandatory false;
 }
 leaf PT {
  type enumeration {
   enum val--1;
   enum val-3;
   enum val-4;
   enum val-8;
   enum val-9;
   enum val-16;
  }
  mandatory false;
 }
 leaf OLD_SBT {
  type enumeration {
   enum val--1;
   enum val-0;
   enum val-4;
   enum val-5;
  }
  mandatory false;
 }
 leaf SBT {
  type enumeration {
   enum val--1;
   enum val-0;
   enum val-4;
   enum val-5;
  }
  mandatory false;
 }
 leaf OLD_SN {
  type union {
   type int8 {
    range "-1..7";
   }
  }
  mandatory false;
 }
 leaf SN {
  type union {
   type int8 {
    range "-1..7";
   }
  }
  mandatory false;
 }
 leaf OLD_SRN {
  type union {
   type int8 {
    range "-1..1";
   }
  }
  mandatory false;
 }
 leaf SRN {
  type union {
   type int8 {
    range "-1..1";
   }
  }
  mandatory false;
 }
 }
 grouping PACKETFILTERING-attributes {
 leaf ACLAUTOSWITCH {
  type boolean;
  mandatory false;
 }
 leaf ACLID {
  type uint16 {
   range "3000..4999";
  }
  mandatory false;
 }
 leaf ACLTYPE {
  type enumeration {
   enum val-0;
   enum val-1;
   enum val-2;
  }
  mandatory false;
 }
 leaf FM {
  type boolean;
  mandatory false;
 }
 leaf MB {
  type boolean;
  mandatory false;
 }
 leaf OMPEERIPLIMITSW {
  type boolean;
  mandatory false;
 }
 leaf OLD_PACKETFILTERINGID {
  type union {
   type int8 {
    range "-1..59";
   }
  }
  mandatory false;
 }
 leaf PACKETFILTERINGID {
  type union {
   type int8 {
    range "-1..59";
   }
  }
  mandatory false;
 }
 leaf PORTID {
  type uint16 {
   range "0..9999";
  }
  mandatory false;
 }
 leaf PT {
  type enumeration {
   enum val-3;
   enum val-4;
   enum val-8;
   enum val-16;
   enum val-18;
  }
  mandatory false;
 }
 }
 grouping PLRTHRESHOLD-attributes {
 leaf PLRAT {
  type uint8 {
   range "0..100";
  }
  mandatory false;
 }
 leaf PLRDT {
  type uint8 {
   range "0..100";
  }
  mandatory false;
 }
 }
 grouping PMTUCFG-attributes {
 leaf AGINGTIME {
  type uint8 {
   range "5..60";
  }
  mandatory false;
 }
 leaf DSCP {
  type uint8 {
   range "0..63";
  }
  mandatory false;
 }
 leaf MODE {
  type boolean;
  mandatory false;
 }
 leaf PORTNO {
  type uint16 {
   range "49152..65535";
  }
  mandatory false;
 }
 leaf PROTOCOLTYPE {
  type boolean;
  mandatory false;
 }
 leaf TIMEOUTDUR {
  type uint16 {
   range "500..5000";
  }
  mandatory false;
 }
 }
 grouping PORTLR-attributes {
 leaf CBS {
  type uint32 {
   range "32..100000000";
  }
  mandatory false;
 }
 leaf CIR {
  type uint32 {
   range "32..100000000";
  }
  mandatory false;
 }
 leaf DLCIR {
  type uint32 {
   range "32..100000000";
  }
  mandatory false;
 }
 leaf EBS {
  type uint32 {
   range "0..100000000";
  }
  mandatory false;
 }
 leaf PORTID {
  type uint16 {
   range "0..9999";
  }
  mandatory false;
 }
 leaf OLD_PORTLRID {
  type union {
   type int8 {
    range "-1..79";
   }
  }
  mandatory false;
 }
 leaf PORTLRID {
  type union {
   type int8 {
    range "-1..79";
   }
  }
  mandatory false;
 }
 leaf PT {
  type enumeration {
   enum val-2;
   enum val-3;
   enum val-4;
   enum val-8;
  }
  mandatory false;
 }
 }
 grouping PORTSECURITY-attributes {
 leaf OLD_CN {
  type union {
   type int8 {
    range "-1..7";
   }
  }
  mandatory false;
 }
 leaf CN {
  type union {
   type int8 {
    range "-1..7";
   }
  }
  mandatory false;
 }
 leaf OLD_PN {
  type union {
   type int8 {
    range "-1..7";
   }
  }
  mandatory false;
 }
 leaf PN {
  type union {
   type int8 {
    range "-1..7";
   }
  }
  mandatory false;
 }
 leaf OLD_PT {
  type enumeration {
   enum val--1;
   enum val-0;
   enum val-1;
   enum val-16;
  }
  mandatory false;
 }
 leaf PT {
  type enumeration {
   enum val--1;
   enum val-0;
   enum val-1;
   enum val-16;
  }
  mandatory false;
 }
 leaf OLD_SBT {
  type enumeration {
   enum val--1;
   enum val-0;
   enum val-3;
   enum val-5;
  }
  mandatory false;
 }
 leaf SBT {
  type enumeration {
   enum val--1;
   enum val-0;
   enum val-3;
   enum val-5;
  }
  mandatory false;
 }
 leaf OLD_SN {
  type union {
   type int8 {
    range "-1..7";
   }
  }
  mandatory false;
 }
 leaf SN {
  type union {
   type int8 {
    range "-1..7";
   }
  }
  mandatory false;
 }
 leaf OLD_SRN {
  type union {
   type int8 {
    range "-1..1";
   }
  }
  mandatory false;
 }
 leaf SRN {
  type union {
   type int8 {
    range "-1..1";
   }
  }
  mandatory false;
 }
 leaf SWITCH {
  type boolean;
  mandatory false;
 }
 }
 grouping PPPLNK-attributes {
 leaf ACFC {
  type boolean;
  mandatory false;
 }
 leaf AUTH {
  type enumeration {
   enum val-0;
   enum val-1;
   enum val-2;
  }
  mandatory false;
 }
 leaf OLD_CN {
  type union {
   type int8 {
    range "-1..7";
   }
  }
  mandatory false;
 }
 leaf CN {
  type union {
   type int8 {
    range "-1..7";
   }
  }
  mandatory false;
 }
 leaf FFAPHOLD {
  type uint16 {
   range "1..1000";
  }
  mandatory false;
 }
 leaf FFDPHOLD {
  type uint16 {
   range "1..1000";
  }
  mandatory false;
 }
 leaf IPHC {
  type boolean;
  mandatory false;
 }
 leaf IPHCSUBOPT {
  type boolean;
  mandatory false;
 }
 leaf IPMASK {
  type inet:ipv4-address;
  mandatory false;
 }
 leaf LOCALIP {
  type inet:ipv4-address;
  mandatory false;
 }
 leaf MAXMFLEN {
  type uint16 {
   range "3..1500";
  }
  mandatory false;
 }
 leaf MAXSFLEN {
  type uint16 {
   range "1..512";
  }
  mandatory false;
 }
 leaf MRU {
  type uint16 {
   range "128..1500";
  }
  mandatory false;
 }
 leaf MUXCP {
  type boolean;
  mandatory false;
 }
 leaf MUXTIME {
  type uint16 {
   range "1..1000";
  }
  mandatory false;
 }
 leaf PEERIP {
  type inet:ipv4-address;
  mandatory false;
 }
 leaf PFC {
  type boolean;
  mandatory false;
 }
 leaf PN {
  type uint8 {
   range "0..7";
  }
  mandatory false;
 }
 leaf PORTID {
  type union {
   type uint32 {
    range "0..4294967295";
   }
  }
  mandatory false;
 }
 leaf OLD_PPPLNKN {
  type union {
   type int8 {
    range "-1..15";
   }
  }
  mandatory false;
 }
 leaf PPPLNKN {
  type union {
   type int8 {
    range "-1..15";
   }
  }
  mandatory false;
 }
 leaf PWD {
  type string {
   length "1..19";
  }
  mandatory false;
 }
 leaf RESTARTTMR {
  type uint16 {
   range "1..65535";
  }
  mandatory false;
 }
 leaf OLD_SBT {
  type enumeration {
   enum val--1;
   enum val-0;
   enum val-3;
   enum val-4;
  }
  mandatory false;
 }
 leaf SBT {
  type enumeration {
   enum val--1;
   enum val-0;
   enum val-3;
   enum val-4;
  }
  mandatory false;
 }
 leaf OLD_SN {
  type union {
   type int8 {
    range "-1..7";
   }
  }
  mandatory false;
 }
 leaf SN {
  type union {
   type int8 {
    range "-1..7";
   }
  }
  mandatory false;
 }
 leaf OLD_SRN {
  type union {
   type int8 {
    range "-1..1";
   }
  }
  mandatory false;
 }
 leaf SRN {
  type union {
   type int8 {
    range "-1..1";
   }
  }
  mandatory false;
 }
 leaf TSN {
  type string;
  mandatory false;
 }
 leaf UN {
  type string {
   length "1..67";
  }
  mandatory false;
 }
 }
 grouping RAE-attributes {
 leaf CTRLCN {
  type uint8 {
   range "0..62";
  }
  mandatory false;
 }
 leaf CTRLSN {
  type uint8 {
   range "0..8";
  }
  mandatory false;
 }
 leaf CTRLSRN {
  type union {
   type uint8 {
    range "4..254";
   }
  }
  mandatory false;
 }
 leaf DEVICENAME {
  type string {
   length "0..83";
  }
  mandatory false;
 }
 leaf DEVICENO {
  type union {
   type int16 {
    range "-1..1023";
   }
  }
  mandatory false;
 }
 leaf SCENARIO {
  type enumeration {
   enum val-1;
   enum val-2;
  }
  mandatory false;
 }
 leaf SERIALNO {
  type string {
   length "0..36";
  }
  mandatory false;
 }
 leaf SUBUNITNUM {
  type uint8 {
   range "1..6";
  }
  mandatory false;
 }
 leaf VENDORCODE {
  type string {
   length "0..2";
  }
  mandatory false;
 }
 }
 grouping RAS-attributes {
 leaf CTRLCN {
  type uint8 {
   range "0..62";
  }
  mandatory false;
 }
 leaf CTRLSN {
  type uint8 {
   range "0..8";
  }
  mandatory false;
 }
 leaf CTRLSRN {
  type union {
   type uint8 {
    range "4..254";
   }
  }
  mandatory false;
 }
 leaf DEVICENAME {
  type string {
   length "0..83";
  }
  mandatory false;
 }
 leaf DEVICENO {
  type union {
   type int16 {
    range "-1..1023";
   }
  }
  mandatory false;
 }
 leaf SCENARIO {
  type enumeration {
   enum val-1;
   enum val-2;
  }
  mandatory false;
 }
 leaf SERIALNO {
  type string {
   length "0..36";
  }
  mandatory false;
 }
 leaf SUBUNITNUM {
  type uint8 {
   range "1..8";
  }
  mandatory false;
 }
 leaf VENDORCODE {
  type string {
   length "0..2";
  }
  mandatory false;
 }
 }
 grouping RCSSERVER-attributes {
 leaf RCSSERVERNAME {
  type string {
   length "1..128";
  }
  mandatory false;
 }
 leaf OLD_RCSSERVERNO {
  type union {
   type int16 {
    range "-1..255";
   }
  }
  mandatory false;
 }
 leaf RCSSERVERNO {
  type union {
   type int16 {
    range "-1..255";
   }
  }
  mandatory false;
 }
 }
 grouping RET-attributes {
 leaf ANTENNAFORM {
  type boolean;
  mandatory false;
 }
 leaf CTRLCN {
  type uint8 {
   range "0..62";
  }
  mandatory false;
 }
 leaf CTRLSN {
  type uint8 {
   range "0..8";
  }
  mandatory false;
 }
 leaf CTRLSRN {
  type union {
   type uint8 {
    range "4..254";
   }
  }
  mandatory false;
 }
 leaf DEVICENAME {
  type string {
   length "0..83";
  }
  mandatory false;
 }
 leaf DEVICENO {
  type union {
   type int16 {
    range "-1..1023";
   }
  }
  mandatory false;
 }
 leaf POLARTYPE {
  type enumeration {
   enum val-1;
   enum val-2;
  }
  mandatory false;
 }
 leaf RETTYPE {
  type enumeration {
   enum val-1;
   enum val-17;
  }
  mandatory false;
 }
 leaf SCENARIO {
  type enumeration {
   enum val-1;
   enum val-2;
   enum val-3;
   enum val-4;
  }
  mandatory false;
 }
 leaf SERIALNO {
  type string {
   length "0..36";
  }
  mandatory false;
 }
 leaf SUBUNITNUM {
  type uint8 {
   range "1..12";
  }
  mandatory false;
 }
 leaf VENDORCODE {
  type string {
   length "0..2";
  }
  mandatory false;
 }
 }
 grouping RETDEVICEDATA-attributes {
 leaf BAND1 {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-48;
   enum val-49;
   enum val-50;
   enum val-51;
   enum val-52;
   enum val-65;
   enum val-66;
   enum val-67;
   enum val-68;
   enum val-69;
   enum val-70;
   enum val-71;
   enum val-72;
   enum val-73;
   enum val-74;
   enum val-75;
   enum val-76;
   enum val-85;
  }
  mandatory false;
 }
 leaf BAND2 {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-48;
   enum val-49;
   enum val-50;
   enum val-51;
   enum val-52;
   enum val-65;
   enum val-66;
   enum val-67;
   enum val-68;
   enum val-69;
   enum val-70;
   enum val-71;
   enum val-72;
   enum val-73;
   enum val-74;
   enum val-75;
   enum val-76;
   enum val-85;
  }
  mandatory false;
 }
 leaf BAND3 {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-48;
   enum val-49;
   enum val-50;
   enum val-51;
   enum val-52;
   enum val-65;
   enum val-66;
   enum val-67;
   enum val-68;
   enum val-69;
   enum val-70;
   enum val-71;
   enum val-72;
   enum val-73;
   enum val-74;
   enum val-75;
   enum val-76;
   enum val-85;
  }
  mandatory false;
 }
 leaf BAND4 {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-48;
   enum val-49;
   enum val-50;
   enum val-51;
   enum val-52;
   enum val-65;
   enum val-66;
   enum val-67;
   enum val-68;
   enum val-69;
   enum val-70;
   enum val-71;
   enum val-72;
   enum val-73;
   enum val-74;
   enum val-75;
   enum val-76;
   enum val-85;
  }
  mandatory false;
 }
 leaf BEAMWIDTH1 {
  type uint16 {
   range "0..359";
  }
  mandatory false;
 }
 leaf BEAMWIDTH2 {
  type uint16 {
   range "0..359";
  }
  mandatory false;
 }
 leaf BEAMWIDTH3 {
  type uint16 {
   range "0..359";
  }
  mandatory false;
 }
 leaf BEAMWIDTH4 {
  type uint16 {
   range "0..359";
  }
  mandatory false;
 }
 leaf BEARING {
  type union {
   type uint32 {
    range "0..4294967295";
   }
  }
  mandatory false;
 }
 leaf BSID {
  type string {
   length "0..32";
  }
  mandatory false;
 }
 leaf DATE {
  type string {
   length "0..6";
  }
  mandatory false;
 }
 leaf DEVICENO {
  type union {
   type int16 {
    range "-1..1023";
   }
  }
  mandatory false;
 }
 leaf GAIN1 {
  type uint8 {
   range "0..255";
  }
  mandatory false;
 }
 leaf GAIN2 {
  type uint8 {
   range "0..255";
  }
  mandatory false;
 }
 leaf GAIN3 {
  type uint8 {
   range "0..255";
  }
  mandatory false;
 }
 leaf GAIN4 {
  type uint8 {
   range "0..255";
  }
  mandatory false;
 }
 leaf INSTALLERID {
  type string {
   length "0..5";
  }
  mandatory false;
 }
 leaf MODELNO {
  type string {
   length "0..15";
  }
  mandatory false;
 }
 leaf SECTORID {
  type string {
   length "0..32";
  }
  mandatory false;
 }
 leaf SERIALNO {
  type string {
   length "0..17";
  }
  mandatory false;
 }
 leaf SUBUNITNO {
  type union {
   type int8 {
    range "-1..12";
   }
  }
  mandatory false;
 }
 leaf TILT {
  type union {
   type int32 {
    range "-900..2147483647";
   }
  }
  mandatory false;
 }
 }
 grouping RETSUBUNIT-attributes {
 leaf AER {
  type uint8 {
   range "0..10";
  }
  mandatory false;
 }
 leaf ANTENNAARRAYTYPE {
  type enumeration {
   enum val-0;
   enum val-1;
   enum val-2;
   enum val-3;
  }
  mandatory false;
 }
 leaf CONNCN1 {
  type union {
   type uint8 {
    range "0..255";
   }
  }
  mandatory false;
 }
 leaf CONNCN2 {
  type union {
   type uint8 {
    range "0..255";
   }
  }
  mandatory false;
 }
 leaf CONNPN1 {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf CONNPN2 {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf CONNSN1 {
  type union {
   type uint8 {
    range "0..255";
   }
  }
  mandatory false;
 }
 leaf CONNSN2 {
  type union {
   type uint8 {
    range "0..255";
   }
  }
  mandatory false;
 }
 leaf CONNSRN1 {
  type union {
   type uint8 {
    range "4..255";
   }
  }
  mandatory false;
 }
 leaf CONNSRN2 {
  type union {
   type uint8 {
    range "4..255";
   }
  }
  mandatory false;
 }
 leaf DEVICENO {
  type union {
   type int16 {
    range "-1..1023";
   }
  }
  mandatory false;
 }
 leaf SUBNAME {
  type string {
   length "0..83";
  }
  mandatory false;
 }
 leaf SUBUNITNO {
  type union {
   type int8 {
    range "-1..12";
   }
  }
  mandatory false;
 }
 leaf TILT {
  type union {
   type int16 {
    range "-300..32767";
   }
  }
  mandatory false;
 }
 }
 grouping RFPATH-attributes {
 leaf ALIAS {
  type string {
   length "0..31";
  }
  mandatory false;
 }
 leaf CN {
  type uint8 {
   range "0..62";
  }
  mandatory false;
 }
 leaf PN {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf OLD_RFPATHID {
  type union {
   type int32 {
    range "-1..65535";
   }
  }
  mandatory false;
 }
 leaf RFPATHID {
  type union {
   type int32 {
    range "-1..65535";
   }
  }
  mandatory false;
 }
 leaf SN {
  type uint8 {
   range "0..8";
  }
  mandatory false;
 }
 leaf SRN {
  type union {
   type uint8 {
    range "4..254";
   }
  }
  mandatory false;
 }
 }
 grouping RSCGRP-attributes {
 leaf BEAR {
  type enumeration {
   enum val--1;
   enum val-0;
   enum val-1;
  }
  mandatory false;
 }
 leaf CN {
  type union {
   type int8 {
    range "-1..7";
   }
  }
  mandatory false;
 }
 leaf OID {
  type uint8 {
   range "0..5";
  }
  mandatory false;
 }
 leaf PN {
  type union {
   type int8 {
    range "-1..15";
   }
  }
  mandatory false;
 }
 leaf PT {
  type enumeration {
   enum val--1;
   enum val-0;
   enum val-1;
   enum val-5;
   enum val-6;
   enum val-8;
   enum val-9;
   enum val-10;
   enum val-15;
  }
  mandatory false;
 }
 leaf RSCGRPID {
  type enumeration {
   enum val--1;
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-126;
   enum val-127;
  }
  mandatory false;
 }
 leaf RU {
  type boolean;
  mandatory false;
 }
 leaf RXBW {
  type uint32 {
   range "32..100000000";
  }
  mandatory false;
 }
 leaf RXCIR {
  type uint32 {
   range "64..100000000";
  }
  mandatory false;
 }
 leaf RXPIR {
  type uint32 {
   range "64..100000000";
  }
  mandatory false;
 }
 leaf SBT {
  type enumeration {
   enum val--1;
   enum val-0;
   enum val-3;
   enum val-4;
   enum val-5;
  }
  mandatory false;
 }
 leaf SN {
  type union {
   type int8 {
    range "-1..7";
   }
  }
  mandatory false;
 }
 leaf SRN {
  type union {
   type int8 {
    range "-1..1";
   }
  }
  mandatory false;
 }
 leaf TXBW {
  type uint32 {
   range "32..100000000";
  }
  mandatory false;
 }
 leaf TXCBS {
  type uint32 {
   range "64..100000000";
  }
  mandatory false;
 }
 leaf TXCIR {
  type uint32 {
   range "64..100000000";
  }
  mandatory false;
 }
 leaf TXEBS {
  type uint32 {
   range "64..100000000";
  }
  mandatory false;
 }
 leaf TXPBS {
  type uint32 {
   range "64..100000000";
  }
  mandatory false;
 }
 leaf TXPIR {
  type uint32 {
   range "64..100000000";
  }
  mandatory false;
 }
 leaf USERLABEL {
  type string {
   length "0..255";
  }
  mandatory false;
 }
 leaf WEIGHT {
  type uint8 {
   range "1..100";
  }
  mandatory false;
 }
 }
 grouping RSCGRPALG-attributes {
 leaf BEAR {
  type enumeration {
   enum val--1;
   enum val-0;
   enum val-1;
  }
  mandatory false;
 }
 leaf CCTTH {
  type uint16 {
   range "0..500";
  }
  mandatory false;
 }
 leaf CN {
  type union {
   type int8 {
    range "-1..7";
   }
  }
  mandatory false;
 }
 leaf CTTH {
  type uint16 {
   range "0..500";
  }
  mandatory false;
 }
 leaf DDTH {
  type uint16 {
   range "0..10000";
  }
  mandatory false;
 }
 leaf DROPPKTNUM {
  type uint16 {
   range "0..8192";
  }
  mandatory false;
 }
 leaf PLRDTH {
  type uint16 {
   range "0..1000";
  }
  mandatory false;
 }
 leaf PN {
  type union {
   type int8 {
    range "-1..15";
   }
  }
  mandatory false;
 }
 leaf PQN {
  type uint8 {
   range "0..6";
  }
  mandatory false;
 }
 leaf PT {
  type enumeration {
   enum val--1;
   enum val-0;
   enum val-1;
   enum val-5;
   enum val-6;
   enum val-8;
   enum val-9;
   enum val-10;
   enum val-15;
  }
  mandatory false;
 }
 leaf RSCGRPID {
  type enumeration {
   enum val--1;
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-127;
  }
  mandatory false;
 }
 leaf RXBWAMIN {
  type uint32 {
   range "64..100000000";
  }
  mandatory false;
 }
 leaf RXBWASW {
  type boolean;
  mandatory false;
 }
 leaf RXRSVBW {
  type uint32 {
   range "0..100000000";
  }
  mandatory false;
 }
 leaf SBT {
  type enumeration {
   enum val--1;
   enum val-0;
   enum val-3;
   enum val-4;
   enum val-5;
  }
  mandatory false;
 }
 leaf SN {
  type union {
   type int8 {
    range "-1..7";
   }
  }
  mandatory false;
 }
 leaf SRN {
  type union {
   type int8 {
    range "-1..1";
   }
  }
  mandatory false;
 }
 leaf TCSW {
  type boolean;
  mandatory false;
 }
 leaf TXBWAMIN {
  type uint32 {
   range "64..100000000";
  }
  mandatory false;
 }
 leaf TXBWASW {
  type boolean;
  mandatory false;
 }
 leaf TXRSVBW {
  type uint32 {
   range "0..100000000";
  }
  mandatory false;
 }
 leaf TXSSW {
  type boolean;
  mandatory false;
 }
 }
 grouping RVD-attributes {
 leaf CTRLCN {
  type uint8 {
   range "0..62";
  }
  mandatory false;
 }
 leaf CTRLSN {
  type uint8 {
   range "0..8";
  }
  mandatory false;
 }
 leaf CTRLSRN {
  type union {
   type uint8 {
    range "4..254";
   }
  }
  mandatory false;
 }
 leaf DEVICENAME {
  type string {
   length "0..83";
  }
  mandatory false;
 }
 leaf DEVICENO {
  type union {
   type int16 {
    range "-1..1023";
   }
  }
  mandatory false;
 }
 leaf SCENARIO {
  type enumeration {
   enum val-1;
   enum val-2;
  }
  mandatory false;
 }
 leaf SERIALNO {
  type string {
   length "0..36";
  }
  mandatory false;
 }
 leaf SUBUNITNUM {
  type uint8 {
   range "1..8";
  }
  mandatory false;
 }
 leaf VENDORCODE {
  type string {
   length "0..2";
  }
  mandatory false;
 }
 }
 grouping RVDDEVICEDATA-attributes {
 leaf BAND1 {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-48;
   enum val-49;
   enum val-50;
   enum val-51;
   enum val-52;
   enum val-65;
   enum val-66;
   enum val-67;
   enum val-68;
   enum val-69;
   enum val-70;
   enum val-71;
   enum val-72;
   enum val-73;
   enum val-74;
   enum val-75;
   enum val-76;
   enum val-85;
  }
  mandatory false;
 }
 leaf BAND2 {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-48;
   enum val-49;
   enum val-50;
   enum val-51;
   enum val-52;
   enum val-65;
   enum val-66;
   enum val-67;
   enum val-68;
   enum val-69;
   enum val-70;
   enum val-71;
   enum val-72;
   enum val-73;
   enum val-74;
   enum val-75;
   enum val-76;
   enum val-85;
  }
  mandatory false;
 }
 leaf BAND3 {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-48;
   enum val-49;
   enum val-50;
   enum val-51;
   enum val-52;
   enum val-65;
   enum val-66;
   enum val-67;
   enum val-68;
   enum val-69;
   enum val-70;
   enum val-71;
   enum val-72;
   enum val-73;
   enum val-74;
   enum val-75;
   enum val-76;
   enum val-85;
  }
  mandatory false;
 }
 leaf BAND4 {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-48;
   enum val-49;
   enum val-50;
   enum val-51;
   enum val-52;
   enum val-65;
   enum val-66;
   enum val-67;
   enum val-68;
   enum val-69;
   enum val-70;
   enum val-71;
   enum val-72;
   enum val-73;
   enum val-74;
   enum val-75;
   enum val-76;
   enum val-85;
  }
  mandatory false;
 }
 leaf BEAMWIDTH1 {
  type uint16 {
   range "0..359";
  }
  mandatory false;
 }
 leaf BEAMWIDTH2 {
  type uint16 {
   range "0..359";
  }
  mandatory false;
 }
 leaf BEAMWIDTH3 {
  type uint16 {
   range "0..359";
  }
  mandatory false;
 }
 leaf BEAMWIDTH4 {
  type uint16 {
   range "0..359";
  }
  mandatory false;
 }
 leaf BEARING {
  type union {
   type uint32 {
    range "0..4294967295";
   }
  }
  mandatory false;
 }
 leaf BSID {
  type string {
   length "0..32";
  }
  mandatory false;
 }
 leaf DATE {
  type string {
   length "0..6";
  }
  mandatory false;
 }
 leaf DEVICENO {
  type union {
   type int16 {
    range "-1..1023";
   }
  }
  mandatory false;
 }
 leaf GAIN1 {
  type uint8 {
   range "0..255";
  }
  mandatory false;
 }
 leaf GAIN2 {
  type uint8 {
   range "0..255";
  }
  mandatory false;
 }
 leaf GAIN3 {
  type uint8 {
   range "0..255";
  }
  mandatory false;
 }
 leaf GAIN4 {
  type uint8 {
   range "0..255";
  }
  mandatory false;
 }
 leaf INSTALLERID {
  type string {
   length "0..5";
  }
  mandatory false;
 }
 leaf MODELNO {
  type string {
   length "0..15";
  }
  mandatory false;
 }
 leaf SECTORID {
  type string {
   length "0..32";
  }
  mandatory false;
 }
 leaf SERIALNO {
  type string {
   length "0..17";
  }
  mandatory false;
 }
 leaf SUBUNITNO {
  type union {
   type int8 {
    range "-1..8";
   }
  }
  mandatory false;
 }
 leaf TILT {
  type union {
   type int32 {
    range "-900..2147483647";
   }
  }
  mandatory false;
 }
 }
 grouping RVDSUBUNIT-attributes {
 leaf CONNCN1 {
  type union {
   type uint8 {
    range "0..255";
   }
  }
  mandatory false;
 }
 leaf CONNCN2 {
  type union {
   type uint8 {
    range "0..255";
   }
  }
  mandatory false;
 }
 leaf CONNPN1 {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf CONNPN2 {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf CONNSN1 {
  type union {
   type uint8 {
    range "0..255";
   }
  }
  mandatory false;
 }
 leaf CONNSN2 {
  type union {
   type uint8 {
    range "0..255";
   }
  }
  mandatory false;
 }
 leaf CONNSRN1 {
  type union {
   type uint8 {
    range "4..255";
   }
  }
  mandatory false;
 }
 leaf CONNSRN2 {
  type union {
   type uint8 {
    range "4..255";
   }
  }
  mandatory false;
 }
 leaf DEVICENO {
  type union {
   type int16 {
    range "-1..1023";
   }
  }
  mandatory false;
 }
 leaf HORIZONTALBW {
  type union {
   type int16 {
    range "-1800..32767";
   }
  }
  mandatory false;
 }
 leaf SDAMODE {
  type enumeration {
   enum val-0;
   enum val-1;
   enum val-255;
  }
  mandatory false;
 }
 leaf SUBNAME {
  type string {
   length "0..83";
  }
  mandatory false;
 }
 leaf SUBUNITNO {
  type union {
   type int8 {
    range "-1..8";
   }
  }
  mandatory false;
 }
 leaf VBEAMWIDTH {
  type uint16 {
   range "0..3599";
  }
  mandatory false;
 }
 }
 grouping SAALLNK-attributes {
 leaf CCTM {
  type uint16 {
   range "100..65535";
  }
  mandatory false;
 }
 leaf CN {
  type uint8 {
   range "0..7";
  }
  mandatory false;
 }
 leaf IDLE {
  type uint16 {
   range "100..65535";
  }
  mandatory false;
 }
 leaf JNRSCGRP {
  type boolean;
  mandatory false;
 }
 leaf KATM {
  type uint16 {
   range "100..65534";
  }
  mandatory false;
 }
 leaf MAXCC {
  type uint8 {
   range "1..255";
  }
  mandatory false;
 }
 leaf MAXLE {
  type uint16 {
   range "3..65535";
  }
  mandatory false;
 }
 leaf MAXPD {
  type uint16 {
   range "1..65535";
  }
  mandatory false;
 }
 leaf MCR {
  type uint16 {
   range "30..37262";
  }
  mandatory false;
 }
 leaf NRTM {
  type uint16 {
   range "101..65535";
  }
  mandatory false;
 }
 leaf PCR {
  type uint16 {
   range "30..37265";
  }
  mandatory false;
 }
 leaf PN {
  type uint8 {
   range "0..7";
  }
  mandatory false;
 }
 leaf POLL {
  type uint16 {
   range "100..65534";
  }
  mandatory false;
 }
 leaf PT {
  type enumeration {
   enum val-0;
   enum val-1;
   enum val-5;
  }
  mandatory false;
 }
 leaf RSCGRPID {
  type uint8 {
   range "0..15";
  }
  mandatory false;
 }
 leaf RU {
  type boolean;
  mandatory false;
 }
 leaf OLD_SAALNO {
  type union {
   type int8 {
    range "-1..63";
   }
  }
  mandatory false;
 }
 leaf SAALNO {
  type union {
   type int8 {
    range "-1..63";
   }
  }
  mandatory false;
 }
 leaf SBT {
  type enumeration {
   enum val-0;
   enum val-3;
   enum val-4;
  }
  mandatory false;
 }
 leaf SCR {
  type uint16 {
   range "30..37262";
  }
  mandatory false;
 }
 leaf SN {
  type uint8 {
   range "0..7";
  }
  mandatory false;
 }
 leaf SRN {
  type uint8 {
   range "0..1";
  }
  mandatory false;
 }
 leaf ST {
  type enumeration {
   enum val-0;
   enum val-1;
   enum val-2;
   enum val-3;
   enum val-4;
  }
  mandatory false;
 }
 leaf VCI {
  type uint16 {
   range "32..511";
  }
  mandatory false;
 }
 leaf VPI {
  type uint8 {
   range "0..255";
  }
  mandatory false;
 }
 }
 grouping SASU-attributes {
 leaf CTRLCN {
  type uint8 {
   range "0..62";
  }
  mandatory false;
 }
 leaf CTRLSN {
  type uint8 {
   range "0..8";
  }
  mandatory false;
 }
 leaf CTRLSRN {
  type union {
   type uint8 {
    range "4..254";
   }
  }
  mandatory false;
 }
 leaf DCSWITCH {
  type enumeration {
   enum val-0;
   enum val-1;
   enum val-2;
   enum val-255;
  }
  mandatory false;
 }
 leaf DEVICENAME {
  type string {
   length "0..83";
  }
  mandatory false;
 }
 leaf DEVICENO {
  type union {
   type int16 {
    range "-1..1023";
   }
  }
  mandatory false;
 }
 leaf SERIALNO {
  type string {
   length "0..36";
  }
  mandatory false;
 }
 leaf VENDORCODE {
  type string {
   length "0..2";
  }
  mandatory false;
 }
 }
 grouping SCTPHOST-attributes {
 leaf CPEPGROUPID1 {
  type uint16 {
   range "0..65535";
  }
  mandatory false;
 }
 leaf CPEPGROUPID2 {
  type uint16 {
   range "0..65535";
  }
  mandatory false;
 }
 leaf DTLSCONNPOLICY {
  type boolean;
  mandatory false;
 }
 leaf DTLSPOLICYID {
  type enumeration {
   enum val-0;
   enum val-255;
  }
  mandatory false;
 }
 leaf IPVERSION {
  type boolean;
  mandatory false;
 }
 leaf OPSHARINGSWITCH {
  type boolean;
  mandatory false;
 }
 leaf PN {
  type uint16 {
   range "1024..65535";
  }
  mandatory false;
 }
 leaf SCTPAUTHCHUNKLST {
  type string;
  mandatory false;
 }
 leaf OLD_SCTPHOSTID {
  type union {
   type int32 {
    range "-1..65535";
   }
  }
  mandatory false;
 }
 leaf SCTPHOSTID {
  type union {
   type int32 {
    range "-1..65535";
   }
  }
  mandatory false;
 }
 leaf SCTPTEMPLATEID {
  type uint16 {
   range "0..65535";
  }
  mandatory false;
 }
 leaf SIGIP1SECHOSTID {
  type uint16 {
   range "0..65535";
  }
  mandatory false;
 }
 leaf SIGIP1SECSWITCH {
  type boolean;
  mandatory false;
 }
 leaf SIGIP1V4 {
  type inet:ipv4-address;
  mandatory false;
 }
 leaf SIGIP1V6 {
  type inet:ipv6-address;
  mandatory false;
 }
 leaf SIGIP2SECHOSTID {
  type uint16 {
   range "0..65535";
  }
  mandatory false;
 }
 leaf SIGIP2SECSWITCH {
  type boolean;
  mandatory false;
 }
 leaf SIGIP2V4 {
  type inet:ipv4-address;
  mandatory false;
 }
 leaf SIGIP2V6 {
  type inet:ipv6-address;
  mandatory false;
 }
 leaf SIMPLEMODESWITCH {
  type enumeration {
   enum val-0;
   enum val-1;
   enum val-2;
   enum val-4;
  }
  mandatory false;
 }
 leaf TRUSTGROUPID {
  type union {
   type uint16 {
    range "0..65535";
   }
  }
  mandatory false;
 }
 leaf UPEPGROUP1TYPE {
  type boolean;
  mandatory false;
 }
 leaf UPEPGROUPID1 {
  type uint16 {
   range "0..65535";
  }
  mandatory false;
 }
 leaf UPEPGROUPID2 {
  type uint16 {
   range "0..65535";
  }
  mandatory false;
 }
 leaf USERLABEL {
  type string {
   length "0..256";
  }
  mandatory false;
 }
 leaf VRFIDX {
  type uint8 {
   range "0..31";
  }
  mandatory false;
 }
 }
 grouping SCTPHOSTREF-attributes {
 leaf EPGROUPID {
  type union {
   type int32 {
    range "-1..65535";
   }
  }
  mandatory false;
 }
 leaf SCTPHOSTID {
  type union {
   type int32 {
    range "-1..65535";
   }
  }
  mandatory false;
 }
 }
 grouping SCTPLNK-attributes {
 leaf AUTOCFGFLAG {
  type boolean;
  mandatory false;
 }
 leaf AUTOSWITCH {
  type boolean;
  mandatory false;
 }
 leaf BLKFLAG {
  type boolean;
  mandatory false;
 }
 leaf CHKSUMTYPE {
  type boolean;
  mandatory false;
 }
 leaf CTRLMODE {
  type boolean;
  mandatory false;
 }
 leaf DESCRI {
  type string {
   length "0..67";
  }
  mandatory false;
 }
 leaf DSCP {
  type uint8 {
   range "0..63";
  }
  mandatory false;
 }
 leaf DSCPSW {
  type boolean;
  mandatory false;
 }
 leaf DTLSCONNPOLICY {
  type boolean;
  mandatory false;
 }
 leaf DTLSPOLICYID {
  type enumeration {
   enum val-0;
   enum val-255;
  }
  mandatory false;
 }
 leaf HBINTER {
  type uint16 {
   range "1000..60000";
  }
  mandatory false;
 }
 leaf IPVERSION {
  type boolean;
  mandatory false;
 }
 leaf LOCIP {
  type inet:ipv4-address;
  mandatory false;
 }
 leaf LOCIP6 {
  type inet:ipv6-address;
  mandatory false;
 }
 leaf LOCPORT {
  type uint16 {
   range "1024..65535";
  }
  mandatory false;
 }
 leaf MAXASSOCRETR {
  type uint8 {
   range "2..254";
  }
  mandatory false;
 }
 leaf MAXPATHRETR {
  type uint8 {
   range "1..253";
  }
  mandatory false;
 }
 leaf MAXSCTPPDUSIZE {
  type uint16 {
   range "580..1480";
  }
  mandatory false;
 }
 leaf MAXSTREAM {
  type uint8 {
   range "1..34";
  }
  mandatory false;
 }
 leaf PEERIP {
  type inet:ipv4-address;
  mandatory false;
 }
 leaf PEERIP6 {
  type inet:ipv6-address;
  mandatory false;
 }
 leaf PEERPORT {
  type uint16 {
   range "1024..65535";
  }
  mandatory false;
 }
 leaf RTOALPHA {
  type uint8 {
   range "1..99";
  }
  mandatory false;
 }
 leaf RTOBETA {
  type uint8 {
   range "1..99";
  }
  mandatory false;
 }
 leaf RTOINIT {
  type uint16 {
   range "10..59999";
  }
  mandatory false;
 }
 leaf RTOMAX {
  type uint16 {
   range "11..60000";
  }
  mandatory false;
 }
 leaf RTOMIN {
  type uint16 {
   range "10..59999";
  }
  mandatory false;
 }
 leaf SCTPAUTHCHUNKLST {
  type string;
  mandatory false;
 }
 leaf OLD_SCTPNO {
  type union {
   type int32 {
    range "-1..79999";
   }
  }
  mandatory false;
 }
 leaf SCTPNO {
  type union {
   type int32 {
    range "-1..79999";
   }
  }
  mandatory false;
 }
 leaf SECLOCIP {
  type inet:ipv4-address;
  mandatory false;
 }
 leaf SECLOCIP6 {
  type inet:ipv6-address;
  mandatory false;
 }
 leaf SECPEERIP {
  type inet:ipv4-address;
  mandatory false;
 }
 leaf SECPEERIP6 {
  type inet:ipv6-address;
  mandatory false;
 }
 leaf SWITCHBACKHBNUM {
  type uint8 {
   range "1..254";
  }
  mandatory false;
 }
 leaf TRUSTGROUPID {
  type union {
   type uint16 {
    range "0..65535";
   }
  }
  mandatory false;
 }
 leaf TSACK {
  type uint16 {
   range "10..500";
  }
  mandatory false;
 }
 leaf VRFIDX {
  type uint8 {
   range "0..31";
  }
  mandatory false;
 }
 }
 grouping SCTPPEER-attributes {
 leaf AUTOCFGFLAG {
  type boolean;
  mandatory false;
 }
 leaf BLKFLAG {
  type boolean;
  mandatory false;
 }
 leaf CTRLMODE {
  type boolean;
  mandatory false;
 }
 leaf EPGROUPID {
  type uint16 {
   range "0..65535";
  }
  mandatory false;
 }
 leaf IPVERSION {
  type boolean;
  mandatory false;
 }
 leaf PN {
  type uint16 {
   range "1024..65535";
  }
  mandatory false;
 }
 leaf REMOTEID {
  type string {
   length "0..127";
  }
  mandatory false;
 }
 leaf OLD_SCTPPEERID {
  type union {
   type int32 {
    range "-1..79999";
   }
  }
  mandatory false;
 }
 leaf SCTPPEERID {
  type union {
   type int32 {
    range "-1..79999";
   }
  }
  mandatory false;
 }
 leaf SIGIP1SECPEERID {
  type union {
   type uint32 {
    range "0..89999";
   }
  }
  mandatory false;
 }
 leaf SIGIP1SECSWITCH {
  type boolean;
  mandatory false;
 }
 leaf SIGIP1V4 {
  type inet:ipv4-address;
  mandatory false;
 }
 leaf SIGIP1V6 {
  type inet:ipv6-address;
  mandatory false;
 }
 leaf SIGIP2SECPEERID {
  type union {
   type uint32 {
    range "0..89999";
   }
  }
  mandatory false;
 }
 leaf SIGIP2SECSWITCH {
  type boolean;
  mandatory false;
 }
 leaf SIGIP2V4 {
  type inet:ipv4-address;
  mandatory false;
 }
 leaf SIGIP2V6 {
  type inet:ipv6-address;
  mandatory false;
 }
 leaf SIMPLEMODESWITCH {
  type boolean;
  mandatory false;
 }
 leaf USERLABEL {
  type string {
   length "0..256";
  }
  mandatory false;
 }
 leaf VRFIDX {
  type uint8 {
   range "0..31";
  }
  mandatory false;
 }
 }
 grouping SCTPPEERREF-attributes {
 leaf EPGROUPID {
  type union {
   type int32 {
    range "-1..65535";
   }
  }
  mandatory false;
 }
 leaf SCTPPEERID {
  type union {
   type int32 {
    range "-1..79999";
   }
  }
  mandatory false;
 }
 }
 grouping SECTOR-attributes {
 leaf ANTAZIMUTH {
  type union {
   type uint16 {
    range "0..65535";
   }
  }
  mandatory false;
 }
 leaf LOCATIONNAME {
  type string {
   length "0..128";
  }
  mandatory false;
 }
 leaf SECNAME {
  type string {
   length "0..99";
  }
  mandatory false;
 }
 leaf OLD_SECTORID {
  type union {
   type int32 {
    range "-1..65535";
   }
  }
  mandatory false;
 }
 leaf SECTORID {
  type union {
   type int32 {
    range "-1..65535";
   }
  }
  mandatory false;
 }
 leaf USERLABEL {
  type string {
   length "0..255";
  }
  mandatory false;
 }
 }
 grouping SECTORANTENNAREF-attributes {
 leaf ANTN {
  type enumeration {
   enum val--1;
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-32;
   enum val-33;
   enum val-34;
   enum val-35;
   enum val-48;
   enum val-49;
   enum val-50;
   enum val-51;
   enum val-64;
   enum val-65;
   enum val-66;
   enum val-67;
   enum val-80;
   enum val-81;
   enum val-82;
   enum val-83;
   enum val-96;
   enum val-97;
   enum val-98;
   enum val-99;
   enum val-112;
   enum val-113;
   enum val-114;
   enum val-115;
  }
  mandatory false;
 }
 leaf CN {
  type union {
   type int8 {
    range "-1..62";
   }
  }
  mandatory false;
 }
 leaf SECTORID {
  type union {
   type int32 {
    range "-1..65535";
   }
  }
  mandatory false;
 }
 leaf SN {
  type union {
   type int16 {
    range "-1..255";
   }
  }
  mandatory false;
 }
 leaf SRN {
  type union {
   type int16 {
    range "-1..254";
   }
  }
  mandatory false;
 }
 }
 grouping SECTOREQM-attributes {
 leaf ANTCFGMODE {
  type boolean;
  mandatory false;
 }
 leaf BEAMAZIMUTHOFFSET {
  type enumeration {
   enum val-0;
   enum val-1;
   enum val-2;
  }
  mandatory false;
 }
 leaf BEAMLAYERSPLIT {
  type enumeration {
   enum val-0;
   enum val-1;
   enum val-2;
  }
  mandatory false;
 }
 leaf BEAMSHAPE {
  type enumeration {
   enum val-0;
   enum val-1;
   enum val-2;
   enum val-3;
  }
  mandatory false;
 }
 leaf RRU2CN {
  type uint8 {
   range "0..62";
  }
  mandatory false;
 }
 leaf RRU2SN {
  type uint8 {
   range "0..8";
  }
  mandatory false;
 }
 leaf RRU2SRN {
  type uint8 {
   range "60..254";
  }
  mandatory false;
 }
 leaf RRUCN {
  type uint8 {
   range "0..62";
  }
  mandatory false;
 }
 leaf RRUNUM {
  type uint8 {
   range "1..2";
  }
  mandatory false;
 }
 leaf RRUSN {
  type uint8 {
   range "0..8";
  }
  mandatory false;
 }
 leaf RRUSRN {
  type union {
   type uint8 {
    range "4..254";
   }
  }
  mandatory false;
 }
 leaf OLD_SECTOREQMID {
  type union {
   type int32 {
    range "-1..65535";
   }
  }
  mandatory false;
 }
 leaf SECTOREQMID {
  type union {
   type int32 {
    range "-1..65535";
   }
  }
  mandatory false;
 }
 leaf SECTORID {
  type uint16 {
   range "0..65535";
  }
  mandatory false;
 }
 }
 grouping SECTOREQMANTENNAREF-attributes {
 leaf ANTN {
  type enumeration {
   enum val--1;
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-32;
   enum val-33;
   enum val-34;
   enum val-35;
   enum val-48;
   enum val-49;
   enum val-50;
   enum val-51;
   enum val-64;
   enum val-65;
   enum val-66;
   enum val-67;
   enum val-80;
   enum val-81;
   enum val-82;
   enum val-83;
   enum val-96;
   enum val-97;
   enum val-98;
   enum val-99;
   enum val-112;
   enum val-113;
   enum val-114;
   enum val-115;
  }
  mandatory false;
 }
 leaf ANTTYPE {
  type enumeration {
   enum val--1;
   enum val-1;
   enum val-2;
   enum val-3;
  }
  mandatory false;
 }
 leaf CN {
  type union {
   type int8 {
    range "-1..62";
   }
  }
  mandatory false;
 }
 leaf SECTOREQMID {
  type union {
   type int32 {
    range "-1..65535";
   }
  }
  mandatory false;
 }
 leaf SN {
  type union {
   type int16 {
    range "-1..255";
   }
  }
  mandatory false;
 }
 leaf SRN {
  type union {
   type int16 {
    range "-1..254";
   }
  }
  mandatory false;
 }
 leaf TXBKPMODE {
  type enumeration {
   enum val--1;
   enum val-0;
   enum val-1;
  }
  mandatory false;
 }
 }
 grouping SECURITYHOST-attributes {
 leaf IPSECPROPNAME {
  type string {
   length "1..15";
  }
  mandatory false;
 }
 leaf IPVERSION {
  type boolean;
  mandatory false;
 }
 leaf LOCIKEIPV4 {
  type inet:ipv4-address;
  mandatory false;
 }
 leaf LOCIKEIPV6 {
  type inet:ipv6-address;
  mandatory false;
 }
 leaf PEERNAME {
  type string {
   length "1..15";
  }
  mandatory false;
 }
 leaf OLD_SECURITYHOSTID {
  type union {
   type int32 {
    range "-1..65535";
   }
  }
  mandatory false;
 }
 leaf SECURITYHOSTID {
  type union {
   type int32 {
    range "-1..65535";
   }
  }
  mandatory false;
 }
 leaf SECURITYTEMPLATEID {
  type uint16 {
   range "0..65535";
  }
  mandatory false;
 }
 leaf SEGWCONFIGMODE {
  type boolean;
  mandatory false;
 }
 leaf SEGWSWITCH {
  type boolean;
  mandatory false;
 }
 leaf USERLABEL {
  type string {
   length "0..256";
  }
  mandatory false;
 }
 leaf VRFIDX {
  type uint8 {
   range "0..31";
  }
  mandatory false;
 }
 }
 grouping SECURITYPEER-attributes {
 leaf AUTOCFGFLAG {
  type boolean;
  mandatory false;
 }
 leaf CTRLMODE {
  type boolean;
  mandatory false;
 }
 leaf IPSECPROPNAME {
  type string {
   length "1..15";
  }
  mandatory false;
 }
 leaf IPVERSION {
  type boolean;
  mandatory false;
 }
 leaf PEERIKEIPV4 {
  type inet:ipv4-address;
  mandatory false;
 }
 leaf PEERIKEIPV6 {
  type inet:ipv6-address;
  mandatory false;
 }
 leaf PEERNAME {
  type string {
   length "1..15";
  }
  mandatory false;
 }
 leaf OLD_SECURITYPEERID {
  type union {
   type int32 {
    range "-1..89999";
   }
  }
  mandatory false;
 }
 leaf SECURITYPEERID {
  type union {
   type int32 {
    range "-1..89999";
   }
  }
  mandatory false;
 }
 leaf SEGWSWITCH {
  type boolean;
  mandatory false;
 }
 leaf USERLABEL {
  type string {
   length "0..256";
  }
  mandatory false;
 }
 leaf VRFIDX {
  type uint8 {
   range "0..31";
  }
  mandatory false;
 }
 }
 grouping SECURITYTEMPLATE-attributes {
 leaf CERTNAME {
  type string {
   length "1..64";
  }
  mandatory false;
 }
 leaf CERTSOURCE {
  type boolean;
  mandatory false;
 }
 leaf CRLPOLICY {
  type enumeration {
   enum val-0;
   enum val-1;
   enum val-2;
  }
  mandatory false;
 }
 leaf DPD {
  type enumeration {
   enum val-0;
   enum val-2;
  }
  mandatory false;
 }
 leaf DPDIDLETIME {
  type uint16 {
   range "3..3600";
  }
  mandatory false;
 }
 leaf DPDRETRI {
  type uint8 {
   range "3..30";
  }
  mandatory false;
 }
 leaf DPDRETRN {
  type uint8 {
   range "3..10";
  }
  mandatory false;
 }
 leaf EXCHMODE {
  type enumeration {
   enum val-2;
   enum val-4;
  }
  mandatory false;
 }
 leaf IKEV2FRGMTU {
  type uint16 {
   range "576..3000";
  }
  mandatory false;
 }
 leaf IKEV2FRGSW {
  type boolean;
  mandatory false;
 }
 leaf IKEVERSION {
  type enumeration {
   enum val-1;
   enum val-2;
  }
  mandatory false;
 }
 leaf IPSECPROPNAME {
  type string {
   length "1..15";
  }
  mandatory false;
 }
 leaf LTCFG {
  type boolean;
  mandatory false;
 }
 leaf LTKB {
  type union {
   type uint32 {
    range "0..4294967295";
   }
  }
  mandatory false;
 }
 leaf LTS {
  type uint32 {
   range "30..604800";
  }
  mandatory false;
 }
 leaf MULTIVPNSWITCH {
  type boolean;
  mandatory false;
 }
 leaf NARROWDOWNSW {
  type boolean;
  mandatory false;
 }
 leaf OCSPSW {
  type boolean;
  mandatory false;
 }
 leaf PFS {
  type enumeration {
   enum val-0;
   enum val-1;
   enum val-2;
   enum val-14;
   enum val-15;
   enum val-19;
   enum val-20;
   enum val-31;
  }
  mandatory false;
 }
 leaf PKEY {
  type string {
   length "0..127";
  }
  mandatory false;
 }
 leaf PROPID {
  type uint8 {
   range "1..99";
  }
  mandatory false;
 }
 leaf REPLAYWND {
  type enumeration {
   enum val-0;
   enum val-1;
   enum val-2;
   enum val-128;
   enum val-256;
   enum val-512;
   enum val-1024;
   enum val-2048;
   enum val-4096;
  }
  mandatory false;
 }
 leaf OLD_SECURITYTEMPLATEID {
  type union {
   type int32 {
    range "-1..65535";
   }
  }
  mandatory false;
 }
 leaf SECURITYTEMPLATEID {
  type union {
   type int32 {
    range "-1..65535";
   }
  }
  mandatory false;
 }
 leaf SEGWSWITCH {
  type boolean;
  mandatory false;
 }
 leaf TRUSTGROUPID {
  type union {
   type uint16 {
    range "0..65535";
   }
  }
  mandatory false;
 }
 }
 grouping SSL-attributes {
 leaf AUTHMETH {
  type boolean;
  mandatory false;
 }
 leaf AUTHMODE {
  type boolean;
  mandatory false;
 }
 leaf CONNTYPE {
  type boolean;
  mandatory false;
 }
 leaf LOWESTCSLEVEL {
  type enumeration {
   enum val-1;
   enum val-2;
   enum val-3;
  }
  mandatory false;
 }
 leaf PID {
  type string {
   length "0..127";
  }
  mandatory false;
 }
 leaf PKEY {
  type string {
   length "0..127";
  }
  mandatory false;
 }
 leaf POLICYID {
  type uint8 {
   range "0..16";
  }
  mandatory false;
 }
 leaf RENEGO {
  type boolean;
  mandatory false;
 }
 leaf RENEGOINTERVAL {
  type uint8 {
   range "0..60";
  }
  mandatory false;
 }
 leaf RRUAUTHMODE {
  type boolean;
  mandatory false;
 }
 leaf RRUHWCERTAUTHSW {
  type boolean;
  mandatory false;
 }
 leaf RRUTLSCONNTYPE {
  type enumeration {
   enum val-0;
   enum val-1;
   enum val-2;
  }
  mandatory false;
 }
 leaf TRUSTGROUPID {
  type union {
   type uint16 {
    range "0..65535";
   }
  }
  mandatory false;
 }
 leaf VERSION {
  type string;
  mandatory false;
 }
 }
 grouping STAGGEREDPOWERRECORD-attributes {
 leaf EFFECTIVEDAY {
  type enumeration {
   enum val-0;
   enum val-1;
   enum val-2;
   enum val-3;
   enum val-4;
   enum val-5;
   enum val-6;
   enum val-255;
  }
  mandatory false;
 }
 leaf EFFECTIVEMONTH {
  type enumeration {
   enum val-0;
   enum val-1;
   enum val-2;
   enum val-3;
   enum val-4;
   enum val-5;
   enum val-6;
   enum val-7;
   enum val-8;
   enum val-9;
   enum val-10;
   enum val-11;
   enum val-255;
  }
  mandatory false;
 }
 leaf ENDTIME {
  type hwat:HH_MM_SS_Time;
  mandatory false;
 }
 leaf PRICELEVEL {
  type enumeration {
   enum val-0;
   enum val-1;
   enum val-2;
  }
  mandatory false;
 }
 leaf OLD_RECORDID {
  type union {
   type int32 {
    range "-1..65535";
   }
  }
  mandatory false;
 }
 leaf RECORDID {
  type union {
   type int32 {
    range "-1..65535";
   }
  }
  mandatory false;
 }
 leaf RECORDTYPE {
  type boolean;
  mandatory false;
 }
 leaf STARTTIME {
  type hwat:HH_MM_SS_Time;
  mandatory false;
 }
 }
 grouping SUBNETVLAN-attributes {
 leaf OLD_IP {
  type inet:ipv4-address;
  mandatory false;
 }
 leaf IP {
  type inet:ipv4-address;
  mandatory false;
 }
 leaf OLD_MASK {
  type inet:ipv4-address;
  mandatory false;
 }
 leaf MASK {
  type inet:ipv4-address;
  mandatory false;
 }
 leaf VLANID {
  type uint16 {
   range "1..4094";
  }
  mandatory false;
 }
 }
 grouping SYSTEMOM-attributes {
 leaf CFGSECLEV {
  type boolean;
  mandatory false;
 }
 leaf DUALBBUCONSCHKSW {
  type boolean;
  mandatory false;
 }
 leaf SECCFGLOCKSW {
  type boolean;
  mandatory false;
 }
 }
 grouping TACALG-attributes {
 leaf EMCTACPSW {
  type boolean;
  mandatory false;
 }
 leaf PORTDLCACSW {
  type boolean;
  mandatory false;
 }
 leaf PORTDLOBSW {
  type boolean;
  mandatory false;
 }
 leaf PORTULCACSW {
  type boolean;
  mandatory false;
 }
 leaf PORTULOBSW {
  type boolean;
  mandatory false;
 }
 leaf RSCGRPDLCACSWITCH {
  type boolean;
  mandatory false;
 }
 leaf RSCGRPULCACSWITCH {
  type boolean;
  mandatory false;
 }
 leaf TRMDLBRONZECACTH {
  type uint8 {
   range "0..100";
  }
  mandatory false;
 }
 leaf TRMDLGBRCACTH {
  type uint8 {
   range "0..100";
  }
  mandatory false;
 }
 leaf TRMDLGOLDCACTH {
  type uint8 {
   range "0..100";
  }
  mandatory false;
 }
 leaf TRMDLHOCACTH {
  type uint8 {
   range "0..100";
  }
  mandatory false;
 }
 leaf TRMDLIRONCACTH {
  type uint8 {
   range "0..100";
  }
  mandatory false;
 }
 leaf TRMDLPRESW {
  type boolean;
  mandatory false;
 }
 leaf TRMDLSILVERCACTH {
  type uint8 {
   range "0..100";
  }
  mandatory false;
 }
 leaf TRMULBRONZECACTH {
  type uint8 {
   range "0..100";
  }
  mandatory false;
 }
 leaf TRMULGBRCACTH {
  type uint8 {
   range "0..100";
  }
  mandatory false;
 }
 leaf TRMULGOLDCACTH {
  type uint8 {
   range "0..100";
  }
  mandatory false;
 }
 leaf TRMULHOCACTH {
  type uint8 {
   range "0..100";
  }
  mandatory false;
 }
 leaf TRMULIRONCACTH {
  type uint8 {
   range "0..100";
  }
  mandatory false;
 }
 leaf TRMULPRESW {
  type boolean;
  mandatory false;
 }
 leaf TRMULSILVERCACTH {
  type uint8 {
   range "0..100";
  }
  mandatory false;
 }
 }
 grouping TASM-attributes {
 leaf ALGORITHM {
  type enumeration {
   enum val-0;
   enum val-1;
   enum val-2;
   enum val-3;
  }
  mandatory false;
 }
 leaf ATRSW {
  type boolean;
  mandatory false;
 }
 leaf BKPMODE {
  type boolean;
  mandatory false;
 }
 leaf CLKALGOPTLFEATOPTSW {
  type string;
  mandatory false;
 }
 leaf CLKSRC {
  type enumeration {
   enum val-0;
   enum val-1;
   enum val-2;
   enum val-3;
   enum val-4;
   enum val-5;
   enum val-6;
   enum val-7;
   enum val-8;
   enum val-10;
   enum val-12;
  }
  mandatory false;
 }
 leaf CLKSYNCMODE {
  type enumeration {
   enum val-0;
   enum val-1;
   enum val-2;
  }
  mandatory false;
 }
 leaf CLOUDSRC {
  type boolean;
  mandatory false;
 }
 leaf CRTGPSTOUTCLEAPSECONDS {
  type int16 {
   range "-1000..1000";
  }
  mandatory false;
 }
 leaf DATE {
  type hwat:yyyy_mm_dd;
  mandatory false;
 }
 leaf DAY {
  type uint8 {
   range "0..7";
  }
  mandatory false;
 }
 leaf ECPRIDEMULLOCKSW {
  type boolean;
  mandatory false;
 }
 leaf ENSYSCLKCHKSW {
  type boolean;
  mandatory false;
 }
 leaf FIXEDMS {
  type enumeration {
   enum val-4;
   enum val-9;
   enum val-15;
  }
  mandatory false;
 }
 leaf FLAG {
  type boolean;
  mandatory false;
 }
 leaf FNSYNCSW {
  type boolean;
  mandatory false;
 }
 leaf FRAMESYNCSW {
  type boolean;
  mandatory false;
 }
 leaf FREECOUNT {
  type uint8 {
   range "3..120";
  }
  mandatory false;
 }
 leaf FREQUENCE {
  type boolean;
  mandatory false;
 }
 leaf GSMFRAMESYNCSW {
  type boolean;
  mandatory false;
 }
 leaf GSM_FBOFFSET {
  type uint8 {
   range "0..80";
  }
  mandatory false;
 }
 leaf HOLDCOUNT {
  type uint8 {
   range "3..120";
  }
  mandatory false;
 }
 leaf HOLDINGDURATION {
  type enumeration {
   enum val-0;
   enum val-24;
   enum val-48;
   enum val-72;
   enum val-96;
   enum val-108;
   enum val-120;
   enum val-132;
   enum val-144;
   enum val-156;
   enum val-168;
  }
  mandatory false;
 }
 leaf HYBRIDCLKCHKENHSW {
  type boolean;
  mandatory false;
 }
 leaf IPCLKABNFILTERSW {
  type boolean;
  mandatory false;
 }
 leaf LEAPSECONDSCHGDATE {
  type hwat:yyyy_mm_dd;
  mandatory false;
 }
 leaf LEAPSECONDSCHGTIME {
  type hwat:HH_MM_SS_Time;
  mandatory false;
 }
 leaf LOCKCOUNT {
  type uint8 {
   range "3..120";
  }
  mandatory false;
 }
 leaf LOOSETIME {
  type boolean;
  mandatory false;
 }
 leaf LPFNSYNCSW {
  type boolean;
  mandatory false;
 }
 leaf MODE {
  type enumeration {
   enum val-0;
   enum val-1;
   enum val-2;
  }
  mandatory false;
 }
 leaf MSCHANGEOPTSW {
  type boolean;
  mandatory false;
 }
 leaf MSCLKDIAGPROCESSSW {
  type string;
  mandatory false;
 }
 leaf MSCLKJOINTDIAGSW {
  type boolean;
  mandatory false;
 }
 leaf MUTUALLOCKSET {
  type string;
  mandatory false;
 }
 leaf NETMODE {
  type boolean;
  mandatory false;
 }
 leaf NEXTGPSTOUTCLEAPSECONDS {
  type int16 {
   range "-1000..1000";
  }
  mandatory false;
 }
 leaf PDALMTHD {
  type uint16 {
   range "500..3000";
  }
  mandatory false;
 }
 leaf PDHOTHD {
  type enumeration {
   enum val-1500;
   enum val-2000;
   enum val-2500;
   enum val-3000;
  }
  mandatory false;
 }
 leaf PEERCLKBKUPSW {
  type boolean;
  mandatory false;
 }
 leaf PERIOD {
  type uint8 {
   range "3..200";
  }
  mandatory false;
 }
 leaf PREMS {
  type enumeration {
   enum val-4;
   enum val-5;
   enum val-8;
   enum val-9;
   enum val-10;
   enum val-15;
  }
  mandatory false;
 }
 leaf QL {
  type enumeration {
   enum val-2;
   enum val-4;
   enum val-8;
   enum val-10;
   enum val-11;
   enum val-32;
   enum val-33;
   enum val-34;
   enum val-35;
  }
  mandatory false;
 }
 leaf SAMPLETIME {
  type uint16 {
   range "1..18000";
  }
  mandatory false;
 }
 leaf SEARCHCOUNT {
  type uint8 {
   range "3..120";
  }
  mandatory false;
 }
 leaf SRCNO {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-65535;
  }
  mandatory false;
 }
 leaf STANDARD {
  type enumeration {
   enum val-1;
   enum val-4;
  }
  mandatory false;
 }
 leaf SWITCHPOLICY {
  type enumeration {
   enum val-0;
   enum val-1;
   enum val-2;
  }
  mandatory false;
 }
 leaf SYNMODE {
  type enumeration {
   enum val-0;
   enum val-1;
   enum val-2;
  }
  mandatory false;
 }
 leaf SYSCLKSRC {
  type boolean;
  mandatory false;
 }
 leaf TIME {
  type hwat:HH_MM_SS_Time;
  mandatory false;
 }
 leaf TM {
  type hwat:HH_MM_SS_Time;
  mandatory false;
 }
 leaf TODCLKOUTENHSW {
  type boolean;
  mandatory false;
 }
 }
 grouping TIMESRC-attributes {
 leaf AUTOSWITCH {
  type boolean;
  mandatory false;
 }
 leaf TIMESRC {
  type enumeration {
   enum val-0;
   enum val-1;
   enum val-2;
   enum val-4;
  }
  mandatory false;
 }
 }
 grouping TMA-attributes {
 leaf CTRLCN {
  type uint8 {
   range "0..62";
  }
  mandatory false;
 }
 leaf CTRLSN {
  type uint8 {
   range "0..8";
  }
  mandatory false;
 }
 leaf CTRLSRN {
  type union {
   type uint8 {
    range "4..254";
   }
  }
  mandatory false;
 }
 leaf DEVICENAME {
  type string {
   length "0..83";
  }
  mandatory false;
 }
 leaf DEVICENO {
  type union {
   type int16 {
    range "-1..1023";
   }
  }
  mandatory false;
 }
 leaf SERIALNO {
  type string {
   length "0..36";
  }
  mandatory false;
 }
 leaf SUBUNITNUM {
  type uint8 {
   range "1..8";
  }
  mandatory false;
 }
 leaf TMATYPE {
  type boolean;
  mandatory false;
 }
 leaf VENDORCODE {
  type string {
   length "0..2";
  }
  mandatory false;
 }
 }
 grouping TOLCALG-attributes {
 leaf TRMDLOLCRELTH {
  type uint8 {
   range "0..100";
  }
  mandatory false;
 }
 leaf TRMDLOLCSWITCH {
  type boolean;
  mandatory false;
 }
 leaf TRMDLOLCTRIGTH {
  type uint8 {
   range "0..100";
  }
  mandatory false;
 }
 leaf TRMOLCRELBEARERNUM {
  type uint8 {
   range "0..100";
  }
  mandatory false;
 }
 leaf TRMULOLCRELTH {
  type uint8 {
   range "0..100";
  }
  mandatory false;
 }
 leaf TRMULOLCSWITCH {
  type boolean;
  mandatory false;
 }
 leaf TRMULOLCTRIGTH {
  type uint8 {
   range "0..100";
  }
  mandatory false;
 }
 }
 grouping TRANSFUNCTIONSW-attributes {
 leaf DLLIMITSW {
  type boolean;
  mandatory false;
 }
 leaf DLTRANSPORTALGSW {
  type boolean;
  mandatory false;
 }
 leaf ETHTRKLBMODE {
  type boolean;
  mandatory false;
 }
 leaf ICMPPORTUNREACHABLESW {
  type boolean;
  mandatory false;
 }
 leaf IPLOOPTSTRSPSW {
  type boolean;
  mandatory false;
 }
 leaf IPMUXDEMULTIPLEXSW {
  type boolean;
  mandatory false;
 }
 leaf IPPMPASSIVEACTIVATIONSW {
  type boolean;
  mandatory false;
 }
 leaf IPRCVSW {
  type boolean;
  mandatory false;
 }
 leaf PATHPINGRSPSW {
  type boolean;
  mandatory false;
 }
 leaf SCTPSERVERSW {
  type boolean;
  mandatory false;
 }
 }
 grouping TREELNKPVC-attributes {
 leaf CDVT {
  type uint32 {
   range "1024..13300000";
  }
  mandatory false;
 }
 leaf CN {
  type uint8 {
   range "0..7";
  }
  mandatory false;
 }
 leaf DESCRI {
  type string {
   length "0..67";
  }
  mandatory false;
 }
 leaf DSTPN {
  type uint8 {
   range "0..7";
  }
  mandatory false;
 }
 leaf DSTPT {
  type enumeration {
   enum val-0;
   enum val-1;
   enum val-5;
  }
  mandatory false;
 }
 leaf DSTRSCGRP {
  type uint8 {
   range "0..15";
  }
  mandatory false;
 }
 leaf DSTSBT {
  type enumeration {
   enum val-0;
   enum val-3;
  }
  mandatory false;
 }
 leaf DSTSN {
  type uint8 {
   range "0..7";
  }
  mandatory false;
 }
 leaf DSTSRN {
  type uint8 {
   range "0..1";
  }
  mandatory false;
 }
 leaf DSTVCI {
  type uint16 {
   range "32..511";
  }
  mandatory false;
 }
 leaf DSTVPI {
  type uint8 {
   range "0..255";
  }
  mandatory false;
 }
 leaf JNRSCGRP {
  type boolean;
  mandatory false;
 }
 leaf MBS {
  type uint16 {
   range "3..10000";
  }
  mandatory false;
 }
 leaf MCR {
  type uint16 {
   range "30..49526";
  }
  mandatory false;
 }
 leaf OLD_NO {
  type union {
   type int32 {
    range "-1..65535";
   }
  }
  mandatory false;
 }
 leaf NO {
  type union {
   type int32 {
    range "-1..65535";
   }
  }
  mandatory false;
 }
 leaf PCR {
  type uint16 {
   range "30..49529";
  }
  mandatory false;
 }
 leaf RU {
  type boolean;
  mandatory false;
 }
 leaf SCR {
  type uint16 {
   range "30..49526";
  }
  mandatory false;
 }
 leaf SRCPN {
  type uint8 {
   range "0..7";
  }
  mandatory false;
 }
 leaf SRCPT {
  type enumeration {
   enum val-0;
   enum val-1;
   enum val-5;
  }
  mandatory false;
 }
 leaf SRCRSCGRP {
  type uint8 {
   range "0..15";
  }
  mandatory false;
 }
 leaf SRCSBT {
  type enumeration {
   enum val-0;
   enum val-3;
  }
  mandatory false;
 }
 leaf SRCSN {
  type uint8 {
   range "0..7";
  }
  mandatory false;
 }
 leaf SRCSRN {
  type uint8 {
   range "0..1";
  }
  mandatory false;
 }
 leaf SRCVCI {
  type uint16 {
   range "32..511";
  }
  mandatory false;
 }
 leaf SRCVPI {
  type uint8 {
   range "0..255";
  }
  mandatory false;
 }
 leaf ST {
  type enumeration {
   enum val-1;
   enum val-2;
   enum val-3;
   enum val-4;
  }
  mandatory false;
 }
 leaf VST {
  type boolean;
  mandatory false;
 }
 }
 grouping TRUSTCERT-attributes {
 leaf OLD_CERTNAME {
  type string {
   length "1..64";
  }
  mandatory false;
 }
 leaf CERTNAME {
  type string {
   length "1..64";
  }
  mandatory false;
 }
 }
 grouping TSCROSS-attributes {
 leaf CN {
  type uint8 {
   range "0..7";
  }
  mandatory false;
 }
 leaf DESCRI {
  type string {
   length "0..67";
  }
  mandatory false;
 }
 leaf DSTPN {
  type uint8 {
   range "0..7";
  }
  mandatory false;
 }
 leaf DSTSBT {
  type enumeration {
   enum val-0;
   enum val-3;
   enum val-4;
  }
  mandatory false;
 }
 leaf DSTSN {
  type uint8 {
   range "0..7";
  }
  mandatory false;
 }
 leaf DSTTSN {
  type string;
  mandatory false;
 }
 leaf OLD_NO {
  type union {
   type int8 {
    range "-1..15";
   }
  }
  mandatory false;
 }
 leaf NO {
  type union {
   type int8 {
    range "-1..15";
   }
  }
  mandatory false;
 }
 leaf SRCPN {
  type uint8 {
   range "0..7";
  }
  mandatory false;
 }
 leaf SRCSBT {
  type enumeration {
   enum val-0;
   enum val-3;
   enum val-4;
  }
  mandatory false;
 }
 leaf SRCSN {
  type uint8 {
   range "0..7";
  }
  mandatory false;
 }
 leaf SRCTSN {
  type string;
  mandatory false;
 }
 leaf SRN {
  type uint8 {
   range "0..1";
  }
  mandatory false;
 }
 }
 grouping TUNNEL-attributes {
 leaf DCN {
  type uint8 {
   range "0..7";
  }
  mandatory false;
 }
 leaf DSN {
  type uint8 {
   range "0..7";
  }
  mandatory false;
 }
 leaf DSRN {
  type uint8 {
   range "0..1";
  }
  mandatory false;
 }
 leaf OLD_SCN {
  type union {
   type int8 {
    range "-1..7";
   }
  }
  mandatory false;
 }
 leaf SCN {
  type union {
   type int8 {
    range "-1..7";
   }
  }
  mandatory false;
 }
 leaf OLD_SSN {
  type union {
   type int8 {
    range "-1..7";
   }
  }
  mandatory false;
 }
 leaf SSN {
  type union {
   type int8 {
    range "-1..7";
   }
  }
  mandatory false;
 }
 leaf OLD_SSRN {
  type union {
   type int8 {
    range "-1..1";
   }
  }
  mandatory false;
 }
 leaf SSRN {
  type union {
   type int8 {
    range "-1..1";
   }
  }
  mandatory false;
 }
 leaf OLD_TUNNELID {
  type union {
   type int8 {
    range "-1..14";
   }
  }
  mandatory false;
 }
 leaf TUNNELID {
  type union {
   type int8 {
    range "-1..14";
   }
  }
  mandatory false;
 }
 leaf TUNNELTYPE {
  type boolean;
  mandatory false;
 }
 }
 grouping TUNNELITF-attributes {
 leaf CTRLMODE {
  type boolean;
  mandatory false;
 }
 leaf FLEXIP4ID {
  type uint8 {
   range "0..127";
  }
  mandatory false;
 }
 leaf LOCALIP4 {
  type inet:ipv4-address;
  mandatory false;
 }
 leaf LOCALIP6 {
  type inet:ipv6-address;
  mandatory false;
 }
 leaf LOCALIPREFMETHOD {
  type boolean;
  mandatory false;
 }
 leaf MODE {
  type enumeration {
   enum val-1;
   enum val-2;
  }
  mandatory false;
 }
 leaf OLD_PORTID {
  type union {
   type int16 {
    range "-1..19999";
   }
  }
  mandatory false;
 }
 leaf PORTID {
  type union {
   type int16 {
    range "-1..19999";
   }
  }
  mandatory false;
 }
 leaf REMOTEIP4 {
  type inet:ipv4-address;
  mandatory false;
 }
 leaf REMOTEIP6 {
  type inet:ipv6-address;
  mandatory false;
 }
 leaf VRFIDX {
  type uint8 {
   range "0..31";
  }
  mandatory false;
 }
 }
 grouping TWAMPCLIENT-attributes {
 leaf OLD_CLIENTID {
  type union {
   type int8 {
    range "-1..23";
   }
  }
  mandatory false;
 }
 leaf CLIENTID {
  type union {
   type int8 {
    range "-1..23";
   }
  }
  mandatory false;
 }
 leaf DSCP {
  type uint8 {
   range "0..63";
  }
  mandatory false;
 }
 leaf IPVERSION {
  type boolean;
  mandatory false;
 }
 leaf LOCALIP {
  type inet:ipv4-address;
  mandatory false;
 }
 leaf LOCALIPV6 {
  type inet:ipv6-address;
  mandatory false;
 }
 leaf PEERIP {
  type inet:ipv4-address;
  mandatory false;
 }
 leaf PEERIPV6 {
  type inet:ipv6-address;
  mandatory false;
 }
 leaf PEERPORT {
  type uint16 {
   range "1..65535";
  }
  mandatory false;
 }
 leaf TWAMPARCH {
  type boolean;
  mandatory false;
 }
 leaf VRFINDEX {
  type uint8 {
   range "0..31";
  }
  mandatory false;
 }
 }
 grouping TWAMPRESPONDER-attributes {
 leaf DSCP {
  type uint8 {
   range "0..63";
  }
  mandatory false;
 }
 leaf IPVERSION {
  type boolean;
  mandatory false;
 }
 leaf LIGHTARCHITECTUREMODE {
  type boolean;
  mandatory false;
 }
 leaf LIGHTLOCALUDPPORT {
  type union {
   type uint32 {
    range "64679..4294967295";
   }
  }
  mandatory false;
 }
 leaf LOCALIP {
  type inet:ipv4-address;
  mandatory false;
 }
 leaf LOCALIPV6 {
  type inet:ipv6-address;
  mandatory false;
 }
 leaf LOCALPORT {
  type union {
   type uint16 {
    range "862..65535";
   }
  }
  mandatory false;
 }
 leaf REFWAIT {
  type uint16 {
   range "10..1800";
  }
  mandatory false;
 }
 leaf OLD_RESPONDERID {
  type union {
   type int8 {
    range "-1..15";
   }
  }
  mandatory false;
 }
 leaf RESPONDERID {
  type union {
   type int8 {
    range "-1..15";
   }
  }
  mandatory false;
 }
 leaf SERVWAIT {
  type uint16 {
   range "10..1800";
  }
  mandatory false;
 }
 leaf TWAMPARCH {
  type boolean;
  mandatory false;
 }
 leaf VRFINDEX {
  type uint8 {
   range "0..31";
  }
  mandatory false;
 }
 }
 grouping TWAMPSENDER-attributes {
 leaf OLD_CLIENTID {
  type union {
   type int8 {
    range "-1..23";
   }
  }
  mandatory false;
 }
 leaf CLIENTID {
  type union {
   type int8 {
    range "-1..23";
   }
  }
  mandatory false;
 }
 leaf DSCP {
  type uint8 {
   range "0..63";
  }
  mandatory false;
 }
 leaf LIGHTARCHITECTUREMODE {
  type boolean;
  mandatory false;
 }
 leaf LOCALUDPPORT {
  type union {
   type uint32 {
    range "64695..4294967295";
   }
  }
  mandatory false;
 }
 leaf PEERUDPPORT {
  type union {
   type uint32 {
    range "1..4294967295";
   }
  }
  mandatory false;
 }
 leaf PKTINT {
  type uint16 {
   range "10..1000";
  }
  mandatory false;
 }
 leaf PKTINTTYPE {
  type boolean;
  mandatory false;
 }
 leaf PKTSIZE {
  type uint16 {
   range "69..1500";
  }
  mandatory false;
 }
 leaf PKTSIZETYPE {
  type boolean;
  mandatory false;
 }
 leaf OLD_SENDERID {
  type union {
   type int8 {
    range "-1..15";
   }
  }
  mandatory false;
 }
 leaf SENDERID {
  type union {
   type int8 {
    range "-1..15";
   }
  }
  mandatory false;
 }
 leaf TWAMPARCH {
  type boolean;
  mandatory false;
 }
 }
 grouping TZ-attributes {
 leaf DST {
  type boolean;
  mandatory false;
 }
 leaf EDAY {
  type uint8 {
   range "1..31";
  }
  mandatory false;
 }
 leaf EM {
  type enumeration {
   enum val-0;
   enum val-1;
   enum val-2;
  }
  mandatory false;
 }
 leaf EMONTH {
  type enumeration {
   enum val-1;
   enum val-2;
   enum val-3;
   enum val-4;
   enum val-5;
   enum val-6;
   enum val-7;
   enum val-8;
   enum val-9;
   enum val-10;
   enum val-11;
   enum val-12;
  }
  mandatory false;
 }
 leaf ET {
  type hwat:HH_MM_SS_Time;
  mandatory false;
 }
 leaf EWEEK {
  type enumeration {
   enum val-1;
   enum val-2;
   enum val-3;
   enum val-4;
   enum val-5;
   enum val-6;
   enum val-7;
  }
  mandatory false;
 }
 leaf EWSEQ {
  type enumeration {
   enum val-0;
   enum val-1;
   enum val-2;
   enum val-3;
   enum val-4;
  }
  mandatory false;
 }
 leaf SDAY {
  type uint8 {
   range "1..31";
  }
  mandatory false;
 }
 leaf SM {
  type enumeration {
   enum val-0;
   enum val-1;
   enum val-2;
  }
  mandatory false;
 }
 leaf SMONTH {
  type enumeration {
   enum val-1;
   enum val-2;
   enum val-3;
   enum val-4;
   enum val-5;
   enum val-6;
   enum val-7;
   enum val-8;
   enum val-9;
   enum val-10;
   enum val-11;
   enum val-12;
  }
  mandatory false;
 }
 leaf ST {
  type hwat:HH_MM_SS_Time;
  mandatory false;
 }
 leaf SWEEK {
  type enumeration {
   enum val-1;
   enum val-2;
   enum val-3;
   enum val-4;
   enum val-5;
   enum val-6;
   enum val-7;
  }
  mandatory false;
 }
 leaf SWSEQ {
  type enumeration {
   enum val-0;
   enum val-1;
   enum val-2;
   enum val-3;
   enum val-4;
  }
  mandatory false;
 }
 leaf TIMEDIFF {
  type int16 {
   range "-720..840";
  }
  mandatory false;
 }
 leaf TO {
  type int8 {
   range "-120..120";
  }
  mandatory false;
 }
 leaf ZONET {
  type enumeration {
   enum val-0;
   enum val-4;
   enum val-8;
   enum val-10;
   enum val-12;
   enum val-16;
   enum val-20;
   enum val-24;
   enum val-28;
   enum val-30;
   enum val-32;
   enum val-34;
   enum val-36;
   enum val-40;
   enum val-44;
   enum val-48;
   enum val-52;
   enum val-56;
   enum val-60;
   enum val-62;
   enum val-64;
   enum val-66;
   enum val-68;
   enum val-70;
   enum val-71;
   enum val-72;
   enum val-74;
   enum val-76;
   enum val-80;
   enum val-83;
   enum val-84;
   enum val-86;
   enum val-88;
   enum val-90;
   enum val-92;
   enum val-94;
   enum val-96;
   enum val-99;
   enum val-100;
   enum val-104;
   enum val-200;
   enum val-1000;
   enum val-1004;
   enum val-1008;
   enum val-1010;
   enum val-1012;
   enum val-1016;
   enum val-1020;
   enum val-1024;
   enum val-1028;
   enum val-1030;
   enum val-1032;
   enum val-1034;
   enum val-1036;
   enum val-1040;
   enum val-1044;
   enum val-1048;
   enum val-1052;
   enum val-1056;
   enum val-1060;
   enum val-1062;
   enum val-1064;
   enum val-1066;
   enum val-1068;
   enum val-1070;
   enum val-1071;
   enum val-1072;
   enum val-1074;
   enum val-1076;
   enum val-1080;
   enum val-1083;
   enum val-1084;
   enum val-1086;
   enum val-1088;
   enum val-1090;
   enum val-1092;
   enum val-1094;
   enum val-1096;
   enum val-1099;
   enum val-1100;
   enum val-1104;
   enum val-1200;
  }
  mandatory false;
 }
 }
 grouping UDPSESSION-attributes {
 leaf CHECKCOUNT {
  type uint8 {
   range "3..10";
  }
  mandatory false;
 }
 leaf CN {
  type uint8 {
   range "0..7";
  }
  mandatory false;
 }
 leaf DSCP {
  type uint8 {
   range "0..63";
  }
  mandatory false;
 }
 leaf INTERVAL {
  type uint8 {
   range "1..60";
  }
  mandatory false;
 }
 leaf LOCALIP {
  type inet:ipv4-address;
  mandatory false;
 }
 leaf PEERIP {
  type inet:ipv4-address;
  mandatory false;
 }
 leaf SN {
  type uint8 {
   range "0..7";
  }
  mandatory false;
 }
 leaf SRN {
  type uint8 {
   range "0..1";
  }
  mandatory false;
 }
 leaf UDPSESSIONGRPID {
  type uint8 {
   range "0..1";
  }
  mandatory false;
 }
 leaf OLD_UDPSN {
  type union {
   type int32 {
    range "-1..65535";
   }
  }
  mandatory false;
 }
 leaf UDPSN {
  type union {
   type int32 {
    range "-1..65535";
   }
  }
  mandatory false;
 }
 }
 grouping UDT-attributes {
 leaf OLD_UDTNO {
  type union {
   type int16 {
    range "-1..255";
   }
  }
  mandatory false;
 }
 leaf UDTNO {
  type union {
   type int16 {
    range "-1..255";
   }
  }
  mandatory false;
 }
 leaf UDTPARAGRPID {
  type uint8 {
   range "0..48";
  }
  mandatory false;
 }
 }
 grouping UDTPARAGRP-attributes {
 leaf ACTFACTOR {
  type uint8 {
   range "0..100";
  }
  mandatory false;
 }
 leaf PRI {
  type uint8 {
   range "0..63";
  }
  mandatory false;
 }
 leaf PRIM2SECPTLOADRATH {
  type uint16 {
   range "0..1000";
  }
  mandatory false;
 }
 leaf PRIMPTLOADTH {
  type uint8 {
   range "0..100";
  }
  mandatory false;
 }
 leaf PRIMTRANRSCTYPE {
  type boolean;
  mandatory false;
 }
 leaf PRIRULE {
  type boolean;
  mandatory false;
 }
 leaf OLD_UDTPARAGRPID {
  type union {
   type int8 {
    range "-1..48";
   }
  }
  mandatory false;
 }
 leaf UDTPARAGRPID {
  type union {
   type int8 {
    range "-1..48";
   }
  }
  mandatory false;
 }
 }
 grouping ULFLOWCTRLPARA-attributes {
 leaf OLD_BEAR {
  type enumeration {
   enum val--1;
   enum val-0;
   enum val-1;
  }
  mandatory false;
 }
 leaf BEAR {
  type enumeration {
   enum val--1;
   enum val-0;
   enum val-1;
  }
  mandatory false;
 }
 leaf BWPRTSWITCH {
  type boolean;
  mandatory false;
 }
 leaf OLD_CN {
  type union {
   type int8 {
    range "-1..7";
   }
  }
  mandatory false;
 }
 leaf CN {
  type union {
   type int8 {
    range "-1..7";
   }
  }
  mandatory false;
 }
 leaf OLD_PN {
  type union {
   type int8 {
    range "-1..15";
   }
  }
  mandatory false;
 }
 leaf PN {
  type union {
   type int8 {
    range "-1..15";
   }
  }
  mandatory false;
 }
 leaf OLD_PT {
  type enumeration {
   enum val--1;
   enum val-0;
   enum val-1;
   enum val-5;
   enum val-6;
   enum val-10;
   enum val-12;
   enum val-13;
   enum val-14;
   enum val-15;
  }
  mandatory false;
 }
 leaf PT {
  type enumeration {
   enum val--1;
   enum val-0;
   enum val-1;
   enum val-5;
   enum val-6;
   enum val-10;
   enum val-12;
   enum val-13;
   enum val-14;
   enum val-15;
  }
  mandatory false;
 }
 leaf OLD_SBT {
  type enumeration {
   enum val--1;
   enum val-0;
   enum val-3;
   enum val-4;
   enum val-5;
  }
  mandatory false;
 }
 leaf SBT {
  type enumeration {
   enum val--1;
   enum val-0;
   enum val-3;
   enum val-4;
   enum val-5;
  }
  mandatory false;
 }
 leaf OLD_SN {
  type union {
   type int8 {
    range "-1..7";
   }
  }
  mandatory false;
 }
 leaf SN {
  type union {
   type int8 {
    range "-1..7";
   }
  }
  mandatory false;
 }
 leaf OLD_SRN {
  type union {
   type int8 {
    range "-1..1";
   }
  }
  mandatory false;
 }
 leaf SRN {
  type union {
   type int8 {
    range "-1..1";
   }
  }
  mandatory false;
 }
 leaf TNLCONGCTRLENHSW {
  type boolean;
  mandatory false;
 }
 leaf TNLCONGCTRLSWITCH {
  type boolean;
  mandatory false;
 }
 leaf ULIUBMINBW {
  type uint32 {
   range "0..1000000";
  }
  mandatory false;
 }
 }
 grouping UNILNK-attributes {
 leaf CN {
  type union {
   type int8 {
    range "-1..7";
   }
  }
  mandatory false;
 }
 leaf SBT {
  type enumeration {
   enum val--1;
   enum val-0;
   enum val-3;
   enum val-4;
  }
  mandatory false;
 }
 leaf SCRAM {
  type boolean;
  mandatory false;
 }
 leaf SN {
  type union {
   type int8 {
    range "-1..7";
   }
  }
  mandatory false;
 }
 leaf SRN {
  type union {
   type int8 {
    range "-1..1";
   }
  }
  mandatory false;
 }
 leaf TS16 {
  type boolean;
  mandatory false;
 }
 leaf UNILNKN {
  type union {
   type int8 {
    range "-1..7";
   }
  }
  mandatory false;
 }
 }
 grouping USERPLANEHOST-attributes {
 leaf FLAG {
  type boolean;
  mandatory false;
 }
 leaf IPSECSWITCH {
  type boolean;
  mandatory false;
 }
 leaf IPVERSION {
  type boolean;
  mandatory false;
 }
 leaf LOCIPV4 {
  type inet:ipv4-address;
  mandatory false;
 }
 leaf LOCIPV6 {
  type inet:ipv6-address;
  mandatory false;
 }
 leaf SECHOSTID {
  type uint16 {
   range "0..65535";
  }
  mandatory false;
 }
 leaf OLD_UPHOSTID {
  type union {
   type int32 {
    range "-1..65535";
   }
  }
  mandatory false;
 }
 leaf UPHOSTID {
  type union {
   type int32 {
    range "-1..65535";
   }
  }
  mandatory false;
 }
 leaf USERLABEL {
  type string {
   length "0..256";
  }
  mandatory false;
 }
 leaf VRFIDX {
  type uint8 {
   range "0..31";
  }
  mandatory false;
 }
 }
 grouping USERPLANEHOSTREF-attributes {
 leaf EPGROUPID {
  type union {
   type int32 {
    range "-1..65535";
   }
  }
  mandatory false;
 }
 leaf UPHOSTID {
  type union {
   type int32 {
    range "-1..65535";
   }
  }
  mandatory false;
 }
 }
 grouping USERPLANEPEER-attributes {
 leaf AUTOCFGFLAG {
  type boolean;
  mandatory false;
 }
 leaf CTRLMODE {
  type boolean;
  mandatory false;
 }
 leaf IPSECSWITCH {
  type boolean;
  mandatory false;
 }
 leaf IPVERSION {
  type boolean;
  mandatory false;
 }
 leaf PEERIPV4 {
  type inet:ipv4-address;
  mandatory false;
 }
 leaf PEERIPV6 {
  type inet:ipv6-address;
  mandatory false;
 }
 leaf REMOTEID {
  type string {
   length "0..127";
  }
  mandatory false;
 }
 leaf SECPEERID {
  type union {
   type uint32 {
    range "0..89999";
   }
  }
  mandatory false;
 }
 leaf STATICCHK {
  type enumeration {
   enum val-0;
   enum val-1;
   enum val-2;
  }
  mandatory false;
 }
 leaf OLD_UPPEERID {
  type union {
   type int32 {
    range "-1..79999";
   }
  }
  mandatory false;
 }
 leaf UPPEERID {
  type union {
   type int32 {
    range "-1..79999";
   }
  }
  mandatory false;
 }
 leaf USERLABEL {
  type string {
   length "0..256";
  }
  mandatory false;
 }
 leaf VRFIDX {
  type uint8 {
   range "0..31";
  }
  mandatory false;
 }
 }
 grouping USERPLANEPEERREF-attributes {
 leaf EPGROUPID {
  type union {
   type int32 {
    range "-1..65535";
   }
  }
  mandatory false;
 }
 leaf UPPEERID {
  type union {
   type int32 {
    range "-1..79999";
   }
  }
  mandatory false;
 }
 }
 grouping VETHPORT-attributes {
 leaf DEPLOYTYPE {
  type boolean;
  mandatory false;
 }
 leaf OLD_PORTID {
  type union {
   type int8 {
    range "-1..0";
   }
  }
  mandatory false;
 }
 leaf PORTID {
  type union {
   type int8 {
    range "-1..0";
   }
  }
  mandatory false;
 }
 leaf USERLABEL {
  type string {
   length "0..255";
  }
  mandatory false;
 }
 leaf VBIID {
  type uint8 {
   range "0";
  }
  mandatory false;
 }
 }
 grouping VLANCLASS-attributes {
 leaf OLD_SRVPRIO {
  type union {
   type int8 {
    range "-1..63";
   }
  }
  mandatory false;
 }
 leaf SRVPRIO {
  type union {
   type int8 {
    range "-1..63";
   }
  }
  mandatory false;
 }
 leaf OLD_TRAFFIC {
  type enumeration {
   enum val--1;
   enum val-0;
   enum val-1;
   enum val-3;
   enum val-4;
   enum val-5;
  }
  mandatory false;
 }
 leaf TRAFFIC {
  type enumeration {
   enum val--1;
   enum val-0;
   enum val-1;
   enum val-3;
   enum val-4;
   enum val-5;
  }
  mandatory false;
 }
 leaf OLD_VLANGROUPNO {
  type union {
   type int8 {
    range "-1..3";
   }
  }
  mandatory false;
 }
 leaf VLANGROUPNO {
  type union {
   type int8 {
    range "-1..3";
   }
  }
  mandatory false;
 }
 leaf VLANID {
  type uint16 {
   range "1..4094";
  }
  mandatory false;
 }
 leaf VLANPRIO {
  type uint8 {
   range "0..7";
  }
  mandatory false;
 }
 }
 grouping VLANMAP-attributes {
 leaf OLD_MASK {
  type inet:ipv4-address;
  mandatory false;
 }
 leaf MASK {
  type inet:ipv4-address;
  mandatory false;
 }
 leaf OLD_NEXTHOPIP {
  type inet:ipv4-address;
  mandatory false;
 }
 leaf NEXTHOPIP {
  type inet:ipv4-address;
  mandatory false;
 }
 leaf SETPRIO {
  type boolean;
  mandatory false;
 }
 leaf VLANGROUPNO {
  type uint8 {
   range "0..3";
  }
  mandatory false;
 }
 leaf VLANID {
  type uint16 {
   range "1..4094";
  }
  mandatory false;
 }
 leaf VLANMODE {
  type boolean;
  mandatory false;
 }
 leaf VLANPRIO {
  type uint8 {
   range "0..7";
  }
  mandatory false;
 }
 leaf OLD_VRFIDX {
  type union {
   type int8 {
    range "-1..7";
   }
  }
  mandatory false;
 }
 leaf VRFIDX {
  type union {
   type int8 {
    range "-1..7";
   }
  }
  mandatory false;
 }
 }
 grouping VRET-attributes {
 leaf CONNCN {
  type uint8 {
   range "0..62";
  }
  mandatory false;
 }
 leaf CONNSN {
  type uint8 {
   range "1..3";
  }
  mandatory false;
 }
 leaf CONNSRN {
  type uint8 {
   range "60..254";
  }
  mandatory false;
 }
 leaf DEVICENAME {
  type string {
   length "0..64";
  }
  mandatory false;
 }
 leaf DEVICENO {
  type union {
   type int16 {
    range "-1..254";
   }
  }
  mandatory false;
 }
 leaf SUBUNITQUANTITY {
  type uint8 {
   range "8";
  }
  mandatory false;
 }
 }
 grouping VRETSUBUNIT-attributes {
 leaf BEAMAZIMUTH {
  type union {
   type int16 {
    range "-300..32767";
   }
  }
  mandatory false;
 }
 leaf BEAMWIDTH {
  type union {
   type uint16 {
    range "330..65535";
   }
  }
  mandatory false;
 }
 leaf CONNCN {
  type uint8 {
   range "0..62";
  }
  mandatory false;
 }
 leaf CONNPN1 {
  type enumeration {
   enum val-0;
   enum val-1;
   enum val-2;
   enum val-3;
   enum val-16;
   enum val-17;
   enum val-18;
   enum val-19;
   enum val-32;
   enum val-33;
   enum val-34;
   enum val-35;
   enum val-48;
   enum val-49;
   enum val-50;
   enum val-51;
   enum val-64;
   enum val-65;
   enum val-66;
   enum val-67;
   enum val-80;
   enum val-81;
   enum val-82;
   enum val-83;
   enum val-96;
   enum val-97;
   enum val-98;
   enum val-99;
   enum val-112;
   enum val-113;
   enum val-114;
   enum val-115;
   enum val-255;
  }
  mandatory false;
 }
 leaf CONNPN2 {
  type enumeration {
   enum val-0;
   enum val-1;
   enum val-2;
   enum val-3;
   enum val-16;
   enum val-17;
   enum val-18;
   enum val-19;
   enum val-32;
   enum val-33;
   enum val-34;
   enum val-35;
   enum val-48;
   enum val-49;
   enum val-50;
   enum val-51;
   enum val-64;
   enum val-65;
   enum val-66;
   enum val-67;
   enum val-80;
   enum val-81;
   enum val-82;
   enum val-83;
   enum val-96;
   enum val-97;
   enum val-98;
   enum val-99;
   enum val-112;
   enum val-113;
   enum val-114;
   enum val-115;
   enum val-255;
  }
  mandatory false;
 }
 leaf CONNPN3 {
  type enumeration {
   enum val-0;
   enum val-1;
   enum val-2;
   enum val-3;
   enum val-16;
   enum val-17;
   enum val-18;
   enum val-19;
   enum val-32;
   enum val-33;
   enum val-34;
   enum val-35;
   enum val-48;
   enum val-49;
   enum val-50;
   enum val-51;
   enum val-64;
   enum val-65;
   enum val-66;
   enum val-67;
   enum val-80;
   enum val-81;
   enum val-82;
   enum val-83;
   enum val-96;
   enum val-97;
   enum val-98;
   enum val-99;
   enum val-112;
   enum val-113;
   enum val-114;
   enum val-115;
   enum val-255;
  }
  mandatory false;
 }
 leaf CONNPN4 {
  type enumeration {
   enum val-0;
   enum val-1;
   enum val-2;
   enum val-3;
   enum val-16;
   enum val-17;
   enum val-18;
   enum val-19;
   enum val-32;
   enum val-33;
   enum val-34;
   enum val-35;
   enum val-48;
   enum val-49;
   enum val-50;
   enum val-51;
   enum val-64;
   enum val-65;
   enum val-66;
   enum val-67;
   enum val-80;
   enum val-81;
   enum val-82;
   enum val-83;
   enum val-96;
   enum val-97;
   enum val-98;
   enum val-99;
   enum val-112;
   enum val-113;
   enum val-114;
   enum val-115;
   enum val-255;
  }
  mandatory false;
 }
 leaf CONNSN {
  type uint8 {
   range "1..3";
  }
  mandatory false;
 }
 leaf CONNSRN {
  type uint8 {
   range "60..254";
  }
  mandatory false;
 }
 leaf DEVICENO {
  type union {
   type int16 {
    range "-1..254";
   }
  }
  mandatory false;
 }
 leaf DLTILT {
  type union {
   type int16 {
    range "-150..32767";
   }
  }
  mandatory false;
 }
 leaf POLARTYPE1 {
  type enumeration {
   enum val-0;
   enum val-1;
   enum val-2;
   enum val-3;
   enum val-4;
   enum val-5;
   enum val-6;
  }
  mandatory false;
 }
 leaf POLARTYPE2 {
  type enumeration {
   enum val-0;
   enum val-1;
   enum val-2;
   enum val-3;
   enum val-4;
   enum val-5;
   enum val-6;
  }
  mandatory false;
 }
 leaf POLARTYPE3 {
  type enumeration {
   enum val-0;
   enum val-1;
   enum val-2;
   enum val-3;
   enum val-4;
   enum val-5;
   enum val-6;
  }
  mandatory false;
 }
 leaf POLARTYPE4 {
  type enumeration {
   enum val-0;
   enum val-1;
   enum val-2;
   enum val-3;
   enum val-4;
   enum val-5;
   enum val-6;
  }
  mandatory false;
 }
 leaf PORTNUM {
  type union {
   type uint8 {
    range "0..4";
   }
  }
  mandatory false;
 }
 leaf SUBNAME {
  type string {
   length "0..64";
  }
  mandatory false;
 }
 leaf SUBUNITNO {
  type union {
   type int8 {
    range "-1..8";
   }
  }
  mandatory false;
 }
 leaf ULTILT {
  type union {
   type int16 {
    range "-150..32767";
   }
  }
  mandatory false;
 }
 }
 grouping VRF-attributes {
 leaf IPSECVPNID {
  type uint8 {
   range "0..63";
  }
  mandatory false;
 }
 leaf IPSECVPNSW {
  type boolean;
  mandatory false;
 }
 leaf USERLABEL {
  type string {
   length "0..255";
  }
  mandatory false;
 }
 leaf OLD_VRFIDX {
  type union {
   type int8 {
    range "-1..31";
   }
  }
  mandatory false;
 }
 leaf VRFIDX {
  type union {
   type int8 {
    range "-1..31";
   }
  }
  mandatory false;
 }
 }
}
