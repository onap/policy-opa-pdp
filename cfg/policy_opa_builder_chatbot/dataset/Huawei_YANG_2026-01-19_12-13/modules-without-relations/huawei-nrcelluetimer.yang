module huawei-nrcelluetimer {
 yang-version 1.1;
 namespace "urn:rdns:com:huawei:oammodel:huawei-nrcelluetimer";
 prefix nrcelluetimer;
 description
 "Auto-generated modular YANG for huawei-nrcelluetimer" ;
 revision "2026-01-19" {
 description "Auto-generated initial revision. Generated at 2026-01-19 12:13.";
 }
 grouping NRCELLUETIMER-attributes {
 leaf DRXPREFERENCEPROHIBITTMR {
  type enumeration {
   enum val-1;
   enum val-2;
   enum val-3;
   enum val-4;
   enum val-5;
   enum val-6;
   enum val-7;
   enum val-8;
   enum val-9;
   enum val-10;
   enum val-11;
   enum val-12;
  }
  mandatory false;
 }
 leaf MAXMIMOLYRPREFPROHIBITTMR {
  type enumeration {
   enum val-0;
   enum val-1;
   enum val-2;
   enum val-3;
   enum val-4;
   enum val-5;
   enum val-6;
   enum val-7;
   enum val-8;
   enum val-9;
   enum val-10;
   enum val-11;
   enum val-12;
   enum val-13;
  }
  mandatory false;
 }
 leaf NRCELLID {
  type union {
   type int32 {
    range "-1..65534";
   }
  }
  mandatory false;
 }
 leaf OVERHEATINGINDPROHIBITTMR {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf T312 {
  type enumeration {
   enum val-0;
   enum val-1;
   enum val-2;
   enum val-3;
   enum val-4;
   enum val-5;
   enum val-6;
   enum val-7;
   enum val-255;
  }
  mandatory false;
 }
 }
}
