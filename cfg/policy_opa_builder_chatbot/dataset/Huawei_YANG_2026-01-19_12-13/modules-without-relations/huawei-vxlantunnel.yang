module huawei-vxlantunnel {
 yang-version 1.1;
 namespace "urn:rdns:com:huawei:oammodel:huawei-vxlantunnel";
 prefix vxlantunnel;
 description
 "Auto-generated modular YANG for huawei-vxlantunnel" ;
 revision "2026-01-19" {
 description "Auto-generated initial revision. Generated at 2026-01-19 12:13.";
 }
 grouping VXLANTUNNEL-attributes {
 leaf NVEPEERID {
  type uint16 {
   range "0..9999";
  }
  mandatory false;
 }
 leaf OLD_TUNNELID {
  type union {
   type int16 {
    range "-1..9999";
   }
  }
  mandatory false;
 }
 leaf TUNNELID {
  type union {
   type int16 {
    range "-1..9999";
   }
  }
  mandatory false;
 }
 leaf VXLANIDX {
  type uint16 {
   range "0..9999";
  }
  mandatory false;
 }
 }
}
