module huawei-cspccellsrsmeasncell {
 yang-version 1.1;
 namespace "urn:rdns:com:huawei:oammodel:huawei-cspccellsrsmeasncell";
 prefix cspccellsrsmeasncell;
 description
 "Auto-generated modular YANG for huawei-cspccellsrsmeasncell" ;
 revision "2026-01-19" {
 description "Auto-generated initial revision. Generated at 2026-01-19 12:13.";
 }
 grouping CSPCCELLSRSMEASNCELL-attributes {
 leaf OLD_CELLID {
  type union {
   type int16 {
    range "-1..255";
   }
  }
  mandatory false;
 }
 leaf CELLID {
  type union {
   type int16 {
    range "-1..255";
   }
  }
  mandatory false;
 }
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf OLD_NCELLENODEBID {
  type union {
   type int32 {
    range "-1..1048575";
   }
  }
  mandatory false;
 }
 leaf NCELLENODEBID {
  type union {
   type int32 {
    range "-1..1048575";
   }
  }
  mandatory false;
 }
 leaf OLD_NCELLID {
  type union {
   type int16 {
    range "-1..255";
   }
  }
  mandatory false;
 }
 leaf NCELLID {
  type union {
   type int16 {
    range "-1..255";
   }
  }
  mandatory false;
 }
 leaf OLD_NCELLMCC {
  type string {
   length "3";
  }
  mandatory false;
 }
 leaf NCELLMCC {
  type string {
   length "3";
  }
  mandatory false;
 }
 leaf OLD_NCELLMNC {
  type string {
   length "2..3";
  }
  mandatory false;
 }
 leaf NCELLMNC {
  type string {
   length "2..3";
  }
  mandatory false;
 }
 leaf OLD_ENODEBID {
  type union {
   type int32 {
    range "-1..1048575";
   }
  }
  mandatory false;
 }
 leaf ENODEBID {
  type union {
   type int32 {
    range "-1..1048575";
   }
  }
  mandatory false;
 }
 }
}
