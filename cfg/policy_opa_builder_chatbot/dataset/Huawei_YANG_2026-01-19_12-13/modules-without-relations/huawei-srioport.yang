module huawei-srioport {
 yang-version 1.1;
 namespace "urn:rdns:com:huawei:oammodel:huawei-srioport";
 prefix srioport;
 description
 "Auto-generated modular YANG for huawei-srioport" ;
 revision "2026-01-19" {
 description "Auto-generated initial revision. Generated at 2026-01-19 12:13.";
 }
 grouping SRIOPORT-attributes {
 leaf OLD_CN {
  type union {
   type int8 {
    range "-1..7";
   }
  }
  mandatory false;
 }
 leaf CN {
  type union {
   type int8 {
    range "-1..7";
   }
  }
  mandatory false;
 }
 leaf OLD_PN {
  type union {
   type int8 {
    range "-1..0";
   }
  }
  mandatory false;
 }
 leaf PN {
  type union {
   type int8 {
    range "-1..0";
   }
  }
  mandatory false;
 }
 leaf OLD_SN {
  type union {
   type int8 {
    range "-1..5";
   }
  }
  mandatory false;
 }
 leaf SN {
  type union {
   type int8 {
    range "-1..5";
   }
  }
  mandatory false;
 }
 leaf OLD_SRN {
  type union {
   type int8 {
    range "-1..1";
   }
  }
  mandatory false;
 }
 leaf SRN {
  type union {
   type int8 {
    range "-1..1";
   }
  }
  mandatory false;
 }
 }
}
