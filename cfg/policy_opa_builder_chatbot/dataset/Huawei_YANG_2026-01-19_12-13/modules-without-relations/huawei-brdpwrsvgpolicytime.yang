module huawei-brdpwrsvgpolicytime {
 yang-version 1.1;
 namespace "urn:rdns:com:huawei:oammodel:huawei-brdpwrsvgpolicytime";
 prefix brdpwrsvgpolicytime;
 import huawei-yang-types {
 prefix hwat;
 }
 description
 "Auto-generated modular YANG for huawei-brdpwrsvgpolicytime" ;
 revision "2026-01-19" {
 description "Auto-generated initial revision. Generated at 2026-01-19 12:13.";
 }
 grouping BRDPWRSVGPOLICYTIME-attributes {
 leaf MPPWRSVGTYPE {
  type enumeration {
   enum val-0;
   enum val-1;
   enum val-2;
  }
  mandatory false;
 }
 leaf OLD_POLICYID {
  type union {
   type int8 {
    range "-1..24";
   }
  }
  mandatory false;
 }
 leaf POLICYID {
  type union {
   type int8 {
    range "-1..24";
   }
  }
  mandatory false;
 }
 leaf STARTTIME {
  type hwat:HH_MM_SS_Time;
  mandatory false;
 }
 leaf STOPTIME {
  type hwat:HH_MM_SS_Time;
  mandatory false;
 }
 leaf OLD_TIMEID {
  type union {
   type int8 {
    range "-1..48";
   }
  }
  mandatory false;
 }
 leaf TIMEID {
  type union {
   type int8 {
    range "-1..48";
   }
  }
  mandatory false;
 }
 }
}
