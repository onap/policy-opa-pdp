module huawei-extconnport {
 yang-version 1.1;
 namespace "urn:rdns:com:huawei:oammodel:huawei-extconnport";
 prefix extconnport;
 description
 "Auto-generated modular YANG for huawei-extconnport" ;
 revision "2026-01-19" {
 description "Auto-generated initial revision. Generated at 2026-01-19 12:13.";
 }
 grouping EXTCONNPORT-attributes {
 leaf CN {
  type uint8 {
   range "0..7";
  }
  mandatory false;
 }
 leaf PN {
  type uint8 {
   range "0..5";
  }
  mandatory false;
 }
 leaf OLD_PORTID {
  type union {
   type int32 {
    range "-1..65535";
   }
  }
  mandatory false;
 }
 leaf PORTID {
  type union {
   type int32 {
    range "-1..65535";
   }
  }
  mandatory false;
 }
 leaf PT {
  type enumeration {
   enum val-5;
   enum val-8;
  }
  mandatory false;
 }
 leaf RATE {
  type enumeration {
   enum val-6;
   enum val-12;
   enum val-255;
  }
  mandatory false;
 }
 leaf SN {
  type uint8 {
   range "0..5";
  }
  mandatory false;
 }
 leaf SRN {
  type uint8 {
   range "0..1";
  }
  mandatory false;
 }
 leaf SUBPN {
  type union {
   type uint8 {
    range "0..255";
   }
  }
  mandatory false;
 }
 }
}
