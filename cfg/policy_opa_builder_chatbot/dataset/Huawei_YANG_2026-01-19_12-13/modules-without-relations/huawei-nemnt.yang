module huawei-nemnt {
 yang-version 1.1;
 namespace "urn:rdns:com:huawei:oammodel:huawei-nemnt";
 prefix nemnt;
 import huawei-yang-types {
 prefix hwat;
 }
 description
 "Auto-generated modular YANG for huawei-nemnt" ;
 revision "2026-01-19" {
 description "Auto-generated initial revision. Generated at 2026-01-19 12:13.";
 }
 grouping NEMNT-attributes {
 leaf ET {
  type hwat:yyyy_mm_dd_HH_MM_SS_Time;
  mandatory false;
 }
 leaf MMSETREMARK {
  type string {
   length "0..255";
  }
  mandatory false;
 }
 leaf MNTMODE {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf ST {
  type hwat:yyyy_mm_dd_HH_MM_SS_Time;
  mandatory false;
 }
 }
}
