module huawei-gnbuediffconfig {
 yang-version 1.1;
 namespace "urn:rdns:com:huawei:oammodel:huawei-gnbuediffconfig";
 prefix gnbuediffconfig;
 description
 "Auto-generated modular YANG for huawei-gnbuediffconfig" ;
 revision "2026-01-19" {
 description "Auto-generated initial revision. Generated at 2026-01-19 12:13.";
 }
 grouping GNBUEDIFFCONFIG-attributes {
 leaf IMEIBWP1TOBWP2DLTHPTTHLD {
  type uint16 {
   range "0..50000";
  }
  mandatory false;
 }
 leaf IMEIBWP1TOBWP2ULTHPTTHLD {
  type uint16 {
   range "0..50000";
  }
  mandatory false;
 }
 leaf IMEIDLSTTRANSITBUFVOLTHLD {
  type union {
   type uint16 {
    range "1..65535";
   }
  }
  mandatory false;
 }
 leaf SERVICEDIFFALGOSWITCH {
  type string;
  mandatory false;
 }
 leaf UEINFOINDEX {
  type union {
   type int16 {
    range "-1..128";
   }
  }
  mandatory false;
 }
 }
}
