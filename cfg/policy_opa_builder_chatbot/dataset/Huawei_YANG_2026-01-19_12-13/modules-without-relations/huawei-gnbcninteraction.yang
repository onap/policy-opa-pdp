module huawei-gnbcninteraction {
 yang-version 1.1;
 namespace "urn:rdns:com:huawei:oammodel:huawei-gnbcninteraction";
 prefix gnbcninteraction;
 description
 "Auto-generated modular YANG for huawei-gnbcninteraction" ;
 revision "2026-01-19" {
 description "Auto-generated initial revision. Generated at 2026-01-19 12:13.";
 }
 grouping GNBCNINTERACTION-attributes {
 leaf DEFAULTPAGINGDRX {
  type enumeration {
   enum val-0;
   enum val-1;
   enum val-2;
   enum val-3;
  }
  mandatory false;
 }
 }
}
