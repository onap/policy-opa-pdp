module huawei-raesubunit {
 yang-version 1.1;
 namespace "urn:rdns:com:huawei:oammodel:huawei-raesubunit";
 prefix raesubunit;
 description
 "Auto-generated modular YANG for huawei-raesubunit" ;
 revision "2026-01-19" {
 description "Auto-generated initial revision. Generated at 2026-01-19 12:13.";
 }
 grouping RAESUBUNIT-attributes {
 leaf CONNCN {
  type union {
   type uint8 {
    range "0..255";
   }
  }
  mandatory false;
 }
 leaf CONNSN {
  type union {
   type uint8 {
    range "0..255";
   }
  }
  mandatory false;
 }
 leaf CONNSRN {
  type union {
   type uint8 {
    range "4..255";
   }
  }
  mandatory false;
 }
 leaf DEVICENO {
  type union {
   type int16 {
    range "-1..1023";
   }
  }
  mandatory false;
 }
 leaf SUBNAME {
  type string {
   length "0..83";
  }
  mandatory false;
 }
 leaf SUBUNITNO {
  type union {
   type int8 {
    range "-1..6";
   }
  }
  mandatory false;
 }
 }
}
