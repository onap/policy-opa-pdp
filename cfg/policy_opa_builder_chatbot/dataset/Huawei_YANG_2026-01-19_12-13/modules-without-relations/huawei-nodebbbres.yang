module huawei-nodebbbres {
 yang-version 1.1;
 namespace "urn:rdns:com:huawei:oammodel:huawei-nodebbbres";
 prefix nodebbbres;
 description
 "Auto-generated modular YANG for huawei-nodebbbres" ;
 revision "2026-01-19" {
 description "Auto-generated initial revision. Generated at 2026-01-19 12:13.";
 }
 grouping NODEBBBRES-attributes {
 leaf ADMSTATE {
  type boolean;
  mandatory false;
 }
 leaf CAPACITY {
  type enumeration {
   enum val-0;
   enum val-1;
   enum val-2;
  }
  mandatory false;
 }
 leaf CN {
  type uint8 {
   range "0..7";
  }
  mandatory false;
 }
 leaf HCE {
  type enumeration {
   enum val-0;
   enum val-16;
   enum val-255;
  }
  mandatory false;
 }
 leaf OLD_NODEBBBRESID {
  type union {
   type int64 {
    range "-1..4294967295";
   }
  }
  mandatory false;
 }
 leaf NODEBBBRESID {
  type union {
   type int64 {
    range "-1..4294967295";
   }
  }
  mandatory false;
 }
 leaf SN {
  type uint8 {
   range "0..6";
  }
  mandatory false;
 }
 leaf SRN {
  type uint8 {
   range "0..1";
  }
  mandatory false;
 }
 }
}
