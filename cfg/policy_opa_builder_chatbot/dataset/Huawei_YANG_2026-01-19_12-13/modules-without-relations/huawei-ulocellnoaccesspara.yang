module huawei-ulocellnoaccesspara {
 yang-version 1.1;
 namespace "urn:rdns:com:huawei:oammodel:huawei-ulocellnoaccesspara";
 prefix ulocellnoaccesspara;
 description
 "Auto-generated modular YANG for huawei-ulocellnoaccesspara" ;
 revision "2026-01-19" {
 description "Auto-generated initial revision. Generated at 2026-01-19 12:13.";
 }
 grouping ULOCELLNOACCESSPARA-attributes {
 leaf AUTORCVRMTHD {
  type enumeration {
   enum val-0;
   enum val-1;
   enum val-2;
   enum val-5;
   enum val-6;
  }
  mandatory false;
 }
 leaf NOFSTRLTIMER {
  type uint8 {
   range "0..72";
  }
  mandatory false;
 }
 leaf NOUETIMER {
  type uint8 {
   range "0..72";
  }
  mandatory false;
 }
 leaf ULOCELLID {
  type union {
   type int32 {
    range "-1..268435455";
   }
  }
  mandatory false;
 }
 }
}
