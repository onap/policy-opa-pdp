module huawei-nrducellmbsmulticast {
 yang-version 1.1;
 namespace "urn:rdns:com:huawei:oammodel:huawei-nrducellmbsmulticast";
 prefix nrducellmbsmulticast;
 description
 "Auto-generated modular YANG for huawei-nrducellmbsmulticast" ;
 revision "2026-01-19" {
 description "Auto-generated initial revision. Generated at 2026-01-19 12:13.";
 }
 grouping NRDUCELLMBSMULTICAST-attributes {
 leaf MBSMULTICASTADMITTHLD {
  type uint8 {
   range "0..50";
  }
  mandatory false;
 }
 leaf MBSMULTICASTMAXPWROFFSET {
  type int8 {
   range "-3..3";
  }
  mandatory false;
 }
 leaf MCS {
  type uint8 {
   range "0..28";
  }
  mandatory false;
 }
 leaf NRDUCELLID {
  type union {
   type int32 {
    range "-1..65534";
   }
  }
  mandatory false;
 }
 }
}
