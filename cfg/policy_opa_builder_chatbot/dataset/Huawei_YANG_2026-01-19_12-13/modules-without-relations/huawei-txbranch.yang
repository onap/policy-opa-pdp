module huawei-txbranch {
 yang-version 1.1;
 namespace "urn:rdns:com:huawei:oammodel:huawei-txbranch";
 prefix txbranch;
 description
 "Auto-generated modular YANG for huawei-txbranch" ;
 revision "2026-01-19" {
 description "Auto-generated initial revision. Generated at 2026-01-19 12:13.";
 }
 grouping TXBRANCH-attributes {
 leaf AUTHDLFREQRANGENO {
  type string;
  mandatory false;
 }
 leaf CN {
  type union {
   type int8 {
    range "-1..62";
   }
  }
  mandatory false;
 }
 leaf SN {
  type union {
   type int8 {
    range "-1..8";
   }
  }
  mandatory false;
 }
 leaf SRN {
  type union {
   type int16 {
    range "-1..254";
   }
  }
  mandatory false;
 }
 leaf TXNO {
  type union {
   type int8 {
    range "-1..63";
   }
  }
  mandatory false;
 }
 leaf TXSW {
  type enumeration {
   enum val-0;
   enum val-1;
   enum val-255;
  }
  mandatory false;
 }
 }
}
