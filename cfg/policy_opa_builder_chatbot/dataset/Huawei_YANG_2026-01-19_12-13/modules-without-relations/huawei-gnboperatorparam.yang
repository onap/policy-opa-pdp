module huawei-gnboperatorparam {
 yang-version 1.1;
 namespace "urn:rdns:com:huawei:oammodel:huawei-gnboperatorparam";
 prefix gnboperatorparam;
 description
 "Auto-generated modular YANG for huawei-gnboperatorparam" ;
 revision "2026-01-19" {
 description "Auto-generated initial revision. Generated at 2026-01-19 12:13.";
 }
 grouping GNBOPERATORPARAM-attributes {
 leaf EMCBEARERARP {
  type uint8 {
   range "1..15";
  }
  mandatory false;
 }
 leaf OPERATORID {
  type union {
   type int8 {
    range "-1..11";
   }
  }
  mandatory false;
 }
 }
}
