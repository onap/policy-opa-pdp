module huawei-vxlan {
 yang-version 1.1;
 namespace "urn:rdns:com:huawei:oammodel:huawei-vxlan";
 prefix vxlan;
 description
 "Auto-generated modular YANG for huawei-vxlan" ;
 revision "2026-01-19" {
 description "Auto-generated initial revision. Generated at 2026-01-19 12:13.";
 }
 grouping VXLAN-attributes {
 leaf NVEID {
  type uint8 {
   range "0..31";
  }
  mandatory false;
 }
 leaf VLANTEMPLATEID {
  type uint8 {
   range "0..31";
  }
  mandatory false;
 }
 leaf VNI {
  type uint32 {
   range "1..16777215";
  }
  mandatory false;
 }
 leaf OLD_VXLANIDX {
  type union {
   type int16 {
    range "-1..9999";
   }
  }
  mandatory false;
 }
 leaf VXLANIDX {
  type union {
   type int16 {
    range "-1..9999";
   }
  }
  mandatory false;
 }
 }
}
