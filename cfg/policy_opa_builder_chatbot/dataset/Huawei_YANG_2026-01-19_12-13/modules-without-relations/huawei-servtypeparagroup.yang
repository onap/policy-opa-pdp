module huawei-servtypeparagroup {
 yang-version 1.1;
 namespace "urn:rdns:com:huawei:oammodel:huawei-servtypeparagroup";
 prefix servtypeparagroup;
 description
 "Auto-generated modular YANG for huawei-servtypeparagroup" ;
 revision "2026-01-19" {
 description "Auto-generated initial revision. Generated at 2026-01-19 12:13.";
 }
 grouping SERVTYPEPARAGROUP-attributes {
 leaf DLDATAVOLUMELOWERTHLD {
  type uint16 {
   range "0..65535";
  }
  mandatory false;
 }
 leaf DLDATAVOLUMEUPPERTHLD {
  type uint16 {
   range "0..65535";
  }
  mandatory false;
 }
 leaf OLD_SERVTYPEPARAGROUPID {
  type union {
   type int8 {
    range "-1..10";
   }
  }
  mandatory false;
 }
 leaf SERVTYPEPARAGROUPID {
  type union {
   type int8 {
    range "-1..10";
   }
  }
  mandatory false;
 }
 leaf SERVICETYPELABEL {
  type string {
   length "0..99";
  }
  mandatory false;
 }
 leaf ULDATAVOLUMELOWERTHLD {
  type uint16 {
   range "0..65535";
  }
  mandatory false;
 }
 leaf ULDATAVOLUMEUPPERTHLD {
  type uint16 {
   range "0..65535";
  }
  mandatory false;
 }
 }
}
