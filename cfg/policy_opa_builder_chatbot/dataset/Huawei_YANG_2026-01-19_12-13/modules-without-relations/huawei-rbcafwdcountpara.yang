module huawei-rbcafwdcountpara {
 yang-version 1.1;
 namespace "urn:rdns:com:huawei:oammodel:huawei-rbcafwdcountpara";
 prefix rbcafwdcountpara;
 description
 "Auto-generated modular YANG for huawei-rbcafwdcountpara" ;
 revision "2026-01-19" {
 description "Auto-generated initial revision. Generated at 2026-01-19 12:13.";
 }
 grouping RBCAFWDCOUNTPARA-attributes {
 leaf OLD_FWDCOUNTERINDEX {
  type union {
   type int8 {
    range "-1..8";
   }
  }
  mandatory false;
 }
 leaf FWDCOUNTERINDEX {
  type union {
   type int8 {
    range "-1..8";
   }
  }
  mandatory false;
 }
 leaf PCCMCC {
  type string {
   length "3";
  }
  mandatory false;
 }
 leaf PCCMNC {
  type string {
   length "2..3";
  }
  mandatory false;
 }
 leaf SCCMCC {
  type string {
   length "3";
  }
  mandatory false;
 }
 leaf SCCMNC {
  type string {
   length "2..3";
  }
  mandatory false;
 }
 }
}
