module huawei-psuis {
 yang-version 1.1;
 namespace "urn:rdns:com:huawei:oammodel:huawei-psuis";
 prefix psuis;
 description
 "Auto-generated modular YANG for huawei-psuis" ;
 revision "2026-01-19" {
 description "Auto-generated initial revision. Generated at 2026-01-19 12:13.";
 }
 grouping PSUIS-attributes {
 leaf PSUISS {
  type boolean;
  mandatory false;
 }
 }
}
