module huawei-ftpclt {
 yang-version 1.1;
 namespace "urn:rdns:com:huawei:oammodel:huawei-ftpclt";
 prefix ftpclt;
 description
 "Auto-generated modular YANG for huawei-ftpclt" ;
 revision "2026-01-19" {
 description "Auto-generated initial revision. Generated at 2026-01-19 12:13.";
 }
 grouping FTPCLT-attributes {
 leaf ENCRYMODE {
  type enumeration {
   enum val-1;
   enum val-2;
  }
  mandatory false;
 }
 leaf MINDHLEN {
  type enumeration {
   enum val-0;
   enum val-512;
   enum val-1024;
   enum val-2048;
   enum val-3072;
   enum val-4096;
  }
  mandatory false;
 }
 leaf POLICYID {
  type uint8 {
   range "0..16";
  }
  mandatory false;
 }
 leaf SPTSTATEFWL {
  type boolean;
  mandatory false;
 }
 leaf SSLCERTAUTH {
  type boolean;
  mandatory false;
 }
 leaf TLSSECCSSW {
  type boolean;
  mandatory false;
 }
 leaf TRUSTGROUPID {
  type union {
   type uint16 {
    range "0..65535";
   }
  }
  mandatory false;
 }
 }
}
