module huawei-lansw {
 yang-version 1.1;
 namespace "urn:rdns:com:huawei:oammodel:huawei-lansw";
 prefix lansw;
 description
 "Auto-generated modular YANG for huawei-lansw" ;
 revision "2026-01-19" {
 description "Auto-generated initial revision. Generated at 2026-01-19 12:13.";
 }
 grouping LANSW-attributes {
 leaf BCPKTRATETHD {
  type uint8 {
   range "50..200";
  }
  mandatory false;
 }
 leaf DYNAMICMACLRNSW {
  type boolean;
  mandatory false;
 }
 leaf MACAGINGTIME {
  type uint8 {
   range "5..30";
  }
  mandatory false;
 }
 leaf SRCMACATTACKALMTHD {
  type uint16 {
   range "1..1000";
  }
  mandatory false;
 }
 leaf SRCMACATTACKCHKSW {
  type boolean;
  mandatory false;
 }
 }
}
