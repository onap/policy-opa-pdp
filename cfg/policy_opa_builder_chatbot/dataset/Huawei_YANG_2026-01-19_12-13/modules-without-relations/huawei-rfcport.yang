module huawei-rfcport {
 yang-version 1.1;
 namespace "urn:rdns:com:huawei:oammodel:huawei-rfcport";
 prefix rfcport;
 description
 "Auto-generated modular YANG for huawei-rfcport" ;
 revision "2026-01-19" {
 description "Auto-generated initial revision. Generated at 2026-01-19 12:13.";
 }
 grouping RFCPORT-attributes {
 leaf CN {
  type union {
   type int8 {
    range "-1..7";
   }
  }
  mandatory false;
 }
 leaf DLSWITCH {
  type boolean;
  mandatory false;
 }
 leaf PN {
  type union {
   type int8 {
    range "-1..9";
   }
  }
  mandatory false;
 }
 leaf PWRATTENUATION {
  type int16 {
   range "-150..0";
  }
  mandatory false;
 }
 leaf SN {
  type union {
   type int8 {
    range "-1..5";
   }
  }
  mandatory false;
 }
 leaf SRN {
  type union {
   type int8 {
    range "-1..1";
   }
  }
  mandatory false;
 }
 leaf ULGAINADJUSTMENT {
  type int16 {
   range "-200..0";
  }
  mandatory false;
 }
 leaf ULSWITCH {
  type boolean;
  mandatory false;
 }
 }
}
