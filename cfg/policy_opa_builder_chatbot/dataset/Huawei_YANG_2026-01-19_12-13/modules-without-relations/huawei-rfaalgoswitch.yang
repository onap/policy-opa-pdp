module huawei-rfaalgoswitch {
 yang-version 1.1;
 namespace "urn:rdns:com:huawei:oammodel:huawei-rfaalgoswitch";
 prefix rfaalgoswitch;
 description
 "Auto-generated modular YANG for huawei-rfaalgoswitch" ;
 revision "2026-01-19" {
 description "Auto-generated initial revision. Generated at 2026-01-19 12:13.";
 }
 grouping RFAALGOSWITCH-attributes {
 leaf ALARMSWITCH {
  type string;
  mandatory false;
 }
 leaf DELAYALIGNMENTSWITCH {
  type boolean;
  mandatory false;
 }
 leaf HRRUENHANCECOMPRESSION {
  type boolean;
  mandatory false;
 }
 leaf NRTDDCPRICOMPRESSIONOPT {
  type boolean;
  mandatory false;
 }
 leaf RFANRTDDCOMPRESSION {
  type enumeration {
   enum val-0;
   enum val-1;
   enum val-3;
  }
  mandatory false;
 }
 leaf TDDDELAYOPT {
  type boolean;
  mandatory false;
 }
 }
}
