module huawei-gnbflexcounterobjcfg {
 yang-version 1.1;
 namespace "urn:rdns:com:huawei:oammodel:huawei-gnbflexcounterobjcfg";
 prefix gnbflexcounterobjcfg;
 description
 "Auto-generated modular YANG for huawei-gnbflexcounterobjcfg" ;
 revision "2026-01-19" {
 description "Auto-generated initial revision. Generated at 2026-01-19 12:13.";
 }
 grouping GNBFLEXCOUNTEROBJCFG-attributes {
 leaf ARP {
  type union {
   type uint8 {
    range "1..255";
   }
  }
  mandatory false;
 }
 leaf OLD_FLEXCOUNTEROBJID {
  type union {
   type int8 {
    range "-1..29";
   }
  }
  mandatory false;
 }
 leaf FLEXCOUNTEROBJID {
  type union {
   type int8 {
    range "-1..29";
   }
  }
  mandatory false;
 }
 leaf OLD_FLEXCOUNTEROBJTYPE {
  type enumeration {
   enum val--1;
   enum val-0;
   enum val-1;
  }
  mandatory false;
 }
 leaf FLEXCOUNTEROBJTYPE {
  type enumeration {
   enum val--1;
   enum val-0;
   enum val-1;
  }
  mandatory false;
 }
 leaf NR5QI {
  type union {
   type uint16 {
    range "0..65535";
   }
  }
  mandatory false;
 }
 leaf OPERATORID {
  type union {
   type uint8 {
    range "0..255";
   }
  }
  mandatory false;
 }
 leaf QCI {
  type union {
   type uint16 {
    range "0..65535";
   }
  }
  mandatory false;
 }
 leaf QCIVALIDPOLICY {
  type enumeration {
   enum val-0;
   enum val-1;
   enum val-2;
  }
  mandatory false;
 }
 leaf RFSPINDEX {
  type union {
   type uint16 {
    range "1..65535";
   }
  }
  mandatory false;
 }
 }
}
