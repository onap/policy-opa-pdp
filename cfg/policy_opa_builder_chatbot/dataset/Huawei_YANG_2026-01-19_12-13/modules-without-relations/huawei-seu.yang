module huawei-seu {
 yang-version 1.1;
 namespace "urn:rdns:com:huawei:oammodel:huawei-seu";
 prefix seu;
 description
 "Auto-generated modular YANG for huawei-seu" ;
 revision "2026-01-19" {
 description "Auto-generated initial revision. Generated at 2026-01-19 12:13.";
 }
 grouping SEU-attributes {
 leaf OLD_CN {
  type union {
   type int8 {
    range "-1..7";
   }
  }
  mandatory false;
 }
 leaf CN {
  type union {
   type int8 {
    range "-1..7";
   }
  }
  mandatory false;
 }
 leaf OVERLOADALMCLRTHLD {
  type uint8 {
   range "0..100";
  }
  mandatory false;
 }
 leaf OVERLOADALMRPTTHLD {
  type uint8 {
   range "0..100";
  }
  mandatory false;
 }
 leaf SEUWM {
  type enumeration {
   enum val-0;
   enum val-1;
   enum val-2;
  }
  mandatory false;
 }
 leaf OLD_SN {
  type union {
   type int8 {
    range "-1..5";
   }
  }
  mandatory false;
 }
 leaf SN {
  type union {
   type int8 {
    range "-1..5";
   }
  }
  mandatory false;
 }
 leaf OLD_SRN {
  type union {
   type int8 {
    range "-1..1";
   }
  }
  mandatory false;
 }
 leaf SRN {
  type union {
   type int8 {
    range "-1..1";
   }
  }
  mandatory false;
 }
 leaf TYPE {
  type enumeration {
   enum val-217;
   enum val-218;
   enum val-219;
  }
  mandatory false;
 }
 }
}
