module huawei-gnbuuinteraction {
 yang-version 1.1;
 namespace "urn:rdns:com:huawei:oammodel:huawei-gnbuuinteraction";
 prefix gnbuuinteraction;
 description
 "Auto-generated modular YANG for huawei-gnbuuinteraction" ;
 revision "2026-01-19" {
 description "Auto-generated initial revision. Generated at 2026-01-19 12:13.";
 }
 grouping GNBUUINTERACTION-attributes {
 leaf RANPAGINGTIMER {
  type uint8 {
   range "30..200";
  }
  mandatory false;
 }
 leaf UECAPBPROCSWITCH {
  type string;
  mandatory false;
 }
 }
}
