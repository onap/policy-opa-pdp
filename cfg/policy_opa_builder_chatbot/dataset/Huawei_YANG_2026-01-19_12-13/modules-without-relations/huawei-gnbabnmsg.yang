module huawei-gnbabnmsg {
 yang-version 1.1;
 namespace "urn:rdns:com:huawei:oammodel:huawei-gnbabnmsg";
 prefix gnbabnmsg;
 description
 "Auto-generated modular YANG for huawei-gnbabnmsg" ;
 revision "2026-01-19" {
 description "Auto-generated initial revision. Generated at 2026-01-19 12:13.";
 }
 grouping GNBABNMSG-attributes {
 leaf MSGMATCHRULELIST {
  type string {
   length "0..20";
  }
  mandatory false;
 }
 leaf MSGMODIFYRULELIST {
  type string {
   length "0..20";
  }
  mandatory false;
 }
 leaf MSGOPTYPE {
  type boolean;
  mandatory false;
 }
 leaf MSGPROTOCOLTYPE {
  type enumeration {
   enum val-0;
   enum val-1;
   enum val-2;
   enum val-5;
   enum val-6;
   enum val-7;
   enum val-8;
  }
  mandatory false;
 }
 leaf MSGTYPE {
  type uint16 {
   range "0..65535";
  }
  mandatory false;
 }
 leaf PROTOCOLIEID {
  type uint16 {
   range "0..65535";
  }
  mandatory false;
 }
 leaf OLD_RULEINDEX {
  type union {
   type int8 {
    range "-1..49";
   }
  }
  mandatory false;
 }
 leaf RULEINDEX {
  type union {
   type int8 {
    range "-1..49";
   }
  }
  mandatory false;
 }
 leaf UEINFOINDEX {
  type uint8 {
   range "0..128";
  }
  mandatory false;
 }
 }
}
