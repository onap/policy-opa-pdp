module huawei-cfmmep {
 yang-version 1.1;
 namespace "urn:rdns:com:huawei:oammodel:huawei-cfmmep";
 prefix cfmmep;
 description
 "Auto-generated modular YANG for huawei-cfmmep" ;
 revision "2026-01-19" {
 description "Auto-generated initial revision. Generated at 2026-01-19 12:13.";
 }
 grouping CFMMEP-attributes {
 leaf CCSW {
  type boolean;
  mandatory false;
 }
 leaf CN {
  type uint8 {
   range "0..7";
  }
  mandatory false;
 }
 leaf OLD_MANAME {
  type string {
   length "1..43";
  }
  mandatory false;
 }
 leaf MANAME {
  type string {
   length "1..43";
  }
  mandatory false;
 }
 leaf OLD_MDNAME {
  type string {
   length "1..43";
  }
  mandatory false;
 }
 leaf MDNAME {
  type string {
   length "1..43";
  }
  mandatory false;
 }
 leaf OLD_MEPID {
  type union {
   type int16 {
    range "-1..8191";
   }
  }
  mandatory false;
 }
 leaf MEPID {
  type union {
   type int16 {
    range "-1..8191";
   }
  }
  mandatory false;
 }
 leaf PN {
  type uint8 {
   range "0..5";
  }
  mandatory false;
 }
 leaf PT {
  type enumeration {
   enum val-3;
   enum val-4;
  }
  mandatory false;
 }
 leaf SBT {
  type enumeration {
   enum val-0;
   enum val-5;
  }
  mandatory false;
 }
 leaf SN {
  type uint8 {
   range "0..7";
  }
  mandatory false;
 }
 leaf SRN {
  type uint8 {
   range "0..1";
  }
  mandatory false;
 }
 }
}
