module huawei-anrmeasureparam {
 yang-version 1.1;
 namespace "urn:rdns:com:huawei:oammodel:huawei-anrmeasureparam";
 prefix anrmeasureparam;
 description
 "Auto-generated modular YANG for huawei-anrmeasureparam" ;
 revision "2026-01-19" {
 description "Auto-generated initial revision. Generated at 2026-01-19 12:13.";
 }
 grouping ANRMEASUREPARAM-attributes {
 leaf A3HYSTFORANR {
  type uint8 {
   range "0..30";
  }
  mandatory false;
 }
 leaf A3OFFSETFORANR {
  type int8 {
   range "-30..30";
  }
  mandatory false;
 }
 leaf A3TIMETOTRIGFORANR {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf A4HYSTFORANR {
  type uint8 {
   range "0..30";
  }
  mandatory false;
 }
 leaf A4THDRSRPFORANR {
  type int16 {
   range "-141..-43";
  }
  mandatory false;
 }
 leaf A4TIMETOTRIGFORANR {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 }
}
