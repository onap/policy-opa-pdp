module huawei-glocellrsvdpara {
 yang-version 1.1;
 namespace "urn:rdns:com:huawei:oammodel:huawei-glocellrsvdpara";
 prefix glocellrsvdpara;
 description
 "Auto-generated modular YANG for huawei-glocellrsvdpara" ;
 revision "2026-01-19" {
 description "Auto-generated initial revision. Generated at 2026-01-19 12:13.";
 }
 grouping GLOCELLRSVDPARA-attributes {
 leaf GLOCELLID {
  type union {
   type int32 {
    range "-1..268435455";
   }
  }
  mandatory false;
 }
 leaf GLOCELLRSVDPARA1 {
  type uint32 {
   range "0..4294967295";
  }
  mandatory false;
 }
 leaf GLOCELLRSVDPARA2 {
  type uint32 {
   range "0..4294967295";
  }
  mandatory false;
 }
 leaf GLOCELLRSVDPARA3 {
  type uint32 {
   range "0..4294967295";
  }
  mandatory false;
 }
 leaf GLOCELLRSVDPARA4 {
  type uint32 {
   range "0..4294967295";
  }
  mandatory false;
 }
 leaf GLOCELLRSVDPARA5 {
  type uint32 {
   range "0..4294967295";
  }
  mandatory false;
 }
 leaf GLOCELLRSVDPARA6 {
  type uint32 {
   range "0..4294967295";
  }
  mandatory false;
 }
 }
}
