module huawei-enodebustraceidcfg {
 yang-version 1.1;
 namespace "urn:rdns:com:huawei:oammodel:huawei-enodebustraceidcfg";
 prefix enodebustraceidcfg;
 description
 "Auto-generated modular YANG for huawei-enodebustraceidcfg" ;
 revision "2026-01-19" {
 description "Auto-generated initial revision. Generated at 2026-01-19 12:13.";
 }
 grouping ENODEBUSTRACEIDCFG-attributes {
 leaf USTRACEID {
  type uint32 {
   range "0..4294967295";
  }
  mandatory false;
 }
 leaf OLD_USTRACEIDINDEX {
  type union {
   type int8 {
    range "-1..23";
   }
  }
  mandatory false;
 }
 leaf USTRACEIDINDEX {
  type union {
   type int8 {
    range "-1..23";
   }
  }
  mandatory false;
 }
 }
}
