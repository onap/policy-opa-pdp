module huawei-weblmt {
 yang-version 1.1;
 namespace "urn:rdns:com:huawei:oammodel:huawei-weblmt";
 prefix weblmt;
 description
 "Auto-generated modular YANG for huawei-weblmt" ;
 revision "2026-01-19" {
 description "Auto-generated initial revision. Generated at 2026-01-19 12:13.";
 }
 grouping WEBLMT-attributes {
 leaf IDLEFORCESW {
  type boolean;
  mandatory false;
 }
 leaf IDLETIMEOUT {
  type uint16 {
   range "1..4320";
  }
  mandatory false;
 }
 leaf MAXLIFETIME {
  type uint16 {
   range "1..4320";
  }
  mandatory false;
 }
 leaf SSLVER {
  type string;
  mandatory false;
 }
 }
}
