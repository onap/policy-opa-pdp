module huawei-softpsclt {
 yang-version 1.1;
 namespace "urn:rdns:com:huawei:oammodel:huawei-softpsclt";
 prefix softpsclt;
 import ietf-interfaces {
 prefix if;
 }
 import ietf-ip {
 prefix ip;
 }
 import ietf-inet-types {
 prefix inet;
 }
 description
 "Auto-generated modular YANG for huawei-softpsclt" ;
 revision "2026-01-19" {
 description "Auto-generated initial revision. Generated at 2026-01-19 12:13.";
 }
 augment "/if:interfaces/if:interface/ip:ipv4" {
 container softpsclt-ipv4 {
  container attributes {
   uses SOFTPSCLT-attributes {
    /* opcjonalnie: tu można ograniczyć do IP-only */
   }
  }
 }
}
 augment "/if:interfaces/if:interface/ip:ipv6" {
 container softpsclt-ipv6 {
  container attributes {
   uses SOFTPSCLT-attributes {
    /* opcjonalnie: tu można ograniczyć do IP-only */
   }
  }
 }
}
 grouping SOFTPSCLT-attributes {
 leaf OLD_IP {
  type inet:ipv4-address;
  mandatory false;
 }
 leaf IP {
  type inet:ipv4-address;
  mandatory false;
 }
 leaf OLD_IPV6 {
  type inet:ipv6-address;
  mandatory false;
 }
 leaf IPV6 {
  type inet:ipv6-address;
  mandatory false;
 }
 leaf OLD_MODE {
  type enumeration {
   enum val--1;
   enum val-0;
   enum val-1;
  }
  mandatory false;
 }
 leaf MODE {
  type enumeration {
   enum val--1;
   enum val-0;
   enum val-1;
  }
  mandatory false;
 }
 }
}
