module huawei-rcsclient {
 yang-version 1.1;
 namespace "urn:rdns:com:huawei:oammodel:huawei-rcsclient";
 prefix rcsclient;
 description
 "Auto-generated modular YANG for huawei-rcsclient" ;
 revision "2026-01-19" {
 description "Auto-generated initial revision. Generated at 2026-01-19 12:13.";
 }
 grouping RCSCLIENT-attributes {
 leaf RCSCLIENTNAME {
  type string {
   length "1..128";
  }
  mandatory false;
 }
 leaf OLD_RCSCLIENTNO {
  type union {
   type int8 {
    range "-1..3";
   }
  }
  mandatory false;
 }
 leaf RCSCLIENTNO {
  type union {
   type int8 {
    range "-1..3";
   }
  }
  mandatory false;
 }
 }
}
