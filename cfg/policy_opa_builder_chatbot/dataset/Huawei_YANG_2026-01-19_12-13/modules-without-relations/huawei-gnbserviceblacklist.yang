module huawei-gnbserviceblacklist {
 yang-version 1.1;
 namespace "urn:rdns:com:huawei:oammodel:huawei-gnbserviceblacklist";
 prefix gnbserviceblacklist;
 description
 "Auto-generated modular YANG for huawei-gnbserviceblacklist" ;
 revision "2026-01-19" {
 description "Auto-generated initial revision. Generated at 2026-01-19 12:13.";
 }
 grouping GNBSERVICEBLACKLIST-attributes {
 leaf IMSSERVICEINDICATOR {
  type string;
  mandatory false;
 }
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf OLD_TAC {
  type union {
   type int32 {
    range "-1..16777215";
   }
  }
  mandatory false;
 }
 leaf TAC {
  type union {
   type int32 {
    range "-1..16777215";
   }
  }
  mandatory false;
 }
 }
}
