module huawei-logpolicy {
 yang-version 1.1;
 namespace "urn:rdns:com:huawei:oammodel:huawei-logpolicy";
 prefix logpolicy;
 description
 "Auto-generated modular YANG for huawei-logpolicy" ;
 revision "2026-01-19" {
 description "Auto-generated initial revision. Generated at 2026-01-19 12:13.";
 }
 grouping LOGPOLICY-attributes {
 leaf ENCRYPTSTORESW {
  type boolean;
  mandatory false;
 }
 }
}
