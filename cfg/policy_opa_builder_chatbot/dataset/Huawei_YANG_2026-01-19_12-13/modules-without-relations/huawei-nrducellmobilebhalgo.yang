module huawei-nrducellmobilebhalgo {
 yang-version 1.1;
 namespace "urn:rdns:com:huawei:oammodel:huawei-nrducellmobilebhalgo";
 prefix nrducellmobilebhalgo;
 description
 "Auto-generated modular YANG for huawei-nrducellmobilebhalgo" ;
 revision "2026-01-19" {
 description "Auto-generated initial revision. Generated at 2026-01-19 12:13.";
 }
 grouping NRDUCELLMOBILEBHALGO-attributes {
 leaf DYNBEAMALLOCDELAYDIFFTHLD {
  type uint8 {
   range "0..255";
  }
  mandatory false;
 }
 leaf MOBILEBACKHAULALGOSW {
  type string;
  mandatory false;
 }
 leaf NRDUCELLID {
  type union {
   type int32 {
    range "-1..65534";
   }
  }
  mandatory false;
 }
 }
}
