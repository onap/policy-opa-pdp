module huawei-ethoam3ah {
 yang-version 1.1;
 namespace "urn:rdns:com:huawei:oammodel:huawei-ethoam3ah";
 prefix ethoam3ah;
 description
 "Auto-generated modular YANG for huawei-ethoam3ah" ;
 revision "2026-01-19" {
 description "Auto-generated initial revision. Generated at 2026-01-19 12:13.";
 }
 grouping ETHOAM3AH-attributes {
 leaf OLD_CN {
  type union {
   type int8 {
    range "-1..7";
   }
  }
  mandatory false;
 }
 leaf CN {
  type union {
   type int8 {
    range "-1..7";
   }
  }
  mandatory false;
 }
 leaf DTPRD {
  type union {
   type uint16 {
    range "10..1000";
   }
  }
  mandatory false;
 }
 leaf ERRFRMEVTPRD {
  type uint8 {
   range "1..60";
  }
  mandatory false;
 }
 leaf ERRFRMEVTTHD {
  type uint16 {
   range "1..65535";
  }
  mandatory false;
 }
 leaf ERRFRMSCDEVTPRD {
  type uint16 {
   range "10..900";
  }
  mandatory false;
 }
 leaf ERRFRMSCDEVTTHD {
  type uint16 {
   range "1..900";
  }
  mandatory false;
 }
 leaf FLTINDFLG {
  type boolean;
  mandatory false;
 }
 leaf PDUSIZE {
  type uint16 {
   range "64..1518";
  }
  mandatory false;
 }
 leaf OLD_PN {
  type union {
   type int8 {
    range "-1..5";
   }
  }
  mandatory false;
 }
 leaf PN {
  type union {
   type int8 {
    range "-1..5";
   }
  }
  mandatory false;
 }
 leaf OLD_PT {
  type enumeration {
   enum val--1;
   enum val-3;
  }
  mandatory false;
 }
 leaf PT {
  type enumeration {
   enum val--1;
   enum val-3;
  }
  mandatory false;
 }
 leaf RMTLBFLG {
  type boolean;
  mandatory false;
 }
 leaf OLD_SBT {
  type enumeration {
   enum val--1;
   enum val-0;
   enum val-5;
  }
  mandatory false;
 }
 leaf SBT {
  type enumeration {
   enum val--1;
   enum val-0;
   enum val-5;
  }
  mandatory false;
 }
 leaf OLD_SN {
  type union {
   type int8 {
    range "-1..7";
   }
  }
  mandatory false;
 }
 leaf SN {
  type union {
   type int8 {
    range "-1..7";
   }
  }
  mandatory false;
 }
 leaf OLD_SRN {
  type union {
   type int8 {
    range "-1..1";
   }
  }
  mandatory false;
 }
 leaf SRN {
  type union {
   type int8 {
    range "-1..1";
   }
  }
  mandatory false;
 }
 leaf WORKMODE {
  type boolean;
  mandatory false;
 }
 }
}
