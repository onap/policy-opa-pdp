module huawei-cfmmd {
 yang-version 1.1;
 namespace "urn:rdns:com:huawei:oammodel:huawei-cfmmd";
 prefix cfmmd;
 description
 "Auto-generated modular YANG for huawei-cfmmd" ;
 revision "2026-01-19" {
 description "Auto-generated initial revision. Generated at 2026-01-19 12:13.";
 }
 grouping CFMMD-attributes {
 leaf LEVEL {
  type uint8 {
   range "0..7";
  }
  mandatory false;
 }
 leaf OLD_MDNAME {
  type string {
   length "1..43";
  }
  mandatory false;
 }
 leaf MDNAME {
  type string {
   length "1..43";
  }
  mandatory false;
 }
 }
}
