module huawei-snmpmng {
 yang-version 1.1;
 namespace "urn:rdns:com:huawei:oammodel:huawei-snmpmng";
 prefix snmpmng;
 import ietf-interfaces {
 prefix if;
 }
 import ietf-ip {
 prefix ip;
 }
 import ietf-inet-types {
 prefix inet;
 }
 description
 "Auto-generated modular YANG for huawei-snmpmng" ;
 revision "2026-01-19" {
 description "Auto-generated initial revision. Generated at 2026-01-19 12:13.";
 }
 augment "/if:interfaces/if:interface/ip:ipv4" {
 container snmpmng-ipv4 {
  container attributes {
   uses SNMPMNG-attributes {
    /* opcjonalnie: tu można ograniczyć do IP-only */
   }
  }
 }
}
 grouping SNMPMNG-attributes {
 leaf IP {
  type inet:ipv4-address;
  mandatory false;
 }
 leaf OLD_MANAGERID {
  type union {
   type int8 {
    range "-1..0";
   }
  }
  mandatory false;
 }
 leaf MANAGERID {
  type union {
   type int8 {
    range "-1..0";
   }
  }
  mandatory false;
 }
 leaf VRFIDX {
  type uint8 {
   range "1..31";
  }
  mandatory false;
 }
 }
}
