module huawei-localip6 {
 yang-version 1.1;
 namespace "urn:rdns:com:huawei:oammodel:huawei-localip6";
 prefix localip6;
 import ietf-interfaces {
 prefix if;
 }
 import ietf-ip {
 prefix ip;
 }
 import ietf-inet-types {
 prefix inet;
 }
 description
 "Auto-generated modular YANG for huawei-localip6" ;
 revision "2026-01-19" {
 description "Auto-generated initial revision. Generated at 2026-01-19 12:13.";
 }
 augment "/if:interfaces/if:interface/ip:ipv6" {
 container localip6-ipv6 {
  container attributes {
   uses LOCALIP6-attributes {
    /* opcjonalnie: tu można ograniczyć do IP-only */
   }
  }
 }
}
 grouping LOCALIP6-attributes {
 leaf IP6 {
  type inet:ipv6-address;
  mandatory false;
 }
 }
}
