module huawei-eucellpribbeqm {
 yang-version 1.1;
 namespace "urn:rdns:com:huawei:oammodel:huawei-eucellpribbeqm";
 prefix eucellpribbeqm;
 description
 "Auto-generated modular YANG for huawei-eucellpribbeqm" ;
 revision "2026-01-19" {
 description "Auto-generated initial revision. Generated at 2026-01-19 12:13.";
 }
 grouping EUCELLPRIBBEQM-attributes {
 leaf LOCALCELLNAME {
  type string;
  mandatory false;
 }
 leaf LOCALCELLID {
  type union {
   type int16 {
    range "-1..255";
   }
  }
  mandatory false;
 }
 leaf PRIBASEBANDEQMID {
  type uint8 {
   range "0..23";
  }
  mandatory false;
 }
 }
}
