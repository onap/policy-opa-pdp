module huawei-celldatacomprconfig {
 yang-version 1.1;
 namespace "urn:rdns:com:huawei:oammodel:huawei-celldatacomprconfig";
 prefix celldatacomprconfig;
 description
 "Auto-generated modular YANG for huawei-celldatacomprconfig" ;
 revision "2026-01-19" {
 description "Auto-generated initial revision. Generated at 2026-01-19 12:13.";
 }
 grouping CELLDATACOMPRCONFIG-attributes {
 leaf LOCALCELLNAME {
  type string;
  mandatory false;
 }
 leaf LOCALCELLID {
  type union {
   type int16 {
    range "-1..255";
   }
  }
  mandatory false;
 }
 leaf STANDARDUDCBUFFERSIZE {
  type enumeration {
   enum val-0;
   enum val-1;
   enum val-2;
  }
  mandatory false;
 }
 leaf STANDARDUDCSWITCH {
  type string;
  mandatory false;
 }
 }
}
