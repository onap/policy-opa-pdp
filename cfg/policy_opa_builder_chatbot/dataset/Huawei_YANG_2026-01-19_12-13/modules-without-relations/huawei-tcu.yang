module huawei-tcu {
 yang-version 1.1;
 namespace "urn:rdns:com:huawei:oammodel:huawei-tcu";
 prefix tcu;
 description
 "Auto-generated modular YANG for huawei-tcu" ;
 revision "2026-01-19" {
 description "Auto-generated initial revision. Generated at 2026-01-19 12:13.";
 }
 grouping TCU-attributes {
 leaf ADDR {
  type uint8 {
   range "1..30";
  }
  mandatory false;
 }
 leaf OLD_CN {
  type union {
   type int8 {
    range "-1..62";
   }
  }
  mandatory false;
 }
 leaf CN {
  type union {
   type int8 {
    range "-1..62";
   }
  }
  mandatory false;
 }
 leaf MCN {
  type uint8 {
   range "0..62";
  }
  mandatory false;
 }
 leaf MPN {
  type uint8 {
   range "0..7";
  }
  mandatory false;
 }
 leaf MSRN {
  type uint8 {
   range "0..254";
  }
  mandatory false;
 }
 leaf SBAF {
  type string;
  mandatory false;
 }
 leaf OLD_SN {
  type union {
   type int8 {
    range "-1..3";
   }
  }
  mandatory false;
 }
 leaf SN {
  type union {
   type int8 {
    range "-1..3";
   }
  }
  mandatory false;
 }
 leaf OLD_SRN {
  type union {
   type int8 {
    range "-1..14";
   }
  }
  mandatory false;
 }
 leaf SRN {
  type union {
   type int8 {
    range "-1..14";
   }
  }
  mandatory false;
 }
 leaf TCMODE {
  type uint16 {
   range "0..65535";
  }
  mandatory false;
 }
 leaf TLTHD {
  type int8 {
   range "-40..10";
  }
  mandatory false;
 }
 leaf TUTHD {
  type uint8 {
   range "20..80";
  }
  mandatory false;
 }
 }
}
