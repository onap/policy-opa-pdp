module huawei-gnbmntgroup {
 yang-version 1.1;
 namespace "urn:rdns:com:huawei:oammodel:huawei-gnbmntgroup";
 prefix gnbmntgroup;
 description
 "Auto-generated modular YANG for huawei-gnbmntgroup" ;
 revision "2026-01-19" {
 description "Auto-generated initial revision. Generated at 2026-01-19 12:13.";
 }
 grouping GNBMNTGROUP-attributes {
 leaf OLD_GROUPID {
  type union {
   type int8 {
    range "-1..127";
   }
  }
  mandatory false;
 }
 leaf GROUPID {
  type union {
   type int8 {
    range "-1..127";
   }
  }
  mandatory false;
 }
 leaf MNTSERVICETYPE {
  type boolean;
  mandatory false;
 }
 leaf MNTUSERTYPE {
  type boolean;
  mandatory false;
 }
 leaf SPID {
  type uint16 {
   range "1..256";
  }
  mandatory false;
 }
 leaf TRACEID {
  type uint32 {
   range "0..4294967295";
  }
  mandatory false;
 }
 leaf UEACCESSFREQDOMLOC {
  type boolean;
  mandatory false;
 }
 leaf UEIDENTMETHOD {
  type boolean;
  mandatory false;
 }
 }
}
