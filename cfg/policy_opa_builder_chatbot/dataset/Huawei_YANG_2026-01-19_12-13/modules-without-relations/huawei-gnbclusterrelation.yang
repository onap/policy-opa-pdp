module huawei-gnbclusterrelation {
 yang-version 1.1;
 namespace "urn:rdns:com:huawei:oammodel:huawei-gnbclusterrelation";
 prefix gnbclusterrelation;
 description
 "Auto-generated modular YANG for huawei-gnbclusterrelation" ;
 revision "2026-01-19" {
 description "Auto-generated initial revision. Generated at 2026-01-19 12:13.";
 }
 grouping GNBCLUSTERRELATION-attributes {
 leaf OLD_CLUSTERID {
  type union {
   type int32 {
    range "-1..49999";
   }
  }
  mandatory false;
 }
 leaf CLUSTERID {
  type union {
   type int32 {
    range "-1..49999";
   }
  }
  mandatory false;
 }
 leaf INTERCLUSTERGNODEBID {
  type uint32 {
   range "0..4294967295";
  }
  mandatory false;
 }
 leaf OLD_INTERCLUSTERID {
  type union {
   type int32 {
    range "-1..49999";
   }
  }
  mandatory false;
 }
 leaf INTERCLUSTERID {
  type union {
   type int32 {
    range "-1..49999";
   }
  }
  mandatory false;
 }
 leaf INTERCLUSTERMCC {
  type string {
   length "3";
  }
  mandatory false;
 }
 leaf INTERCLUSTERMNC {
  type string {
   length "2..3";
  }
  mandatory false;
 }
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf OLD_GNODEBID {
  type union {
   type int64 {
    range "-1..4294967295";
   }
  }
  mandatory false;
 }
 leaf GNODEBID {
  type union {
   type int64 {
    range "-1..4294967295";
   }
  }
  mandatory false;
 }
 }
}
