module huawei-btruncqcipara {
 yang-version 1.1;
 namespace "urn:rdns:com:huawei:oammodel:huawei-btruncqcipara";
 prefix btruncqcipara;
 description
 "Auto-generated modular YANG for huawei-btruncqcipara" ;
 revision "2026-01-19" {
 description "Auto-generated initial revision. Generated at 2026-01-19 12:13.";
 }
 grouping BTRUNCQCIPARA-attributes {
 leaf OLD_TQCI {
  type union {
   type int16 {
    range "-1..255";
   }
  }
  mandatory false;
 }
 leaf TQCI {
  type union {
   type int16 {
    range "-1..255";
   }
  }
  mandatory false;
 }
 leaf TRLCPDCPPARAGROUPID {
  type uint8 {
   range "0..255";
  }
  mandatory false;
 }
 }
}
