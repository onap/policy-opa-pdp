module huawei-gnbroaminguehomeplmn {
 yang-version 1.1;
 namespace "urn:rdns:com:huawei:oammodel:huawei-gnbroaminguehomeplmn";
 prefix gnbroaminguehomeplmn;
 description
 "Auto-generated modular YANG for huawei-gnbroaminguehomeplmn" ;
 revision "2026-01-19" {
 description "Auto-generated initial revision. Generated at 2026-01-19 12:13.";
 }
 grouping GNBROAMINGUEHOMEPLMN-attributes {
 leaf OLD_HOMEMCC {
  type string {
   length "3";
  }
  mandatory false;
 }
 leaf HOMEMCC {
  type string {
   length "3";
  }
  mandatory false;
 }
 leaf OLD_HOMEMNC {
  type string {
   length "2..3";
  }
  mandatory false;
 }
 leaf HOMEMNC {
  type string {
   length "2..3";
  }
  mandatory false;
 }
 leaf OLD_OPERATORID {
  type union {
   type int8 {
    range "-1..11";
   }
  }
  mandatory false;
 }
 leaf OPERATORID {
  type union {
   type int8 {
    range "-1..11";
   }
  }
  mandatory false;
 }
 }
}
