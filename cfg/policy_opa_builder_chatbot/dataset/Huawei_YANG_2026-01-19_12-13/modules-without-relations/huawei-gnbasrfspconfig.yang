module huawei-gnbasrfspconfig {
 yang-version 1.1;
 namespace "urn:rdns:com:huawei:oammodel:huawei-gnbasrfspconfig";
 prefix gnbasrfspconfig;
 description
 "Auto-generated modular YANG for huawei-gnbasrfspconfig" ;
 revision "2026-01-19" {
 description "Auto-generated initial revision. Generated at 2026-01-19 12:13.";
 }
 grouping GNBASRFSPCONFIG-attributes {
 leaf OLD_RFSPINDEX {
  type union {
   type int16 {
    range "-1..256";
   }
  }
  mandatory false;
 }
 leaf RFSPINDEX {
  type union {
   type int16 {
    range "-1..256";
   }
  }
  mandatory false;
 }
 leaf SPEEDTURBOSERVIDENTMODE {
  type uint16 {
   range "0..65535";
  }
  mandatory false;
 }
 }
}
