module huawei-bbp {
 yang-version 1.1;
 namespace "urn:rdns:com:huawei:oammodel:huawei-bbp";
 prefix bbp;
 description
 "Auto-generated modular YANG for huawei-bbp" ;
 revision "2026-01-19" {
 description "Auto-generated initial revision. Generated at 2026-01-19 12:13.";
 }
 grouping BBP-attributes {
 leaf ADMSTATE {
  type boolean;
  mandatory false;
 }
 leaf BBRESALLOCMODE {
  type boolean;
  mandatory false;
 }
 leaf BBWS {
  type string;
  mandatory false;
 }
 leaf BLKTP {
  type enumeration {
   enum val-0;
   enum val-1;
   enum val-2;
  }
  mandatory false;
 }
 leaf BRDSPEC {
  type string {
   length "0..15";
  }
  mandatory false;
 }
 leaf CCNE {
  type boolean;
  mandatory false;
 }
 leaf CELLDEPLOY {
  type enumeration {
   enum val-0;
   enum val-1;
   enum val-2;
  }
  mandatory false;
 }
 leaf OLD_CN {
  type union {
   type int8 {
    range "-1..7";
   }
  }
  mandatory false;
 }
 leaf CN {
  type union {
   type int8 {
    range "-1..7";
   }
  }
  mandatory false;
 }
 leaf CPRIEX {
  type boolean;
  mandatory false;
 }
 leaf CPRIEXMODE {
  type boolean;
  mandatory false;
 }
 leaf CPRIITFTYPE {
  type enumeration {
   enum val-0;
   enum val-1;
   enum val-2;
   enum val-3;
   enum val-4;
   enum val-5;
  }
  mandatory false;
 }
 leaf CPRIPANELPORTNUM {
  type union {
   type uint8 {
    range "6..9";
   }
  }
  mandatory false;
 }
 leaf EXFUNCSW {
  type string;
  mandatory false;
 }
 leaf FRAMEOFFSETMODE {
  type boolean;
  mandatory false;
 }
 leaf HCE {
  type enumeration {
   enum val-0;
   enum val-16;
   enum val-255;
  }
  mandatory false;
 }
 leaf LTEFLEXSPECSW {
  type boolean;
  mandatory false;
 }
 leaf OVERLOADALMCLRTHLD {
  type uint8 {
   range "0..100";
  }
  mandatory false;
 }
 leaf OVERLOADALMRPTTHLD {
  type uint8 {
   range "0..100";
  }
  mandatory false;
 }
 leaf PWRSVGSW {
  type enumeration {
   enum val-0;
   enum val-1;
   enum val-2;
  }
  mandatory false;
 }
 leaf OLD_SN {
  type union {
   type int8 {
    range "-1..6";
   }
  }
  mandatory false;
 }
 leaf SN {
  type union {
   type int8 {
    range "-1..6";
   }
  }
  mandatory false;
 }
 leaf OLD_SRN {
  type union {
   type int8 {
    range "-1..1";
   }
  }
  mandatory false;
 }
 leaf SRN {
  type union {
   type int8 {
    range "-1..1";
   }
  }
  mandatory false;
 }
 leaf SRT {
  type enumeration {
   enum val-0;
   enum val-1;
   enum val-2;
   enum val-4;
   enum val-5;
   enum val-6;
   enum val-7;
   enum val-8;
   enum val-9;
  }
  mandatory false;
 }
 leaf TIME {
  type uint32 {
   range "0..4294967295";
  }
  mandatory false;
 }
 leaf TYPE {
  type enumeration {
   enum val-2;
   enum val-181;
   enum val-4098;
   enum val-8194;
   enum val-12290;
   enum val-12546;
   enum val-12802;
  }
  mandatory false;
 }
 leaf WM {
  type enumeration {
   enum val-0;
   enum val-1;
   enum val-2;
   enum val-3;
   enum val-4;
   enum val-5;
   enum val-6;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 }
}
