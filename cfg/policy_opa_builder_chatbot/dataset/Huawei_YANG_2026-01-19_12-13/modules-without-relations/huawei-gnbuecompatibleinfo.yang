module huawei-gnbuecompatibleinfo {
 yang-version 1.1;
 namespace "urn:rdns:com:huawei:oammodel:huawei-gnbuecompatibleinfo";
 prefix gnbuecompatibleinfo;
 description
 "Auto-generated modular YANG for huawei-gnbuecompatibleinfo" ;
 revision "2026-01-19" {
 description "Auto-generated initial revision. Generated at 2026-01-19 12:13.";
 }
 grouping GNBUECOMPATIBLEINFO-attributes {
 leaf BLACKLISTCTRLSWITCH {
  type string;
  mandatory false;
 }
 leaf OLD_FREQUENCYBAND {
  type enumeration {
   enum val--1;
   enum val-0;
   enum val-1;
   enum val-2;
   enum val-3;
   enum val-5;
   enum val-7;
   enum val-8;
   enum val-12;
   enum val-13;
   enum val-20;
   enum val-25;
   enum val-28;
   enum val-38;
   enum val-39;
   enum val-40;
   enum val-41;
   enum val-66;
   enum val-71;
   enum val-75;
   enum val-77;
   enum val-78;
   enum val-79;
   enum val-257;
   enum val-258;
   enum val-260;
   enum val-261;
  }
  mandatory false;
 }
 leaf FREQUENCYBAND {
  type enumeration {
   enum val--1;
   enum val-0;
   enum val-1;
   enum val-2;
   enum val-3;
   enum val-5;
   enum val-7;
   enum val-8;
   enum val-12;
   enum val-13;
   enum val-20;
   enum val-25;
   enum val-28;
   enum val-38;
   enum val-39;
   enum val-40;
   enum val-41;
   enum val-66;
   enum val-71;
   enum val-75;
   enum val-77;
   enum val-78;
   enum val-79;
   enum val-257;
   enum val-258;
   enum val-260;
   enum val-261;
  }
  mandatory false;
 }
 leaf OLD_OPERATORID {
  type union {
   type int16 {
    range "-1..255";
   }
  }
  mandatory false;
 }
 leaf OPERATORID {
  type union {
   type int16 {
    range "-1..255";
   }
  }
  mandatory false;
 }
 leaf OLD_UEINFOINDEX {
  type union {
   type int16 {
    range "-1..128";
   }
  }
  mandatory false;
 }
 leaf UEINFOINDEX {
  type union {
   type int16 {
    range "-1..128";
   }
  }
  mandatory false;
 }
 }
}
