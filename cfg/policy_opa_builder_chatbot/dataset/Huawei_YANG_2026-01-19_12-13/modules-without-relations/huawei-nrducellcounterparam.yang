module huawei-nrducellcounterparam {
 yang-version 1.1;
 namespace "urn:rdns:com:huawei:oammodel:huawei-nrducellcounterparam";
 prefix nrducellcounterparam;
 description
 "Auto-generated modular YANG for huawei-nrducellcounterparam" ;
 revision "2026-01-19" {
 description "Auto-generated initial revision. Generated at 2026-01-19 12:13.";
 }
 grouping NRDUCELLCOUNTERPARAM-attributes {
 leaf COUNTERINDEX {
  type union {
   type int16 {
    range "-1..255";
   }
  }
  mandatory false;
 }
 leaf COUNTERTYPE {
  type enumeration {
   enum val--1;
   enum val-0;
   enum val-1;
   enum val-2;
  }
  mandatory false;
 }
 leaf NRDUCELLID {
  type union {
   type int32 {
    range "-1..65534";
   }
  }
  mandatory false;
 }
 leaf RANGESTARTVALUE {
  type uint32 {
   range "0..4294967295";
  }
  mandatory false;
 }
 }
}
