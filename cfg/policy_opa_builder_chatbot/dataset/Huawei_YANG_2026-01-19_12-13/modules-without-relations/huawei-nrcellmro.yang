module huawei-nrcellmro {
 yang-version 1.1;
 namespace "urn:rdns:com:huawei:oammodel:huawei-nrcellmro";
 prefix nrcellmro;
 description
 "Auto-generated modular YANG for huawei-nrcellmro" ;
 revision "2026-01-19" {
 description "Auto-generated initial revision. Generated at 2026-01-19 12:13.";
 }
 grouping NRCELLMRO-attributes {
 leaf ABNCOVERAGERSRPTHLD {
  type int16 {
   range "-156..-31";
  }
  mandatory false;
 }
 leaf MODESWITCH {
  type string;
  mandatory false;
 }
 leaf MROSWITCH {
  type string;
  mandatory false;
 }
 leaf NRCELLID {
  type union {
   type int32 {
    range "-1..65534";
   }
  }
  mandatory false;
 }
 }
}
