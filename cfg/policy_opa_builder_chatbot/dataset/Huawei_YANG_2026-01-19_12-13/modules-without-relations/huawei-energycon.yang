module huawei-energycon {
 yang-version 1.1;
 namespace "urn:rdns:com:huawei:oammodel:huawei-energycon";
 prefix energycon;
 description
 "Auto-generated modular YANG for huawei-energycon" ;
 revision "2026-01-19" {
 description "Auto-generated initial revision. Generated at 2026-01-19 12:13.";
 }
 grouping ENERGYCON-attributes {
 leaf MP {
  type boolean;
  mandatory false;
 }
 }
}
