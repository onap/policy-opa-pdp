module huawei-extrrures {
 yang-version 1.1;
 namespace "urn:rdns:com:huawei:oammodel:huawei-extrrures";
 prefix extrrures;
 description
 "Auto-generated modular YANG for huawei-extrrures" ;
 revision "2026-01-19" {
 description "Auto-generated initial revision. Generated at 2026-01-19 12:13.";
 }
 grouping EXTRRURES-attributes {
 leaf OLD_CN {
  type union {
   type int8 {
    range "-1..15";
   }
  }
  mandatory false;
 }
 leaf CN {
  type union {
   type int8 {
    range "-1..15";
   }
  }
  mandatory false;
 }
 leaf RCSSERVERNO {
  type uint8 {
   range "0..255";
  }
  mandatory false;
 }
 leaf RT {
  type boolean;
  mandatory false;
 }
 leaf SERVERRRUNAME {
  type string {
   length "1..128";
  }
  mandatory false;
 }
 leaf OLD_SN {
  type union {
   type int8 {
    range "-1..0";
   }
  }
  mandatory false;
 }
 leaf SN {
  type union {
   type int8 {
    range "-1..0";
   }
  }
  mandatory false;
 }
 leaf OLD_SRN {
  type union {
   type int16 {
    range "-1..254";
   }
  }
  mandatory false;
 }
 leaf SRN {
  type union {
   type int16 {
    range "-1..254";
   }
  }
  mandatory false;
 }
 leaf USERLABEL {
  type string {
   length "0..255";
  }
  mandatory false;
 }
 }
}
