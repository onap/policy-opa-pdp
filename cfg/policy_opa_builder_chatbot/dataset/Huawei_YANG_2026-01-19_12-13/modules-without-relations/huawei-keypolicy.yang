module huawei-keypolicy {
 yang-version 1.1;
 namespace "urn:rdns:com:huawei:oammodel:huawei-keypolicy";
 prefix keypolicy;
 description
 "Auto-generated modular YANG for huawei-keypolicy" ;
 revision "2026-01-19" {
 description "Auto-generated initial revision. Generated at 2026-01-19 12:13.";
 }
 grouping KEYPOLICY-attributes {
 leaf PERIOD {
  type uint16 {
   range "90..732";
  }
  mandatory false;
 }
 }
}
