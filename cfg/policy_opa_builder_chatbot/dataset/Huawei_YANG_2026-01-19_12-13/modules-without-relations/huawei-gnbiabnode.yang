module huawei-gnbiabnode {
 yang-version 1.1;
 namespace "urn:rdns:com:huawei:oammodel:huawei-gnbiabnode";
 prefix gnbiabnode;
 description
 "Auto-generated modular YANG for huawei-gnbiabnode" ;
 revision "2026-01-19" {
 description "Auto-generated initial revision. Generated at 2026-01-19 12:13.";
 }
 grouping GNBIABNODE-attributes {
 leaf OLD_IABNODEID {
  type union {
   type int32 {
    range "-1..65534";
   }
  }
  mandatory false;
 }
 leaf IABNODEID {
  type union {
   type int32 {
    range "-1..65534";
   }
  }
  mandatory false;
 }
 leaf UBRUID {
  type uint16 {
   range "0..65535";
  }
  mandatory false;
 }
 leaf GNBDUID {
  type uint64 {
   range "0..68719476735";
  }
  mandatory false;
 }
 }
}
