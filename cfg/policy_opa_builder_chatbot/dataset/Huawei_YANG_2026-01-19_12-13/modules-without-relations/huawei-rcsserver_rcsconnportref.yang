module huawei-rcsserver_rcsconnportref {
 yang-version 1.1;
 namespace "urn:rdns:com:huawei:oammodel:huawei-rcsserver_rcsconnportref";
 prefix rcsserver_rcsconnportref;
 description
 "Auto-generated modular YANG for huawei-rcsserver_rcsconnportref" ;
 revision "2026-01-19" {
 description "Auto-generated initial revision. Generated at 2026-01-19 12:13.";
 }
 grouping RCSSERVER_RCSCONNPORTREF-attributes {
 leaf PORTID {
  type union {
   type int32 {
    range "-1..65535";
   }
  }
  mandatory false;
 }
 leaf RCSSERVERNO {
  type union {
   type int16 {
    range "-1..255";
   }
  }
  mandatory false;
 }
 }
}
