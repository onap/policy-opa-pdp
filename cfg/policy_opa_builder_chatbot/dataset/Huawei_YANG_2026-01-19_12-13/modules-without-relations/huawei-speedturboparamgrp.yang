module huawei-speedturboparamgrp {
 yang-version 1.1;
 namespace "urn:rdns:com:huawei:oammodel:huawei-speedturboparamgrp";
 prefix speedturboparamgrp;
 description
 "Auto-generated modular YANG for huawei-speedturboparamgrp" ;
 revision "2026-01-19" {
 description "Auto-generated initial revision. Generated at 2026-01-19 12:13.";
 }
 grouping SPEEDTURBOPARAMGRP-attributes {
 leaf DLTRAFFICVOLUMETHLD {
  type uint32 {
   range "0..20000000";
  }
  mandatory false;
 }
 leaf DLTRAFFICVOLUMEUPPERTHLD {
  type uint32 {
   range "0..20000000";
  }
  mandatory false;
 }
 leaf IDLESERVDATAVOLTHLD {
  type uint16 {
   range "0..65535";
  }
  mandatory false;
 }
 leaf IDLESERVWINDOWSIZE {
  type uint8 {
   range "2..63";
  }
  mandatory false;
 }
 leaf IPV4PKTNUMLOWERTHLD {
  type union {
   type uint8 {
    range "0..255";
   }
  }
  mandatory false;
 }
 leaf IPV4PKTNUMUPPERTHLD {
  type union {
   type uint8 {
    range "0..255";
   }
  }
  mandatory false;
 }
 leaf IPV6PKTNUMLOWERTHLD {
  type union {
   type uint8 {
    range "0..255";
   }
  }
  mandatory false;
 }
 leaf IPV6PKTNUMUPPERTHLD {
  type union {
   type uint8 {
    range "0..255";
   }
  }
  mandatory false;
 }
 leaf PKTSIZEDIFFTHLD {
  type uint8 {
   range "0..20";
  }
  mandatory false;
 }
 leaf SERVSAMPLINGPERIOD {
  type uint8 {
   range "1..100";
  }
  mandatory false;
 }
 leaf SERVICESENSINGTYPE {
  type enumeration {
   enum val-0;
   enum val-1;
   enum val-2;
   enum val-3;
   enum val-4;
  }
  mandatory false;
 }
 leaf SPDTURBODLIPPKTSIZEOFFSET {
  type uint16 {
   range "0..1500";
  }
  mandatory false;
 }
 leaf SPDTURBOIDENTINTERVAL {
  type uint8 {
   range "1..15";
  }
  mandatory false;
 }
 leaf SPDTURBOIDENTMODE {
  type enumeration {
   enum val-0;
   enum val-1;
   enum val-2;
  }
  mandatory false;
 }
 leaf SPDTURBOSECONDASGRPID {
  type union {
   type uint8 {
    range "0..255";
   }
  }
  mandatory false;
 }
 leaf SPDTURBOSECONDPARAGRPINDEX {
  type union {
   type uint8 {
    range "0..255";
   }
  }
  mandatory false;
 }
 leaf SPDTURBOULIPPKTSIZEOFFSET {
  type uint16 {
   range "0..1500";
  }
  mandatory false;
 }
 leaf SPEEDTURBOALGOSWITCH {
  type string;
  mandatory false;
 }
 leaf SPEEDTURBODETECTINTVL {
  type uint8 {
   range "0..10";
  }
  mandatory false;
 }
 leaf SPEEDTURBODLIPPKTSIZE {
  type uint16 {
   range "1..1500";
  }
  mandatory false;
 }
 leaf SPEEDTURBOIPPKTNUMHIGHTHLD {
  type uint8 {
   range "2..15";
  }
  mandatory false;
 }
 leaf SPEEDTURBOIPPKTNUMTHLD {
  type uint8 {
   range "1..15";
  }
  mandatory false;
 }
 leaf SPEEDTURBOKEEPALIVETIMER {
  type uint16 {
   range "2..65535";
  }
  mandatory false;
 }
 leaf SPEEDTURBOPARAGROUPID {
  type union {
   type uint8 {
    range "0..255";
   }
  }
  mandatory false;
 }
 leaf OLD_SPEEDTURBOPARAMGRPINDEX {
  type union {
   type int8 {
    range "-1..15";
   }
  }
  mandatory false;
 }
 leaf SPEEDTURBOPARAMGRPINDEX {
  type union {
   type int8 {
    range "-1..15";
   }
  }
  mandatory false;
 }
 leaf SPEEDTURBOTIMEWINDOW {
  type uint16 {
   range "1..5000";
  }
  mandatory false;
 }
 leaf SPEEDTURBOUEIDENTTIMER {
  type uint16 {
   range "0..3600";
  }
  mandatory false;
 }
 leaf SPEEDTURBOULDETECTINTVL {
  type uint8 {
   range "0..60";
  }
  mandatory false;
 }
 leaf SPEEDTURBOULIPPKTSIZE {
  type uint16 {
   range "1..1500";
  }
  mandatory false;
 }
 leaf STDLPKTLENGTHLOWERTHLD {
  type uint16 {
   range "0..1500";
  }
  mandatory false;
 }
 leaf STDLPKTLENGTHUPPERTHLD {
  type uint16 {
   range "0..1500";
  }
  mandatory false;
 }
 leaf STULPKTLENGTHLOWERTHLD {
  type uint16 {
   range "0..1500";
  }
  mandatory false;
 }
 leaf STULPKTLENGTHUPPERTHLD {
  type uint16 {
   range "0..1500";
  }
  mandatory false;
 }
 leaf ULTRAFFICVOLUMELOWERTHLD {
  type uint32 {
   range "0..20000000";
  }
  mandatory false;
 }
 leaf ULTRAFFICVOLUMETHLD {
  type uint32 {
   range "0..20000000";
  }
  mandatory false;
 }
 leaf USERIDENTTYPE {
  type boolean;
  mandatory false;
 }
 }
}
