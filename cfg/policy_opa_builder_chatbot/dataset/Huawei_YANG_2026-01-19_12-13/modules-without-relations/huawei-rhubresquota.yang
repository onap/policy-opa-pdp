module huawei-rhubresquota {
 yang-version 1.1;
 namespace "urn:rdns:com:huawei:oammodel:huawei-rhubresquota";
 prefix rhubresquota;
 description
 "Auto-generated modular YANG for huawei-rhubresquota" ;
 revision "2026-01-19" {
 description "Auto-generated initial revision. Generated at 2026-01-19 12:13.";
 }
 grouping RHUBRESQUOTA-attributes {
 leaf INTERRHUBRFCOMBCAPC {
  type uint8 {
   range "0..128";
  }
  mandatory false;
 }
 leaf RCSCLIENTNO {
  type uint8 {
   range "0..3";
  }
  mandatory false;
 }
 leaf RFCOMBCAPC {
  type uint8 {
   range "0..128";
  }
  mandatory false;
 }
 leaf OLD_RHUBRESQUOTAID {
  type union {
   type int8 {
    range "-1..31";
   }
  }
  mandatory false;
 }
 leaf RHUBRESQUOTAID {
  type union {
   type int8 {
    range "-1..31";
   }
  }
  mandatory false;
 }
 leaf SCOPE {
  type boolean;
  mandatory false;
 }
 }
}
