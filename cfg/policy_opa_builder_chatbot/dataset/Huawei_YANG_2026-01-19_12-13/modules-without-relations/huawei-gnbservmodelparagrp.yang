module huawei-gnbservmodelparagrp {
 yang-version 1.1;
 namespace "urn:rdns:com:huawei:oammodel:huawei-gnbservmodelparagrp";
 prefix gnbservmodelparagrp;
 description
 "Auto-generated modular YANG for huawei-gnbservmodelparagrp" ;
 revision "2026-01-19" {
 description "Auto-generated initial revision. Generated at 2026-01-19 12:13.";
 }
 grouping GNBSERVMODELPARAGRP-attributes {
 leaf PREDICTSERVCHARACTERISTICS {
  type enumeration {
   enum val-0;
   enum val-1;
   enum val-2;
   enum val-3;
  }
  mandatory false;
 }
 leaf OLD_SERVICEMODELPARAGRPID {
  type union {
   type int8 {
    range "-1..64";
   }
  }
  mandatory false;
 }
 leaf SERVICEMODELPARAGRPID {
  type union {
   type int8 {
    range "-1..64";
   }
  }
  mandatory false;
 }
 leaf SERVICETYPEPARAGRPID {
  type uint8 {
   range "1..10";
  }
  mandatory false;
 }
 }
}
