module huawei-enodebusimeisvcfg {
 yang-version 1.1;
 namespace "urn:rdns:com:huawei:oammodel:huawei-enodebusimeisvcfg";
 prefix enodebusimeisvcfg;
 description
 "Auto-generated modular YANG for huawei-enodebusimeisvcfg" ;
 revision "2026-01-19" {
 description "Auto-generated initial revision. Generated at 2026-01-19 12:13.";
 }
 grouping ENODEBUSIMEISVCFG-attributes {
 leaf OLD_IMEISVSVN {
  type union {
   type int16 {
    range "-1..255";
   }
  }
  mandatory false;
 }
 leaf IMEISVSVN {
  type union {
   type int16 {
    range "-1..255";
   }
  }
  mandatory false;
 }
 leaf OLD_IMEISVTAC {
  type union {
   type int32 {
    range "-1..99999999";
   }
  }
  mandatory false;
 }
 leaf IMEISVTAC {
  type union {
   type int32 {
    range "-1..99999999";
   }
  }
  mandatory false;
 }
 leaf UETYPEDESC {
  type string {
   length "0..80";
  }
  mandatory false;
 }
 }
}
