module huawei-brdpwrsvgpolicy {
 yang-version 1.1;
 namespace "urn:rdns:com:huawei:oammodel:huawei-brdpwrsvgpolicy";
 prefix brdpwrsvgpolicy;
 description
 "Auto-generated modular YANG for huawei-brdpwrsvgpolicy" ;
 revision "2026-01-19" {
 description "Auto-generated initial revision. Generated at 2026-01-19 12:13.";
 }
 grouping BRDPWRSVGPOLICY-attributes {
 leaf DORMANCYTIMER {
  type uint8 {
   range "1..10";
  }
  mandatory false;
 }
 leaf POLICYID {
  type union {
   type int8 {
    range "-1..24";
   }
  }
  mandatory false;
 }
 leaf POWERSAVINGTYPE {
  type enumeration {
   enum val-0;
   enum val-1;
   enum val-2;
   enum val-3;
  }
  mandatory false;
 }
 }
}
