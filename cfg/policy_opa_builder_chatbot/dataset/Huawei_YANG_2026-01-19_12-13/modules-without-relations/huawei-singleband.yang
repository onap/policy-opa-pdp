module huawei-singleband {
 yang-version 1.1;
 namespace "urn:rdns:com:huawei:oammodel:huawei-singleband";
 prefix singleband;
 description
 "Auto-generated modular YANG for huawei-singleband" ;
 revision "2026-01-19" {
 description "Auto-generated initial revision. Generated at 2026-01-19 12:13.";
 }
 grouping SINGLEBAND-attributes {
 leaf OLD_BANDGROUPID {
  type union {
   type int8 {
    range "-1..31";
   }
  }
  mandatory false;
 }
 leaf BANDGROUPID {
  type union {
   type int8 {
    range "-1..31";
   }
  }
  mandatory false;
 }
 leaf OLD_BANDID {
  type union {
   type int8 {
    range "-1..31";
   }
  }
  mandatory false;
 }
 leaf BANDID {
  type union {
   type int8 {
    range "-1..31";
   }
  }
  mandatory false;
 }
 leaf LTEBAND {
  type uint16 {
   range "1..256";
  }
  mandatory false;
 }
 leaf NRBAND {
  type enumeration {
   enum val-1;
   enum val-2;
   enum val-3;
   enum val-5;
   enum val-7;
   enum val-8;
   enum val-12;
   enum val-13;
   enum val-20;
   enum val-25;
   enum val-28;
   enum val-38;
   enum val-40;
   enum val-41;
   enum val-66;
   enum val-71;
   enum val-75;
   enum val-77;
   enum val-78;
   enum val-79;
   enum val-80;
   enum val-81;
   enum val-82;
   enum val-83;
   enum val-84;
   enum val-86;
   enum val-89;
   enum val-97;
   enum val-150;
   enum val-198;
   enum val-199;
   enum val-257;
   enum val-258;
   enum val-260;
   enum val-261;
  }
  mandatory false;
 }
 leaf STANDARD {
  type boolean;
  mandatory false;
 }
 }
}
