module huawei-rcsconnportref {
 yang-version 1.1;
 namespace "urn:rdns:com:huawei:oammodel:huawei-rcsconnportref";
 prefix rcsconnportref;
 description
 "Auto-generated modular YANG for huawei-rcsconnportref" ;
 revision "2026-01-19" {
 description "Auto-generated initial revision. Generated at 2026-01-19 12:13.";
 }
 grouping RCSCONNPORTREF-attributes {
 leaf PORTID {
  type union {
   type int32 {
    range "-1..65535";
   }
  }
  mandatory false;
 }
 }
}
