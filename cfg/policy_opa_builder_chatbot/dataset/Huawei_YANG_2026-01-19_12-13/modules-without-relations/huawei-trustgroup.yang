module huawei-trustgroup {
 yang-version 1.1;
 namespace "urn:rdns:com:huawei:oammodel:huawei-trustgroup";
 prefix trustgroup;
 description
 "Auto-generated modular YANG for huawei-trustgroup" ;
 revision "2026-01-19" {
 description "Auto-generated initial revision. Generated at 2026-01-19 12:13.";
 }
 grouping TRUSTGROUP-attributes {
 leaf TRUSTGROUPDESC {
  type string {
   length "0..255";
  }
  mandatory false;
 }
 leaf OLD_TRUSTGROUPID {
  type union {
   type int8 {
    range "-1..7";
   }
  }
  mandatory false;
 }
 leaf TRUSTGROUPID {
  type union {
   type int8 {
    range "-1..7";
   }
  }
  mandatory false;
 }
 }
}
