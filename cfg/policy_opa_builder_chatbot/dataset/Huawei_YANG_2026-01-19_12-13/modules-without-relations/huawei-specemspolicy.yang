module huawei-specemspolicy {
 yang-version 1.1;
 namespace "urn:rdns:com:huawei:oammodel:huawei-specemspolicy";
 prefix specemspolicy;
 description
 "Auto-generated modular YANG for huawei-specemspolicy" ;
 revision "2026-01-19" {
 description "Auto-generated initial revision. Generated at 2026-01-19 12:13.";
 }
 grouping SPECEMSPOLICY-attributes {
 leaf PORTSWITCH {
  type boolean;
  mandatory false;
 }
 }
}
