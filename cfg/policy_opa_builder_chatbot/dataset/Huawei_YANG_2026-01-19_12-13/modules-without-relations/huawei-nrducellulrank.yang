module huawei-nrducellulrank {
 yang-version 1.1;
 namespace "urn:rdns:com:huawei:oammodel:huawei-nrducellulrank";
 prefix nrducellulrank;
 description
 "Auto-generated modular YANG for huawei-nrducellulrank" ;
 revision "2026-01-19" {
 description "Auto-generated initial revision. Generated at 2026-01-19 12:13.";
 }
 grouping NRDUCELLULRANK-attributes {
 leaf NRDUCELLID {
  type union {
   type int32 {
    range "-1..65534";
   }
  }
  mandatory false;
 }
 leaf RANK1TORANK2EFFOFFSET {
  type uint8 {
   range "0..10";
  }
  mandatory false;
 }
 leaf RANK2TORANK1RBTHLDCOEFF {
  type uint16 {
   range "1..2730";
  }
  mandatory false;
 }
 leaf RANKDECSPCTEFFHYSTHLD {
  type int8 {
   range "-100..100";
  }
  mandatory false;
 }
 leaf RANKINCSPCTEFFHYSTHLD {
  type int8 {
   range "-100..100";
  }
  mandatory false;
 }
 leaf ULFIXEDRANK {
  type enumeration {
   enum val-0;
   enum val-1;
   enum val-2;
   enum val-3;
   enum val-4;
  }
  mandatory false;
 }
 leaf ULRANKALGOSW {
  type string;
  mandatory false;
 }
 }
}
