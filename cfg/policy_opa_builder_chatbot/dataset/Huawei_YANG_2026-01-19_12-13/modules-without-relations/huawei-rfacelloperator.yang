module huawei-rfacelloperator {
 yang-version 1.1;
 namespace "urn:rdns:com:huawei:oammodel:huawei-rfacelloperator";
 prefix rfacelloperator;
 description
 "Auto-generated modular YANG for huawei-rfacelloperator" ;
 revision "2026-01-19" {
 description "Auto-generated initial revision. Generated at 2026-01-19 12:13.";
 }
 grouping RFACELLOPERATOR-attributes {
 leaf LOCALCELLID {
  type union {
   type int16 {
    range "-1..255";
   }
  }
  mandatory false;
 }
 leaf RFAOPERATORID {
  type uint8 {
   range "0..5";
  }
  mandatory false;
 }
 }
}
