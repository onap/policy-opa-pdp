module huawei-nsanrlteasgrpmapping {
 yang-version 1.1;
 namespace "urn:rdns:com:huawei:oammodel:huawei-nsanrlteasgrpmapping";
 prefix nsanrlteasgrpmapping;
 description
 "Auto-generated modular YANG for huawei-nsanrlteasgrpmapping" ;
 revision "2026-01-19" {
 description "Auto-generated initial revision. Generated at 2026-01-19 12:13.";
 }
 grouping NSANRLTEASGRPMAPPING-attributes {
 leaf LTEASGROUPID {
  type union {
   type uint8 {
    range "0..255";
   }
  }
  mandatory false;
 }
 leaf OLD_NRASGROUPID {
  type union {
   type int8 {
    range "-1..15";
   }
  }
  mandatory false;
 }
 leaf NRASGROUPID {
  type union {
   type int8 {
    range "-1..15";
   }
  }
  mandatory false;
 }
 leaf SPEEDTURBOASGROUPID {
  type union {
   type uint8 {
    range "0..255";
   }
  }
  mandatory false;
 }
 leaf SPEEDTURBOPARAMGRPINDEX {
  type uint8 {
   range "0..15";
  }
  mandatory false;
 }
 }
}
