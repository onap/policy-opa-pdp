module huawei-brdresassignment {
 yang-version 1.1;
 namespace "urn:rdns:com:huawei:oammodel:huawei-brdresassignment";
 prefix brdresassignment;
 description
 "Auto-generated modular YANG for huawei-brdresassignment" ;
 revision "2026-01-19" {
 description "Auto-generated initial revision. Generated at 2026-01-19 12:13.";
 }
 grouping BRDRESASSIGNMENT-attributes {
 leaf BRDASSIGNMENT {
  type enumeration {
   enum val-0;
   enum val-1;
   enum val-4;
   enum val-5;
   enum val-8;
   enum val-9;
   enum val-13;
   enum val-20;
  }
  mandatory false;
 }
 leaf CN {
  type union {
   type int8 {
    range "-1..7";
   }
  }
  mandatory false;
 }
 leaf SN {
  type union {
   type int8 {
    range "-1..7";
   }
  }
  mandatory false;
 }
 leaf SRN {
  type union {
   type int8 {
    range "-1..1";
   }
  }
  mandatory false;
 }
 }
}
