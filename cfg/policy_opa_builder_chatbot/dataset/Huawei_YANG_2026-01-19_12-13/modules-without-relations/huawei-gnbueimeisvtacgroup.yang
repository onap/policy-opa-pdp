module huawei-gnbueimeisvtacgroup {
 yang-version 1.1;
 namespace "urn:rdns:com:huawei:oammodel:huawei-gnbueimeisvtacgroup";
 prefix gnbueimeisvtacgroup;
 description
 "Auto-generated modular YANG for huawei-gnbueimeisvtacgroup" ;
 revision "2026-01-19" {
 description "Auto-generated initial revision. Generated at 2026-01-19 12:13.";
 }
 grouping GNBUEIMEISVTACGROUP-attributes {
 leaf OLD_UEIMEISVTAC {
  type union {
   type int32 {
    range "-1..99999999";
   }
  }
  mandatory false;
 }
 leaf UEIMEISVTAC {
  type union {
   type int32 {
    range "-1..99999999";
   }
  }
  mandatory false;
 }
 leaf OLD_UEIMEISVTACGROUPID {
  type union {
   type int16 {
    range "-1..255";
   }
  }
  mandatory false;
 }
 leaf UEIMEISVTACGROUPID {
  type union {
   type int16 {
    range "-1..255";
   }
  }
  mandatory false;
 }
 }
}
