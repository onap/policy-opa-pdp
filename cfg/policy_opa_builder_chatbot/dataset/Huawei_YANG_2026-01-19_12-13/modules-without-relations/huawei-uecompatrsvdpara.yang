module huawei-uecompatrsvdpara {
 yang-version 1.1;
 namespace "urn:rdns:com:huawei:oammodel:huawei-uecompatrsvdpara";
 prefix uecompatrsvdpara;
 description
 "Auto-generated modular YANG for huawei-uecompatrsvdpara" ;
 revision "2026-01-19" {
 description "Auto-generated initial revision. Generated at 2026-01-19 12:13.";
 }
 grouping UECOMPATRSVDPARA-attributes {
 leaf INDEX {
  type union {
   type int8 {
    range "-1..127";
   }
  }
  mandatory false;
 }
 leaf RSVDSWPARA0 {
  type string;
  mandatory false;
 }
 leaf RSVDSWPARA1 {
  type string;
  mandatory false;
 }
 }
}
