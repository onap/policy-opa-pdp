module huawei-pingfilter {
 yang-version 1.1;
 namespace "urn:rdns:com:huawei:oammodel:huawei-pingfilter";
 prefix pingfilter;
 import ietf-interfaces {
 prefix if;
 }
 import ietf-ip {
 prefix ip;
 }
 import ietf-inet-types {
 prefix inet;
 }
 description
 "Auto-generated modular YANG for huawei-pingfilter" ;
 revision "2026-01-19" {
 description "Auto-generated initial revision. Generated at 2026-01-19 12:13.";
 }
 augment "/if:interfaces/if:interface/ip:ipv4" {
 container pingfilter-ipv4 {
  container attributes {
   uses PINGFILTER-attributes {
    /* opcjonalnie: tu można ograniczyć do IP-only */
   }
  }
 }
}
 grouping PINGFILTER-attributes {
 leaf OLD_IP {
  type inet:ipv4-address;
  mandatory false;
 }
 leaf IP {
  type inet:ipv4-address;
  mandatory false;
 }
 leaf OLD_MASK {
  type inet:ipv4-address;
  mandatory false;
 }
 leaf MASK {
  type inet:ipv4-address;
  mandatory false;
 }
 leaf OLD_VRFIDX {
  type union {
   type int8 {
    range "-1..31";
   }
  }
  mandatory false;
 }
 leaf VRFIDX {
  type union {
   type int8 {
    range "-1..31";
   }
  }
  mandatory false;
 }
 }
}
