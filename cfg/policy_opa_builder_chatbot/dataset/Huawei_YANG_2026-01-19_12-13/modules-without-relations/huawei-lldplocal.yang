module huawei-lldplocal {
 yang-version 1.1;
 namespace "urn:rdns:com:huawei:oammodel:huawei-lldplocal";
 prefix lldplocal;
 description
 "Auto-generated modular YANG for huawei-lldplocal" ;
 revision "2026-01-19" {
 description "Auto-generated initial revision. Generated at 2026-01-19 12:13.";
 }
 grouping LLDPLOCAL-attributes {
 leaf BNDVLAN {
  type boolean;
  mandatory false;
 }
 leaf CN {
  type union {
   type int8 {
    range "-1..7";
   }
  }
  mandatory false;
 }
 leaf PN {
  type union {
   type int8 {
    range "-1..5";
   }
  }
  mandatory false;
 }
 leaf SBT {
  type enumeration {
   enum val--1;
   enum val-0;
   enum val-5;
  }
  mandatory false;
 }
 leaf SN {
  type union {
   type int8 {
    range "-1..7";
   }
  }
  mandatory false;
 }
 leaf SRN {
  type union {
   type int8 {
    range "-1..1";
   }
  }
  mandatory false;
 }
 leaf VLANID {
  type uint16 {
   range "1..4094";
  }
  mandatory false;
 }
 leaf VLANPRI {
  type uint8 {
   range "0..7";
  }
  mandatory false;
 }
 }
}
