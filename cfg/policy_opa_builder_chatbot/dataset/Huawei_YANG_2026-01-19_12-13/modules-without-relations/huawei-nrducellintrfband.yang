module huawei-nrducellintrfband {
 yang-version 1.1;
 namespace "urn:rdns:com:huawei:oammodel:huawei-nrducellintrfband";
 prefix nrducellintrfband;
 description
 "Auto-generated modular YANG for huawei-nrducellintrfband" ;
 revision "2026-01-19" {
 description "Auto-generated initial revision. Generated at 2026-01-19 12:13.";
 }
 grouping NRDUCELLINTRFBAND-attributes {
 leaf ENDRB {
  type uint16 {
   range "0..272";
  }
  mandatory false;
 }
 leaf OLD_INTERFERENCEBANDINDEX {
  type union {
   type int8 {
    range "-1..5";
   }
  }
  mandatory false;
 }
 leaf INTERFERENCEBANDINDEX {
  type union {
   type int8 {
    range "-1..5";
   }
  }
  mandatory false;
 }
 leaf INTERFERENCEDIRECTION {
  type enumeration {
   enum val-0;
   enum val-1;
   enum val-2;
  }
  mandatory false;
 }
 leaf OLD_NRDUCELLID {
  type union {
   type int32 {
    range "-1..65534";
   }
  }
  mandatory false;
 }
 leaf NRDUCELLID {
  type union {
   type int32 {
    range "-1..65534";
   }
  }
  mandatory false;
 }
 leaf STARTRB {
  type uint16 {
   range "0..272";
  }
  mandatory false;
 }
 }
}
