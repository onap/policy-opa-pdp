module huawei-gnbcux2interface {
 yang-version 1.1;
 namespace "urn:rdns:com:huawei:oammodel:huawei-gnbcux2interface";
 prefix gnbcux2interface;
 description
 "Auto-generated modular YANG for huawei-gnbcux2interface" ;
 revision "2026-01-19" {
 description "Auto-generated initial revision. Generated at 2026-01-19 12:13.";
 }
 grouping GNBCUX2INTERFACE-attributes {
 leaf GNBCUX2CPBEARERID {
  type uint32 {
   range "70000..79999";
  }
  mandatory false;
 }
 leaf OLD_GNBCUX2INTERFACEID {
  type union {
   type int32 {
    range "-1..65535";
   }
  }
  mandatory false;
 }
 leaf GNBCUX2INTERFACEID {
  type union {
   type int32 {
    range "-1..65535";
   }
  }
  mandatory false;
 }
 }
}
