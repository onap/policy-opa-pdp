module huawei-mdu {
 yang-version 1.1;
 namespace "urn:rdns:com:huawei:oammodel:huawei-mdu";
 prefix mdu;
 description
 "Auto-generated modular YANG for huawei-mdu" ;
 revision "2026-01-19" {
 description "Auto-generated initial revision. Generated at 2026-01-19 12:13.";
 }
 grouping MDU-attributes {
 leaf ADMSTATE {
  type boolean;
  mandatory false;
 }
 leaf BBWS {
  type string;
  mandatory false;
 }
 leaf BLKTP {
  type enumeration {
   enum val-0;
   enum val-1;
   enum val-2;
  }
  mandatory false;
 }
 leaf BRDSPEC {
  type string {
   length "0..15";
  }
  mandatory false;
 }
 leaf CCNE {
  type boolean;
  mandatory false;
 }
 leaf OLD_CN {
  type union {
   type int8 {
    range "-1..7";
   }
  }
  mandatory false;
 }
 leaf CN {
  type union {
   type int8 {
    range "-1..7";
   }
  }
  mandatory false;
 }
 leaf FRAMEOFFSETMODE {
  type boolean;
  mandatory false;
 }
 leaf OLD_SN {
  type union {
   type int8 {
    range "-1..6";
   }
  }
  mandatory false;
 }
 leaf SN {
  type union {
   type int8 {
    range "-1..6";
   }
  }
  mandatory false;
 }
 leaf OLD_SRN {
  type union {
   type int8 {
    range "-1..1";
   }
  }
  mandatory false;
 }
 leaf SRN {
  type union {
   type int8 {
    range "-1..1";
   }
  }
  mandatory false;
 }
 leaf TIME {
  type uint32 {
   range "0..4294967295";
  }
  mandatory false;
 }
 leaf TYPE {
  type enumeration {
   enum val-50;
   enum val-51;
  }
  mandatory false;
 }
 leaf WM {
  type enumeration {
   enum val-14;
   enum val-18;
   enum val-22;
  }
  mandatory false;
 }
 }
}
