module huawei-cascadeport {
 yang-version 1.1;
 namespace "urn:rdns:com:huawei:oammodel:huawei-cascadeport";
 prefix cascadeport;
 description
 "Auto-generated modular YANG for huawei-cascadeport" ;
 revision "2026-01-19" {
 description "Auto-generated initial revision. Generated at 2026-01-19 12:13.";
 }
 grouping CASCADEPORT-attributes {
 leaf CN {
  type union {
   type int8 {
    range "-1..7";
   }
  }
  mandatory false;
 }
 leaf PM {
  type enumeration {
   enum val-0;
   enum val-1;
   enum val-2;
   enum val-3;
   enum val-4;
  }
  mandatory false;
 }
 leaf PN {
  type union {
   type int8 {
    range "-1..8";
   }
  }
  mandatory false;
 }
 leaf PT {
  type enumeration {
   enum val--1;
   enum val-0;
   enum val-1;
  }
  mandatory false;
 }
 leaf SN {
  type union {
   type int8 {
    range "-1..7";
   }
  }
  mandatory false;
 }
 leaf SRN {
  type union {
   type int8 {
    range "-1..1";
   }
  }
  mandatory false;
 }
 leaf SW {
  type boolean;
  mandatory false;
 }
 }
}
