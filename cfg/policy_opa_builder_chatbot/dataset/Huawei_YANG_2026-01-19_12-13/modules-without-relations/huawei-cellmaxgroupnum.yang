module huawei-cellmaxgroupnum {
 yang-version 1.1;
 namespace "urn:rdns:com:huawei:oammodel:huawei-cellmaxgroupnum";
 prefix cellmaxgroupnum;
 description
 "Auto-generated modular YANG for huawei-cellmaxgroupnum" ;
 revision "2026-01-19" {
 description "Auto-generated initial revision. Generated at 2026-01-19 12:13.";
 }
 grouping CELLMAXGROUPNUM-attributes {
 leaf LOCALCELLNAME {
  type string;
  mandatory false;
 }
 leaf LOCALCELLID {
  type union {
   type int16 {
    range "-1..255";
   }
  }
  mandatory false;
 }
 leaf MAXPSGROUPNUM {
  type uint8 {
   range "0..200";
  }
  mandatory false;
 }
 }
}
