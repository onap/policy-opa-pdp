module huawei-dieselgen {
 yang-version 1.1;
 namespace "urn:rdns:com:huawei:oammodel:huawei-dieselgen";
 prefix dieselgen;
 description
 "Auto-generated modular YANG for huawei-dieselgen" ;
 revision "2026-01-19" {
 description "Auto-generated initial revision. Generated at 2026-01-19 12:13.";
 }
 grouping DIESELGEN-attributes {
 leaf CN {
  type union {
   type int8 {
    range "-1..62";
   }
  }
  mandatory false;
 }
 leaf ICF {
  type boolean;
  mandatory false;
 }
 leaf POWER {
  type uint16 {
   range "1..1000";
  }
  mandatory false;
 }
 leaf SN {
  type union {
   type int8 {
    range "-1..0";
   }
  }
  mandatory false;
 }
 leaf SRN {
  type union {
   type int8 {
    range "-1..7";
   }
  }
  mandatory false;
 }
 }
}
