module huawei-enodeboamparam {
 yang-version 1.1;
 namespace "urn:rdns:com:huawei:oammodel:huawei-enodeboamparam";
 prefix enodeboamparam;
 import ietf-inet-types {
 prefix inet;
 }
 description
 "Auto-generated modular YANG for huawei-enodeboamparam" ;
 revision "2026-01-19" {
 description "Auto-generated initial revision. Generated at 2026-01-19 12:13.";
 }
 grouping ENODEBOAMPARAM-attributes {
 leaf CONFIGADAPTOPTSWITCH {
  type string;
  mandatory false;
 }
 leaf INTERFACESONCONFIGSWITCH {
  type string;
  mandatory false;
 }
 leaf TRANSPORTOAMSWITCH {
  type inet:port-number;
  mandatory false;
 }
 }
}
