module huawei-nodebclspatimer {
 yang-version 1.1;
 namespace "urn:rdns:com:huawei:oammodel:huawei-nodebclspatimer";
 prefix nodebclspatimer;
 description
 "Auto-generated modular YANG for huawei-nodebclspatimer" ;
 revision "2026-01-19" {
 description "Auto-generated initial revision. Generated at 2026-01-19 12:13.";
 }
 grouping NODEBCLSPATIMER-attributes {
 leaf LOWERLIMIT {
  type uint8 {
   range "0..255";
  }
  mandatory false;
 }
 leaf UPPERLIMIT {
  type uint8 {
   range "0..255";
  }
  mandatory false;
 }
 }
}
