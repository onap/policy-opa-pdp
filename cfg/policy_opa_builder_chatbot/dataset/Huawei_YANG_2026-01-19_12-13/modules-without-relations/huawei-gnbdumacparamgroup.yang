module huawei-gnbdumacparamgroup {
 yang-version 1.1;
 namespace "urn:rdns:com:huawei:oammodel:huawei-gnbdumacparamgroup";
 prefix gnbdumacparamgroup;
 description
 "Auto-generated modular YANG for huawei-gnbdumacparamgroup" ;
 revision "2026-01-19" {
 description "Auto-generated initial revision. Generated at 2026-01-19 12:13.";
 }
 grouping GNBDUMACPARAMGROUP-attributes {
 leaf DLEXPBASEDSCHGUARUSERRATE {
  type uint32 {
   range "0..1000000";
  }
  mandatory false;
 }
 leaf DLGUARANTEEDRATE {
  type uint32 {
   range "0..1000000";
  }
  mandatory false;
 }
 leaf DLSCHPRIWEIGHTFACTOR {
  type uint16 {
   range "1..1000";
  }
  mandatory false;
 }
 leaf LOGICALCHNGRPID {
  type uint8 {
   range "0..7";
  }
  mandatory false;
 }
 leaf LOGICALCHNPRIORITY {
  type uint8 {
   range "1..16";
  }
  mandatory false;
 }
 leaf OLD_MACPARAMGROUPID {
  type union {
   type int16 {
    range "-1..172";
   }
  }
  mandatory false;
 }
 leaf MACPARAMGROUPID {
  type union {
   type int16 {
    range "-1..172";
   }
  }
  mandatory false;
 }
 leaf SCHEDULINGTYPE {
  type enumeration {
   enum val-0;
   enum val-1;
   enum val-2;
   enum val-3;
   enum val-4;
   enum val-5;
   enum val-6;
  }
  mandatory false;
 }
 leaf ULEXPBASEDSCHGUARUSERRATE {
  type uint32 {
   range "0..1000000";
  }
  mandatory false;
 }
 leaf ULGUARANTEEDRATE {
  type uint32 {
   range "0..1000000";
  }
  mandatory false;
 }
 leaf ULSCHPRIWEIGHTFACTOR {
  type uint16 {
   range "1..1000";
  }
  mandatory false;
 }
 }
}
