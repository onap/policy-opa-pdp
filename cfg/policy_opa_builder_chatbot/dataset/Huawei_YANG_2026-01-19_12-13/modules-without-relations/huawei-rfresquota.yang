module huawei-rfresquota {
 yang-version 1.1;
 namespace "urn:rdns:com:huawei:oammodel:huawei-rfresquota";
 prefix rfresquota;
 description
 "Auto-generated modular YANG for huawei-rfresquota" ;
 revision "2026-01-19" {
 description "Auto-generated initial revision. Generated at 2026-01-19 12:13.";
 }
 grouping RFRESQUOTA-attributes {
 leaf BANDMAXFREQ {
  type uint32 {
   range "0..4294967295";
  }
  mandatory false;
 }
 leaf BANDMINFREQ {
  type uint32 {
   range "0..4294967295";
  }
  mandatory false;
 }
 leaf MAXPWR {
  type uint16 {
   range "0..40000";
  }
  mandatory false;
 }
 leaf RCSCLIENTNO {
  type uint8 {
   range "0..3";
  }
  mandatory false;
 }
 leaf OLD_RFRESQUOTAID {
  type union {
   type int8 {
    range "-1..127";
   }
  }
  mandatory false;
 }
 leaf RFRESQUOTAID {
  type union {
   type int8 {
    range "-1..127";
   }
  }
  mandatory false;
 }
 leaf SCOPE {
  type boolean;
  mandatory false;
 }
 }
}
