module huawei-nrducellsimulateload {
 yang-version 1.1;
 namespace "urn:rdns:com:huawei:oammodel:huawei-nrducellsimulateload";
 prefix nrducellsimulateload;
 description
 "Auto-generated modular YANG for huawei-nrducellsimulateload" ;
 revision "2026-01-19" {
 description "Auto-generated initial revision. Generated at 2026-01-19 12:13.";
 }
 grouping NRDUCELLSIMULATELOAD-attributes {
 leaf BEAMPOLARIZATION {
  type enumeration {
   enum val-0;
   enum val-1;
   enum val-2;
   enum val-3;
  }
  mandatory false;
 }
 leaf NRDUCELLID {
  type union {
   type int32 {
    range "-1..65534";
   }
  }
  mandatory false;
 }
 leaf SIMULATEDLOADENHSWITCH {
  type boolean;
  mandatory false;
 }
 }
}
