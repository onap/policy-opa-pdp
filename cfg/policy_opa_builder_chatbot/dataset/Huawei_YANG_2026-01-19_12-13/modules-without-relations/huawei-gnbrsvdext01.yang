module huawei-gnbrsvdext01 {
 yang-version 1.1;
 namespace "urn:rdns:com:huawei:oammodel:huawei-gnbrsvdext01";
 prefix gnbrsvdext01;
 description
 "Auto-generated modular YANG for huawei-gnbrsvdext01" ;
 revision "2026-01-19" {
 description "Auto-generated initial revision. Generated at 2026-01-19 12:13.";
 }
 grouping GNBRSVDEXT01-attributes {
 leaf RSVDSWPARAM0 {
  type string;
  mandatory false;
 }
 leaf RSVDSWPARAM1 {
  type string;
  mandatory false;
 }
 leaf RSVDSWPARAM2 {
  type string;
  mandatory false;
 }
 leaf RSVDSWPARAM3 {
  type string;
  mandatory false;
 }
 leaf RSVDSWPARAM4 {
  type string;
  mandatory false;
 }
 }
}
