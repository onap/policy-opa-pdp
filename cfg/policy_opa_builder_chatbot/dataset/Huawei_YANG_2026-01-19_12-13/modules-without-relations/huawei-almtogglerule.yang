module huawei-almtogglerule {
 yang-version 1.1;
 namespace "urn:rdns:com:huawei:oammodel:huawei-almtogglerule";
 prefix almtogglerule;
 description
 "Auto-generated modular YANG for huawei-almtogglerule" ;
 revision "2026-01-19" {
 description "Auto-generated initial revision. Generated at 2026-01-19 12:13.";
 }
 grouping ALMTOGGLERULE-attributes {
 leaf OLD_ALARMID {
  type union {
   type int32 {
    range "-1..65533";
   }
  }
  mandatory false;
 }
 leaf ALARMID {
  type union {
   type int32 {
    range "-1..65533";
   }
  }
  mandatory false;
 }
 leaf ALMTOGGLESWITCH {
  type boolean;
  mandatory false;
 }
 }
}
