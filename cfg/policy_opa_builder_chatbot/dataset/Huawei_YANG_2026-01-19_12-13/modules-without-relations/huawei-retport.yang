module huawei-retport {
 yang-version 1.1;
 namespace "urn:rdns:com:huawei:oammodel:huawei-retport";
 prefix retport;
 description
 "Auto-generated modular YANG for huawei-retport" ;
 revision "2026-01-19" {
 description "Auto-generated initial revision. Generated at 2026-01-19 12:13.";
 }
 grouping RETPORT-attributes {
 leaf CN {
  type union {
   type int8 {
    range "-1..15";
   }
  }
  mandatory false;
 }
 leaf OCTHD {
  type uint16 {
   range "0..3500";
  }
  mandatory false;
 }
 leaf OOTHD {
  type uint16 {
   range "0..3500";
  }
  mandatory false;
 }
 leaf PN {
  type enumeration {
   enum val--1;
   enum val-2;
  }
  mandatory false;
 }
 leaf PWRSWITCH {
  type boolean;
  mandatory false;
 }
 leaf SN {
  type union {
   type int8 {
    range "-1..5";
   }
  }
  mandatory false;
 }
 leaf SRN {
  type union {
   type int16 {
    range "-1..254";
   }
  }
  mandatory false;
 }
 leaf THRESHOLDTYPE {
  type enumeration {
   enum val-0;
   enum val-4;
   enum val-5;
   enum val-6;
   enum val-7;
   enum val-8;
  }
  mandatory false;
 }
 leaf UCTHD {
  type uint16 {
   range "0..3500";
  }
  mandatory false;
 }
 leaf UOTHD {
  type uint16 {
   range "0..3500";
  }
  mandatory false;
 }
 }
}
