module huawei-pdu {
 yang-version 1.1;
 namespace "urn:rdns:com:huawei:oammodel:huawei-pdu";
 prefix pdu;
 description
 "Auto-generated modular YANG for huawei-pdu" ;
 revision "2026-01-19" {
 description "Auto-generated initial revision. Generated at 2026-01-19 12:13.";
 }
 grouping PDU-attributes {
 leaf OLD_CN {
  type union {
   type int8 {
    range "-1..62";
   }
  }
  mandatory false;
 }
 leaf CN {
  type union {
   type int8 {
    range "-1..62";
   }
  }
  mandatory false;
 }
 leaf GPSM {
  type boolean;
  mandatory false;
 }
 leaf PDUTYPE {
  type boolean;
  mandatory false;
 }
 leaf OLD_SN {
  type union {
   type int8 {
    range "-1..12";
   }
  }
  mandatory false;
 }
 leaf SN {
  type union {
   type int8 {
    range "-1..12";
   }
  }
  mandatory false;
 }
 leaf OLD_SRN {
  type union {
   type int8 {
    range "-1..18";
   }
  }
  mandatory false;
 }
 leaf SRN {
  type union {
   type int8 {
    range "-1..18";
   }
  }
  mandatory false;
 }
 }
}
