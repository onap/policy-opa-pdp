module huawei-nrducellconnmgmt {
 yang-version 1.1;
 namespace "urn:rdns:com:huawei:oammodel:huawei-nrducellconnmgmt";
 prefix nrducellconnmgmt;
 description
 "Auto-generated modular YANG for huawei-nrducellconnmgmt" ;
 revision "2026-01-19" {
 description "Auto-generated initial revision. Generated at 2026-01-19 12:13.";
 }
 grouping NRDUCELLCONNMGMT-attributes {
 leaf IABCTRLSWITCH {
  type string;
  mandatory false;
 }
 leaf NRDUCELLID {
  type union {
   type int32 {
    range "-1..65534";
   }
  }
  mandatory false;
 }
 }
}
