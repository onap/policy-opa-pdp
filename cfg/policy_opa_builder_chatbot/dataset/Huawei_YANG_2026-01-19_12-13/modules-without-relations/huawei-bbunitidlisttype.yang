module huawei-bbunitidlisttype {
 yang-version 1.1;
 namespace "urn:rdns:com:huawei:oammodel:huawei-bbunitidlisttype";
 prefix bbunitidlisttype;
 description
 "Auto-generated modular YANG for huawei-bbunitidlisttype" ;
 revision "2026-01-19" {
 description "Auto-generated initial revision. Generated at 2026-01-19 12:13.";
 }
 grouping BBUNITIDLISTTYPE-attributes {
 leaf BBUNITID {
  type union {
   type int16 {
    range "-1..255";
   }
  }
  mandatory false;
 }
 leaf ULOCELLID {
  type union {
   type int32 {
    range "-1..268435455";
   }
  }
  mandatory false;
 }
 }
}
