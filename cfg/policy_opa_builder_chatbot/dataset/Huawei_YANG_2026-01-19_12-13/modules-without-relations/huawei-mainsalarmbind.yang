module huawei-mainsalarmbind {
 yang-version 1.1;
 namespace "urn:rdns:com:huawei:oammodel:huawei-mainsalarmbind";
 prefix mainsalarmbind;
 description
 "Auto-generated modular YANG for huawei-mainsalarmbind" ;
 revision "2026-01-19" {
 description "Auto-generated initial revision. Generated at 2026-01-19 12:13.";
 }
 grouping MAINSALARMBIND-attributes {
 leaf ISDSWITCH {
  type boolean;
  mandatory false;
 }
 leaf NMSACN {
  type uint8 {
   range "0..62";
  }
  mandatory false;
 }
 leaf NMSAPN {
  type uint8 {
   range "0..35";
  }
  mandatory false;
 }
 leaf NMSASN {
  type union {
   type uint8 {
    range "0..19";
   }
  }
  mandatory false;
 }
 leaf NMSASRN {
  type union {
   type uint8 {
    range "0..254";
   }
  }
  mandatory false;
 }
 }
}
