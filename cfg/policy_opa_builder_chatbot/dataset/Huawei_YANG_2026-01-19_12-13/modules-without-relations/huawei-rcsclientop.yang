module huawei-rcsclientop {
 yang-version 1.1;
 namespace "urn:rdns:com:huawei:oammodel:huawei-rcsclientop";
 prefix rcsclientop;
 description
 "Auto-generated modular YANG for huawei-rcsclientop" ;
 revision "2026-01-19" {
 description "Auto-generated initial revision. Generated at 2026-01-19 12:13.";
 }
 grouping RCSCLIENTOP-attributes {
 leaf RFAOPERATORID {
  type uint8 {
   range "0..5";
  }
  mandatory false;
 }
 leaf RCSCLIENTNO {
  type union {
   type int8 {
    range "-1..3";
   }
  }
  mandatory false;
 }
 }
}
