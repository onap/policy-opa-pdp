module huawei-tracetask {
 yang-version 1.1;
 namespace "urn:rdns:com:huawei:oammodel:huawei-tracetask";
 prefix tracetask;
 description
 "Auto-generated modular YANG for huawei-tracetask" ;
 revision "2026-01-19" {
 description "Auto-generated initial revision. Generated at 2026-01-19 12:13.";
 }
 grouping TRACETASK-attributes {
 leaf FLOWCONTROLLEVEL {
  type uint8 {
   range "1..5";
  }
  mandatory false;
 }
 leaf TRACETYPE {
  type enumeration {
   enum val--1;
   enum val-0;
   enum val-1;
   enum val-2;
  }
  mandatory false;
 }
 }
}
