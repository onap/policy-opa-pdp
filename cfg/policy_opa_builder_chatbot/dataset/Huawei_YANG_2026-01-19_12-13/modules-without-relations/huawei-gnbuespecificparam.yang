module huawei-gnbuespecificparam {
 yang-version 1.1;
 namespace "urn:rdns:com:huawei:oammodel:huawei-gnbuespecificparam";
 prefix gnbuespecificparam;
 description
 "Auto-generated modular YANG for huawei-gnbuespecificparam" ;
 revision "2026-01-19" {
 description "Auto-generated initial revision. Generated at 2026-01-19 12:13.";
 }
 grouping GNBUESPECIFICPARAM-attributes {
 leaf CONFIGVALUE {
  type int32 {
   range "-2147483648..2147483647";
  }
  mandatory false;
 }
 leaf MOID {
  type uint32 {
   range "0..4294967295";
  }
  mandatory false;
 }
 leaf PARACTRLSWITCH {
  type string;
  mandatory false;
 }
 leaf PARAMBITID {
  type union {
   type uint8 {
    range "0..255";
   }
  }
  mandatory false;
 }
 leaf PARAMID {
  type uint16 {
   range "0..65535";
  }
  mandatory false;
 }
 leaf SPECIFICUECONFIGDESC {
  type string {
   length "0..80";
  }
  mandatory false;
 }
 leaf OLD_SPECIFICUECONFIGINDEX {
  type union {
   type int16 {
    range "-1..255";
   }
  }
  mandatory false;
 }
 leaf SPECIFICUECONFIGINDEX {
  type union {
   type int16 {
    range "-1..255";
   }
  }
  mandatory false;
 }
 leaf UEINFOINDEX {
  type uint8 {
   range "1..128";
  }
  mandatory false;
 }
 }
}
