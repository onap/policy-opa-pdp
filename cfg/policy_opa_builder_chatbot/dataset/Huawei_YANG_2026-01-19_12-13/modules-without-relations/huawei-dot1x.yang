module huawei-dot1x {
 yang-version 1.1;
 namespace "urn:rdns:com:huawei:oammodel:huawei-dot1x";
 prefix dot1x;
 description
 "Auto-generated modular YANG for huawei-dot1x" ;
 revision "2026-01-19" {
 description "Auto-generated initial revision. Generated at 2026-01-19 12:13.";
 }
 grouping DOT1X-attributes {
 leaf AM {
  type enumeration {
   enum val-13;
  }
  mandatory false;
 }
 leaf CN {
  type union {
   type int8 {
    range "-1..7";
   }
  }
  mandatory false;
 }
 leaf PN {
  type union {
   type int8 {
    range "-1..5";
   }
  }
  mandatory false;
 }
 leaf SBT {
  type enumeration {
   enum val--1;
   enum val-0;
   enum val-5;
  }
  mandatory false;
 }
 leaf SN {
  type union {
   type int8 {
    range "-1..7";
   }
  }
  mandatory false;
 }
 leaf SRN {
  type union {
   type int8 {
    range "-1..1";
   }
  }
  mandatory false;
 }
 }
}
