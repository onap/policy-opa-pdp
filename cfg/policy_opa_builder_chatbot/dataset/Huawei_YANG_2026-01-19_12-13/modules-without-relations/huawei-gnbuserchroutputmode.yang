module huawei-gnbuserchroutputmode {
 yang-version 1.1;
 namespace "urn:rdns:com:huawei:oammodel:huawei-gnbuserchroutputmode";
 prefix gnbuserchroutputmode;
 description
 "Auto-generated modular YANG for huawei-gnbuserchroutputmode" ;
 revision "2026-01-19" {
 description "Auto-generated initial revision. Generated at 2026-01-19 12:13.";
 }
 grouping GNBUSERCHROUTPUTMODE-attributes {
 leaf CHROUTPUTPOLICY {
  type boolean;
  mandatory false;
 }
 leaf OLD_USERTYPE {
  type enumeration {
   enum val--1;
   enum val-0;
  }
  mandatory false;
 }
 leaf USERTYPE {
  type enumeration {
   enum val--1;
   enum val-0;
  }
  mandatory false;
 }
 }
}
