module huawei-phyport {
 yang-version 1.1;
 namespace "urn:rdns:com:huawei:oammodel:huawei-phyport";
 prefix phyport;
 description
 "Auto-generated modular YANG for huawei-phyport" ;
 revision "2026-01-19" {
 description "Auto-generated initial revision. Generated at 2026-01-19 12:13.";
 }
 grouping PHYPORT-attributes {
 leaf ADMINISTRATIVESTATE {
  type boolean;
  mandatory false;
 }
 leaf CN {
  type union {
   type int8 {
    range "-1..7";
   }
  }
  mandatory false;
 }
 leaf PN {
  type union {
   type int8 {
    range "-1..1";
   }
  }
  mandatory false;
 }
 leaf PT {
  type enumeration {
   enum val--1;
   enum val-0;
   enum val-1;
   enum val-2;
  }
  mandatory false;
 }
 leaf SN {
  type union {
   type int8 {
    range "-1..7";
   }
  }
  mandatory false;
 }
 leaf SRN {
  type union {
   type int8 {
    range "-1..1";
   }
  }
  mandatory false;
 }
 }
}
