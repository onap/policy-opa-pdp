module huawei-nrexternalgnb {
 yang-version 1.1;
 namespace "urn:rdns:com:huawei:oammodel:huawei-nrexternalgnb";
 prefix nrexternalgnb;
 description
 "Auto-generated modular YANG for huawei-nrexternalgnb" ;
 revision "2026-01-19" {
 description "Auto-generated initial revision. Generated at 2026-01-19 12:13.";
 }
 grouping NREXTERNALGNB-attributes {
 leaf COMPATIBILITYCONFIG {
  type string;
  mandatory false;
 }
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf PLMNPOLICY {
  type boolean;
  mandatory false;
 }
 leaf OLD_GNBID {
  type union {
   type int64 {
    range "-1..4294967295";
   }
  }
  mandatory false;
 }
 leaf GNBID {
  type union {
   type int64 {
    range "-1..4294967295";
   }
  }
  mandatory false;
 }
 }
}
