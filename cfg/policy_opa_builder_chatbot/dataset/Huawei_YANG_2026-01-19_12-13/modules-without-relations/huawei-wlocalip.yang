module huawei-wlocalip {
 yang-version 1.1;
 namespace "urn:rdns:com:huawei:oammodel:huawei-wlocalip";
 prefix wlocalip;
 import ietf-interfaces {
 prefix if;
 }
 import ietf-ip {
 prefix ip;
 }
 import ietf-inet-types {
 prefix inet;
 }
 description
 "Auto-generated modular YANG for huawei-wlocalip" ;
 revision "2026-01-19" {
 description "Auto-generated initial revision. Generated at 2026-01-19 12:13.";
 }
 augment "/if:interfaces/if:interface/ip:ipv4" {
 container wlocalip-ipv4 {
  container attributes {
   uses WLOCALIP-attributes {
    /* opcjonalnie: tu można ograniczyć do IP-only */
   }
  }
 }
}
 grouping WLOCALIP-attributes {
 leaf IP {
  type inet:ipv4-address;
  mandatory false;
 }
 leaf OLD_IPIDX {
  type union {
   type int8 {
    range "-1..0";
   }
  }
  mandatory false;
 }
 leaf IPIDX {
  type union {
   type int8 {
    range "-1..0";
   }
  }
  mandatory false;
 }
 leaf MASK {
  type inet:ipv4-address;
  mandatory false;
 }
 }
}
