module huawei-trustcert2group {
 yang-version 1.1;
 namespace "urn:rdns:com:huawei:oammodel:huawei-trustcert2group";
 prefix trustcert2group;
 description
 "Auto-generated modular YANG for huawei-trustcert2group" ;
 revision "2026-01-19" {
 description "Auto-generated initial revision. Generated at 2026-01-19 12:13.";
 }
 grouping TRUSTCERT2GROUP-attributes {
 leaf OLD_CERTNAME {
  type string {
   length "1..64";
  }
  mandatory false;
 }
 leaf CERTNAME {
  type string {
   length "1..64";
  }
  mandatory false;
 }
 leaf OLD_TRUSTGROUPID {
  type union {
   type int8 {
    range "-1..7";
   }
  }
  mandatory false;
 }
 leaf TRUSTGROUPID {
  type union {
   type int8 {
    range "-1..7";
   }
  }
  mandatory false;
 }
 }
}
