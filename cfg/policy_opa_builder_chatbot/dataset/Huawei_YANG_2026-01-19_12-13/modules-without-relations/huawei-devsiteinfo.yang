module huawei-devsiteinfo {
 yang-version 1.1;
 namespace "urn:rdns:com:huawei:oammodel:huawei-devsiteinfo";
 prefix devsiteinfo;
 description
 "Auto-generated modular YANG for huawei-devsiteinfo" ;
 revision "2026-01-19" {
 description "Auto-generated initial revision. Generated at 2026-01-19 12:13.";
 }
 grouping DEVSITEINFO-attributes {
 leaf CN {
  type union {
   type int8 {
    range "-1..15";
   }
  }
  mandatory false;
 }
 leaf RFPHYSITEID {
  type uint16 {
   range "0..1023";
  }
  mandatory false;
 }
 leaf SN {
  type union {
   type int8 {
    range "-1..5";
   }
  }
  mandatory false;
 }
 leaf SRN {
  type union {
   type int16 {
    range "-1..254";
   }
  }
  mandatory false;
 }
 }
}
