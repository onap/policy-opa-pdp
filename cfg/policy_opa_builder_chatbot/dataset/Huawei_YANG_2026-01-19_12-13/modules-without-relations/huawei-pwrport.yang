module huawei-pwrport {
 yang-version 1.1;
 namespace "urn:rdns:com:huawei:oammodel:huawei-pwrport";
 prefix pwrport;
 description
 "Auto-generated modular YANG for huawei-pwrport" ;
 revision "2026-01-19" {
 description "Auto-generated initial revision. Generated at 2026-01-19 12:13.";
 }
 grouping PWRPORT-attributes {
 leaf CN {
  type union {
   type int8 {
    range "-1..7";
   }
  }
  mandatory false;
 }
 leaf PN {
  type union {
   type int8 {
    range "-1..0";
   }
  }
  mandatory false;
 }
 leaf POWERTYPE {
  type boolean;
  mandatory false;
 }
 leaf SN {
  type union {
   type int8 {
    range "-1..19";
   }
  }
  mandatory false;
 }
 leaf SRN {
  type union {
   type int8 {
    range "-1..1";
   }
  }
  mandatory false;
 }
 }
}
