module huawei-subif {
 yang-version 1.1;
 namespace "urn:rdns:com:huawei:oammodel:huawei-subif";
 prefix subif;
 description
 "Auto-generated modular YANG for huawei-subif" ;
 revision "2026-01-19" {
 description "Auto-generated initial revision. Generated at 2026-01-19 12:13.";
 }
 grouping SUBIF-attributes {
 leaf ARPPROXY {
  type boolean;
  mandatory false;
 }
 leaf OLD_CN {
  type union {
   type int8 {
    range "-1..7";
   }
  }
  mandatory false;
 }
 leaf CN {
  type union {
   type int8 {
    range "-1..7";
   }
  }
  mandatory false;
 }
 leaf OLD_ID {
  type union {
   type int8 {
    range "-1..63";
   }
  }
  mandatory false;
 }
 leaf ID {
  type union {
   type int8 {
    range "-1..63";
   }
  }
  mandatory false;
 }
 leaf PN {
  type uint8 {
   range "0..3";
  }
  mandatory false;
 }
 leaf PT {
  type enumeration {
   enum val-3;
   enum val-4;
  }
  mandatory false;
 }
 leaf OLD_SBT {
  type enumeration {
   enum val--1;
   enum val-0;
  }
  mandatory false;
 }
 leaf SBT {
  type enumeration {
   enum val--1;
   enum val-0;
  }
  mandatory false;
 }
 leaf OLD_SN {
  type union {
   type int8 {
    range "-1..7";
   }
  }
  mandatory false;
 }
 leaf SN {
  type union {
   type int8 {
    range "-1..7";
   }
  }
  mandatory false;
 }
 leaf OLD_SRN {
  type union {
   type int8 {
    range "-1..1";
   }
  }
  mandatory false;
 }
 leaf SRN {
  type union {
   type int8 {
    range "-1..1";
   }
  }
  mandatory false;
 }
 leaf VRFIDX {
  type uint8 {
   range "0..7";
  }
  mandatory false;
 }
 }
}
