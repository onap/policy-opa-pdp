module huawei-gnbeqvplmn {
 yang-version 1.1;
 namespace "urn:rdns:com:huawei:oammodel:huawei-gnbeqvplmn";
 prefix gnbeqvplmn;
 description
 "Auto-generated modular YANG for huawei-gnbeqvplmn" ;
 revision "2026-01-19" {
 description "Auto-generated initial revision. Generated at 2026-01-19 12:13.";
 }
 grouping GNBEQVPLMN-attributes {
 leaf EQUIVALENTMCC {
  type string {
   length "3";
  }
  mandatory false;
 }
 leaf EQUIVALENTMNC {
  type string {
   length "2..3";
  }
  mandatory false;
 }
 leaf OPERATORID {
  type union {
   type int8 {
    range "-1..11";
   }
  }
  mandatory false;
 }
 }
}
