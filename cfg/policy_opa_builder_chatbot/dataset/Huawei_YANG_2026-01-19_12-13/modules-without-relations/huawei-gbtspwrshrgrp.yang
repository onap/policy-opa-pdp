module huawei-gbtspwrshrgrp {
 yang-version 1.1;
 namespace "urn:rdns:com:huawei:oammodel:huawei-gbtspwrshrgrp";
 prefix gbtspwrshrgrp;
 description
 "Auto-generated modular YANG for huawei-gbtspwrshrgrp" ;
 revision "2026-01-19" {
 description "Auto-generated initial revision. Generated at 2026-01-19 12:13.";
 }
 grouping GBTSPWRSHRGRP-attributes {
 leaf PWRSHAREGSMBUSYRSVPWR {
  type union {
   type uint16 {
    range "0..65535";
   }
  }
  mandatory false;
 }
 leaf PWRSHAREGSMIDLEHS {
  type uint8 {
   range "0..255";
  }
  mandatory false;
 }
 leaf PWRSHAREGSMIDLERSVPWR {
  type union {
   type uint16 {
    range "0..65535";
   }
  }
  mandatory false;
 }
 leaf PWRSHAREGSMIDLETH {
  type uint8 {
   range "0..255";
  }
  mandatory false;
 }
 leaf PWRSHAREPWRLOAD {
  type uint8 {
   range "0..100";
  }
  mandatory false;
 }
 leaf PWRSHARERCVPWR {
  type union {
   type uint16 {
    range "0..65535";
   }
  }
  mandatory false;
 }
 leaf PWRSHARERCVPWRPD {
  type union {
   type uint16 {
    range "0..65535";
   }
  }
  mandatory false;
 }
 leaf PWRSHARERSVFACTOR {
  type uint8 {
   range "0..100";
  }
  mandatory false;
 }
 leaf PWRSHARETM {
  type string;
  mandatory false;
 }
 leaf PWRSHARETRXNUM {
  type uint8 {
   range "1..255";
  }
  mandatory false;
 }
 leaf OLD_PWRSHRGRPID {
  type union {
   type int32 {
    range "-1..65535";
   }
  }
  mandatory false;
 }
 leaf PWRSHRGRPID {
  type union {
   type int32 {
    range "-1..65535";
   }
  }
  mandatory false;
 }
 leaf PWRSHRTYPE {
  type enumeration {
   enum val-0;
   enum val-1;
   enum val-2;
  }
  mandatory false;
 }
 leaf SECTOREQMID1 {
  type uint16 {
   range "0..65535";
  }
  mandatory false;
 }
 leaf SECTOREQMID2 {
  type uint16 {
   range "0..65535";
  }
  mandatory false;
 }
 }
}
