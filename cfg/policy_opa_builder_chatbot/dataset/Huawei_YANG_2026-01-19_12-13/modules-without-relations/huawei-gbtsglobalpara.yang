module huawei-gbtsglobalpara {
 yang-version 1.1;
 namespace "urn:rdns:com:huawei:oammodel:huawei-gbtsglobalpara";
 prefix gbtsglobalpara;
 description
 "Auto-generated modular YANG for huawei-gbtsglobalpara" ;
 revision "2026-01-19" {
 description "Auto-generated initial revision. Generated at 2026-01-19 12:13.";
 }
 grouping GBTSGLOBALPARA-attributes {
 leaf CLOCKPHASEADJOPTSW {
  type boolean;
  mandatory false;
 }
 leaf MCSTANDARD {
  type enumeration {
   enum val-0;
   enum val-1;
   enum val-2;
   enum val-3;
  }
  mandatory false;
 }
 }
}
