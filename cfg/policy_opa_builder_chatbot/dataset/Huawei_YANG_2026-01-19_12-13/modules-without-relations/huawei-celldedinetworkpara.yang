module huawei-celldedinetworkpara {
 yang-version 1.1;
 namespace "urn:rdns:com:huawei:oammodel:huawei-celldedinetworkpara";
 prefix celldedinetworkpara;
 description
 "Auto-generated modular YANG for huawei-celldedinetworkpara" ;
 revision "2026-01-19" {
 description "Auto-generated initial revision. Generated at 2026-01-19 12:13.";
 }
 grouping CELLDEDINETWORKPARA-attributes {
 leaf LOCALCELLNAME {
  type string;
  mandatory false;
 }
 leaf BSRUPDATEOFFSET {
  type uint8 {
   range "0..19";
  }
  mandatory false;
 }
 leaf BTRUNCDLTIMECOORDSTARTPOS {
  type union {
   type uint8 {
    range "0..255";
   }
  }
  mandatory false;
 }
 leaf CELLDEDINETWORKFUNSWITCH {
  type string;
  mandatory false;
 }
 leaf DEDINETWORKSIB20TYPE {
  type boolean;
  mandatory false;
 }
 leaf EDGEBANDINDEX {
  type uint8 {
   range "0..2";
  }
  mandatory false;
 }
 leaf EDGEBANDRATIO {
  type boolean;
  mandatory false;
 }
 leaf LOCALCELLID {
  type union {
   type int16 {
    range "-1..255";
   }
  }
  mandatory false;
 }
 leaf MAXINTERFAVOIDRBNUMRATIO {
  type uint8 {
   range "5..60";
  }
  mandatory false;
 }
 leaf MAXINTERFAVOIDRBSEGNUM {
  type uint8 {
   range "1..100";
  }
  mandatory false;
 }
 leaf RBENTERINTERFAVOIDTHLD {
  type uint8 {
   range "0..60";
  }
  mandatory false;
 }
 leaf RBEXITINTERFAVOIDTHLD {
  type uint8 {
   range "0..60";
  }
  mandatory false;
 }
 leaf RBINTERFAVOIDDETECTPERIOD {
  type uint16 {
   range "100..5000";
  }
  mandatory false;
 }
 leaf RBSLOWVARYINGTHLD {
  type uint8 {
   range "1..100";
  }
  mandatory false;
 }
 }
}
