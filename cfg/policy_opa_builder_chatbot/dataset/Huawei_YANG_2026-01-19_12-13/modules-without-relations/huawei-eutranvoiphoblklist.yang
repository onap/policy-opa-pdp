module huawei-eutranvoiphoblklist {
 yang-version 1.1;
 namespace "urn:rdns:com:huawei:oammodel:huawei-eutranvoiphoblklist";
 prefix eutranvoiphoblklist;
 description
 "Auto-generated modular YANG for huawei-eutranvoiphoblklist" ;
 revision "2026-01-19" {
 description "Auto-generated initial revision. Generated at 2026-01-19 12:13.";
 }
 grouping EUTRANVOIPHOBLKLIST-attributes {
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf OLD_TAC {
  type union {
   type int32 {
    range "-1..65535";
   }
  }
  mandatory false;
 }
 leaf TAC {
  type union {
   type int32 {
    range "-1..65535";
   }
  }
  mandatory false;
 }
 }
}
