module huawei-nrducelluecoop {
 yang-version 1.1;
 namespace "urn:rdns:com:huawei:oammodel:huawei-nrducelluecoop";
 prefix nrducelluecoop;
 description
 "Auto-generated modular YANG for huawei-nrducelluecoop" ;
 revision "2026-01-19" {
 description "Auto-generated initial revision. Generated at 2026-01-19 12:13.";
 }
 grouping NRDUCELLUECOOP-attributes {
 leaf NRDUCELLID {
  type union {
   type int32 {
    range "-1..65534";
   }
  }
  mandatory false;
 }
 leaf SPECUECOOPERATIONSWITCH {
  type string;
  mandatory false;
 }
 leaf SRSTXPORT {
  type enumeration {
   enum val-0;
   enum val-1;
   enum val-2;
  }
  mandatory false;
 }
 leaf UEACCESSSWITCH {
  type string;
  mandatory false;
 }
 leaf ULRANK1TWOTXSINRADJUST {
  type uint8 {
   range "0..30";
  }
  mandatory false;
 }
 }
}
