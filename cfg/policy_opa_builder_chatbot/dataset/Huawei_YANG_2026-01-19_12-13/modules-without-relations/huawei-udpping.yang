module huawei-udpping {
 yang-version 1.1;
 namespace "urn:rdns:com:huawei:oammodel:huawei-udpping";
 prefix udpping;
 description
 "Auto-generated modular YANG for huawei-udpping" ;
 revision "2026-01-19" {
 description "Auto-generated initial revision. Generated at 2026-01-19 12:13.";
 }
 grouping UDPPING-attributes {
 leaf DSCP {
  type uint8 {
   range "0..63";
  }
  mandatory false;
 }
 leaf TIMEOUTCNT {
  type uint8 {
   range "3..6";
  }
  mandatory false;
 }
 leaf TIMEOUTTHD {
  type uint16 {
   range "5000..60000";
  }
  mandatory false;
 }
 }
}
