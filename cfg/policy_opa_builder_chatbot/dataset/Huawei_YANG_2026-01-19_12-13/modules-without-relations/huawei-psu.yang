module huawei-psu {
 yang-version 1.1;
 namespace "urn:rdns:com:huawei:oammodel:huawei-psu";
 prefix psu;
 description
 "Auto-generated modular YANG for huawei-psu" ;
 revision "2026-01-19" {
 description "Auto-generated initial revision. Generated at 2026-01-19 12:13.";
 }
 grouping PSU-attributes {
 leaf OLD_CN {
  type union {
   type int8 {
    range "-1..62";
   }
  }
  mandatory false;
 }
 leaf CN {
  type union {
   type int8 {
    range "-1..62";
   }
  }
  mandatory false;
 }
 leaf PSUTYPE {
  type boolean;
  mandatory false;
 }
 leaf OLD_SN {
  type union {
   type int8 {
    range "-1..10";
   }
  }
  mandatory false;
 }
 leaf SN {
  type union {
   type int8 {
    range "-1..10";
   }
  }
  mandatory false;
 }
 leaf OLD_SRN {
  type union {
   type int8 {
    range "-1..7";
   }
  }
  mandatory false;
 }
 leaf SRN {
  type union {
   type int8 {
    range "-1..7";
   }
  }
  mandatory false;
 }
 }
}
