module huawei-almfilter {
 yang-version 1.1;
 namespace "urn:rdns:com:huawei:oammodel:huawei-almfilter";
 prefix almfilter;
 description
 "Auto-generated modular YANG for huawei-almfilter" ;
 revision "2026-01-19" {
 description "Auto-generated initial revision. Generated at 2026-01-19 12:13.";
 }
 grouping ALMFILTER-attributes {
 leaf OLD_AID {
  type union {
   type int32 {
    range "-1..65533";
   }
  }
  mandatory false;
 }
 leaf AID {
  type union {
   type int32 {
    range "-1..65533";
   }
  }
  mandatory false;
 }
 leaf CTH {
  type uint16 {
   range "0..65535";
  }
  mandatory false;
 }
 leaf CTW {
  type uint16 {
   range "0..65535";
  }
  mandatory false;
 }
 leaf RTH {
  type uint16 {
   range "0..65535";
  }
  mandatory false;
 }
 leaf OLD_RTP {
  type enumeration {
   enum val--1;
   enum val-0;
   enum val-1;
  }
  mandatory false;
 }
 leaf RTP {
  type enumeration {
   enum val--1;
   enum val-0;
   enum val-1;
  }
  mandatory false;
 }
 leaf RTW {
  type uint16 {
   range "0..65535";
  }
  mandatory false;
 }
 leaf STATCTH {
  type uint16 {
   range "0..65535";
  }
  mandatory false;
 }
 leaf STATRTH {
  type uint16 {
   range "0..65535";
  }
  mandatory false;
 }
 leaf STATTW {
  type uint16 {
   range "0..65535";
  }
  mandatory false;
 }
 }
}
