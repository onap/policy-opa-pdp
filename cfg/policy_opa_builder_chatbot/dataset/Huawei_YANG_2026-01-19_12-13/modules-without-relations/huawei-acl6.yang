module huawei-acl6 {
 yang-version 1.1;
 namespace "urn:rdns:com:huawei:oammodel:huawei-acl6";
 prefix acl6;
 description
 "Auto-generated modular YANG for huawei-acl6" ;
 revision "2026-01-19" {
 description "Auto-generated initial revision. Generated at 2026-01-19 12:13.";
 }
 grouping ACL6-attributes {
 leaf ACLDESC {
  type string {
   length "0..127";
  }
  mandatory false;
 }
 leaf OLD_ACLID {
  type union {
   type int16 {
    range "-1..9999";
   }
  }
  mandatory false;
 }
 leaf ACLID {
  type union {
   type int16 {
    range "-1..9999";
   }
  }
  mandatory false;
 }
 leaf CTRLMODE {
  type boolean;
  mandatory false;
 }
 }
}
