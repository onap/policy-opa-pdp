module huawei-gnbcountermap5qicfg {
 yang-version 1.1;
 namespace "urn:rdns:com:huawei:oammodel:huawei-gnbcountermap5qicfg";
 prefix gnbcountermap5qicfg;
 import ietf-inet-types {
 prefix inet;
 }
 description
 "Auto-generated modular YANG for huawei-gnbcountermap5qicfg" ;
 revision "2026-01-19" {
 description "Auto-generated initial revision. Generated at 2026-01-19 12:13.";
 }
 grouping GNBCOUNTERMAP5QICFG-attributes {
 leaf COUNTERMAPPED5QI {
  type union {
   type int16 {
    range "-1..20000";
   }
  }
  mandatory false;
 }
 leaf COUNTEROBJSUBSCRIPTIONIND {
  type inet:ip-address;
  mandatory false;
 }
 leaf SERVICETYPE {
  type enumeration {
   enum val--1;
   enum val-0;
   enum val-1;
  }
  mandatory false;
 }
 }
}
