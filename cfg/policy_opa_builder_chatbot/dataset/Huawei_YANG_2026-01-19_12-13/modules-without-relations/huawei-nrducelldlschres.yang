module huawei-nrducelldlschres {
 yang-version 1.1;
 namespace "urn:rdns:com:huawei:oammodel:huawei-nrducelldlschres";
 prefix nrducelldlschres;
 description
 "Auto-generated modular YANG for huawei-nrducelldlschres" ;
 revision "2026-01-19" {
 description "Auto-generated initial revision. Generated at 2026-01-19 12:13.";
 }
 grouping NRDUCELLDLSCHRES-attributes {
 leaf DLEXPOPTRBINCREASEPCT {
  type uint8 {
   range "0..100";
  }
  mandatory false;
 }
 leaf DLFREQRESALLOCINCCOEFF {
  type uint16 {
   range "0..273";
  }
  mandatory false;
 }
 leaf DLSCHRESALGOSW {
  type string;
  mandatory false;
 }
 leaf NRDUCELLID {
  type union {
   type int32 {
    range "-1..65534";
   }
  }
  mandatory false;
 }
 leaf SMALLPKTTYPE1ROBUSTSCHPOL {
  type enumeration {
   enum val-0;
   enum val-1;
   enum val-2;
   enum val-3;
  }
  mandatory false;
 }
 leaf SPCTSHRPDSCHSTARTSYMBOL {
  type enumeration {
   enum val-0;
   enum val-1;
   enum val-2;
  }
  mandatory false;
 }
 }
}
