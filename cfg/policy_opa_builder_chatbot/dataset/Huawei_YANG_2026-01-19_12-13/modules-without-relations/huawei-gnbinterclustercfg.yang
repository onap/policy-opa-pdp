module huawei-gnbinterclustercfg {
 yang-version 1.1;
 namespace "urn:rdns:com:huawei:oammodel:huawei-gnbinterclustercfg";
 prefix gnbinterclustercfg;
 description
 "Auto-generated modular YANG for huawei-gnbinterclustercfg" ;
 revision "2026-01-19" {
 description "Auto-generated initial revision. Generated at 2026-01-19 12:13.";
 }
 grouping GNBINTERCLUSTERCFG-attributes {
 leaf INTERCLUSCOMMCALIBFACTOR {
  type uint8 {
   range "1..10";
  }
  mandatory false;
 }
 leaf INTERCLUSTERCASCADETHLD {
  type uint8 {
   range "1..20";
  }
  mandatory false;
 }
 leaf OLD_INTERCLUSTERID {
  type union {
   type int32 {
    range "-1..49999";
   }
  }
  mandatory false;
 }
 leaf INTERCLUSTERID {
  type union {
   type int32 {
    range "-1..49999";
   }
  }
  mandatory false;
 }
 }
}
