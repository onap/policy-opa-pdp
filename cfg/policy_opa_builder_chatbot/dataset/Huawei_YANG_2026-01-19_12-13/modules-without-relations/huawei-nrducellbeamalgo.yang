module huawei-nrducellbeamalgo {
 yang-version 1.1;
 namespace "urn:rdns:com:huawei:oammodel:huawei-nrducellbeamalgo";
 prefix nrducellbeamalgo;
 description
 "Auto-generated modular YANG for huawei-nrducellbeamalgo" ;
 revision "2026-01-19" {
 description "Auto-generated initial revision. Generated at 2026-01-19 12:13.";
 }
 grouping NRDUCELLBEAMALGO-attributes {
 leaf AERIALSSBTIMEPOS {
  type enumeration {
   enum val-0;
   enum val-1;
   enum val-2;
  }
  mandatory false;
 }
 leaf BEAMADAPTSWITCH {
  type boolean;
  mandatory false;
 }
 leaf BEAMOPTALGOSWITCH {
  type string;
  mandatory false;
 }
 leaf BEAMPERCEIVEMODE {
  type enumeration {
   enum val-1;
   enum val-2;
  }
  mandatory false;
 }
 leaf CHANNELOPTALGOSWITCH {
  type string;
  mandatory false;
 }
 leaf GNDAERIALWTADAPTALGOTIMER {
  type uint8 {
   range "10..60";
  }
  mandatory false;
 }
 leaf NRDUCELLID {
  type union {
   type int32 {
    range "-1..65534";
   }
  }
  mandatory false;
 }
 leaf SCHOPTALGOSWITCH {
  type string;
  mandatory false;
 }
 leaf SRSBEAMSCANDURATION {
  type uint16 {
   range "2..300";
  }
  mandatory false;
 }
 leaf USERSCANDURATION {
  type enumeration {
   enum val-12;
   enum val-32;
   enum val-65;
   enum val-125;
  }
  mandatory false;
 }
 leaf WEIGHTALGOSWITCH {
  type string;
  mandatory false;
 }
 }
}
