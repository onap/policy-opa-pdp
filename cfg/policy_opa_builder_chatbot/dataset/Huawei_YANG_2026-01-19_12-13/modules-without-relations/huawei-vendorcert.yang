module huawei-vendorcert {
 yang-version 1.1;
 namespace "urn:rdns:com:huawei:oammodel:huawei-vendorcert";
 prefix vendorcert;
 description
 "Auto-generated modular YANG for huawei-vendorcert" ;
 revision "2026-01-19" {
 description "Auto-generated initial revision. Generated at 2026-01-19 12:13.";
 }
 grouping VENDORCERT-attributes {
 leaf CERTCHKTSKPOLICY {
  type boolean;
  mandatory false;
 }
 leaf VENDORCERTCHKSW {
  type boolean;
  mandatory false;
 }
 leaf VENDORCERTNAME {
  type enumeration {
   enum val--1;
   enum val-0;
   enum val-1;
  }
  mandatory false;
 }
 }
}
