module huawei-gnbschadapttotfcmdl {
 yang-version 1.1;
 namespace "urn:rdns:com:huawei:oammodel:huawei-gnbschadapttotfcmdl";
 prefix gnbschadapttotfcmdl;
 description
 "Auto-generated modular YANG for huawei-gnbschadapttotfcmdl" ;
 revision "2026-01-19" {
 description "Auto-generated initial revision. Generated at 2026-01-19 12:13.";
 }
 grouping GNBSCHADAPTTOTFCMDL-attributes {
 leaf PVTGTPUEXTHDRMAXTRANSNUM {
  type uint8 {
   range "1..100";
  }
  mandatory false;
 }
 leaf SCHADAPTTOTFCMDLVALIDPRD {
  type uint8 {
   range "3..60";
  }
  mandatory false;
 }
 leaf SCHADAPTTOTFCMODELPOL {
  type enumeration {
   enum val-0;
   enum val-1;
   enum val-2;
   enum val-3;
  }
  mandatory false;
 }
 }
}
