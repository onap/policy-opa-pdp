module huawei-tmasubunit {
 yang-version 1.1;
 namespace "urn:rdns:com:huawei:oammodel:huawei-tmasubunit";
 prefix tmasubunit;
 description
 "Auto-generated modular YANG for huawei-tmasubunit" ;
 revision "2026-01-19" {
 description "Auto-generated initial revision. Generated at 2026-01-19 12:13.";
 }
 grouping TMASUBUNIT-attributes {
 leaf CONNCN {
  type union {
   type uint8 {
    range "0..255";
   }
  }
  mandatory false;
 }
 leaf CONNPN {
  type enumeration {
   enum val-0;
   enum val-1;
   enum val-2;
   enum val-3;
   enum val-4;
   enum val-5;
   enum val-6;
   enum val-7;
  }
  mandatory false;
 }
 leaf CONNSN {
  type union {
   type uint8 {
    range "0..255";
   }
  }
  mandatory false;
 }
 leaf CONNSRN {
  type union {
   type uint8 {
    range "4..255";
   }
  }
  mandatory false;
 }
 leaf DEVICENO {
  type union {
   type int16 {
    range "-1..1023";
   }
  }
  mandatory false;
 }
 leaf GAIN {
  type uint8 {
   range "0..255";
  }
  mandatory false;
 }
 leaf MODE {
  type enumeration {
   enum val-0;
   enum val-1;
   enum val-255;
  }
  mandatory false;
 }
 leaf SUBUNITNO {
  type union {
   type int8 {
    range "-1..8";
   }
  }
  mandatory false;
 }
 }
}
