module huawei-localip {
 yang-version 1.1;
 namespace "urn:rdns:com:huawei:oammodel:huawei-localip";
 prefix localip;
 import ietf-interfaces {
 prefix if;
 }
 import ietf-ip {
 prefix ip;
 }
 import ietf-inet-types {
 prefix inet;
 }
 description
 "Auto-generated modular YANG for huawei-localip" ;
 revision "2026-01-19" {
 description "Auto-generated initial revision. Generated at 2026-01-19 12:13.";
 }
 augment "/if:interfaces/if:interface/ip:ipv4" {
 container localip-ipv4 {
  container attributes {
   uses LOCALIP-attributes {
    /* opcjonalnie: tu można ograniczyć do IP-only */
   }
  }
 }
}
 grouping LOCALIP-attributes {
 leaf IP {
  type inet:ipv4-address;
  mandatory false;
 }
 leaf MASK {
  type inet:ipv4-address;
  mandatory false;
 }
 }
}
