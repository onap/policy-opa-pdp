module huawei-nrcellpri {
 yang-version 1.1;
 namespace "urn:rdns:com:huawei:oammodel:huawei-nrcellpri";
 prefix nrcellpri;
 description
 "Auto-generated modular YANG for huawei-nrcellpri" ;
 revision "2026-01-19" {
 description "Auto-generated initial revision. Generated at 2026-01-19 12:13.";
 }
 grouping NRCELLPRI-attributes {
 leaf HIGHPRIUENUMOFS {
  type uint8 {
   range "0..100";
  }
  mandatory false;
 }
 leaf HOREESTUENUMOFS {
  type uint8 {
   range "0..100";
  }
  mandatory false;
 }
 leaf NRCELLID {
  type union {
   type int32 {
    range "-1..65534";
   }
  }
  mandatory false;
 }
 leaf USERNUMADMTHLD {
  type uint16 {
   range "0..65535";
  }
  mandatory false;
 }
 }
}
