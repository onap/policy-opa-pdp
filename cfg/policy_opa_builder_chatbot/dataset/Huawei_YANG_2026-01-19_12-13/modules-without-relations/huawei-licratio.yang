module huawei-licratio {
 yang-version 1.1;
 namespace "urn:rdns:com:huawei:oammodel:huawei-licratio";
 prefix licratio;
 description
 "Auto-generated modular YANG for huawei-licratio" ;
 revision "2026-01-19" {
 description "Auto-generated initial revision. Generated at 2026-01-19 12:13.";
 }
 grouping LICRATIO-attributes {
 leaf TRAFFICSHARINGTYPE {
  type boolean;
  mandatory false;
 }
 leaf UPLICRATIO {
  type uint8 {
   range "1..100";
  }
  mandatory false;
 }
 }
}
