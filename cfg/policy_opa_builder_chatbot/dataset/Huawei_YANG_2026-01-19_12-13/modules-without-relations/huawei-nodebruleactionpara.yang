module huawei-nodebruleactionpara {
 yang-version 1.1;
 namespace "urn:rdns:com:huawei:oammodel:huawei-nodebruleactionpara";
 prefix nodebruleactionpara;
 description
 "Auto-generated modular YANG for huawei-nodebruleactionpara" ;
 revision "2026-01-19" {
 description "Auto-generated initial revision. Generated at 2026-01-19 12:13.";
 }
 grouping NODEBRULEACTIONPARA-attributes {
 leaf ADMINSTATE {
  type boolean;
  mandatory false;
 }
 leaf MOCNAME {
  type enumeration {
   enum val--1;
   enum val-0;
   enum val-1;
   enum val-2;
  }
  mandatory false;
 }
 leaf PARAENUMVALUE {
  type enumeration {
   enum val-0;
   enum val-1;
   enum val-2;
   enum val-3;
   enum val-255;
  }
  mandatory false;
 }
 leaf PARAINTERVALVALUE {
  type union {
   type uint32 {
    range "0..2147483647";
   }
  }
  mandatory false;
 }
 leaf PARANAME {
  type enumeration {
   enum val--1;
   enum val-0;
   enum val-1;
   enum val-2;
   enum val-3;
   enum val-4;
   enum val-5;
   enum val-6;
   enum val-7;
   enum val-8;
  }
  mandatory false;
 }
 leaf RULEID {
  type union {
   type int8 {
    range "-1..10";
   }
  }
  mandatory false;
 }
 leaf USERLABEL {
  type string {
   length "0..256";
  }
  mandatory false;
 }
 }
}
