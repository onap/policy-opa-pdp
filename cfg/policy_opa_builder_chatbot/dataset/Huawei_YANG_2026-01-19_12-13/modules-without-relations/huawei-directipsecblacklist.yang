module huawei-directipsecblacklist {
 yang-version 1.1;
 namespace "urn:rdns:com:huawei:oammodel:huawei-directipsecblacklist";
 prefix directipsecblacklist;
 import ietf-interfaces {
 prefix if;
 }
 import ietf-ip {
 prefix ip;
 }
 import ietf-inet-types {
 prefix inet;
 }
 description
 "Auto-generated modular YANG for huawei-directipsecblacklist" ;
 revision "2026-01-19" {
 description "Auto-generated initial revision. Generated at 2026-01-19 12:13.";
 }
 augment "/if:interfaces/if:interface/ip:ipv4" {
 container directipsecblacklist-ipv4 {
  container attributes {
   uses DIRECTIPSECBLACKLIST-attributes {
    /* opcjonalnie: tu można ograniczyć do IP-only */
   }
  }
 }
}
 augment "/if:interfaces/if:interface/ip:ipv6" {
 container directipsecblacklist-ipv6 {
  container attributes {
   uses DIRECTIPSECBLACKLIST-attributes {
    /* opcjonalnie: tu można ograniczyć do IP-only */
   }
  }
 }
}
 grouping DIRECTIPSECBLACKLIST-attributes {
 leaf OLD_DIRECTIPSECBLACKLISTID {
  type union {
   type int16 {
    range "-1..383";
   }
  }
  mandatory false;
 }
 leaf DIRECTIPSECBLACKLISTID {
  type union {
   type int16 {
    range "-1..383";
   }
  }
  mandatory false;
 }
 leaf IPVERSION {
  type boolean;
  mandatory false;
 }
 leaf SECURITYPEERIPV4 {
  type inet:ipv4-address;
  mandatory false;
 }
 leaf SECURITYPEERIPV6 {
  type inet:ipv6-address;
  mandatory false;
 }
 leaf VRFIDX {
  type uint8 {
   range "0..31";
  }
  mandatory false;
 }
 }
}
