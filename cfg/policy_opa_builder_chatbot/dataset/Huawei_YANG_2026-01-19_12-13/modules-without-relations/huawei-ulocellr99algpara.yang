module huawei-ulocellr99algpara {
 yang-version 1.1;
 namespace "urn:rdns:com:huawei:oammodel:huawei-ulocellr99algpara";
 prefix ulocellr99algpara;
 description
 "Auto-generated modular YANG for huawei-ulocellr99algpara" ;
 revision "2026-01-19" {
 description "Auto-generated initial revision. Generated at 2026-01-19 12:13.";
 }
 grouping ULOCELLR99ALGPARA-attributes {
 leaf LONGTH {
  type uint8 {
   range "0..100";
  }
  mandatory false;
 }
 leaf PWRCNGCACSW {
  type boolean;
  mandatory false;
 }
 leaf SHORTTH {
  type uint8 {
   range "0..120";
  }
  mandatory false;
 }
 leaf SHORTTHFORRTRRC {
  type uint8 {
   range "0..200";
  }
  mandatory false;
 }
 leaf ULOCELLID {
  type union {
   type int32 {
    range "-1..268435455";
   }
  }
  mandatory false;
 }
 }
}
