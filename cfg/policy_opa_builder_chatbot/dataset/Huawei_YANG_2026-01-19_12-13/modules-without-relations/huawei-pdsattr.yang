module huawei-pdsattr {
 yang-version 1.1;
 namespace "urn:rdns:com:huawei:oammodel:huawei-pdsattr";
 prefix pdsattr;
 description
 "Auto-generated modular YANG for huawei-pdsattr" ;
 revision "2026-01-19" {
 description "Auto-generated initial revision. Generated at 2026-01-19 12:13.";
 }
 grouping PDSATTR-attributes {
 leaf CLSDT {
  type uint16 {
   range "0..1440";
  }
  mandatory false;
 }
 leaf OLD_CN {
  type union {
   type int8 {
    range "-1..62";
   }
  }
  mandatory false;
 }
 leaf CN {
  type union {
   type int8 {
    range "-1..62";
   }
  }
  mandatory false;
 }
 leaf CSDTS {
  type boolean;
  mandatory false;
 }
 leaf ESNGROUP {
  type string {
   length "0..199";
  }
  mandatory false;
 }
 leaf PDSDESC {
  type string {
   length "0..199";
  }
  mandatory false;
 }
 leaf OLD_SN {
  type union {
   type int8 {
    range "-1..12";
   }
  }
  mandatory false;
 }
 leaf SN {
  type union {
   type int8 {
    range "-1..12";
   }
  }
  mandatory false;
 }
 leaf OLD_SRN {
  type union {
   type int8 {
    range "-1..7";
   }
  }
  mandatory false;
 }
 leaf SRN {
  type union {
   type int8 {
    range "-1..7";
   }
  }
  mandatory false;
 }
 }
}
