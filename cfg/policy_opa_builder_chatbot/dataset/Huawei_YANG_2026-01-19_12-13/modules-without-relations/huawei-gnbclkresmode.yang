module huawei-gnbclkresmode {
 yang-version 1.1;
 namespace "urn:rdns:com:huawei:oammodel:huawei-gnbclkresmode";
 prefix gnbclkresmode;
 description
 "Auto-generated modular YANG for huawei-gnbclkresmode" ;
 revision "2026-01-19" {
 description "Auto-generated initial revision. Generated at 2026-01-19 12:13.";
 }
 grouping GNBCLKRESMODE-attributes {
 leaf CLKOUTOFSYNCALGOSW {
  type string;
  mandatory false;
 }
 leaf CLKWORKMODE {
  type boolean;
  mandatory false;
 }
 leaf OUTOFSYNSEQTHLD {
  type uint8 {
   range "20..60";
  }
  mandatory false;
 }
 }
}
