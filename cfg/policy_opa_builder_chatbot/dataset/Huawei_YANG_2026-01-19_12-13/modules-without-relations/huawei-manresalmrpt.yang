module huawei-manresalmrpt {
 yang-version 1.1;
 namespace "urn:rdns:com:huawei:oammodel:huawei-manresalmrpt";
 prefix manresalmrpt;
 description
 "Auto-generated modular YANG for huawei-manresalmrpt" ;
 revision "2026-01-19" {
 description "Auto-generated initial revision. Generated at 2026-01-19 12:13.";
 }
 grouping MANRESALMRPT-attributes {
 leaf SWITCH {
  type boolean;
  mandatory false;
 }
 }
}
