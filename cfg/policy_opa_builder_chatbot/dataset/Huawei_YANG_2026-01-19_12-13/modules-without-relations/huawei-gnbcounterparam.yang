module huawei-gnbcounterparam {
 yang-version 1.1;
 namespace "urn:rdns:com:huawei:oammodel:huawei-gnbcounterparam";
 prefix gnbcounterparam;
 description
 "Auto-generated modular YANG for huawei-gnbcounterparam" ;
 revision "2026-01-19" {
 description "Auto-generated initial revision. Generated at 2026-01-19 12:13.";
 }
 grouping GNBCOUNTERPARAM-attributes {
 leaf GNBCOUNTERINDEX {
  type union {
   type int16 {
    range "-1..255";
   }
  }
  mandatory false;
 }
 leaf GNBCOUNTERTYPE {
  type enumeration {
   enum val--1;
   enum val-0;
   enum val-1;
   enum val-2;
  }
  mandatory false;
 }
 leaf GNBRANGESTARTVALUE {
  type int32 {
   range "-2147483648..2147483647";
  }
  mandatory false;
 }
 }
}
