module huawei-gnbasappparam {
 yang-version 1.1;
 namespace "urn:rdns:com:huawei:oammodel:huawei-gnbasappparam";
 prefix gnbasappparam;
 import ietf-interfaces {
 prefix if;
 }
 import ietf-ip {
 prefix ip;
 }
 import ietf-inet-types {
 prefix inet;
 }
 description
 "Auto-generated modular YANG for huawei-gnbasappparam" ;
 revision "2026-01-19" {
 description "Auto-generated initial revision. Generated at 2026-01-19 12:13.";
 }
 augment "/if:interfaces/if:interface/ip:ipv4" {
 container gnbasappparam-ipv4 {
  container attributes {
   uses GNBASAPPPARAM-attributes {
    /* opcjonalnie: tu można ograniczyć do IP-only */
   }
  }
 }
}
 augment "/if:interfaces/if:interface/ip:ipv6" {
 container gnbasappparam-ipv6 {
  container attributes {
   uses GNBASAPPPARAM-attributes {
    /* opcjonalnie: tu można ograniczyć do IP-only */
   }
  }
 }
}
 grouping GNBASAPPPARAM-attributes {
 leaf APPDOMAINNAME {
  type string {
   length "0..49";
  }
  mandatory false;
 }
 leaf APPIDENTIFICATIONTYPE {
  type enumeration {
   enum val-0;
   enum val-1;
   enum val-2;
   enum val-3;
   enum val-4;
  }
  mandatory false;
 }
 leaf OLD_APPINDEX {
  type union {
   type int16 {
    range "-1..129";
   }
  }
  mandatory false;
 }
 leaf APPINDEX {
  type union {
   type int16 {
    range "-1..129";
   }
  }
  mandatory false;
 }
 leaf APPIPV4 {
  type inet:ipv4-address;
  mandatory false;
 }
 leaf APPIPV6 {
  type inet:ipv6-address;
  mandatory false;
 }
 leaf APPUSAGE {
  type string;
  mandatory false;
 }
 leaf DSTPORT {
  type uint16 {
   range "0..65535";
  }
  mandatory false;
 }
 leaf NR5QI {
  type union {
   type uint16 {
    range "0..65535";
   }
  }
  mandatory false;
 }
 leaf SECONDSPEEDTURBOGROUPID {
  type union {
   type uint8 {
    range "0..255";
   }
  }
  mandatory false;
 }
 leaf SERVAWAREPOL {
  type boolean;
  mandatory false;
 }
 leaf SPEEDTURBOGROUPID {
  type uint8 {
   range "0..9";
  }
  mandatory false;
 }
 leaf TCPDSTPORT {
  type uint16 {
   range "0..65535";
  }
  mandatory false;
 }
 leaf UEDLAMBR {
  type union {
   type uint16 {
    range "0..65535";
   }
  }
  mandatory false;
 }
 }
}
