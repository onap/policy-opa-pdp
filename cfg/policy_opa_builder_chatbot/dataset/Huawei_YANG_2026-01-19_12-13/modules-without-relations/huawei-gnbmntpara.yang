module huawei-gnbmntpara {
 yang-version 1.1;
 namespace "urn:rdns:com:huawei:oammodel:huawei-gnbmntpara";
 prefix gnbmntpara;
 description
 "Auto-generated modular YANG for huawei-gnbmntpara" ;
 revision "2026-01-19" {
 description "Auto-generated initial revision. Generated at 2026-01-19 12:13.";
 }
 grouping GNBMNTPARA-attributes {
 leaf MNTALGOSW {
  type string;
  mandatory false;
 }
 leaf MNTEXNUPAGINGTIMER {
  type enumeration {
   enum val-0;
   enum val-1;
   enum val-2;
  }
  mandatory false;
 }
 leaf MNTUEPOLICY {
  type string;
  mandatory false;
 }
 leaf NCELLNUM {
  type uint16 {
   range "1..384";
  }
  mandatory false;
 }
 leaf NSAMNTSPLITPOLICY {
  type enumeration {
   enum val-0;
   enum val-1;
   enum val-2;
   enum val-3;
  }
  mandatory false;
 }
 leaf TOPNCELLNUM {
  type uint16 {
   range "0..384";
  }
  mandatory false;
 }
 }
}
