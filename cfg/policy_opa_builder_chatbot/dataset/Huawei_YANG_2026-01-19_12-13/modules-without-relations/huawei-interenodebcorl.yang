module huawei-interenodebcorl {
 yang-version 1.1;
 namespace "urn:rdns:com:huawei:oammodel:huawei-interenodebcorl";
 prefix interenodebcorl;
 description
 "Auto-generated modular YANG for huawei-interenodebcorl" ;
 revision "2026-01-19" {
 description "Auto-generated initial revision. Generated at 2026-01-19 12:13.";
 }
 grouping INTERENODEBCORL-attributes {
 leaf OLD_ENODEBID {
  type union {
   type int32 {
    range "-1..1048575";
   }
  }
  mandatory false;
 }
 leaf ENODEBID {
  type union {
   type int32 {
    range "-1..1048575";
   }
  }
  mandatory false;
 }
 }
}
