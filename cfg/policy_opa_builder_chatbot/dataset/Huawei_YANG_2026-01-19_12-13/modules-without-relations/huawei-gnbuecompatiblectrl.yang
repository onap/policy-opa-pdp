module huawei-gnbuecompatiblectrl {
 yang-version 1.1;
 namespace "urn:rdns:com:huawei:oammodel:huawei-gnbuecompatiblectrl";
 prefix gnbuecompatiblectrl;
 description
 "Auto-generated modular YANG for huawei-gnbuecompatiblectrl" ;
 revision "2026-01-19" {
 description "Auto-generated initial revision. Generated at 2026-01-19 12:13.";
 }
 grouping GNBUECOMPATIBLECTRL-attributes {
 leaf OSSOAMCOMPATIBLESW {
  type string;
  mandatory false;
 }
 leaf OSSOAMWHITELISTCTRLSW {
  type string;
  mandatory false;
 }
 leaf OLD_UEINFOINDEX {
  type union {
   type int16 {
    range "-1..128";
   }
  }
  mandatory false;
 }
 leaf UEINFOINDEX {
  type union {
   type int16 {
    range "-1..128";
   }
  }
  mandatory false;
 }
 }
}
