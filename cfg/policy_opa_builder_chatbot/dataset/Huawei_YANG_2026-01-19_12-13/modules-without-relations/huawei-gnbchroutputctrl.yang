module huawei-gnbchroutputctrl {
 yang-version 1.1;
 namespace "urn:rdns:com:huawei:oammodel:huawei-gnbchroutputctrl";
 prefix gnbchroutputctrl;
 description
 "Auto-generated modular YANG for huawei-gnbchroutputctrl" ;
 revision "2026-01-19" {
 description "Auto-generated initial revision. Generated at 2026-01-19 12:13.";
 }
 grouping GNBCHROUTPUTCTRL-attributes {
 leaf CHROUTPUTCTRLSWITCH {
  type string;
  mandatory false;
 }
 leaf CHRREPORTSWITCH {
  type boolean;
  mandatory false;
 }
 }
}
