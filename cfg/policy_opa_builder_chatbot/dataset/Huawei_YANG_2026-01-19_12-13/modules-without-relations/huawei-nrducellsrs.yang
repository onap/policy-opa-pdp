module huawei-nrducellsrs {
 yang-version 1.1;
 namespace "urn:rdns:com:huawei:oammodel:huawei-nrducellsrs";
 prefix nrducellsrs;
 description
 "Auto-generated modular YANG for huawei-nrducellsrs" ;
 revision "2026-01-19" {
 description "Auto-generated initial revision. Generated at 2026-01-19 12:13.";
 }
 grouping NRDUCELLSRS-attributes {
 leaf HIGHQUALITYUSERSRSTHLD {
  type uint8 {
   range "0..20";
  }
  mandatory false;
 }
 leaf LARGEPKTUEMAXSRSMEASPRD {
  type enumeration {
   enum val-160;
   enum val-240;
   enum val-320;
   enum val-480;
   enum val-640;
  }
  mandatory false;
 }
 leaf NRDUCELLID {
  type union {
   type int32 {
    range "-1..65534";
   }
  }
  mandatory false;
 }
 leaf PUSCHINTRFTHLD {
  type int16 {
   range "-140..-50";
  }
  mandatory false;
 }
 leaf SCENARIOSRSRESALLOCPOL {
  type boolean;
  mandatory false;
 }
 leaf SMALLPKTUEMAXSRSMEASPRD {
  type enumeration {
   enum val-320;
   enum val-480;
   enum val-640;
   enum val-960;
   enum val-1280;
  }
  mandatory false;
 }
 leaf SRSALGOEXTSWITCH {
  type string;
  mandatory false;
 }
 leaf SRSALGOSWITCH {
  type string;
  mandatory false;
 }
 leaf SRSBLINDISDEGREE {
  type uint8 {
   range "0..10";
  }
  mandatory false;
 }
 leaf SRSCHNPERIOD {
  type enumeration {
   enum val-5;
   enum val-10;
   enum val-20;
   enum val-40;
   enum val-80;
   enum val-160;
   enum val-320;
  }
  mandatory false;
 }
 leaf SRSCOMBMODE {
  type boolean;
  mandatory false;
 }
 leaf SRSCONFIGTHLD {
  type uint16 {
   range "0..270";
  }
  mandatory false;
 }
 leaf SRSDETECTIONALGOSWITCH {
  type string;
  mandatory false;
 }
 leaf SRSINTRFRANDOMINDEX {
  type union {
   type uint8 {
    range "0..255";
   }
  }
  mandatory false;
 }
 leaf SRSNARROWBANDINDEXBSRS {
  type uint8 {
   range "0..3";
  }
  mandatory false;
 }
 leaf SRSNARROWBANDINDEXCSRS {
  type uint8 {
   range "2..63";
  }
  mandatory false;
 }
 leaf SRSPERIOD {
  type enumeration {
   enum val-3;
   enum val-5;
   enum val-7;
   enum val-9;
   enum val-11;
   enum val-12;
   enum val-13;
   enum val-14;
  }
  mandatory false;
 }
 leaf SRSRESSTARTPOSITION {
  type uint8 {
   range "0..1";
  }
  mandatory false;
 }
 leaf SRSSHORTRESALLOCPOL {
  type enumeration {
   enum val-0;
   enum val-1;
   enum val-2;
  }
  mandatory false;
 }
 leaf SRSWIDEBANDINDEXBSRS {
  type uint8 {
   range "0..3";
  }
  mandatory false;
 }
 leaf SRSWIDEBANDINDEXCSRS {
  type union {
   type uint8 {
    range "2..255";
   }
  }
  mandatory false;
 }
 leaf SRSWIDETONARROWTHLD {
  type int8 {
   range "-50..50";
  }
  mandatory false;
 }
 leaf URLLCPOOFFSET {
  type uint8 {
   range "0..15";
  }
  mandatory false;
 }
 }
}
