module huawei-tldralg {
 yang-version 1.1;
 namespace "urn:rdns:com:huawei:oammodel:huawei-tldralg";
 prefix tldralg;
 description
 "Auto-generated modular YANG for huawei-tldralg" ;
 revision "2026-01-19" {
 description "Auto-generated initial revision. Generated at 2026-01-19 12:13.";
 }
 grouping TLDRALG-attributes {
 leaf TRMDLLDRCLRTH {
  type uint8 {
   range "0..100";
  }
  mandatory false;
 }
 leaf TRMDLLDRTRGTH {
  type uint8 {
   range "0..100";
  }
  mandatory false;
 }
 leaf TRMDLMLDCLRTH {
  type uint8 {
   range "0..100";
  }
  mandatory false;
 }
 leaf TRMDLMLDTRGTH {
  type uint8 {
   range "0..100";
  }
  mandatory false;
 }
 leaf TRMULLDRCLRTH {
  type uint8 {
   range "0..100";
  }
  mandatory false;
 }
 leaf TRMULLDRTRGTH {
  type uint8 {
   range "0..100";
  }
  mandatory false;
 }
 leaf TRMULMLDCLRTH {
  type uint8 {
   range "0..100";
  }
  mandatory false;
 }
 leaf TRMULMLDTRGTH {
  type uint8 {
   range "0..100";
  }
  mandatory false;
 }
 }
}
