module huawei-nrdutrpredundancy {
 yang-version 1.1;
 namespace "urn:rdns:com:huawei:oammodel:huawei-nrdutrpredundancy";
 prefix nrdutrpredundancy;
 description
 "Auto-generated modular YANG for huawei-nrdutrpredundancy" ;
 revision "2026-01-19" {
 description "Auto-generated initial revision. Generated at 2026-01-19 12:13.";
 }
 grouping NRDUTRPREDUNDANCY-attributes {
 leaf NRDUCELLTRPID {
  type union {
   type int32 {
    range "-1..65534";
   }
  }
  mandatory false;
 }
 leaf PEERNRDUCELLTRPID {
  type uint16 {
   range "0..65534";
  }
  mandatory false;
 }
 }
}
