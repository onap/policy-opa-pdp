module huawei-gnbbeamweight {
 yang-version 1.1;
 namespace "urn:rdns:com:huawei:oammodel:huawei-gnbbeamweight";
 prefix gnbbeamweight;
 description
 "Auto-generated modular YANG for huawei-gnbbeamweight" ;
 revision "2026-01-19" {
 description "Auto-generated initial revision. Generated at 2026-01-19 12:13.";
 }
 grouping GNBBEAMWEIGHT-attributes {
 leaf WEIGHT0 {
  type uint32 {
   range "0..4294967295";
  }
  mandatory false;
 }
 leaf WEIGHT1 {
  type uint32 {
   range "0..4294967295";
  }
  mandatory false;
 }
 leaf WEIGHT10 {
  type uint32 {
   range "0..4294967295";
  }
  mandatory false;
 }
 leaf WEIGHT11 {
  type uint32 {
   range "0..4294967295";
  }
  mandatory false;
 }
 leaf WEIGHT12 {
  type uint32 {
   range "0..4294967295";
  }
  mandatory false;
 }
 leaf WEIGHT13 {
  type uint32 {
   range "0..4294967295";
  }
  mandatory false;
 }
 leaf WEIGHT14 {
  type uint32 {
   range "0..4294967295";
  }
  mandatory false;
 }
 leaf WEIGHT15 {
  type uint32 {
   range "0..4294967295";
  }
  mandatory false;
 }
 leaf WEIGHT16 {
  type uint32 {
   range "0..4294967295";
  }
  mandatory false;
 }
 leaf WEIGHT17 {
  type uint32 {
   range "0..4294967295";
  }
  mandatory false;
 }
 leaf WEIGHT18 {
  type uint32 {
   range "0..4294967295";
  }
  mandatory false;
 }
 leaf WEIGHT19 {
  type uint32 {
   range "0..4294967295";
  }
  mandatory false;
 }
 leaf WEIGHT2 {
  type uint32 {
   range "0..4294967295";
  }
  mandatory false;
 }
 leaf WEIGHT20 {
  type uint32 {
   range "0..4294967295";
  }
  mandatory false;
 }
 leaf WEIGHT21 {
  type uint32 {
   range "0..4294967295";
  }
  mandatory false;
 }
 leaf WEIGHT22 {
  type uint32 {
   range "0..4294967295";
  }
  mandatory false;
 }
 leaf WEIGHT23 {
  type uint32 {
   range "0..4294967295";
  }
  mandatory false;
 }
 leaf WEIGHT24 {
  type uint32 {
   range "0..4294967295";
  }
  mandatory false;
 }
 leaf WEIGHT25 {
  type uint32 {
   range "0..4294967295";
  }
  mandatory false;
 }
 leaf WEIGHT26 {
  type uint32 {
   range "0..4294967295";
  }
  mandatory false;
 }
 leaf WEIGHT27 {
  type uint32 {
   range "0..4294967295";
  }
  mandatory false;
 }
 leaf WEIGHT28 {
  type uint32 {
   range "0..4294967295";
  }
  mandatory false;
 }
 leaf WEIGHT29 {
  type uint32 {
   range "0..4294967295";
  }
  mandatory false;
 }
 leaf WEIGHT3 {
  type uint32 {
   range "0..4294967295";
  }
  mandatory false;
 }
 leaf WEIGHT30 {
  type uint32 {
   range "0..4294967295";
  }
  mandatory false;
 }
 leaf WEIGHT31 {
  type uint32 {
   range "0..4294967295";
  }
  mandatory false;
 }
 leaf WEIGHT4 {
  type uint32 {
   range "0..4294967295";
  }
  mandatory false;
 }
 leaf WEIGHT5 {
  type uint32 {
   range "0..4294967295";
  }
  mandatory false;
 }
 leaf WEIGHT6 {
  type uint32 {
   range "0..4294967295";
  }
  mandatory false;
 }
 leaf WEIGHT7 {
  type uint32 {
   range "0..4294967295";
  }
  mandatory false;
 }
 leaf WEIGHT8 {
  type uint32 {
   range "0..4294967295";
  }
  mandatory false;
 }
 leaf WEIGHT9 {
  type uint32 {
   range "0..4294967295";
  }
  mandatory false;
 }
 leaf OLD_WEIGHTID {
  type union {
   type int32 {
    range "-1..65534";
   }
  }
  mandatory false;
 }
 leaf WEIGHTID {
  type union {
   type int32 {
    range "-1..65534";
   }
  }
  mandatory false;
 }
 leaf WEIGHTNUM {
  type enumeration {
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
  }
  mandatory false;
 }
 }
}
