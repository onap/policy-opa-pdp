module huawei-gnbasueconfig {
 yang-version 1.1;
 namespace "urn:rdns:com:huawei:oammodel:huawei-gnbasueconfig";
 prefix gnbasueconfig;
 description
 "Auto-generated modular YANG for huawei-gnbasueconfig" ;
 revision "2026-01-19" {
 description "Auto-generated initial revision. Generated at 2026-01-19 12:13.";
 }
 grouping GNBASUECONFIG-attributes {
 leaf STBLACKLISTCTRLSWITCH {
  type string;
  mandatory false;
 }
 leaf SPEEDTURBOSERVIDENTMODE {
  type uint16 {
   range "0..65535";
  }
  mandatory false;
 }
 leaf OLD_UEINFOINDEX {
  type union {
   type int16 {
    range "-1..128";
   }
  }
  mandatory false;
 }
 leaf UEINFOINDEX {
  type union {
   type int16 {
    range "-1..128";
   }
  }
  mandatory false;
 }
 }
}
