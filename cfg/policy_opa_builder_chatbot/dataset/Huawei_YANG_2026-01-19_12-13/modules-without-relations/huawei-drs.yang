module huawei-drs {
 yang-version 1.1;
 namespace "urn:rdns:com:huawei:oammodel:huawei-drs";
 prefix drs;
 description
 "Auto-generated modular YANG for huawei-drs" ;
 revision "2026-01-19" {
 description "Auto-generated initial revision. Generated at 2026-01-19 12:13.";
 }
 grouping DRS-attributes {
 leaf OLD_CN {
  type union {
   type int8 {
    range "-1..15";
   }
  }
  mandatory false;
 }
 leaf CN {
  type union {
   type int8 {
    range "-1..15";
   }
  }
  mandatory false;
 }
 leaf DRSNAME {
  type string {
   length "0..128";
  }
  mandatory false;
 }
 leaf HPBW {
  type enumeration {
   enum val-0;
   enum val-1;
   enum val-2;
   enum val-3;
  }
  mandatory false;
 }
 leaf LEDSW {
  type boolean;
  mandatory false;
 }
 leaf OLD_SN {
  type union {
   type int8 {
    range "-1..3";
   }
  }
  mandatory false;
 }
 leaf SN {
  type union {
   type int8 {
    range "-1..3";
   }
  }
  mandatory false;
 }
 leaf OLD_SRN {
  type union {
   type int16 {
    range "-1..254";
   }
  }
  mandatory false;
 }
 leaf SRN {
  type union {
   type int16 {
    range "-1..254";
   }
  }
  mandatory false;
 }
 }
}
