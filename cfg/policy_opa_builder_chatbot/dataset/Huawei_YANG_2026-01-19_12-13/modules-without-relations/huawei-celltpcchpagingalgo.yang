module huawei-celltpcchpagingalgo {
 yang-version 1.1;
 namespace "urn:rdns:com:huawei:oammodel:huawei-celltpcchpagingalgo";
 prefix celltpcchpagingalgo;
 description
 "Auto-generated modular YANG for huawei-celltpcchpagingalgo" ;
 revision "2026-01-19" {
 description "Auto-generated initial revision. Generated at 2026-01-19 12:13.";
 }
 grouping CELLTPCCHPAGINGALGO-attributes {
 leaf LOCALCELLNAME {
  type string;
  mandatory false;
 }
 leaf LOCALCELLID {
  type union {
   type int16 {
    range "-1..255";
   }
  }
  mandatory false;
 }
 leaf TPCCHCLOSESHTCYCPAGINGCNT {
  type uint8 {
   range "1..10";
  }
  mandatory false;
 }
 leaf TPCCHLONGCYCMAXMULSHORTCYC {
  type uint8 {
   range "1..100";
  }
  mandatory false;
 }
 leaf TPCCHLONGCYCMINMULSHORTCYC {
  type uint8 {
   range "1..20";
  }
  mandatory false;
 }
 leaf TPCCHLONGCYCMULOFSHORTCYC {
  type uint8 {
   range "1..100";
  }
  mandatory false;
 }
 leaf TPCCHLONGCYCLEADJSWITCH {
  type boolean;
  mandatory false;
 }
 leaf TPCCHPAGINGQUEUEPRISW {
  type boolean;
  mandatory false;
 }
 leaf TPCCHPTPSHORTCYCPAGINGCNT {
  type uint8 {
   range "1..10";
  }
  mandatory false;
 }
 leaf TPCCHSHORTCYCPAGINGCNT {
  type uint8 {
   range "1..10";
  }
  mandatory false;
 }
 }
}
