module huawei-nrducellsibconfig {
 yang-version 1.1;
 namespace "urn:rdns:com:huawei:oammodel:huawei-nrducellsibconfig";
 prefix nrducellsibconfig;
 description
 "Auto-generated modular YANG for huawei-nrducellsibconfig" ;
 revision "2026-01-19" {
 description "Auto-generated initial revision. Generated at 2026-01-19 12:13.";
 }
 grouping NRDUCELLSIBCONFIG-attributes {
 leaf NRDUCELLID {
  type union {
   type int32 {
    range "-1..65534";
   }
  }
  mandatory false;
 }
 leaf PWSREDUNDANCYTRANSNUM {
  type uint8 {
   range "0..10";
  }
  mandatory false;
 }
 leaf PWSSERVICEHOLDDURATION {
  type uint16 {
   range "0..360";
  }
  mandatory false;
 }
 }
}
