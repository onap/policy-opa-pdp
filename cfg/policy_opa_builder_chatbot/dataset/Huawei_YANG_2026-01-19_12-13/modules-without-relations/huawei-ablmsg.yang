module huawei-ablmsg {
 yang-version 1.1;
 namespace "urn:rdns:com:huawei:oammodel:huawei-ablmsg";
 prefix ablmsg;
 description
 "Auto-generated modular YANG for huawei-ablmsg" ;
 revision "2026-01-19" {
 description "Auto-generated initial revision. Generated at 2026-01-19 12:13.";
 }
 grouping ABLMSG-attributes {
 leaf IMEISVDESC {
  type string {
   length "0..40";
  }
  mandatory false;
 }
 leaf IMEISVSVN {
  type uint8 {
   range "0..99";
  }
  mandatory false;
 }
 leaf IMEISVTAC {
  type uint32 {
   range "0..99999999";
  }
  mandatory false;
 }
 leaf MATCHCONTENT1 {
  type string {
   length "0..100";
  }
  mandatory false;
 }
 leaf MATCHCONTENT2 {
  type string {
   length "0..100";
  }
  mandatory false;
 }
 leaf MATCHCONTENT3 {
  type string {
   length "0..100";
  }
  mandatory false;
 }
 leaf MATCHCONTENTEXTENSION {
  type uint32 {
   range "0..4294967295";
  }
  mandatory false;
 }
 leaf MATCHCOUNT {
  type enumeration {
   enum val-0;
   enum val-1;
   enum val-2;
   enum val-3;
  }
  mandatory false;
 }
 leaf MATCHFIELDOFFSET1 {
  type uint32 {
   range "0..268435455";
  }
  mandatory false;
 }
 leaf MATCHFIELDOFFSET2 {
  type uint32 {
   range "0..268435455";
  }
  mandatory false;
 }
 leaf MATCHFIELDOFFSET3 {
  type uint32 {
   range "0..268435455";
  }
  mandatory false;
 }
 leaf MATCHLEN1 {
  type uint16 {
   range "1..800";
  }
  mandatory false;
 }
 leaf MATCHLEN2 {
  type uint16 {
   range "1..800";
  }
  mandatory false;
 }
 leaf MATCHLEN3 {
  type uint16 {
   range "1..800";
  }
  mandatory false;
 }
 leaf MODIFYCONTENT1 {
  type string {
   length "0..100";
  }
  mandatory false;
 }
 leaf MODIFYCONTENT2 {
  type string {
   length "0..100";
  }
  mandatory false;
 }
 leaf MODIFYCONTENT3 {
  type string {
   length "0..100";
  }
  mandatory false;
 }
 leaf MODIFYCOUNT {
  type enumeration {
   enum val-0;
   enum val-1;
   enum val-2;
   enum val-3;
  }
  mandatory false;
 }
 leaf MODIFYFIELDOFFSET1 {
  type uint32 {
   range "0..268435455";
  }
  mandatory false;
 }
 leaf MODIFYFIELDOFFSET2 {
  type uint32 {
   range "0..268435455";
  }
  mandatory false;
 }
 leaf MODIFYFIELDOFFSET3 {
  type uint32 {
   range "0..268435455";
  }
  mandatory false;
 }
 leaf MODIFYLEN1 {
  type uint16 {
   range "1..800";
  }
  mandatory false;
 }
 leaf MODIFYLEN2 {
  type uint16 {
   range "1..800";
  }
  mandatory false;
 }
 leaf MODIFYLEN3 {
  type uint16 {
   range "1..800";
  }
  mandatory false;
 }
 leaf MSGITFTYPE {
  type enumeration {
   enum val-0;
   enum val-1;
   enum val-2;
   enum val-3;
   enum val-4;
  }
  mandatory false;
 }
 leaf MSGOPTYPE {
  type boolean;
  mandatory false;
 }
 leaf MSGTYPE {
  type uint16 {
   range "0..65535";
  }
  mandatory false;
 }
 leaf PROTOCOLIEID {
  type uint16 {
   range "0..65535";
  }
  mandatory false;
 }
 leaf RULECFGTYPE {
  type enumeration {
   enum val-0;
   enum val-1;
   enum val-2;
   enum val-3;
  }
  mandatory false;
 }
 leaf OLD_RULEINDEX {
  type union {
   type int8 {
    range "-1..49";
   }
  }
  mandatory false;
 }
 leaf RULEINDEX {
  type union {
   type int8 {
    range "-1..49";
   }
  }
  mandatory false;
 }
 leaf UECAPINDEX {
  type uint8 {
   range "0..63";
  }
  mandatory false;
 }
 }
}
