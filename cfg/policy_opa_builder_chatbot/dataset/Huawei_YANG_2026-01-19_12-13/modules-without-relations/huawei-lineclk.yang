module huawei-lineclk {
 yang-version 1.1;
 namespace "urn:rdns:com:huawei:oammodel:huawei-lineclk";
 prefix lineclk;
 description
 "Auto-generated modular YANG for huawei-lineclk" ;
 revision "2026-01-19" {
 description "Auto-generated initial revision. Generated at 2026-01-19 12:13.";
 }
 grouping LINECLK-attributes {
 leaf CN {
  type uint8 {
   range "0..7";
  }
  mandatory false;
 }
 leaf OLD_LN {
  type union {
   type int8 {
    range "-1..0";
   }
  }
  mandatory false;
 }
 leaf LN {
  type union {
   type int8 {
    range "-1..0";
   }
  }
  mandatory false;
 }
 leaf PN {
  type uint8 {
   range "0..7";
  }
  mandatory false;
 }
 leaf PRI {
  type uint8 {
   range "1..4";
  }
  mandatory false;
 }
 leaf SN {
  type uint8 {
   range "0..7";
  }
  mandatory false;
 }
 leaf SRN {
  type uint8 {
   range "0..1";
  }
  mandatory false;
 }
 }
}
