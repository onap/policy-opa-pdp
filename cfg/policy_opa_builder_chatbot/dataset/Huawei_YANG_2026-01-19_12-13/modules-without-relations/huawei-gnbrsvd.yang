module huawei-gnbrsvd {
 yang-version 1.1;
 namespace "urn:rdns:com:huawei:oammodel:huawei-gnbrsvd";
 prefix gnbrsvd;
 description
 "Auto-generated modular YANG for huawei-gnbrsvd" ;
 revision "2026-01-19" {
 description "Auto-generated initial revision. Generated at 2026-01-19 12:13.";
 }
 grouping GNBRSVD-attributes {
 leaf RSVDPARAM102 {
  type uint32 {
   range "0..4294967295";
  }
  mandatory false;
 }
 leaf RSVDPARAM103 {
  type uint32 {
   range "0..4294967295";
  }
  mandatory false;
 }
 leaf RSVDPARAM104 {
  type uint32 {
   range "0..4294967295";
  }
  mandatory false;
 }
 leaf RSVDPARAM105 {
  type uint32 {
   range "0..4294967295";
  }
  mandatory false;
 }
 leaf RSVDPARAM106 {
  type uint32 {
   range "0..4294967295";
  }
  mandatory false;
 }
 leaf RSVDPARAM107 {
  type uint32 {
   range "0..4294967295";
  }
  mandatory false;
 }
 leaf RSVDPARAM108 {
  type uint32 {
   range "0..4294967295";
  }
  mandatory false;
 }
 leaf RSVDPARAM109 {
  type uint32 {
   range "0..4294967295";
  }
  mandatory false;
 }
 leaf RSVDPARAM110 {
  type uint32 {
   range "0..4294967295";
  }
  mandatory false;
 }
 leaf RSVDPARAM111 {
  type uint32 {
   range "0..4294967295";
  }
  mandatory false;
 }
 leaf RSVDPARAM112 {
  type uint32 {
   range "0..4294967295";
  }
  mandatory false;
 }
 leaf RSVDPARAM113 {
  type uint32 {
   range "0..4294967295";
  }
  mandatory false;
 }
 leaf RSVDPARAM114 {
  type uint32 {
   range "0..4294967295";
  }
  mandatory false;
 }
 leaf RSVDPARAM115 {
  type uint32 {
   range "0..4294967295";
  }
  mandatory false;
 }
 leaf RSVDPARAM116 {
  type uint32 {
   range "0..4294967295";
  }
  mandatory false;
 }
 leaf RSVDPARAM117 {
  type uint32 {
   range "0..4294967295";
  }
  mandatory false;
 }
 leaf RSVDPARAM118 {
  type uint32 {
   range "0..4294967295";
  }
  mandatory false;
 }
 leaf RSVDPARAM128 {
  type uint32 {
   range "0..4294967295";
  }
  mandatory false;
 }
 leaf RSVDPARAM129 {
  type uint32 {
   range "0..4294967295";
  }
  mandatory false;
 }
 leaf RSVDPARAM130 {
  type uint32 {
   range "0..4294967295";
  }
  mandatory false;
 }
 leaf RSVDPARAM131 {
  type uint32 {
   range "0..4294967295";
  }
  mandatory false;
 }
 leaf RSVDPARAM132 {
  type uint32 {
   range "0..4294967295";
  }
  mandatory false;
 }
 leaf RSVDPARAM133 {
  type uint32 {
   range "0..4294967295";
  }
  mandatory false;
 }
 leaf RSVDPARAM134 {
  type uint32 {
   range "0..4294967295";
  }
  mandatory false;
 }
 leaf RSVDPARAM135 {
  type uint32 {
   range "0..4294967295";
  }
  mandatory false;
 }
 leaf RSVDPARAM136 {
  type uint32 {
   range "0..4294967295";
  }
  mandatory false;
 }
 leaf RSVDPARAM137 {
  type uint32 {
   range "0..4294967295";
  }
  mandatory false;
 }
 leaf RSVDPARAM138 {
  type uint32 {
   range "0..4294967295";
  }
  mandatory false;
 }
 leaf RSVDPARAM36 {
  type uint32 {
   range "0..4294967295";
  }
  mandatory false;
 }
 leaf RSVDPARAM43 {
  type uint32 {
   range "0..4294967295";
  }
  mandatory false;
 }
 leaf RSVDPARAM50 {
  type uint32 {
   range "0..4294967295";
  }
  mandatory false;
 }
 leaf RSVDPARAM58 {
  type uint32 {
   range "0..4294967295";
  }
  mandatory false;
 }
 leaf RSVDPARAM60 {
  type uint32 {
   range "0..4294967295";
  }
  mandatory false;
 }
 leaf RSVDPARAM61 {
  type uint32 {
   range "0..4294967295";
  }
  mandatory false;
 }
 leaf RSVDPARAM62 {
  type uint32 {
   range "0..4294967295";
  }
  mandatory false;
 }
 leaf RSVDPARAM63 {
  type uint32 {
   range "0..4294967295";
  }
  mandatory false;
 }
 leaf RSVDPARAM64 {
  type uint32 {
   range "0..4294967295";
  }
  mandatory false;
 }
 leaf RSVDPARAM65 {
  type uint32 {
   range "0..4294967295";
  }
  mandatory false;
 }
 leaf RSVDPARAM66 {
  type uint32 {
   range "0..4294967295";
  }
  mandatory false;
 }
 leaf RSVDPARAM67 {
  type uint32 {
   range "0..4294967295";
  }
  mandatory false;
 }
 leaf RSVDPARAM68 {
  type uint32 {
   range "0..4294967295";
  }
  mandatory false;
 }
 leaf RSVDPARAM69 {
  type uint32 {
   range "0..4294967295";
  }
  mandatory false;
 }
 leaf RSVDPARAM70 {
  type uint32 {
   range "0..4294967295";
  }
  mandatory false;
 }
 leaf RSVDPARAM71 {
  type uint32 {
   range "0..4294967295";
  }
  mandatory false;
 }
 leaf RSVDPARAM72 {
  type uint32 {
   range "0..4294967295";
  }
  mandatory false;
 }
 leaf RSVDPARAM73 {
  type uint32 {
   range "0..4294967295";
  }
  mandatory false;
 }
 leaf RSVDPARAM74 {
  type uint32 {
   range "0..4294967295";
  }
  mandatory false;
 }
 leaf RSVDPARAM75 {
  type uint32 {
   range "0..4294967295";
  }
  mandatory false;
 }
 leaf RSVDPARAM76 {
  type uint32 {
   range "0..4294967295";
  }
  mandatory false;
 }
 leaf RSVDPARAM77 {
  type uint32 {
   range "0..4294967295";
  }
  mandatory false;
 }
 leaf RSVDPARAM78 {
  type uint32 {
   range "0..4294967295";
  }
  mandatory false;
 }
 leaf RSVDPARAM79 {
  type uint32 {
   range "0..4294967295";
  }
  mandatory false;
 }
 leaf RSVDPARAM80 {
  type uint32 {
   range "0..4294967295";
  }
  mandatory false;
 }
 leaf RSVDPARAM81 {
  type uint32 {
   range "0..4294967295";
  }
  mandatory false;
 }
 leaf RSVDPARAM82 {
  type uint32 {
   range "0..4294967295";
  }
  mandatory false;
 }
 leaf RSVDPARAM83 {
  type uint32 {
   range "0..4294967295";
  }
  mandatory false;
 }
 leaf RSVDPARAM84 {
  type uint32 {
   range "0..4294967295";
  }
  mandatory false;
 }
 leaf RSVDPARAM85 {
  type uint32 {
   range "0..4294967295";
  }
  mandatory false;
 }
 leaf RSVDPARAM86 {
  type uint32 {
   range "0..4294967295";
  }
  mandatory false;
 }
 leaf RSVDPARAM87 {
  type uint32 {
   range "0..4294967295";
  }
  mandatory false;
 }
 leaf RSVDPARAM88 {
  type uint32 {
   range "0..4294967295";
  }
  mandatory false;
 }
 leaf RSVDPARAM89 {
  type uint32 {
   range "0..4294967295";
  }
  mandatory false;
 }
 leaf RSVDPARAM90 {
  type uint32 {
   range "0..4294967295";
  }
  mandatory false;
 }
 leaf RSVDPARAM91 {
  type uint32 {
   range "0..4294967295";
  }
  mandatory false;
 }
 leaf RSVDPARAM92 {
  type uint32 {
   range "0..4294967295";
  }
  mandatory false;
 }
 leaf RSVDPARAM93 {
  type uint32 {
   range "0..4294967295";
  }
  mandatory false;
 }
 leaf RSVDPARAM94 {
  type uint32 {
   range "0..4294967295";
  }
  mandatory false;
 }
 leaf RSVDPARAM95 {
  type uint32 {
   range "0..4294967295";
  }
  mandatory false;
 }
 leaf RSVDPARAM96 {
  type uint32 {
   range "0..4294967295";
  }
  mandatory false;
 }
 leaf RSVDPARAM97 {
  type uint32 {
   range "0..4294967295";
  }
  mandatory false;
 }
 leaf RSVDPARAM98 {
  type uint32 {
   range "0..4294967295";
  }
  mandatory false;
 }
 leaf RSVDPARAM99 {
  type uint32 {
   range "0..4294967295";
  }
  mandatory false;
 }
 leaf RSVDSWPARAM0 {
  type string;
  mandatory false;
 }
 leaf RSVDSWPARAM2 {
  type string;
  mandatory false;
 }
 leaf RSVDSWPARAM3 {
  type string;
  mandatory false;
 }
 leaf RSVDSWPARAM4 {
  type string;
  mandatory false;
 }
 }
}
