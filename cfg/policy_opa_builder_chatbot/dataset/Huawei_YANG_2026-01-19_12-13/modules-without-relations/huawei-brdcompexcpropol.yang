module huawei-brdcompexcpropol {
 yang-version 1.1;
 namespace "urn:rdns:com:huawei:oammodel:huawei-brdcompexcpropol";
 prefix brdcompexcpropol;
 description
 "Auto-generated modular YANG for huawei-brdcompexcpropol" ;
 revision "2026-01-19" {
 description "Auto-generated initial revision. Generated at 2026-01-19 12:13.";
 }
 grouping BRDCOMPEXCPROPOL-attributes {
 leaf ASSOABNRANGE {
  type enumeration {
   enum val-0;
   enum val-1;
   enum val-2;
  }
  mandatory false;
 }
 leaf OLD_CN {
  type union {
   type int16 {
    range "-1..255";
   }
  }
  mandatory false;
 }
 leaf CN {
  type union {
   type int16 {
    range "-1..255";
   }
  }
  mandatory false;
 }
 leaf EFFHOUR {
  type uint8 {
   range "0..23";
  }
  mandatory false;
 }
 leaf EFFMIN {
  type uint8 {
   range "0..59";
  }
  mandatory false;
 }
 leaf EFFMODE {
  type boolean;
  mandatory false;
 }
 leaf OLD_EFFRANGE {
  type enumeration {
   enum val--1;
   enum val-0;
   enum val-1;
  }
  mandatory false;
 }
 leaf EFFRANGE {
  type enumeration {
   enum val--1;
   enum val-0;
   enum val-1;
  }
  mandatory false;
 }
 leaf OLD_SN {
  type union {
   type int16 {
    range "-1..255";
   }
  }
  mandatory false;
 }
 leaf SN {
  type union {
   type int16 {
    range "-1..255";
   }
  }
  mandatory false;
 }
 leaf OLD_SRN {
  type union {
   type int16 {
    range "-1..255";
   }
  }
  mandatory false;
 }
 leaf SRN {
  type union {
   type int16 {
    range "-1..255";
   }
  }
  mandatory false;
 }
 }
}
