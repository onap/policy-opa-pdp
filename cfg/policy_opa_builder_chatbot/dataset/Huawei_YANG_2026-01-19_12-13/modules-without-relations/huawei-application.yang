module huawei-application {
 yang-version 1.1;
 namespace "urn:rdns:com:huawei:oammodel:huawei-application";
 prefix application;
 import huawei-yang-types {
 prefix hwat;
 }
 description
 "Auto-generated modular YANG for huawei-application" ;
 revision "2026-01-19" {
 description "Auto-generated initial revision. Generated at 2026-01-19 12:13.";
 }
 grouping APPLICATION-attributes {
 leaf AID {
  type union {
   type int16 {
    range "-1..255";
   }
  }
  mandatory false;
 }
 leaf AN {
  type string {
   length "1..31";
  }
  mandatory false;
 }
 leaf APPET {
  type hwat:yyyy_mm_dd_HH_MM_SS_Time;
  mandatory false;
 }
 leaf APPHOTPATCHVERSION {
  type string {
   length "0..63";
  }
  mandatory false;
 }
 leaf APPMMSETREMARK {
  type string {
   length "0..255";
  }
  mandatory false;
 }
 leaf APPMNTMODE {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf APPST {
  type hwat:yyyy_mm_dd_HH_MM_SS_Time;
  mandatory false;
 }
 leaf AT {
  type enumeration {
   enum val-1;
   enum val-2;
   enum val-3;
   enum val-8;
   enum val-10;
   enum val-255;
  }
  mandatory false;
 }
 leaf AV {
  type string {
   length "0..63";
  }
  mandatory false;
 }
 leaf EXTAPPTYPE {
  type string {
   length "1..31";
  }
  mandatory false;
 }
 leaf HOTPATCHVERSION {
  type string {
   length "0..63";
  }
  mandatory false;
 }
 leaf RUNMODE {
  type boolean;
  mandatory false;
 }
 leaf SWVERSION {
  type string {
   length "0..63";
  }
  mandatory false;
 }
 }
}
