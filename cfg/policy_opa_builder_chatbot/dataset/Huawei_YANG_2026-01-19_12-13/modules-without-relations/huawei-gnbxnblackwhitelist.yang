module huawei-gnbxnblackwhitelist {
 yang-version 1.1;
 namespace "urn:rdns:com:huawei:oammodel:huawei-gnbxnblackwhitelist";
 prefix gnbxnblackwhitelist;
 description
 "Auto-generated modular YANG for huawei-gnbxnblackwhitelist" ;
 revision "2026-01-19" {
 description "Auto-generated initial revision. Generated at 2026-01-19 12:13.";
 }
 grouping GNBXNBLACKWHITELIST-attributes {
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf XNLISTTYPE {
  type boolean;
  mandatory false;
 }
 leaf OLD_GNBID {
  type union {
   type int64 {
    range "-1..4294967295";
   }
  }
  mandatory false;
 }
 leaf GNBID {
  type union {
   type int64 {
    range "-1..4294967295";
   }
  }
  mandatory false;
 }
 }
}
