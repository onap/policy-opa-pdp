module huawei-nrcellnrdcconfig {
 yang-version 1.1;
 namespace "urn:rdns:com:huawei:oammodel:huawei-nrcellnrdcconfig";
 prefix nrcellnrdcconfig;
 description
 "Auto-generated modular YANG for huawei-nrcellnrdcconfig" ;
 revision "2026-01-19" {
 description "Auto-generated initial revision. Generated at 2026-01-19 12:13.";
 }
 grouping NRCELLNRDCCONFIG-attributes {
 leaf DLSPLITDELAYTHLD {
  type uint8 {
   range "0..100";
  }
  mandatory false;
 }
 leaf DLSPLITMCGINITRATE {
  type uint16 {
   range "1..65000";
  }
  mandatory false;
 }
 leaf DLSPLITRSVDVOLTIMEFACTOR {
  type uint8 {
   range "0..100";
  }
  mandatory false;
 }
 leaf DLSPLITSCGINITRATE {
  type uint16 {
   range "1..1000";
  }
  mandatory false;
 }
 leaf DLSPLITSNOFFSET {
  type uint8 {
   range "1..100";
  }
  mandatory false;
 }
 leaf DLSPLITSTOPPENALTYPRD {
  type uint16 {
   range "1..600";
  }
  mandatory false;
 }
 leaf DLSPLITSTOPRATERATIOTHLD {
  type uint8 {
   range "1..100";
  }
  mandatory false;
 }
 leaf DLSPLITSTOPTIMETOTRIGGER {
  type uint8 {
   range "1..200";
  }
  mandatory false;
 }
 leaf EXCDLSPLITSTOPPENALTYPRD {
  type uint16 {
   range "1..600";
  }
  mandatory false;
 }
 leaf FASTRETRANSTRIGTHLD {
  type uint16 {
   range "0..5000";
  }
  mandatory false;
 }
 leaf NRCELLID {
  type union {
   type int32 {
    range "-1..65534";
   }
  }
  mandatory false;
 }
 leaf NRDCALGOSWITCH {
  type string;
  mandatory false;
 }
 leaf PSCELLA2RSRPTHLD {
  type int16 {
   range "-156..-31";
  }
  mandatory false;
 }
 leaf ULSPLITMCGULAMBRRATIO {
  type uint8 {
   range "1..99";
  }
  mandatory false;
 }
 }
}
