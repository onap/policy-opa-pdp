module huawei-epmu {
 yang-version 1.1;
 namespace "urn:rdns:com:huawei:oammodel:huawei-epmu";
 prefix epmu;
 description
 "Auto-generated modular YANG for huawei-epmu" ;
 revision "2026-01-19" {
 description "Auto-generated initial revision. Generated at 2026-01-19 12:13.";
 }
 grouping EPMU-attributes {
 leaf ADDR {
  type uint8 {
   range "1..254";
  }
  mandatory false;
 }
 leaf AGENTID {
  type uint32 {
   range "0..4294967295";
  }
  mandatory false;
 }
 leaf BAUDRATE {
  type enumeration {
   enum val-0;
   enum val-1;
   enum val-2;
  }
  mandatory false;
 }
 leaf OLD_CN {
  type union {
   type int8 {
    range "-1..62";
   }
  }
  mandatory false;
 }
 leaf CN {
  type union {
   type int8 {
    range "-1..62";
   }
  }
  mandatory false;
 }
 leaf CONNCN {
  type uint8 {
   range "0..62";
  }
  mandatory false;
 }
 leaf CONNSRN {
  type uint8 {
   range "17..18";
  }
  mandatory false;
 }
 leaf DESC {
  type string {
   length "0..199";
  }
  mandatory false;
 }
 leaf MIBINDEX {
  type union {
   type uint8 {
    range "0..255";
   }
  }
  mandatory false;
 }
 leaf PSGID {
  type uint8 {
   range "0..254";
  }
  mandatory false;
 }
 leaf PTYPE {
  type boolean;
  mandatory false;
 }
 leaf OLD_SN {
  type union {
   type int8 {
    range "-1..0";
   }
  }
  mandatory false;
 }
 leaf SN {
  type union {
   type int8 {
    range "-1..0";
   }
  }
  mandatory false;
 }
 leaf OLD_SRN {
  type union {
   type int8 {
    range "-1..59";
   }
  }
  mandatory false;
 }
 leaf SRN {
  type union {
   type int8 {
    range "-1..59";
   }
  }
  mandatory false;
 }
 }
}
