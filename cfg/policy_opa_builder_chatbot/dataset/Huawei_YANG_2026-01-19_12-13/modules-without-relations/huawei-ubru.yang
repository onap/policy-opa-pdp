module huawei-ubru {
 yang-version 1.1;
 namespace "urn:rdns:com:huawei:oammodel:huawei-ubru";
 prefix ubru;
 description
 "Auto-generated modular YANG for huawei-ubru" ;
 revision "2026-01-19" {
 description "Auto-generated initial revision. Generated at 2026-01-19 12:13.";
 }
 grouping UBRU-attributes {
 leaf OLD_CN {
  type union {
   type int8 {
    range "-1..15";
   }
  }
  mandatory false;
 }
 leaf CN {
  type union {
   type int8 {
    range "-1..15";
   }
  }
  mandatory false;
 }
 leaf ESN {
  type string {
   length "0..23";
  }
  mandatory false;
 }
 leaf LEDSW {
  type boolean;
  mandatory false;
 }
 leaf OLD_SN {
  type union {
   type int8 {
    range "-1..0";
   }
  }
  mandatory false;
 }
 leaf SN {
  type union {
   type int8 {
    range "-1..0";
   }
  }
  mandatory false;
 }
 leaf OLD_SRN {
  type union {
   type int16 {
    range "-1..254";
   }
  }
  mandatory false;
 }
 leaf SRN {
  type union {
   type int16 {
    range "-1..254";
   }
  }
  mandatory false;
 }
 leaf TYPE {
  type enumeration {
   enum val-190;
  }
  mandatory false;
 }
 leaf UID {
  type uint16 {
   range "0..65535";
  }
  mandatory false;
 }
 }
}
