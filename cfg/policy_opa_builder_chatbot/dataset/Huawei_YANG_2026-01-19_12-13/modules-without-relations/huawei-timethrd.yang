module huawei-timethrd {
 yang-version 1.1;
 namespace "urn:rdns:com:huawei:oammodel:huawei-timethrd";
 prefix timethrd;
 description
 "Auto-generated modular YANG for huawei-timethrd" ;
 revision "2026-01-19" {
 description "Auto-generated initial revision. Generated at 2026-01-19 12:13.";
 }
 grouping TIMETHRD-attributes {
 leaf PROCMODE {
  type boolean;
  mandatory false;
 }
 leaf THRD {
  type uint16 {
   range "1..65535";
  }
  mandatory false;
 }
 leaf TIMESRCENHPROCSW {
  type boolean;
  mandatory false;
 }
 }
}
