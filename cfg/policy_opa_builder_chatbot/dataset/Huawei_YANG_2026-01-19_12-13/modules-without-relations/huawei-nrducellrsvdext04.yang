module huawei-nrducellrsvdext04 {
 yang-version 1.1;
 namespace "urn:rdns:com:huawei:oammodel:huawei-nrducellrsvdext04";
 prefix nrducellrsvdext04;
 description
 "Auto-generated modular YANG for huawei-nrducellrsvdext04" ;
 revision "2026-01-19" {
 description "Auto-generated initial revision. Generated at 2026-01-19 12:13.";
 }
 grouping NRDUCELLRSVDEXT04-attributes {
 leaf NRDUCELLID {
  type union {
   type int32 {
    range "-1..65534";
   }
  }
  mandatory false;
 }
 leaf RSVDPARAM15 {
  type uint32 {
   range "0..4294967295";
  }
  mandatory false;
 }
 leaf RSVDPARAM19 {
  type uint32 {
   range "0..4294967295";
  }
  mandatory false;
 }
 leaf RSVDPARAM21 {
  type uint32 {
   range "0..4294967295";
  }
  mandatory false;
 }
 leaf RSVDPARAM23 {
  type uint32 {
   range "0..4294967295";
  }
  mandatory false;
 }
 leaf RSVDPARAM24 {
  type uint32 {
   range "0..4294967295";
  }
  mandatory false;
 }
 leaf RSVDPARAM34 {
  type uint32 {
   range "0..4294967295";
  }
  mandatory false;
 }
 leaf RSVDPARAM35 {
  type uint32 {
   range "0..4294967295";
  }
  mandatory false;
 }
 leaf RSVDPARAM36 {
  type uint32 {
   range "0..4294967295";
  }
  mandatory false;
 }
 leaf RSVDPARAM37 {
  type uint32 {
   range "0..4294967295";
  }
  mandatory false;
 }
 leaf RSVDPARAM38 {
  type uint32 {
   range "0..4294967295";
  }
  mandatory false;
 }
 leaf RSVDPARAM39 {
  type uint32 {
   range "0..4294967295";
  }
  mandatory false;
 }
 leaf RSVDPARAM4 {
  type uint32 {
   range "0..4294967295";
  }
  mandatory false;
 }
 leaf RSVDPARAM40 {
  type uint32 {
   range "0..4294967295";
  }
  mandatory false;
 }
 leaf RSVDPARAM41 {
  type uint32 {
   range "0..4294967295";
  }
  mandatory false;
 }
 leaf RSVDPARAM42 {
  type uint32 {
   range "0..4294967295";
  }
  mandatory false;
 }
 leaf RSVDPARAM43 {
  type uint32 {
   range "0..4294967295";
  }
  mandatory false;
 }
 leaf RSVDPARAM44 {
  type uint32 {
   range "0..4294967295";
  }
  mandatory false;
 }
 leaf RSVDPARAM45 {
  type uint32 {
   range "0..4294967295";
  }
  mandatory false;
 }
 leaf RSVDPARAM46 {
  type uint32 {
   range "0..4294967295";
  }
  mandatory false;
 }
 leaf RSVDPARAM47 {
  type uint32 {
   range "0..4294967295";
  }
  mandatory false;
 }
 leaf RSVDPARAM48 {
  type uint32 {
   range "0..4294967295";
  }
  mandatory false;
 }
 leaf RSVDPARAM49 {
  type uint32 {
   range "0..4294967295";
  }
  mandatory false;
 }
 leaf RSVDPARAM50 {
  type uint32 {
   range "0..4294967295";
  }
  mandatory false;
 }
 leaf RSVDPARAM51 {
  type uint32 {
   range "0..4294967295";
  }
  mandatory false;
 }
 leaf RSVDPARAM52 {
  type uint32 {
   range "0..4294967295";
  }
  mandatory false;
 }
 leaf RSVDPARAM53 {
  type uint32 {
   range "0..4294967295";
  }
  mandatory false;
 }
 leaf RSVDPARAM54 {
  type uint32 {
   range "0..4294967295";
  }
  mandatory false;
 }
 leaf RSVDPARAM55 {
  type uint32 {
   range "0..4294967295";
  }
  mandatory false;
 }
 leaf RSVDPARAM56 {
  type uint32 {
   range "0..4294967295";
  }
  mandatory false;
 }
 leaf RSVDPARAM57 {
  type uint32 {
   range "0..4294967295";
  }
  mandatory false;
 }
 leaf RSVDPARAM58 {
  type uint32 {
   range "0..4294967295";
  }
  mandatory false;
 }
 leaf RSVDPARAM59 {
  type uint32 {
   range "0..4294967295";
  }
  mandatory false;
 }
 leaf RSVDPARAM60 {
  type uint32 {
   range "0..4294967295";
  }
  mandatory false;
 }
 leaf RSVDPARAM61 {
  type uint32 {
   range "0..4294967295";
  }
  mandatory false;
 }
 leaf RSVDPARAM62 {
  type uint32 {
   range "0..4294967295";
  }
  mandatory false;
 }
 leaf RSVDPARAM63 {
  type uint32 {
   range "0..4294967295";
  }
  mandatory false;
 }
 leaf RSVDPARAM64 {
  type uint32 {
   range "0..4294967295";
  }
  mandatory false;
 }
 leaf RSVDPARAM65 {
  type uint32 {
   range "0..4294967295";
  }
  mandatory false;
 }
 leaf RSVDPARAM66 {
  type uint32 {
   range "0..4294967295";
  }
  mandatory false;
 }
 leaf RSVDPARAM67 {
  type uint32 {
   range "0..4294967295";
  }
  mandatory false;
 }
 leaf RSVDSWPARAM0 {
  type string;
  mandatory false;
 }
 leaf RSVDSWPARAM1 {
  type string;
  mandatory false;
 }
 leaf RSVDSWPARAM2 {
  type string;
  mandatory false;
 }
 }
}
