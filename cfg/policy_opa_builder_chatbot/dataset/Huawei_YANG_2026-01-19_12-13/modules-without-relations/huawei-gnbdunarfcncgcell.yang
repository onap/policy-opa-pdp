module huawei-gnbdunarfcncgcell {
 yang-version 1.1;
 namespace "urn:rdns:com:huawei:oammodel:huawei-gnbdunarfcncgcell";
 prefix gnbdunarfcncgcell;
 description
 "Auto-generated modular YANG for huawei-gnbdunarfcncgcell" ;
 revision "2026-01-19" {
 description "Auto-generated initial revision. Generated at 2026-01-19 12:13.";
 }
 grouping GNBDUNARFCNCGCELL-attributes {
 leaf NARFCNCELLGROUPID {
  type union {
   type int16 {
    range "-1..191";
   }
  }
  mandatory false;
 }
 leaf NRDUCELLID {
  type union {
   type int32 {
    range "-1..65534";
   }
  }
  mandatory false;
 }
 }
}
