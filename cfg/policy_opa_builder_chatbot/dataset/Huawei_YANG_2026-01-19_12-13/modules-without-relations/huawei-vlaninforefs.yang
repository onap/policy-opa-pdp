module huawei-vlaninforefs {
 yang-version 1.1;
 namespace "urn:rdns:com:huawei:oammodel:huawei-vlaninforefs";
 prefix vlaninforefs;
 description
 "Auto-generated modular YANG for huawei-vlaninforefs" ;
 revision "2026-01-19" {
 description "Auto-generated initial revision. Generated at 2026-01-19 12:13.";
 }
 grouping VLANINFOREFS-attributes {
 leaf VBIPORTID {
  type union {
   type int8 {
    range "-1..99";
   }
  }
  mandatory false;
 }
 leaf VLANID {
  type union {
   type int16 {
    range "-1..4094";
   }
  }
  mandatory false;
 }
 leaf VLANTAGMODE {
  type enumeration {
   enum val--1;
   enum val-0;
   enum val-1;
  }
  mandatory false;
 }
 }
}
