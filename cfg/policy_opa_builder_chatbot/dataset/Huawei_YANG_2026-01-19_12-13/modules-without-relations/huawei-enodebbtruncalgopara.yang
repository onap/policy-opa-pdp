module huawei-enodebbtruncalgopara {
 yang-version 1.1;
 namespace "urn:rdns:com:huawei:oammodel:huawei-enodebbtruncalgopara";
 prefix enodebbtruncalgopara;
 description
 "Auto-generated modular YANG for huawei-enodebbtruncalgopara" ;
 revision "2026-01-19" {
 description "Auto-generated initial revision. Generated at 2026-01-19 12:13.";
 }
 grouping ENODEBBTRUNCALGOPARA-attributes {
 leaf AMROVERPDCPDLINITBUFFERNUM {
  type uint8 {
   range "0..20";
  }
  mandatory false;
 }
 leaf AMROVERPDCPDLMAXBUFFERNUM {
  type uint8 {
   range "0..20";
  }
  mandatory false;
 }
 }
}
