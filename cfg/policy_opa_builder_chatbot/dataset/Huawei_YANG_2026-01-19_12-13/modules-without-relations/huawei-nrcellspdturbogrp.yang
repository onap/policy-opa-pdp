module huawei-nrcellspdturbogrp {
 yang-version 1.1;
 namespace "urn:rdns:com:huawei:oammodel:huawei-nrcellspdturbogrp";
 prefix nrcellspdturbogrp;
 description
 "Auto-generated modular YANG for huawei-nrcellspdturbogrp" ;
 revision "2026-01-19" {
 description "Auto-generated initial revision. Generated at 2026-01-19 12:13.";
 }
 grouping NRCELLSPDTURBOGRP-attributes {
 leaf INTERFREQA4A5TIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf OLD_NRCELLID {
  type union {
   type int32 {
    range "-1..65534";
   }
  }
  mandatory false;
 }
 leaf NRCELLID {
  type union {
   type int32 {
    range "-1..65534";
   }
  }
  mandatory false;
 }
 leaf NSADLDEJITTERBUFFERPKTNUM {
  type uint8 {
   range "0..10";
  }
  mandatory false;
 }
 leaf NSADLDEJITTERPKTINTERVAL {
  type uint8 {
   range "10..200";
  }
  mandatory false;
 }
 leaf SADLDEJITTERBUFFERPKTNUM {
  type uint8 {
   range "0..10";
  }
  mandatory false;
 }
 leaf SADLDEJITTERPKTINTERVAL {
  type uint8 {
   range "10..200";
  }
  mandatory false;
 }
 leaf SPDTURBOFLAGVALIDITYPRDOFS {
  type uint16 {
   range "0..65535";
  }
  mandatory false;
 }
 leaf SPDTURBOPDCPPARAMGROUPID {
  type union {
   type uint8 {
    range "0..255";
   }
  }
  mandatory false;
 }
 leaf OLD_SPEEDTURBOGROUPID {
  type union {
   type int8 {
    range "-1..9";
   }
  }
  mandatory false;
 }
 leaf SPEEDTURBOGROUPID {
  type union {
   type int8 {
    range "-1..9";
   }
  }
  mandatory false;
 }
 leaf SPEEDTURBOPDCPALGOSW {
  type string;
  mandatory false;
 }
 leaf SPEEDTURBOSWITCH {
  type string;
  mandatory false;
 }
 leaf SPEEDTURBOTARGETFREQ {
  type uint32 {
   range "0..4294967295";
  }
  mandatory false;
 }
 leaf STNSAULKEEPINLTEAFTERHOSW {
  type enumeration {
   enum val-0;
   enum val-1;
   enum val-2;
  }
  mandatory false;
 }
 leaf VONRSPDTURBOFLAGDELAYPRD {
  type uint16 {
   range "30..300";
  }
  mandatory false;
 }
 leaf VOICEPOLICYSWITCH {
  type string;
  mandatory false;
 }
 }
}
