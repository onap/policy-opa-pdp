module huawei-enbueimeisvgroup {
 yang-version 1.1;
 namespace "urn:rdns:com:huawei:oammodel:huawei-enbueimeisvgroup";
 prefix enbueimeisvgroup;
 description
 "Auto-generated modular YANG for huawei-enbueimeisvgroup" ;
 revision "2026-01-19" {
 description "Auto-generated initial revision. Generated at 2026-01-19 12:13.";
 }
 grouping ENBUEIMEISVGROUP-attributes {
 leaf OLD_UEIMEISVGROUPID {
  type union {
   type int8 {
    range "-1..9";
   }
  }
  mandatory false;
 }
 leaf UEIMEISVGROUPID {
  type union {
   type int8 {
    range "-1..9";
   }
  }
  mandatory false;
 }
 leaf OLD_UEIMEISVSVN {
  type union {
   type int16 {
    range "-1..255";
   }
  }
  mandatory false;
 }
 leaf UEIMEISVSVN {
  type union {
   type int16 {
    range "-1..255";
   }
  }
  mandatory false;
 }
 leaf OLD_UEIMEISVTAC {
  type union {
   type int32 {
    range "-1..99999999";
   }
  }
  mandatory false;
 }
 leaf UEIMEISVTAC {
  type union {
   type int32 {
    range "-1..99999999";
   }
  }
  mandatory false;
 }
 }
}
