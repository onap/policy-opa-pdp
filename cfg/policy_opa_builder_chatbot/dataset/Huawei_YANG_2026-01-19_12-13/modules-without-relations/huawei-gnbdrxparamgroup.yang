module huawei-gnbdrxparamgroup {
 yang-version 1.1;
 namespace "urn:rdns:com:huawei:oammodel:huawei-gnbdrxparamgroup";
 prefix gnbdrxparamgroup;
 description
 "Auto-generated modular YANG for huawei-gnbdrxparamgroup" ;
 revision "2026-01-19" {
 description "Auto-generated initial revision. Generated at 2026-01-19 12:13.";
 }
 grouping GNBDRXPARAMGROUP-attributes {
 leaf OLD_DRXPARAMGROUPID {
  type union {
   type int8 {
    range "-1..65";
   }
  }
  mandatory false;
 }
 leaf DRXPARAMGROUPID {
  type union {
   type int8 {
    range "-1..65";
   }
  }
  mandatory false;
 }
 leaf LONGCYCLE {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf SHORTCYCLE {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
  }
  mandatory false;
 }
 leaf SHORTCYCLETIMER {
  type uint8 {
   range "0..16";
  }
  mandatory false;
 }
 }
}
