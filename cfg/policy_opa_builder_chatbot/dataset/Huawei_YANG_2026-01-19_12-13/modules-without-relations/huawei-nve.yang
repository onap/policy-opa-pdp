module huawei-nve {
 yang-version 1.1;
 namespace "urn:rdns:com:huawei:oammodel:huawei-nve";
 prefix nve;
 import ietf-interfaces {
 prefix if;
 }
 import ietf-ip {
 prefix ip;
 }
 import ietf-inet-types {
 prefix inet;
 }
 description
 "Auto-generated modular YANG for huawei-nve" ;
 revision "2026-01-19" {
 description "Auto-generated initial revision. Generated at 2026-01-19 12:13.";
 }
 augment "/if:interfaces/if:interface/ip:ipv4" {
 container nve-ipv4 {
  container attributes {
   uses NVE-attributes {
    /* opcjonalnie: tu można ograniczyć do IP-only */
   }
  }
 }
}
 grouping NVE-attributes {
 leaf LOCIP {
  type inet:ipv4-address;
  mandatory false;
 }
 leaf OLD_NVEID {
  type union {
   type int8 {
    range "-1..31";
   }
  }
  mandatory false;
 }
 leaf NVEID {
  type union {
   type int8 {
    range "-1..31";
   }
  }
  mandatory false;
 }
 leaf VRFIDX {
  type uint8 {
   range "1..7";
  }
  mandatory false;
 }
 }
}
