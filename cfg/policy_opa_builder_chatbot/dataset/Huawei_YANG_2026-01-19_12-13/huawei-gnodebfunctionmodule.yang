module huawei-gnodebfunctionmodule {
 yang-version 1.1;
 namespace "urn:rdns:com:huawei:oammodel:huawei-gnodebfunctionmodule";
 prefix gnodebfunctionmodule;
 import huawei-ne {
 prefix ne;
 }
 import ietf-inet-types {
 prefix inet;
 }
 import ietf-interfaces {
 prefix if;
 }
 import ietf-ip {
 prefix ip;
 }
 import huawei-yang-types {
 prefix hwat;
 }
 import ietf-yang-types {
 prefix yang;
 }
 description
 "Auto-generated modular YANG for huawei-gnodebfunctionmodule" ;
 revision "2026-01-19" {
 description "Auto-generated abstract group module (aggregated lists from relations.xml). Generated at 2026-01-19 12:13.";
 }
 augment "/ne:NE" {
 container gNodeBFunctionModule {
  description "Abstract group container injected between NE and its direct child.";
  container attributes {
    leaf neName {
     type string;
     mandatory false;
    }
    leaf productversion {
     type string;
     mandatory false;
    }
  }
 }
 }
 augment "/ne:NE/gnodebfunctionmodule:gNodeBFunctionModule/GNODEBFUNCTION" {
  list GNB5QICONFIG {
   max-elements 30;
   key "ASREFLECTIVEQOSSWITCH";
   leaf ASREFLECTIVEQOSSWITCH {
    type leafref {
     path "../attributes/ASREFLECTIVEQOSSWITCH";
     require-instance true;
    }
   }
   container attributes {
    uses GNB5QICONFIG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBAIRINTFSECPARAM {
   max-elements 1;
   key "AIRINTFANTIDDOSSW";
   leaf AIRINTFANTIDDOSSW {
    type leafref {
     path "../attributes/AIRINTFANTIDDOSSW";
     require-instance true;
    }
   }
   container attributes {
    uses GNBAIRINTFSECPARAM-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBAMFDOMAINNAME {
   max-elements 32;
   key "GNBCUNGID";
   leaf GNBCUNGID {
    type leafref {
     path "../attributes/GNBCUNGID";
     require-instance true;
    }
   }
   container attributes {
    uses GNBAMFDOMAINNAME-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBCAFREQUENCY {
   max-elements 32;
   key "CAFREQGROUPID";
   leaf CAFREQGROUPID {
    type leafref {
     path "../attributes/CAFREQGROUPID";
     require-instance true;
    }
   }
   container attributes {
    uses GNBCAFREQUENCY-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBCAG {
   max-elements 144;
   key "CAGID";
   leaf CAGID {
    type leafref {
     path "../attributes/CAGID";
     require-instance true;
    }
   }
   container attributes {
    uses GNBCAG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBCAGGRP {
   max-elements 144;
   key "CAGGRPID";
   leaf CAGGRPID {
    type leafref {
     path "../attributes/CAGGRPID";
     require-instance true;
    }
   }
   container attributes {
    uses GNBCAGGRP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBCELLBLACKLIST {
   max-elements 288;
   key "CELLBLACKLISTID";
   leaf CELLBLACKLISTID {
    type leafref {
     path "../attributes/CELLBLACKLISTID";
     require-instance true;
    }
   }
   container attributes {
    uses GNBCELLBLACKLIST-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBCIPHERCAPB {
   max-elements 4;
   key "CIPHERALGO";
   leaf CIPHERALGO {
    type leafref {
     path "../attributes/CIPHERALGO";
     require-instance true;
    }
   }
   container attributes {
    uses GNBCIPHERCAPB-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBCLOUDXPARAMGROUP {
   max-elements 40;
   key "GNBCLOUDXPARAMGROUPID";
   leaf GNBCLOUDXPARAMGROUPID {
    type leafref {
     path "../attributes/GNBCLOUDXPARAMGROUPID";
     require-instance true;
    }
   }
   container attributes {
    uses GNBCLOUDXPARAMGROUP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBCLUSTER {
   max-elements 36;
   key "CLUSTERID";
   leaf CLUSTERID {
    type leafref {
     path "../attributes/CLUSTERID";
     require-instance true;
    }
   }
   container attributes {
    uses GNBCLUSTER-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBCONNSTATETIMER {
   max-elements 1;
   key "INACTIVETOIDLETIMERADJSTEP";
   leaf INACTIVETOIDLETIMERADJSTEP {
    type leafref {
     path "../attributes/INACTIVETOIDLETIMERADJSTEP";
     require-instance true;
    }
   }
   container attributes {
    uses GNBCONNSTATETIMER-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBCUNG {
   max-elements 6;
   key "GNBCUNGID";
   leaf GNBCUNGID {
    type leafref {
     path "../attributes/GNBCUNGID";
     require-instance true;
    }
   }
   container attributes {
    uses GNBCUNG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBCUNGINTERFACE {
   max-elements 96;
   key "GNBCUNGINTERFACEID";
   leaf GNBCUNGINTERFACEID {
    type leafref {
     path "../attributes/GNBCUNGINTERFACEID";
     require-instance true;
    }
   }
   container attributes {
    uses GNBCUNGINTERFACE-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBCUNGNS {
   max-elements 108;
   key "GNBCUNGID";
   leaf GNBCUNGID {
    type leafref {
     path "../attributes/GNBCUNGID";
     require-instance true;
    }
   }
   container attributes {
    uses GNBCUNGNS-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/GNBCUNG" {
  list GNBCUNGOP {
   max-elements 12;
   key "GNBCUNGID";
   leaf GNBCUNGID {
    type leafref {
     path "../attributes/GNBCUNGID";
     require-instance true;
    }
   }
   container attributes {
    uses GNBCUNGOP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/GNBCUNG" {
  list GNBCUNGTRACKINGAREA {
   max-elements 216;
   key "GNBCUNGID";
   leaf GNBCUNGID {
    type leafref {
     path "../attributes/GNBCUNGID";
     require-instance true;
    }
   }
   container attributes {
    uses GNBCUNGTRACKINGAREA-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBCUS1 {
   max-elements 12;
   key "GNBCUS1ID";
   leaf GNBCUS1ID {
    type leafref {
     path "../attributes/GNBCUS1ID";
     require-instance true;
    }
   }
   container attributes {
    uses GNBCUS1-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/GNBCUS1" {
  list GNBCUS1OP {
   max-elements 12;
   key "GNBCUS1ID";
   leaf GNBCUS1ID {
    type leafref {
     path "../attributes/GNBCUS1ID";
     require-instance true;
    }
   }
   container attributes {
    uses GNBCUS1OP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBCUX2 {
   max-elements 12;
   key "GNBCUX2ID";
   leaf GNBCUX2ID {
    type leafref {
     path "../attributes/GNBCUX2ID";
     require-instance true;
    }
   }
   container attributes {
    uses GNBCUX2-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/GNBCUX2" {
  list GNBCUX2OP {
   max-elements 12;
   key "GNBCUX2ID";
   leaf GNBCUX2ID {
    type leafref {
     path "../attributes/GNBCUX2ID";
     require-instance true;
    }
   }
   container attributes {
    uses GNBCUX2OP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBCUXN {
   max-elements 12;
   key "GNBCUXNID";
   leaf GNBCUXNID {
    type leafref {
     path "../attributes/GNBCUXNID";
     require-instance true;
    }
   }
   container attributes {
    uses GNBCUXN-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBCUXNINTERFACE {
   max-elements 768;
   key "GNBCUXNINTERFACEID";
   leaf GNBCUXNINTERFACEID {
    type leafref {
     path "../attributes/GNBCUXNINTERFACEID";
     require-instance true;
    }
   }
   container attributes {
    uses GNBCUXNINTERFACE-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/GNBCUXN" {
  list GNBCUXNOP {
   max-elements 12;
   key "GNBCUXNID";
   leaf GNBCUXNID {
    type leafref {
     path "../attributes/GNBCUXNID";
     require-instance true;
    }
   }
   container attributes {
    uses GNBCUXNOP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBDEDNSADCBANDCOMB {
   max-elements 64;
   key "NRBANDID";
   leaf NRBANDID {
    type leafref {
     path "../attributes/NRBANDID";
     require-instance true;
    }
   }
   container attributes {
    uses GNBDEDNSADCBANDCOMB-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBDIFFUSEREXPGROUP {
   max-elements 40;
   key "GNBDIFFUSEREXPGROUPID";
   leaf GNBDIFFUSEREXPGROUPID {
    type leafref {
     path "../attributes/GNBDIFFUSEREXPGROUPID";
     require-instance true;
    }
   }
   container attributes {
    uses GNBDIFFUSEREXPGROUP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBDUEXN {
   max-elements 1;
   key "GNBDUEXNID";
   leaf GNBDUEXNID {
    type leafref {
     path "../attributes/GNBDUEXNID";
     require-instance true;
    }
   }
   container attributes {
    uses GNBDUEXN-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBDUEXNOP {
   max-elements 12;
   key "GNBDUEXNID";
   leaf GNBDUEXNID {
    type leafref {
     path "../attributes/GNBDUEXNID";
     require-instance true;
    }
   }
   container attributes {
    uses GNBDUEXNOP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBDULTENRSPCTSHRCG {
   max-elements 11;
   key "NRSPCTSHRCELLGRPID";
   leaf NRSPCTSHRCELLGRPID {
    type leafref {
     path "../attributes/NRSPCTSHRCELLGRPID";
     require-instance true;
    }
   }
   container attributes {
    uses GNBDULTENRSPCTSHRCG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBDUPARAM {
   max-elements 1;
   key "LTENRPOWERSHRENABLETIME";
   leaf LTENRPOWERSHRENABLETIME {
    type leafref {
     path "../attributes/LTENRPOWERSHRENABLETIME";
     require-instance true;
    }
   }
   container attributes {
    uses GNBDUPARAM-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBDUQCIALGOPARAMGRP {
   max-elements 144;
   key "QCIALGOPARAMGROUPID";
   leaf QCIALGOPARAMGROUPID {
    type leafref {
     path "../attributes/QCIALGOPARAMGROUPID";
     require-instance true;
    }
   }
   container attributes {
    uses GNBDUQCIALGOPARAMGRP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/GNBOPERATOR" {
  list GNBDURFSPCONFIG {
   max-elements 257;
   key "OPERATORID";
   leaf OPERATORID {
    type leafref {
     path "../attributes/OPERATORID";
     require-instance true;
    }
   }
   container attributes {
    uses GNBDURFSPCONFIG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBDUSCHPARAMGROUP {
   max-elements 60;
   key "SCHEDULEPARAMGROUPID";
   leaf SCHEDULEPARAMGROUPID {
    type leafref {
     path "../attributes/SCHEDULEPARAMGROUPID";
     require-instance true;
    }
   }
   container attributes {
    uses GNBDUSCHPARAMGROUP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBDUSPSGRP {
   max-elements 64;
   key "NRSPSGRPID";
   leaf NRSPSGRPID {
    type leafref {
     path "../attributes/NRSPSGRPID";
     require-instance true;
    }
   }
   container attributes {
    uses GNBDUSPSGRP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/GNBEUTRAEXTERNALCELL" {
  list GNBEUTRAEXTCELLPLMN {
   max-elements 5;
   key "CELLID ENODEBID MCC MNC";
   leaf CELLID {
    type leafref {
     path "../attributes/CELLID";
     require-instance true;
    }
   }
   leaf ENODEBID {
    type leafref {
     path "../attributes/ENODEBID";
     require-instance true;
    }
   }
   leaf MCC {
    type leafref {
     path "../attributes/MCC";
     require-instance true;
    }
   }
   leaf MNC {
    type leafref {
     path "../attributes/MNC";
     require-instance true;
    }
   }
   container attributes {
    uses GNBEUTRAEXTCELLPLMN-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBEUTRAEXTERNALCELL {
   max-elements 4608;
   key "CELLID";
   leaf CELLID {
    type leafref {
     path "../attributes/CELLID";
     require-instance true;
    }
   }
   container attributes {
    uses GNBEUTRAEXTERNALCELL-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBEUTRANBLACKLIST {
   max-elements 128;
   key "ENODEBID";
   leaf ENODEBID {
    type leafref {
     path "../attributes/ENODEBID";
     require-instance true;
    }
   }
   container attributes {
    uses GNBEUTRANBLACKLIST-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBFREQPRIORITYGROUP {
   max-elements 4080;
   key "GNBFREQPRIORITYGROUPID";
   leaf GNBFREQPRIORITYGROUPID {
    type leafref {
     path "../attributes/GNBFREQPRIORITYGROUPID";
     require-instance true;
    }
   }
   container attributes {
    uses GNBFREQPRIORITYGROUP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBINCRCFG {
   max-elements 1;
   key "INCRCFGID";
   leaf INCRCFGID {
    type leafref {
     path "../attributes/INCRCFGID";
     require-instance true;
    }
   }
   container attributes {
    uses GNBINCRCFG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBINTEGRITYCAPB {
   max-elements 3;
   key "INTEGRITYALGO";
   leaf INTEGRITYALGO {
    type leafref {
     path "../attributes/INTEGRITYALGO";
     require-instance true;
    }
   }
   container attributes {
    uses GNBINTEGRITYCAPB-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBINTERFACEPARAM {
   max-elements 1;
   key "EXNUPAGINGTIMER";
   leaf EXNUPAGINGTIMER {
    type leafref {
     path "../attributes/EXNUPAGINGTIMER";
     require-instance true;
    }
   }
   container attributes {
    uses GNBINTERFACEPARAM-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBLICENSECONFIG {
   max-elements 1;
   key "ANTBWLICENSEPOLICY";
   leaf ANTBWLICENSEPOLICY {
    type leafref {
     path "../attributes/ANTBWLICENSEPOLICY";
     require-instance true;
    }
   }
   container attributes {
    uses GNBLICENSECONFIG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/GNBCLUSTER" {
  list GNBMIMOCLUSTERCELL {
   max-elements 18;
   key "CLUSTERID";
   leaf CLUSTERID {
    type leafref {
     path "../attributes/CLUSTERID";
     require-instance true;
    }
   }
   container attributes {
    uses GNBMIMOCLUSTERCELL-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBMOBILITYCOMMPARAM {
   max-elements 1;
   key "ADAPTCOVRSRPTHLD";
   leaf ADAPTCOVRSRPTHLD {
    type leafref {
     path "../attributes/ADAPTCOVRSRPTHLD";
     require-instance true;
    }
   }
   container attributes {
    uses GNBMOBILITYCOMMPARAM-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBMOBILITYCTRLLIST {
   max-elements 16;
   key "GNODEBENDID";
   leaf GNODEBENDID {
    type leafref {
     path "../attributes/GNODEBENDID";
     require-instance true;
    }
   }
   container attributes {
    uses GNBMOBILITYCTRLLIST-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBNCELLPLMNLIST {
   max-elements 32;
   key "MCC";
   leaf MCC {
    type leafref {
     path "../attributes/MCC";
     require-instance true;
    }
   }
   container attributes {
    uses GNBNCELLPLMNLIST-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/GNBOPERATOR" {
  list GNBNETWORKSLICE {
   max-elements 1024;
   key "OPERATORID";
   leaf OPERATORID {
    type leafref {
     path "../attributes/OPERATORID";
     require-instance true;
    }
   }
   container attributes {
    uses GNBNETWORKSLICE-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBNGHOFREQRELATION {
   max-elements 384;
   key "MCC";
   leaf MCC {
    type leafref {
     path "../attributes/MCC";
     require-instance true;
    }
   }
   container attributes {
    uses GNBNGHOFREQRELATION-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBNGSONCONFIG {
   max-elements 1;
   key "NGCSONSWITCH";
   leaf NGCSONSWITCH {
    type leafref {
     path "../attributes/NGCSONSWITCH";
     require-instance true;
    }
   }
   container attributes {
    uses GNBNGSONCONFIG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBNRBLACKLIST {
   max-elements 128;
   key "GNODEBID";
   leaf GNODEBID {
    type leafref {
     path "../attributes/GNODEBID";
     require-instance true;
    }
   }
   container attributes {
    uses GNBNRBLACKLIST-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBNRLTECELLCOMB {
   max-elements 288;
   key "CELLID";
   leaf CELLID {
    type leafref {
     path "../attributes/CELLID";
     require-instance true;
    }
   }
   container attributes {
    uses GNBNRLTECELLCOMB-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBOAMPARAM {
   max-elements 1;
   key "ABNUEULDATAERRORJUDGETHLD";
   leaf ABNUEULDATAERRORJUDGETHLD {
    type leafref {
     path "../attributes/ABNUEULDATAERRORJUDGETHLD";
     require-instance true;
    }
   }
   container attributes {
    uses GNBOAMPARAM-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBOP5QICONFIG {
   max-elements 60;
   key "OPERATORID";
   leaf OPERATORID {
    type leafref {
     path "../attributes/OPERATORID";
     require-instance true;
    }
   }
   container attributes {
    uses GNBOP5QICONFIG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBOPERATOR {
   max-elements 12;
   key "GNBID";
   leaf GNBID {
    type leafref {
     path "../attributes/GNBID";
     require-instance true;
    }
   }
   container attributes {
    uses GNBOPERATOR-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/GNBOPERATOR" {
  list GNBOPERATORQCIPARAM {
   max-elements 50;
   key "OPERATORID";
   leaf OPERATORID {
    type leafref {
     path "../attributes/OPERATORID";
     require-instance true;
    }
   }
   container attributes {
    uses GNBOPERATORQCIPARAM-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBPDCPPARAMGROUP {
   max-elements 166;
   key "PDCPPARAMGROUPID";
   leaf PDCPPARAMGROUPID {
    type leafref {
     path "../attributes/PDCPPARAMGROUPID";
     require-instance true;
    }
   }
   container attributes {
    uses GNBPDCPPARAMGROUP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBPIMINTRFDETECTION {
   max-elements 1;
   key "PIMINTERFDETECTDURATION";
   leaf PIMINTERFDETECTDURATION {
    type leafref {
     path "../attributes/PIMINTERFDETECTDURATION";
     require-instance true;
    }
   }
   container attributes {
    uses GNBPIMINTRFDETECTION-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBPWRSAVINGALGO {
   max-elements 1;
   key "CELLLOADFILTERMODE";
   leaf CELLLOADFILTERMODE {
    type leafref {
     path "../attributes/CELLLOADFILTERMODE";
     require-instance true;
    }
   }
   container attributes {
    uses GNBPWRSAVINGALGO-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBQCIALGOPARAMGRP {
   max-elements 144;
   key "QCIALGOPARAMGROUPID";
   leaf QCIALGOPARAMGROUPID {
    type leafref {
     path "../attributes/QCIALGOPARAMGROUPID";
     require-instance true;
    }
   }
   container attributes {
    uses GNBQCIALGOPARAMGRP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBQCIBEARER {
   max-elements 30;
   key "POWERSAVINGPOLICYGRPINDEX";
   leaf POWERSAVINGPOLICYGRPINDEX {
    type leafref {
     path "../attributes/POWERSAVINGPOLICYGRPINDEX";
     require-instance true;
    }
   }
   container attributes {
    uses GNBQCIBEARER-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBREDCAPSERVIDENCFG {
   max-elements 2;
   key "SERVPARAMGROUPID";
   leaf SERVPARAMGROUPID {
    type leafref {
     path "../attributes/SERVPARAMGROUPID";
     require-instance true;
    }
   }
   container attributes {
    uses GNBREDCAPSERVIDENCFG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/GNBOPERATOR" {
  list GNBRFSPCONFIG {
   max-elements 257;
   key "OPERATORID";
   leaf OPERATORID {
    type leafref {
     path "../attributes/OPERATORID";
     require-instance true;
    }
   }
   container attributes {
    uses GNBRFSPCONFIG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBSHARINGMODE {
   max-elements 1;
   key "ACCESSPENALTYTIMER";
   leaf ACCESSPENALTYTIMER {
    type leafref {
     path "../attributes/ACCESSPENALTYTIMER";
     require-instance true;
    }
   }
   container attributes {
    uses GNBSHARINGMODE-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBSIBCONFIG {
   max-elements 121;
   key "SIBCONFIGID";
   leaf SIBCONFIGID {
    type leafref {
     path "../attributes/SIBCONFIGID";
     require-instance true;
    }
   }
   container attributes {
    uses GNBSIBCONFIG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBSRVINTERHOFREQGRP {
   max-elements 1440;
   key "GNBSRVINTERFHOFREQGROUPID";
   leaf GNBSRVINTERFHOFREQGROUPID {
    type leafref {
     path "../attributes/GNBSRVINTERFHOFREQGROUPID";
     require-instance true;
    }
   }
   container attributes {
    uses GNBSRVINTERHOFREQGRP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBTANS {
   max-elements 1024;
   key "OPERATORID";
   leaf OPERATORID {
    type leafref {
     path "../attributes/OPERATORID";
     require-instance true;
    }
   }
   container attributes {
    uses GNBTANS-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBTRACKINGAREA {
   max-elements 108;
   key "TRACKINGAREAID";
   leaf TRACKINGAREAID {
    type leafref {
     path "../attributes/TRACKINGAREAID";
     require-instance true;
    }
   }
   container attributes {
    uses GNBTRACKINGAREA-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBUACPARAMGROUP {
   max-elements 128;
   key "ACCESSCONTROLPARAMGRPID";
   leaf ACCESSCONTROLPARAMGRPID {
    type leafref {
     path "../attributes/ACCESSCONTROLPARAMGRPID";
     require-instance true;
    }
   }
   container attributes {
    uses GNBUACPARAMGROUP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBUEOPERATORDIFFGRP {
   max-elements 3000;
   key "OPERATORID";
   leaf OPERATORID {
    type leafref {
     path "../attributes/OPERATORID";
     require-instance true;
    }
   }
   container attributes {
    uses GNBUEOPERATORDIFFGRP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBWTCPPARAGROUP {
   max-elements 10;
   key "WTCPPARAGROUPID";
   leaf WTCPPARAGROUPID {
    type leafref {
     path "../attributes/WTCPPARAGROUPID";
     require-instance true;
    }
   }
   container attributes {
    uses GNBWTCPPARAGROUP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBX2SONCONFIG {
   max-elements 1;
   key "X2SONCONFIGSWITCH";
   leaf X2SONCONFIGSWITCH {
    type leafref {
     path "../attributes/X2SONCONFIGSWITCH";
     require-instance true;
    }
   }
   container attributes {
    uses GNBX2SONCONFIG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNBXNSONCONFIG {
   max-elements 1;
   key "XNSONCONFIGSWITCH";
   leaf XNSONCONFIGSWITCH {
    type leafref {
     path "../attributes/XNSONCONFIGSWITCH";
     require-instance true;
    }
   }
   container attributes {
    uses GNBXNSONCONFIG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNODEBALGO {
   max-elements 1;
   key "CHNCALIBPOLSW";
   leaf CHNCALIBPOLSW {
    type leafref {
     path "../attributes/CHNCALIBPOLSW";
     require-instance true;
    }
   }
   container attributes {
    uses GNODEBALGO-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNODEBAMFCONFIG {
   max-elements 32;
   key "AMFCONFIGINDEX";
   leaf AMFCONFIGINDEX {
    type leafref {
     path "../attributes/AMFCONFIGINDEX";
     require-instance true;
    }
   }
   container attributes {
    uses GNODEBAMFCONFIG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list GNODEBCARRMGMT {
   max-elements 1;
   key "CAENHANCEDALGOSWITCH";
   leaf CAENHANCEDALGOSWITCH {
    type leafref {
     path "../attributes/CAENHANCEDALGOSWITCH";
     require-instance true;
    }
   }
   container attributes {
    uses GNODEBCARRMGMT-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule" {
  list GNODEBFUNCTION {
   max-elements 1;
   key "GNBID";
   leaf GNBID {
    type leafref {
     path "../attributes/GNBID";
     require-instance true;
    }
   }
   container attributes {
    uses GNODEBFUNCTION-attributes;
    leaf modifier {
     type hwat:modifier_M;
     mandatory false;
    }
    leaf remark {
     type string;
     mandatory false;
    }
    leaf template {
     type string;
     mandatory false;
    }
   }
  }
 }
 augment "/ne:NE/gnodebfunctionmodule:gNodeBFunctionModule/GNODEBFUNCTION" {
  list GNODEBPARAM {
   max-elements 1;
   key "ABNDLDATASPLITPENALTYPRD";
   leaf ABNDLDATASPLITPENALTYPRD {
    type leafref {
     path "../attributes/ABNDLDATASPLITPENALTYPRD";
     require-instance true;
    }
   }
   container attributes {
    uses GNODEBPARAM-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list NRCELL {
   max-elements 144;
   key "NRCELLID";
   leaf NRCELLID {
    type leafref {
     path "../attributes/NRCELLID";
     require-instance true;
    }
   }
   container attributes {
    uses NRCELL-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLALGOSWITCH {
   max-elements 1;
   key "NRCELLID";
   leaf NRCELLID {
    type leafref {
     path "../attributes/NRCELLID";
     require-instance true;
    }
   }
   container attributes {
    uses NRCELLALGOSWITCH-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLCAMGMTCONFIG {
   max-elements 1;
   key "NRCELLID";
   leaf NRCELLID {
    type leafref {
     path "../attributes/NRCELLID";
     require-instance true;
    }
   }
   container attributes {
    uses NRCELLCAMGMTCONFIG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLCOMP {
   max-elements 1;
   key "NRCELLID";
   leaf NRCELLID {
    type leafref {
     path "../attributes/NRCELLID";
     require-instance true;
    }
   }
   container attributes {
    uses NRCELLCOMP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLEUTRANNFREQ {
   max-elements 64;
   key "NRCELLID";
   leaf NRCELLID {
    type leafref {
     path "../attributes/NRCELLID";
     require-instance true;
    }
   }
   container attributes {
    uses NRCELLEUTRANNFREQ-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLEUTRANRELATION {
   max-elements 384;
   key "NRCELLID";
   leaf NRCELLID {
    type leafref {
     path "../attributes/NRCELLID";
     require-instance true;
    }
   }
   container attributes {
    uses NRCELLEUTRANRELATION-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLFEATURESWITCH {
   max-elements 1;
   key "NRCELLID";
   leaf NRCELLID {
    type leafref {
     path "../attributes/NRCELLID";
     require-instance true;
    }
   }
   container attributes {
    uses NRCELLFEATURESWITCH-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLFREQRELATION {
   max-elements 16;
   key "NRCELLID";
   leaf NRCELLID {
    type leafref {
     path "../attributes/NRCELLID";
     require-instance true;
    }
   }
   container attributes {
    uses NRCELLFREQRELATION-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLHOEUTRANMEAGRP {
   max-elements 15;
   key "NRCELLID";
   leaf NRCELLID {
    type leafref {
     path "../attributes/NRCELLID";
     require-instance true;
    }
   }
   container attributes {
    uses NRCELLHOEUTRANMEAGRP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLINTERFHOMEAGRP {
   max-elements 15;
   key "NRCELLID";
   leaf NRCELLID {
    type leafref {
     path "../attributes/NRCELLID";
     require-instance true;
    }
   }
   container attributes {
    uses NRCELLINTERFHOMEAGRP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLINTERRHOMEAGRP {
   max-elements 15;
   key "NRCELLID";
   leaf NRCELLID {
    type leafref {
     path "../attributes/NRCELLID";
     require-instance true;
    }
   }
   container attributes {
    uses NRCELLINTERRHOMEAGRP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLINTRAFHOMEAGRP {
   max-elements 15;
   key "NRCELLID";
   leaf NRCELLID {
    type leafref {
     path "../attributes/NRCELLID";
     require-instance true;
    }
   }
   container attributes {
    uses NRCELLINTRAFHOMEAGRP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLMLB {
   max-elements 1;
   key "NRCELLID";
   leaf NRCELLID {
    type leafref {
     path "../attributes/NRCELLID";
     require-instance true;
    }
   }
   container attributes {
    uses NRCELLMLB-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLMOBILITYCONFIG {
   max-elements 1;
   key "NRCELLID";
   leaf NRCELLID {
    type leafref {
     path "../attributes/NRCELLID";
     require-instance true;
    }
   }
   container attributes {
    uses NRCELLMOBILITYCONFIG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLMULTIFSCHCOORD {
   max-elements 1;
   key "NRCELLID";
   leaf NRCELLID {
    type leafref {
     path "../attributes/NRCELLID";
     require-instance true;
    }
   }
   container attributes {
    uses NRCELLMULTIFSCHCOORD-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLNSADCCONFIG {
   max-elements 1;
   key "NRCELLID";
   leaf NRCELLID {
    type leafref {
     path "../attributes/NRCELLID";
     require-instance true;
    }
   }
   container attributes {
    uses NRCELLNSADCCONFIG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLNSADCCONFIGGRP {
   max-elements 15;
   key "NRCELLID";
   leaf NRCELLID {
    type leafref {
     path "../attributes/NRCELLID";
     require-instance true;
    }
   }
   container attributes {
    uses NRCELLNSADCCONFIGGRP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLNSGRP {
   max-elements 6;
   key "NRCELLID";
   leaf NRCELLID {
    type leafref {
     path "../attributes/NRCELLID";
     require-instance true;
    }
   }
   container attributes {
    uses NRCELLNSGRP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLNSGRPNS {
   max-elements 18;
   key "NRCELLID";
   leaf NRCELLID {
    type leafref {
     path "../attributes/NRCELLID";
     require-instance true;
    }
   }
   container attributes {
    uses NRCELLNSGRPNS-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLOAMPARAM {
   max-elements 1;
   key "NRCELLID";
   leaf NRCELLID {
    type leafref {
     path "../attributes/NRCELLID";
     require-instance true;
    }
   }
   container attributes {
    uses NRCELLOAMPARAM-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLOPPOLICY {
   max-elements 12;
   key "NRCELLID";
   leaf NRCELLID {
    type leafref {
     path "../attributes/NRCELLID";
     require-instance true;
    }
   }
   container attributes {
    uses NRCELLOPPOLICY-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLOPQCIBEARER {
   max-elements 60;
   key "NRCELLID";
   leaf NRCELLID {
    type leafref {
     path "../attributes/NRCELLID";
     require-instance true;
    }
   }
   container attributes {
    uses NRCELLOPQCIBEARER-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLOPRFSP {
   max-elements 36;
   key "NRCELLID";
   leaf NRCELLID {
    type leafref {
     path "../attributes/NRCELLID";
     require-instance true;
    }
   }
   container attributes {
    uses NRCELLOPRFSP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLPSPOLICYGRP {
   max-elements 10;
   key "NRCELLID";
   leaf NRCELLID {
    type leafref {
     path "../attributes/NRCELLID";
     require-instance true;
    }
   }
   container attributes {
    uses NRCELLPSPOLICYGRP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLQCIBEARER {
   max-elements 50;
   key "NRCELLID";
   leaf NRCELLID {
    type leafref {
     path "../attributes/NRCELLID";
     require-instance true;
    }
   }
   container attributes {
    uses NRCELLQCIBEARER-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLREDCAP {
   max-elements 1;
   key "NRCELLID";
   leaf NRCELLID {
    type leafref {
     path "../attributes/NRCELLID";
     require-instance true;
    }
   }
   container attributes {
    uses NRCELLREDCAP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLRELATION {
   max-elements 768;
   key "NRCELLID";
   leaf NRCELLID {
    type leafref {
     path "../attributes/NRCELLID";
     require-instance true;
    }
   }
   container attributes {
    uses NRCELLRELATION-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLRES {
   max-elements 6;
   key "NRCELLID";
   leaf NRCELLID {
    type leafref {
     path "../attributes/NRCELLID";
     require-instance true;
    }
   }
   container attributes {
    uses NRCELLRES-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLRESELCONFIG {
   max-elements 1;
   key "NRCELLID";
   leaf NRCELLID {
    type leafref {
     path "../attributes/NRCELLID";
     require-instance true;
    }
   }
   container attributes {
    uses NRCELLRESELCONFIG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLSERVEXP {
   max-elements 1;
   key "NRCELLID";
   leaf NRCELLID {
    type leafref {
     path "../attributes/NRCELLID";
     require-instance true;
    }
   }
   container attributes {
    uses NRCELLSERVEXP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLSMARTMULTICARR {
   max-elements 1;
   key "NRCELLID";
   leaf NRCELLID {
    type leafref {
     path "../attributes/NRCELLID";
     require-instance true;
    }
   }
   container attributes {
    uses NRCELLSMARTMULTICARR-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLSULFREQUENCY {
   max-elements 1;
   key "NRCELLID";
   leaf NRCELLID {
    type leafref {
     path "../attributes/NRCELLID";
     require-instance true;
    }
   }
   container attributes {
    uses NRCELLSULFREQUENCY-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRCELLUSERMEASCFG {
   max-elements 1000;
   key "NRCELLID";
   leaf NRCELLID {
    type leafref {
     path "../attributes/NRCELLID";
     require-instance true;
    }
   }
   container attributes {
    uses NRCELLUSERMEASCFG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list NRDUCELL {
   max-elements 144;
   key "NRDUCELLID";
   leaf NRDUCELLID {
    type leafref {
     path "../attributes/NRDUCELLID";
     require-instance true;
    }
   }
   container attributes {
    uses NRDUCELL-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELLTRP" {
  list NRDUCELL3DEIRPTHLD {
   max-elements 28;
   key "NRDUCELLTRPID";
   leaf NRDUCELLTRPID {
    type leafref {
     path "../attributes/NRDUCELLTRPID";
     require-instance true;
    }
   }
   container attributes {
    uses NRDUCELL3DEIRPTHLD-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLAIALGO {
   max-elements 1;
   key "NRDUCELLID";
   leaf NRDUCELLID {
    type leafref {
     path "../attributes/NRDUCELLID";
     require-instance true;
    }
   }
   container attributes {
    uses NRDUCELLAIALGO-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLALGOSWITCH {
   max-elements 1;
   key "NRDUCELLID";
   leaf NRDUCELLID {
    type leafref {
     path "../attributes/NRDUCELLID";
     require-instance true;
    }
   }
   container attributes {
    uses NRDUCELLALGOSWITCH-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLASSIST {
   max-elements 1;
   key "NRDUCELLID";
   leaf NRDUCELLID {
    type leafref {
     path "../attributes/NRDUCELLID";
     require-instance true;
    }
   }
   container attributes {
    uses NRDUCELLASSIST-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLBICARRIER {
   max-elements 1;
   key "NRDUCELLID";
   leaf NRDUCELLID {
    type leafref {
     path "../attributes/NRDUCELLID";
     require-instance true;
    }
   }
   container attributes {
    uses NRDUCELLBICARRIER-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLCARRMGMT {
   max-elements 1;
   key "NRDUCELLID";
   leaf NRDUCELLID {
    type leafref {
     path "../attributes/NRDUCELLID";
     require-instance true;
    }
   }
   container attributes {
    uses NRDUCELLCARRMGMT-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLCHNCOVALGO {
   max-elements 1;
   key "NRDUCELLID";
   leaf NRDUCELLID {
    type leafref {
     path "../attributes/NRDUCELLID";
     require-instance true;
    }
   }
   container attributes {
    uses NRDUCELLCHNCOVALGO-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLCHNPWR {
   max-elements 1;
   key "NRDUCELLID";
   leaf NRDUCELLID {
    type leafref {
     path "../attributes/NRDUCELLID";
     require-instance true;
    }
   }
   container attributes {
    uses NRDUCELLCHNPWR-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLCOLLABCOOP {
   max-elements 1;
   key "NRDUCELLID";
   leaf NRDUCELLID {
    type leafref {
     path "../attributes/NRDUCELLID";
     require-instance true;
    }
   }
   container attributes {
    uses NRDUCELLCOLLABCOOP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLCOLLABSERV {
   max-elements 1;
   key "NRDUCELLID";
   leaf NRDUCELLID {
    type leafref {
     path "../attributes/NRDUCELLID";
     require-instance true;
    }
   }
   container attributes {
    uses NRDUCELLCOLLABSERV-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLCOMMONSW {
   max-elements 1;
   key "NRDUCELLID";
   leaf NRDUCELLID {
    type leafref {
     path "../attributes/NRDUCELLID";
     require-instance true;
    }
   }
   container attributes {
    uses NRDUCELLCOMMONSW-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLCOMP {
   max-elements 1;
   key "NRDUCELLID";
   leaf NRDUCELLID {
    type leafref {
     path "../attributes/NRDUCELLID";
     require-instance true;
    }
   }
   container attributes {
    uses NRDUCELLCOMP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLCORESET {
   max-elements 1;
   key "NRDUCELLID";
   leaf NRDUCELLID {
    type leafref {
     path "../attributes/NRDUCELLID";
     require-instance true;
    }
   }
   container attributes {
    uses NRDUCELLCORESET-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELLTRP" {
  list NRDUCELLCOVERAGE {
   max-elements 48;
   key "NRDUCELLTRPID";
   leaf NRDUCELLTRPID {
    type leafref {
     path "../attributes/NRDUCELLTRPID";
     require-instance true;
    }
   }
   container attributes {
    uses NRDUCELLCOVERAGE-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLCSIRS {
   max-elements 1;
   key "NRDUCELLID";
   leaf NRDUCELLID {
    type leafref {
     path "../attributes/NRDUCELLID";
     require-instance true;
    }
   }
   container attributes {
    uses NRDUCELLCSIRS-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLDLAMC {
   max-elements 1;
   key "NRDUCELLID";
   leaf NRDUCELLID {
    type leafref {
     path "../attributes/NRDUCELLID";
     require-instance true;
    }
   }
   container attributes {
    uses NRDUCELLDLAMC-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLDLMIMO {
   max-elements 1;
   key "NRDUCELLID";
   leaf NRDUCELLID {
    type leafref {
     path "../attributes/NRDUCELLID";
     require-instance true;
    }
   }
   container attributes {
    uses NRDUCELLDLMIMO-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLDLRANK {
   max-elements 1;
   key "NRDUCELLID";
   leaf NRDUCELLID {
    type leafref {
     path "../attributes/NRDUCELLID";
     require-instance true;
    }
   }
   container attributes {
    uses NRDUCELLDLRANK-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLDLSCH {
   max-elements 1;
   key "NRDUCELLID";
   leaf NRDUCELLID {
    type leafref {
     path "../attributes/NRDUCELLID";
     require-instance true;
    }
   }
   container attributes {
    uses NRDUCELLDLSCH-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLDMRS {
   max-elements 1;
   key "NRDUCELLID";
   leaf NRDUCELLID {
    type leafref {
     path "../attributes/NRDUCELLID";
     require-instance true;
    }
   }
   container attributes {
    uses NRDUCELLDMRS-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLFEATURESW {
   max-elements 1;
   key "NRDUCELLID";
   leaf NRDUCELLID {
    type leafref {
     path "../attributes/NRDUCELLID";
     require-instance true;
    }
   }
   container attributes {
    uses NRDUCELLFEATURESW-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLFWAQOS {
   max-elements 1;
   key "NRDUCELLID";
   leaf NRDUCELLID {
    type leafref {
     path "../attributes/NRDUCELLID";
     require-instance true;
    }
   }
   container attributes {
    uses NRDUCELLFWAQOS-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLHIGHSPEEDMOB {
   max-elements 1;
   key "NRDUCELLID";
   leaf NRDUCELLID {
    type leafref {
     path "../attributes/NRDUCELLID";
     require-instance true;
    }
   }
   container attributes {
    uses NRDUCELLHIGHSPEEDMOB-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLINTRFAVOID {
   max-elements 2;
   key "NRDUCELLID";
   leaf NRDUCELLID {
    type leafref {
     path "../attributes/NRDUCELLID";
     require-instance true;
    }
   }
   container attributes {
    uses NRDUCELLINTRFAVOID-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLISOLATIONDET {
   max-elements 2;
   key "NRDUCELLID";
   leaf NRDUCELLID {
    type leafref {
     path "../attributes/NRDUCELLID";
     require-instance true;
    }
   }
   container attributes {
    uses NRDUCELLISOLATIONDET-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLMEAS {
   max-elements 1;
   key "NRDUCELLID";
   leaf NRDUCELLID {
    type leafref {
     path "../attributes/NRDUCELLID";
     require-instance true;
    }
   }
   container attributes {
    uses NRDUCELLMEAS-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLNONCONSPCT {
   max-elements 6;
   key "NRDUCELLID";
   leaf NRDUCELLID {
    type leafref {
     path "../attributes/NRDUCELLID";
     require-instance true;
    }
   }
   container attributes {
    uses NRDUCELLNONCONSPCT-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLNSADCCONFIG {
   max-elements 1;
   key "NRDUCELLID";
   leaf NRDUCELLID {
    type leafref {
     path "../attributes/NRDUCELLID";
     require-instance true;
    }
   }
   container attributes {
    uses NRDUCELLNSADCCONFIG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLNSGRP {
   max-elements 6;
   key "NRDUCELLID";
   leaf NRDUCELLID {
    type leafref {
     path "../attributes/NRDUCELLID";
     require-instance true;
    }
   }
   container attributes {
    uses NRDUCELLNSGRP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLNSGRPNS {
   max-elements 18;
   key "NRDUCELLID";
   leaf NRDUCELLID {
    type leafref {
     path "../attributes/NRDUCELLID";
     require-instance true;
    }
   }
   container attributes {
    uses NRDUCELLNSGRPNS-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLNSMGMTCONFIG {
   max-elements 1;
   key "NRDUCELLID";
   leaf NRDUCELLID {
    type leafref {
     path "../attributes/NRDUCELLID";
     require-instance true;
    }
   }
   container attributes {
    uses NRDUCELLNSMGMTCONFIG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLOP {
   max-elements 12;
   key "NRDUCELLID";
   leaf NRDUCELLID {
    type leafref {
     path "../attributes/NRDUCELLID";
     require-instance true;
    }
   }
   container attributes {
    uses NRDUCELLOP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLOPFWAQOS {
   max-elements 6;
   key "NRDUCELLID";
   leaf NRDUCELLID {
    type leafref {
     path "../attributes/NRDUCELLID";
     require-instance true;
    }
   }
   container attributes {
    uses NRDUCELLOPFWAQOS-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLOPQCI {
   max-elements 36;
   key "NRDUCELLID";
   leaf NRDUCELLID {
    type leafref {
     path "../attributes/NRDUCELLID";
     require-instance true;
    }
   }
   container attributes {
    uses NRDUCELLOPQCI-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLOPRFSP {
   max-elements 36;
   key "NRDUCELLID";
   leaf NRDUCELLID {
    type leafref {
     path "../attributes/NRDUCELLID";
     require-instance true;
    }
   }
   container attributes {
    uses NRDUCELLOPRFSP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLPAGINGCONFIG {
   max-elements 1;
   key "NRDUCELLID";
   leaf NRDUCELLID {
    type leafref {
     path "../attributes/NRDUCELLID";
     require-instance true;
    }
   }
   container attributes {
    uses NRDUCELLPAGINGCONFIG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLPDCCH {
   max-elements 1;
   key "NRDUCELLID";
   leaf NRDUCELLID {
    type leafref {
     path "../attributes/NRDUCELLID";
     require-instance true;
    }
   }
   container attributes {
    uses NRDUCELLPDCCH-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLPDCCHALGO {
   max-elements 1;
   key "NRDUCELLID";
   leaf NRDUCELLID {
    type leafref {
     path "../attributes/NRDUCELLID";
     require-instance true;
    }
   }
   container attributes {
    uses NRDUCELLPDCCHALGO-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLPDSCH {
   max-elements 1;
   key "NRDUCELLID";
   leaf NRDUCELLID {
    type leafref {
     path "../attributes/NRDUCELLID";
     require-instance true;
    }
   }
   container attributes {
    uses NRDUCELLPDSCH-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLPDSCHPRECODE {
   max-elements 1;
   key "NRDUCELLID";
   leaf NRDUCELLID {
    type leafref {
     path "../attributes/NRDUCELLID";
     require-instance true;
    }
   }
   container attributes {
    uses NRDUCELLPDSCHPRECODE-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLPIMINTRFAVD {
   max-elements 1;
   key "NRDUCELLID";
   leaf NRDUCELLID {
    type leafref {
     path "../attributes/NRDUCELLID";
     require-instance true;
    }
   }
   container attributes {
    uses NRDUCELLPIMINTRFAVD-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLPOSALGO {
   max-elements 1;
   key "NRDUCELLID";
   leaf NRDUCELLID {
    type leafref {
     path "../attributes/NRDUCELLID";
     require-instance true;
    }
   }
   container attributes {
    uses NRDUCELLPOSALGO-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLPOWERSAVING {
   max-elements 32;
   key "NRDUCELLID";
   leaf NRDUCELLID {
    type leafref {
     path "../attributes/NRDUCELLID";
     require-instance true;
    }
   }
   container attributes {
    uses NRDUCELLPOWERSAVING-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLPRACH {
   max-elements 1;
   key "NRDUCELLID";
   leaf NRDUCELLID {
    type leafref {
     path "../attributes/NRDUCELLID";
     require-instance true;
    }
   }
   container attributes {
    uses NRDUCELLPRACH-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLPSPOLICYGRP {
   max-elements 10;
   key "NRDUCELLID";
   leaf NRDUCELLID {
    type leafref {
     path "../attributes/NRDUCELLID";
     require-instance true;
    }
   }
   container attributes {
    uses NRDUCELLPSPOLICYGRP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLPUCCH {
   max-elements 1;
   key "NRDUCELLID";
   leaf NRDUCELLID {
    type leafref {
     path "../attributes/NRDUCELLID";
     require-instance true;
    }
   }
   container attributes {
    uses NRDUCELLPUCCH-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLPUSCH {
   max-elements 1;
   key "NRDUCELLID";
   leaf NRDUCELLID {
    type leafref {
     path "../attributes/NRDUCELLID";
     require-instance true;
    }
   }
   container attributes {
    uses NRDUCELLPUSCH-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLPWRSAVEALGO {
   max-elements 1;
   key "NRDUCELLID";
   leaf NRDUCELLID {
    type leafref {
     path "../attributes/NRDUCELLID";
     require-instance true;
    }
   }
   container attributes {
    uses NRDUCELLPWRSAVEALGO-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLRAC {
   max-elements 1;
   key "NRDUCELLID";
   leaf NRDUCELLID {
    type leafref {
     path "../attributes/NRDUCELLID";
     require-instance true;
    }
   }
   container attributes {
    uses NRDUCELLRAC-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLRBRESERVE {
   max-elements 10;
   key "NRDUCELLID";
   leaf NRDUCELLID {
    type leafref {
     path "../attributes/NRDUCELLID";
     require-instance true;
    }
   }
   container attributes {
    uses NRDUCELLRBRESERVE-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLREDCAP {
   max-elements 1;
   key "NRDUCELLID";
   leaf NRDUCELLID {
    type leafref {
     path "../attributes/NRDUCELLID";
     require-instance true;
    }
   }
   container attributes {
    uses NRDUCELLREDCAP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLREINFLRNALGO {
   max-elements 1;
   key "NRDUCELLID";
   leaf NRDUCELLID {
    type leafref {
     path "../attributes/NRDUCELLID";
     require-instance true;
    }
   }
   container attributes {
    uses NRDUCELLREINFLRNALGO-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLRES {
   max-elements 6;
   key "NRDUCELLID";
   leaf NRDUCELLID {
    type leafref {
     path "../attributes/NRDUCELLID";
     require-instance true;
    }
   }
   container attributes {
    uses NRDUCELLRES-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLRIMCONFIG {
   max-elements 1;
   key "NRDUCELLID";
   leaf NRDUCELLID {
    type leafref {
     path "../attributes/NRDUCELLID";
     require-instance true;
    }
   }
   container attributes {
    uses NRDUCELLRIMCONFIG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLSELCONFIG {
   max-elements 1;
   key "NRDUCELLID";
   leaf NRDUCELLID {
    type leafref {
     path "../attributes/NRDUCELLID";
     require-instance true;
    }
   }
   container attributes {
    uses NRDUCELLSELCONFIG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLSERVEXP {
   max-elements 1;
   key "NRDUCELLID";
   leaf NRDUCELLID {
    type leafref {
     path "../attributes/NRDUCELLID";
     require-instance true;
    }
   }
   container attributes {
    uses NRDUCELLSERVEXP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELLTRP" {
  list NRDUCELLSMARTPWRLOCK {
   max-elements 1;
   key "NRDUCELLTRPID";
   leaf NRDUCELLTRPID {
    type leafref {
     path "../attributes/NRDUCELLTRPID";
     require-instance true;
    }
   }
   container attributes {
    uses NRDUCELLSMARTPWRLOCK-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLSPCTCLOUD {
   max-elements 1;
   key "NRDUCELLID";
   leaf NRDUCELLID {
    type leafref {
     path "../attributes/NRDUCELLID";
     require-instance true;
    }
   }
   container attributes {
    uses NRDUCELLSPCTCLOUD-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLSRSMEAS {
   max-elements 1;
   key "NRDUCELLID";
   leaf NRDUCELLID {
    type leafref {
     path "../attributes/NRDUCELLID";
     require-instance true;
    }
   }
   container attributes {
    uses NRDUCELLSRSMEAS-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLSULRELATION {
   max-elements 1;
   key "NRDUCELLID";
   leaf NRDUCELLID {
    type leafref {
     path "../attributes/NRDUCELLID";
     require-instance true;
    }
   }
   container attributes {
    uses NRDUCELLSULRELATION-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list NRDUCELLTRP {
   max-elements 144;
   key "NRDUCELLTRPID";
   leaf NRDUCELLTRPID {
    type leafref {
     path "../attributes/NRDUCELLTRPID";
     require-instance true;
    }
   }
   container attributes {
    uses NRDUCELLTRP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELLTRP" {
  list NRDUCELLTRPBEAM {
   max-elements 1;
   key "NRDUCELLTRPID";
   leaf NRDUCELLTRPID {
    type leafref {
     path "../attributes/NRDUCELLTRPID";
     require-instance true;
    }
   }
   container attributes {
    uses NRDUCELLTRPBEAM-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELLTRP/NRDUCELLTRPBEAM" {
  list NRDUCELLTRPCUSTBEAM {
   max-elements 8;
   key "NRDUCELLTRPID";
   leaf NRDUCELLTRPID {
    type leafref {
     path "../attributes/NRDUCELLTRPID";
     require-instance true;
    }
   }
   container attributes {
    uses NRDUCELLTRPCUSTBEAM-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELLTRP" {
  list NRDUCELLTRPDLSCH {
   max-elements 1;
   key "NRDUCELLTRPID";
   leaf NRDUCELLTRPID {
    type leafref {
     path "../attributes/NRDUCELLTRPID";
     require-instance true;
    }
   }
   container attributes {
    uses NRDUCELLTRPDLSCH-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELLTRP" {
  list NRDUCELLTRPDYNPWRSHR {
   max-elements 1;
   key "NRDUCELLTRPID";
   leaf NRDUCELLTRPID {
    type leafref {
     path "../attributes/NRDUCELLTRPID";
     require-instance true;
    }
   }
   container attributes {
    uses NRDUCELLTRPDYNPWRSHR-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELLTRP" {
  list NRDUCELLTRPIFINFO {
   max-elements 1;
   key "NRDUCELLTRPID";
   leaf NRDUCELLTRPID {
    type leafref {
     path "../attributes/NRDUCELLTRPID";
     require-instance true;
    }
   }
   container attributes {
    uses NRDUCELLTRPIFINFO-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELLTRP" {
  list NRDUCELLTRPMMWAVBEAM {
   max-elements 1;
   key "NRDUCELLTRPID";
   leaf NRDUCELLTRPID {
    type leafref {
     path "../attributes/NRDUCELLTRPID";
     require-instance true;
    }
   }
   container attributes {
    uses NRDUCELLTRPMMWAVBEAM-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELLTRP" {
  list NRDUCELLTRPSHARING {
   max-elements 10;
   key "NRDUCELLTRPID";
   leaf NRDUCELLTRPID {
    type leafref {
     path "../attributes/NRDUCELLTRPID";
     require-instance true;
    }
   }
   container attributes {
    uses NRDUCELLTRPSHARING-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELLTRP" {
  list NRDUCELLTRPULSCH {
   max-elements 1;
   key "NRDUCELLTRPID";
   leaf NRDUCELLTRPID {
    type leafref {
     path "../attributes/NRDUCELLTRPID";
     require-instance true;
    }
   }
   container attributes {
    uses NRDUCELLTRPULSCH-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLUACBAR {
   max-elements 441;
   key "NRDUCELLID";
   leaf NRDUCELLID {
    type leafref {
     path "../attributes/NRDUCELLID";
     require-instance true;
    }
   }
   container attributes {
    uses NRDUCELLUACBAR-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLUEPWRSAVING {
   max-elements 1;
   key "NRDUCELLID";
   leaf NRDUCELLID {
    type leafref {
     path "../attributes/NRDUCELLID";
     require-instance true;
    }
   }
   container attributes {
    uses NRDUCELLUEPWRSAVING-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLUETIMERCONST {
   max-elements 1;
   key "NRDUCELLID";
   leaf NRDUCELLID {
    type leafref {
     path "../attributes/NRDUCELLID";
     require-instance true;
    }
   }
   container attributes {
    uses NRDUCELLUETIMERCONST-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLULMIMO {
   max-elements 1;
   key "NRDUCELLID";
   leaf NRDUCELLID {
    type leafref {
     path "../attributes/NRDUCELLID";
     require-instance true;
    }
   }
   container attributes {
    uses NRDUCELLULMIMO-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLULPCCONFIG {
   max-elements 1;
   key "NRDUCELLID";
   leaf NRDUCELLID {
    type leafref {
     path "../attributes/NRDUCELLID";
     require-instance true;
    }
   }
   container attributes {
    uses NRDUCELLULPCCONFIG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLULSCH {
   max-elements 1;
   key "NRDUCELLID";
   leaf NRDUCELLID {
    type leafref {
     path "../attributes/NRDUCELLID";
     require-instance true;
    }
   }
   container attributes {
    uses NRDUCELLULSCH-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLULTACONFIG {
   max-elements 1;
   key "NRDUCELLID";
   leaf NRDUCELLID {
    type leafref {
     path "../attributes/NRDUCELLID";
     require-instance true;
    }
   }
   container attributes {
    uses NRDUCELLULTACONFIG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLVIRTUALRADAR {
   max-elements 1;
   key "NRDUCELLID";
   leaf NRDUCELLID {
    type leafref {
     path "../attributes/NRDUCELLID";
     require-instance true;
    }
   }
   container attributes {
    uses NRDUCELLVIRTUALRADAR-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELL" {
  list NRDUCELLVOICEALGO {
   max-elements 1;
   key "NRDUCELLID";
   leaf NRDUCELLID {
    type leafref {
     path "../attributes/NRDUCELLID";
     require-instance true;
    }
   }
   container attributes {
    uses NRDUCELLVOICEALGO-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUCELLTRP" {
  list NRDUFDDCELLTRPBEAM {
   max-elements 1;
   key "NRDUCELLTRPID";
   leaf NRDUCELLTRPID {
    type leafref {
     path "../attributes/NRDUCELLTRPID";
     require-instance true;
    }
   }
   container attributes {
    uses NRDUFDDCELLTRPBEAM-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list NRDUSECTORSPLITGROUP {
   max-elements 48;
   key "NRDUSECTORSPLITGROUPID";
   leaf NRDUSECTORSPLITGROUPID {
    type leafref {
     path "../attributes/NRDUSECTORSPLITGROUPID";
     require-instance true;
    }
   }
   container attributes {
    uses NRDUSECTORSPLITGROUP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRDUSECTORSPLITGROUP" {
  list NRDUSECTORSPLITTRP {
   max-elements 3;
   key "NRDUSECTORSPLITGROUPID";
   leaf NRDUSECTORSPLITGROUPID {
    type leafref {
     path "../attributes/NRDUSECTORSPLITGROUPID";
     require-instance true;
    }
   }
   container attributes {
    uses NRDUSECTORSPLITTRP-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION" {
  list NREXTERNALNCELL {
   max-elements 4608;
   key "GNBID";
   leaf GNBID {
    type leafref {
     path "../attributes/GNBID";
     require-instance true;
    }
   }
   container attributes {
    uses NREXTERNALNCELL-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NREXTERNALNCELL" {
  list NREXTERNALNCELLCAG {
   max-elements 5;
   key "MCC MNC GNBID CELLID";
   leaf MCC {
    type leafref {
     path "../attributes/MCC";
     require-instance true;
    }
   }
   leaf MNC {
    type leafref {
     path "../attributes/MNC";
     require-instance true;
    }
   }
   leaf GNBID {
    type leafref {
     path "../attributes/GNBID";
     require-instance true;
    }
   }
   leaf CELLID {
    type leafref {
     path "../attributes/CELLID";
     require-instance true;
    }
   }
   container attributes {
    uses NREXTERNALNCELLCAG-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NREXTERNALNCELL" {
  list NREXTERNALNCELLPLMN {
   max-elements 11;
   key "CELLID GNBID MNC MCC";
   leaf CELLID {
    type leafref {
     path "../attributes/CELLID";
     require-instance true;
    }
   }
   leaf GNBID {
    type leafref {
     path "../attributes/GNBID";
     require-instance true;
    }
   }
   leaf MNC {
    type leafref {
     path "../attributes/MNC";
     require-instance true;
    }
   }
   leaf MCC {
    type leafref {
     path "../attributes/MCC";
     require-instance true;
    }
   }
   container attributes {
    uses NREXTERNALNCELLPLMN-attributes;
    leaf modifier {
     type hwat:modifier_AMD;
     mandatory false;
    }
    leaf remark {
     type string;
     mandatory false;
    }
    leaf template {
     type string;
     mandatory false;
    }
   }
  }
 }
 augment "/ne:NE/gnodebfunctionmodule:gNodeBFunctionModule/GNODEBFUNCTION/NRCELL" {
  list NRINTERRATHOPARAM {
   max-elements 1;
   key "NRCELLID";
   leaf NRCELLID {
    type leafref {
     path "../attributes/NRCELLID";
     require-instance true;
    }
   }
   container attributes {
    uses NRINTERRATHOPARAM-attributes;
    leaf modifier {
     type hwat:modifier_AMD;
     mandatory false;
    }
    leaf remark {
     type string;
     mandatory false;
    }
    leaf template {
     type string;
     mandatory false;
    }
   }
  }
 }
 augment "/if:interfaces/if:interface/ip:ipv4" {
  container gnbincrcfg-ipv4 {
   container attributes {
    uses GNBINCRCFG-attributes;
   }
  }
 }
 augment "/if:interfaces/if:interface/ip:ipv6" {
  container gnbincrcfg-ipv6 {
   container attributes {
    uses GNBINCRCFG-attributes;
   }
  }
 }
 augment "/if:interfaces/if:interface" {
  container attributes {
   uses GNODEBPARAM-attributes;
  }
 }
 grouping GNB5QICONFIG-attributes {
 leaf ASREFLECTIVEQOSSWITCH {
  type boolean;
  mandatory false;
 }
 leaf CHRRPTIND {
  type boolean;
  mandatory false;
 }
 leaf COUNTEROBJSUBSCRIPTIONIND {
  type boolean;
  mandatory false;
 }
 leaf OLD_NR5QI {
  type union {
   type int16 {
    range "-1..255";
   }
  }
  mandatory false;
 }
 leaf NR5QI {
  type union {
   type int16 {
    range "-1..255";
   }
  }
  mandatory false;
 }
 leaf NR5QIALGOSWITCH {
  type string;
  mandatory false;
 }
 leaf PWRSAVINGALGOSWITCH {
  type string;
  mandatory false;
 }
 leaf PWRSAVINGPROTECTMODE {
  type boolean;
  mandatory false;
 }
 leaf QCI {
  type uint8 {
   range "0..255";
  }
  mandatory false;
 }
 leaf SERVICETYPEIND {
  type string;
  mandatory false;
 }
 }
 grouping GNBAIRINTFSECPARAM-attributes {
 leaf AIRINTFANTIDDOSSW {
  type string;
  mandatory false;
 }
 leaf AIRINTFSIGPROTECTTHLD {
  type uint16 {
   range "10..65535";
  }
  mandatory false;
 }
 leaf COUNTERCHECKSWITCH {
  type enumeration {
   enum val-0;
   enum val-1;
   enum val-2;
  }
  mandatory false;
 }
 leaf EMCUERATIODETTHLD {
  type union {
   type uint8 {
    range "1..255";
   }
  }
  mandatory false;
 }
 leaf UENUMPREEMPTDDOSCHKSW {
  type boolean;
  mandatory false;
 }
 leaf UNAUTHEMERGENCYCALLSWITCH {
  type boolean;
  mandatory false;
 }
 leaf UPDEFAULTCIPHERSWITCH {
  type boolean;
  mandatory false;
 }
 leaf UPFORCEDCIPHERSWITCH {
  type boolean;
  mandatory false;
 }
 leaf XNHOSECPROTECTSWITCH {
  type boolean;
  mandatory false;
 }
 }
 grouping GNBAMFDOMAINNAME-attributes {
 leaf OLD_AMFDOMAINNAME {
  type string {
   length "1..127";
  }
  mandatory false;
 }
 leaf AMFDOMAINNAME {
  type string {
   length "1..127";
  }
  mandatory false;
 }
 leaf OLD_GNBCUNGID {
  type union {
   type int8 {
    range "-1..35";
   }
  }
  mandatory false;
 }
 leaf GNBCUNGID {
  type union {
   type int8 {
    range "-1..35";
   }
  }
  mandatory false;
 }
 }
 grouping GNBCAFREQUENCY-attributes {
 leaf CAA2RSRPTHLDOFFSET {
  type int8 {
   range "-31..66";
  }
  mandatory false;
 }
 leaf OLD_CAFREQGROUPID {
  type union {
   type int8 {
    range "-1..31";
   }
  }
  mandatory false;
 }
 leaf CAFREQGROUPID {
  type union {
   type int8 {
    range "-1..31";
   }
  }
  mandatory false;
 }
 leaf CASCCA5RSRPTHLD2OFFSET {
  type int8 {
   range "-35..62";
  }
  mandatory false;
 }
 leaf OLD_DLNARFCN {
  type union {
   type int32 {
    range "-1..2279165";
   }
  }
  mandatory false;
 }
 leaf DLNARFCN {
  type union {
   type int32 {
    range "-1..2279165";
   }
  }
  mandatory false;
 }
 leaf OPERATORIDLIST {
  type uint32 {
   range "0..4294967295";
  }
  mandatory false;
 }
 leaf SSBFREQPOS {
  type union {
   type uint32 {
    range "2..2279165";
   }
  }
  mandatory false;
 }
 }
 grouping GNBCAG-attributes {
 leaf CAGID {
  type uint32 {
   range "0..4294967295";
  }
  mandatory false;
 }
 leaf CAGNAME {
  type string {
   length "0..48";
  }
  mandatory false;
 }
 leaf OLD_CAGNWINDEX {
  type union {
   type int16 {
    range "-1..143";
   }
  }
  mandatory false;
 }
 leaf CAGNWINDEX {
  type union {
   type int16 {
    range "-1..143";
   }
  }
  mandatory false;
 }
 leaf MANUALSELECTIONALLOWED {
  type boolean;
  mandatory false;
 }
 leaf OPERATORID {
  type uint8 {
   range "0..11";
  }
  mandatory false;
 }
 }
 grouping GNBCAGGRP-attributes {
 leaf OLD_CAGGRPID {
  type union {
   type int16 {
    range "-1..143";
   }
  }
  mandatory false;
 }
 leaf CAGGRPID {
  type union {
   type int16 {
    range "-1..143";
   }
  }
  mandatory false;
 }
 leaf OLD_CAGNWINDEX {
  type union {
   type int16 {
    range "-1..143";
   }
  }
  mandatory false;
 }
 leaf CAGNWINDEX {
  type union {
   type int16 {
    range "-1..143";
   }
  }
  mandatory false;
 }
 }
 grouping GNBCELLBLACKLIST-attributes {
 leaf OLD_CELLBLACKLISTID {
  type union {
   type int32 {
    range "-1..65534";
   }
  }
  mandatory false;
 }
 leaf CELLBLACKLISTID {
  type union {
   type int32 {
    range "-1..65534";
   }
  }
  mandatory false;
 }
 leaf PHYSICALCELLIDRANGE {
  type enumeration {
   enum val-1;
   enum val-4;
   enum val-8;
   enum val-12;
   enum val-16;
   enum val-24;
   enum val-32;
   enum val-48;
   enum val-64;
   enum val-84;
   enum val-96;
   enum val-128;
   enum val-168;
   enum val-252;
   enum val-504;
   enum val-1008;
  }
  mandatory false;
 }
 leaf RATTYPE {
  type boolean;
  mandatory false;
 }
 leaf OLD_STARTPHYSICALCELLID {
  type union {
   type int16 {
    range "-1..1007";
   }
  }
  mandatory false;
 }
 leaf STARTPHYSICALCELLID {
  type union {
   type int16 {
    range "-1..1007";
   }
  }
  mandatory false;
 }
 }
 grouping GNBCIPHERCAPB-attributes {
 leaf CIPHERALGO {
  type enumeration {
   enum val-0;
   enum val-1;
   enum val-2;
   enum val-3;
   enum val-4;
  }
  mandatory false;
 }
 leaf CIPHERALGOPRIORITY {
  type enumeration {
   enum val--1;
   enum val-0;
   enum val-1;
   enum val-2;
   enum val-3;
  }
  mandatory false;
 }
 }
 grouping GNBCLOUDXPARAMGROUP-attributes {
 leaf CLOUDXQCI {
  type uint8 {
   range "0..255";
  }
  mandatory false;
 }
 leaf DELAYBASEDCARRSELPOLICY {
  type boolean;
  mandatory false;
 }
 leaf DLDELAYCARRSELHYS {
  type uint8 {
   range "20..80";
  }
  mandatory false;
 }
 leaf DLYCARRSELDLCCEFAILRATETHD {
  type uint8 {
   range "10..20";
  }
  mandatory false;
 }
 leaf DLYCARRSELDLFRMLOSRATETHD {
  type uint8 {
   range "0..10";
  }
  mandatory false;
 }
 leaf DLYCARRSELDLFRMLOSSRATEHYS {
  type uint8 {
   range "0..10";
  }
  mandatory false;
 }
 leaf DLYCARRSELDLPRBUSAGETHLD {
  type uint8 {
   range "10..45";
  }
  mandatory false;
 }
 leaf OLD_GNBCLOUDXPARAMGROUPID {
  type union {
   type int8 {
    range "-1..15";
   }
  }
  mandatory false;
 }
 leaf GNBCLOUDXPARAMGROUPID {
  type union {
   type int8 {
    range "-1..15";
   }
  }
  mandatory false;
 }
 }
 grouping GNBCLUSTER-attributes {
 leaf CALIBFILTERCOEFF {
  type uint8 {
   range "0..100";
  }
  mandatory false;
 }
 leaf CALIBROBUSTSW {
  type string;
  mandatory false;
 }
 leaf OLD_CLUSTERID {
  type union {
   type int32 {
    range "-1..49999";
   }
  }
  mandatory false;
 }
 leaf CLUSTERID {
  type union {
   type int32 {
    range "-1..49999";
   }
  }
  mandatory false;
 }
 leaf CLUSTERTYPE {
  type enumeration {
   enum val-0;
   enum val-1;
   enum val-2;
  }
  mandatory false;
 }
 leaf COMMCALIBFACTOR {
  type uint8 {
   range "1..10";
  }
  mandatory false;
 }
 leaf MANUALCALIBSW {
  type string;
  mandatory false;
 }
 }
 grouping GNBCONNSTATETIMER-attributes {
 leaf INACTIVETOIDLETIMERADJSTEP {
  type uint16 {
   range "1..300";
  }
  mandatory false;
 }
 leaf INITCONTEXTSETUPREQMSGTMR {
  type uint8 {
   range "1..24";
  }
  mandatory false;
 }
 leaf INITCONTEXTSETUPREQWAITTMR {
  type uint8 {
   range "1..200";
  }
  mandatory false;
 }
 leaf NGMESSAGEWAITINGTIMER {
  type uint8 {
   range "1..200";
  }
  mandatory false;
 }
 leaf RRCRELDELAYTMR {
  type uint8 {
   range "0..20";
  }
  mandatory false;
 }
 leaf RRCRELWAITTIMEROFFSET {
  type uint16 {
   range "0..10000";
  }
  mandatory false;
 }
 leaf SIGUENONASMSGTRANSTMR {
  type uint8 {
   range "2..50";
  }
  mandatory false;
 }
 leaf UEINACTIVETOIDLETIMER {
  type uint16 {
   range "300..3600";
  }
  mandatory false;
 }
 leaf UUMESSAGEWAITINGTIMER {
  type uint8 {
   range "1..200";
  }
  mandatory false;
 }
 leaf XNMESSAGEWAITINGTIMER {
  type uint8 {
   range "1..200";
  }
  mandatory false;
 }
 }
 grouping GNBCUNG-attributes {
 leaf CPEPGROUPID {
  type union {
   type uint32 {
    range "0..4294967295";
   }
  }
  mandatory false;
 }
 leaf CUNGTYPE {
  type enumeration {
   enum val-0;
   enum val-1;
   enum val-2;
   enum val-3;
  }
  mandatory false;
 }
 leaf N3MBTRANSMODE {
  type enumeration {
   enum val-0;
   enum val-1;
   enum val-2;
  }
  mandatory false;
 }
 leaf PROTOCOLCRSWITCH {
  type string;
  mandatory false;
 }
 leaf UPEPGROUPID {
  type union {
   type uint32 {
    range "0..4294967295";
   }
  }
  mandatory false;
 }
 leaf USERLABEL {
  type string {
   length "0..256";
  }
  mandatory false;
 }
 leaf OLD_GNBCUNGID {
  type union {
   type int8 {
    range "-1..35";
   }
  }
  mandatory false;
 }
 leaf GNBCUNGID {
  type union {
   type int8 {
    range "-1..35";
   }
  }
  mandatory false;
 }
 }
 grouping GNBCUNGINTERFACE-attributes {
 leaf AMFNAME {
  type string {
   length "0..150";
  }
  mandatory false;
 }
 leaf SERVEDGUAMIS {
  type string {
   length "0..300";
  }
  mandatory false;
 }
 leaf SERVINGNETWORKSLICEID {
  type string {
   length "0..300";
  }
  mandatory false;
 }
 leaf GNBCUNGCPBEARERID {
  type uint32 {
   range "70000..79999";
  }
  mandatory false;
 }
 leaf GNBCUNGINTERFACEATTRIBUTE {
  type boolean;
  mandatory false;
 }
 leaf OLD_GNBCUNGINTERFACEID {
  type union {
   type int32 {
    range "-1..65534";
   }
  }
  mandatory false;
 }
 leaf GNBCUNGINTERFACEID {
  type union {
   type int32 {
    range "-1..65534";
   }
  }
  mandatory false;
 }
 leaf GNBOPERATORID {
  type string {
   length "0..127";
  }
  mandatory false;
 }
 }
 grouping GNBCUNGNS-attributes {
 leaf ASSOCEPGROUPMODE {
  type enumeration {
   enum val-0;
   enum val-1;
   enum val-2;
  }
  mandatory false;
 }
 leaf OPERATORID {
  type union {
   type int8 {
    range "-1..11";
   }
  }
  mandatory false;
 }
 leaf SLICEDIFFERENTIATOR {
  type union {
   type int32 {
    range "-1..16777215";
   }
  }
  mandatory false;
 }
 leaf SLICESERVICETYPE {
  type union {
   type int16 {
    range "-1..255";
   }
  }
  mandatory false;
 }
 leaf GNBCUNGID {
  type union {
   type int8 {
    range "-1..35";
   }
  }
  mandatory false;
 }
 }
 grouping GNBCUNGOP-attributes {
 leaf OPERATORID {
  type union {
   type int8 {
    range "-1..11";
   }
  }
  mandatory false;
 }
 leaf GNBCUNGID {
  type union {
   type int8 {
    range "-1..35";
   }
  }
  mandatory false;
 }
 }
 grouping GNBCUNGTRACKINGAREA-attributes {
 leaf TRACKINGAREAID {
  type union {
   type int32 {
    range "-1..65535";
   }
  }
  mandatory false;
 }
 leaf GNBCUNGID {
  type union {
   type int8 {
    range "-1..35";
   }
  }
  mandatory false;
 }
 }
 grouping GNBCUS1-attributes {
 leaf UPEPGROUPID {
  type uint16 {
   range "0..65535";
  }
  mandatory false;
 }
 leaf USERLABEL {
  type string {
   length "0..256";
  }
  mandatory false;
 }
 leaf OLD_GNBCUS1ID {
  type union {
   type int16 {
    range "-1..255";
   }
  }
  mandatory false;
 }
 leaf GNBCUS1ID {
  type union {
   type int16 {
    range "-1..255";
   }
  }
  mandatory false;
 }
 }
 grouping GNBCUS1OP-attributes {
 leaf OPERATORID {
  type union {
   type int8 {
    range "-1..11";
   }
  }
  mandatory false;
 }
 leaf GNBCUS1ID {
  type union {
   type int16 {
    range "-1..255";
   }
  }
  mandatory false;
 }
 }
 grouping GNBCUX2-attributes {
 leaf CPEPGROUPID {
  type uint16 {
   range "0..65535";
  }
  mandatory false;
 }
 leaf UPEPGROUPID {
  type uint16 {
   range "0..65535";
  }
  mandatory false;
 }
 leaf OLD_GNBCUX2ID {
  type union {
   type int16 {
    range "-1..255";
   }
  }
  mandatory false;
 }
 leaf GNBCUX2ID {
  type union {
   type int16 {
    range "-1..255";
   }
  }
  mandatory false;
 }
 }
 grouping GNBCUX2OP-attributes {
 leaf OPERATORID {
  type union {
   type int8 {
    range "-1..11";
   }
  }
  mandatory false;
 }
 leaf GNBCUX2ID {
  type union {
   type int16 {
    range "-1..255";
   }
  }
  mandatory false;
 }
 }
 grouping GNBCUXN-attributes {
 leaf CPEPGROUPID {
  type uint16 {
   range "0..65535";
  }
  mandatory false;
 }
 leaf UPEPGROUPID {
  type uint16 {
   range "0..65535";
  }
  mandatory false;
 }
 leaf OLD_GNBCUXNID {
  type union {
   type int8 {
    range "-1..11";
   }
  }
  mandatory false;
 }
 leaf GNBCUXNID {
  type union {
   type int8 {
    range "-1..11";
   }
  }
  mandatory false;
 }
 }
 grouping GNBCUXNINTERFACE-attributes {
 leaf GNBCUXNCPBEARERID {
  type uint32 {
   range "70000..79999";
  }
  mandatory false;
 }
 leaf OLD_GNBCUXNINTERFACEID {
  type union {
   type int32 {
    range "-1..65535";
   }
  }
  mandatory false;
 }
 leaf GNBCUXNINTERFACEID {
  type union {
   type int32 {
    range "-1..65535";
   }
  }
  mandatory false;
 }
 }
 grouping GNBCUXNOP-attributes {
 leaf OPERATORID {
  type union {
   type int8 {
    range "-1..11";
   }
  }
  mandatory false;
 }
 leaf GNBCUXNID {
  type union {
   type int8 {
    range "-1..11";
   }
  }
  mandatory false;
 }
 }
 grouping GNBDEDNSADCBANDCOMB-attributes {
 leaf AGGREGATIONATTRIBUTE {
  type string;
  mandatory false;
 }
 leaf OLD_LTEBANDID {
  type union {
   type int16 {
    range "-1..256";
   }
  }
  mandatory false;
 }
 leaf LTEBANDID {
  type union {
   type int16 {
    range "-1..256";
   }
  }
  mandatory false;
 }
 leaf OLD_NRBANDID {
  type enumeration {
   enum val--1;
   enum val-1;
   enum val-3;
   enum val-5;
   enum val-7;
   enum val-8;
   enum val-12;
   enum val-13;
   enum val-20;
   enum val-28;
   enum val-38;
   enum val-40;
   enum val-41;
   enum val-66;
   enum val-71;
   enum val-77;
   enum val-78;
   enum val-79;
   enum val-80;
   enum val-82;
   enum val-83;
   enum val-84;
   enum val-86;
   enum val-257;
   enum val-258;
   enum val-260;
   enum val-261;
  }
  mandatory false;
 }
 leaf NRBANDID {
  type enumeration {
   enum val--1;
   enum val-1;
   enum val-3;
   enum val-5;
   enum val-7;
   enum val-8;
   enum val-12;
   enum val-13;
   enum val-20;
   enum val-28;
   enum val-38;
   enum val-40;
   enum val-41;
   enum val-66;
   enum val-71;
   enum val-77;
   enum val-78;
   enum val-79;
   enum val-80;
   enum val-82;
   enum val-83;
   enum val-84;
   enum val-86;
   enum val-257;
   enum val-258;
   enum val-260;
   enum val-261;
  }
  mandatory false;
 }
 }
 grouping GNBDIFFUSEREXPGROUP-attributes {
 leaf OLD_POLICYINDEX {
  type union {
   type int8 {
    range "-1..15";
   }
  }
  mandatory false;
 }
 leaf POLICYINDEX {
  type union {
   type int8 {
    range "-1..15";
   }
  }
  mandatory false;
 }
 leaf USERGRADEBYQCI {
  type union {
   type uint16 {
    range "0..65535";
   }
  }
  mandatory false;
 }
 leaf GNBCLOUDXPARAMGROUPID {
  type union {
   type uint8 {
    range "0..255";
   }
  }
  mandatory false;
 }
 leaf GNBDIFFLAYERPARAGROUPID {
  type uint8 {
   range "0..255";
  }
  mandatory false;
 }
 leaf OLD_GNBDIFFUSEREXPGROUPID {
  type union {
   type int8 {
    range "-1..15";
   }
  }
  mandatory false;
 }
 leaf GNBDIFFUSEREXPGROUPID {
  type union {
   type int8 {
    range "-1..15";
   }
  }
  mandatory false;
 }
 }
 grouping GNBDUEXN-attributes {
 leaf UPEPGROUPID {
  type uint16 {
   range "0..65535";
  }
  mandatory false;
 }
 leaf OLD_GNBDUEXNID {
  type union {
   type int16 {
    range "-1..255";
   }
  }
  mandatory false;
 }
 leaf GNBDUEXNID {
  type union {
   type int16 {
    range "-1..255";
   }
  }
  mandatory false;
 }
 }
 grouping GNBDUEXNOP-attributes {
 leaf OLD_OPERATORID {
  type union {
   type int8 {
    range "-1..11";
   }
  }
  mandatory false;
 }
 leaf OPERATORID {
  type union {
   type int8 {
    range "-1..11";
   }
  }
  mandatory false;
 }
 leaf UPEPGROUPID {
  type uint16 {
   range "0..65535";
  }
  mandatory false;
 }
 leaf OLD_GNBDUEXNID {
  type union {
   type int16 {
    range "-1..255";
   }
  }
  mandatory false;
 }
 leaf GNBDUEXNID {
  type union {
   type int16 {
    range "-1..255";
   }
  }
  mandatory false;
 }
 }
 grouping GNBDULTENRSPCTSHRCG-attributes {
 leaf FDDLTENRSPCTSHRSWITCH {
  type string;
  mandatory false;
 }
 leaf LTEBIGEVENTASSUREUENUMTHLD {
  type uint16 {
   range "0..1200";
  }
  mandatory false;
 }
 leaf LTENRSPCTSHRCOMMONSWITCH {
  type string;
  mandatory false;
 }
 leaf LTESPCTSHRCELLGRPID {
  type uint8 {
   range "0..23";
  }
  mandatory false;
 }
 leaf NRRESERVEDRBENDINDEX {
  type uint16 {
   range "0..272";
  }
  mandatory false;
 }
 leaf NRRESERVEDRBSTARTINDEX {
  type uint16 {
   range "0..272";
  }
  mandatory false;
 }
 leaf NRRRCCONNUENUMTHLD {
  type uint8 {
   range "0..100";
  }
  mandatory false;
 }
 leaf OLD_NRSPCTSHRCELLGRPID {
  type union {
   type int8 {
    range "-1..23";
   }
  }
  mandatory false;
 }
 leaf NRSPCTSHRCELLGRPID {
  type union {
   type int8 {
    range "-1..23";
   }
  }
  mandatory false;
 }
 leaf NRULRESERVEDRBENDINDEX {
  type union {
   type uint16 {
    range "0..65535";
   }
  }
  mandatory false;
 }
 leaf NRULRESERVEDRBSTARTINDEX {
  type union {
   type uint16 {
    range "0..65535";
   }
  }
  mandatory false;
 }
 leaf PRBUSAGETHLD {
  type uint8 {
   range "0..100";
  }
  mandatory false;
 }
 leaf PRBUSAGETHLDOFFSET {
  type uint8 {
   range "0..30";
  }
  mandatory false;
 }
 leaf RRCCONNUENUMTHLD {
  type uint16 {
   range "0..1200";
  }
  mandatory false;
 }
 leaf ULPRBUSAGETHLD {
  type uint8 {
   range "0..100";
  }
  mandatory false;
 }
 }
 grouping GNBDUPARAM-attributes {
 leaf LTENRPOWERSHRENABLETIME {
  type string;
  mandatory false;
 }
 }
 grouping GNBDUQCIALGOPARAMGRP-attributes {
 leaf OLD_QCIALGOPARAMGROUPID {
  type union {
   type int16 {
    range "-1..143";
   }
  }
  mandatory false;
 }
 leaf QCIALGOPARAMGROUPID {
  type union {
   type int16 {
    range "-1..143";
   }
  }
  mandatory false;
 }
 leaf QCIALGOSWITCH {
  type string;
  mandatory false;
 }
 leaf RETRANSCCEAGGLEVELOFS {
  type uint8 {
   range "0..2";
  }
  mandatory false;
 }
 }
 grouping GNBDURFSPCONFIG-attributes {
 leaf DLEXPBASEDSCHGUARUSERRATE {
  type uint32 {
   range "0..1000000";
  }
  mandatory false;
 }
 leaf DLSCHPRICOEFFICIENT {
  type uint16 {
   range "1..10000";
  }
  mandatory false;
 }
 leaf DUDRXPARAMGROUPID {
  type union {
   type uint8 {
    range "0..255";
   }
  }
  mandatory false;
 }
 leaf OLD_OPERATORID {
  type union {
   type int8 {
    range "-1..11";
   }
  }
  mandatory false;
 }
 leaf OPERATORID {
  type union {
   type int8 {
    range "-1..11";
   }
  }
  mandatory false;
 }
 leaf OLD_RFSPINDEX {
  type union {
   type int16 {
    range "-1..256";
   }
  }
  mandatory false;
 }
 leaf RFSPINDEX {
  type union {
   type int16 {
    range "-1..256";
   }
  }
  mandatory false;
 }
 leaf ULEXPBASEDSCHGUARUSERRATE {
  type uint32 {
   range "0..1000000";
  }
  mandatory false;
 }
 leaf ULSCHPRICOEFFICIENT {
  type uint16 {
   range "1..10000";
  }
  mandatory false;
 }
 }
 grouping GNBDUSCHPARAMGROUP-attributes {
 leaf CYCLETIME {
  type enumeration {
   enum val-0;
   enum val-1;
   enum val-2;
   enum val-3;
   enum val-4;
   enum val-5;
   enum val-6;
  }
  mandatory false;
 }
 leaf DLAMCADJUSTSTEP {
  type uint16 {
   range "0..400";
  }
  mandatory false;
 }
 leaf DLCQIADJVALUE {
  type uint8 {
   range "1..150";
  }
  mandatory false;
 }
 leaf DLFLOWCTRLRATELIMIT0 {
  type union {
   type uint32 {
    range "50..4294967295";
   }
  }
  mandatory false;
 }
 leaf DLFLOWCTRLRATELIMIT1 {
  type union {
   type uint32 {
    range "50..4294967295";
   }
  }
  mandatory false;
 }
 leaf DLINITIALMCSADJVALUE {
  type int8 {
   range "-27..27";
  }
  mandatory false;
 }
 leaf DLMAXHARQRETRANSNUM {
  type uint8 {
   range "0..6";
  }
  mandatory false;
 }
 leaf DLMAXMCS {
  type uint8 {
   range "0..28";
  }
  mandatory false;
 }
 leaf DLMCSADJVALUE {
  type uint8 {
   range "0..10";
  }
  mandatory false;
 }
 leaf DLMINMCS {
  type uint8 {
   range "0..28";
  }
  mandatory false;
 }
 leaf DLSPSPERIOD {
  type enumeration {
   enum val-0;
   enum val-1;
   enum val-2;
  }
  mandatory false;
 }
 leaf DLSPSTBSIZE {
  type uint16 {
   range "0..1000";
  }
  mandatory false;
 }
 leaf DLTARGETIBLER {
  type union {
   type uint32 {
    range "0..100000";
   }
  }
  mandatory false;
 }
 leaf NEARPOINTPUSCHSINRTHLDOFS {
  type uint8 {
   range "0..4";
  }
  mandatory false;
 }
 leaf PDCCHBLERTARGET {
  type uint8 {
   range "0..200";
  }
  mandatory false;
 }
 leaf PDCCHMINAGGLVL {
  type enumeration {
   enum val-0;
   enum val-1;
   enum val-2;
   enum val-3;
  }
  mandatory false;
 }
 leaf PDCCHSINROFFSET {
  type uint8 {
   range "0..150";
  }
  mandatory false;
 }
 leaf PUSCHOUTERLOOPPCTARGET {
  type uint16 {
   range "0..600";
  }
  mandatory false;
 }
 leaf PUSCHRSRPTHLD {
  type int16 {
   range "-202..24";
  }
  mandatory false;
 }
 leaf REDCAPSTABLEULEXPGUARRATE {
  type uint32 {
   range "0..200000";
  }
  mandatory false;
 }
 leaf SCHEDULEOPTSWITCH {
  type string;
  mandatory false;
 }
 leaf OLD_SCHEDULEPARAMGROUPID {
  type union {
   type int8 {
    range "-1..60";
   }
  }
  mandatory false;
 }
 leaf SCHEDULEPARAMGROUPID {
  type union {
   type int8 {
    range "-1..60";
   }
  }
  mandatory false;
 }
 leaf SLOTAGGREGATIONIND {
  type boolean;
  mandatory false;
 }
 leaf SPECSERVICEDLMAXRANK {
  type enumeration {
   enum val-0;
   enum val-1;
   enum val-2;
  }
  mandatory false;
 }
 leaf SRPERIOD {
  type enumeration {
   enum val-0;
   enum val-1;
   enum val-2;
   enum val-3;
   enum val-4;
  }
  mandatory false;
 }
 leaf SRSCHFIRSTTBSIZE {
  type uint16 {
   range "0..65535";
  }
  mandatory false;
 }
 leaf STABLEULEXPGUARRATE {
  type uint32 {
   range "0..1000000";
  }
  mandatory false;
 }
 leaf STABLEULEXPPOL {
  type enumeration {
   enum val-0;
   enum val-1;
   enum val-2;
  }
  mandatory false;
 }
 leaf SURVIVALTIME {
  type uint8 {
   range "1..20";
  }
  mandatory false;
 }
 leaf ULAMCADJUSTSTEP {
  type uint16 {
   range "0..400";
  }
  mandatory false;
 }
 leaf ULFLOWCTRLRATELIMIT0 {
  type union {
   type uint32 {
    range "50..4294967295";
   }
  }
  mandatory false;
 }
 leaf ULFLOWCTRLRATELIMIT1 {
  type union {
   type uint32 {
    range "50..4294967295";
   }
  }
  mandatory false;
 }
 leaf ULGFTBSIZEFACTOR {
  type uint16 {
   range "1..1000";
  }
  mandatory false;
 }
 leaf ULGFTRANSFORMPRECODER {
  type boolean;
  mandatory false;
 }
 leaf ULINITTRANSMCSDECREASE {
  type uint8 {
   range "1..5";
  }
  mandatory false;
 }
 leaf ULINITIALMCSADJVALUE {
  type int8 {
   range "-27..27";
  }
  mandatory false;
 }
 leaf ULLIVEWEBCASTFARUESINRTHLD {
  type int16 {
   range "-100..150";
  }
  mandatory false;
 }
 leaf ULMAXHARQRETRANSNUM {
  type uint8 {
   range "0..6";
  }
  mandatory false;
 }
 leaf ULMAXMCS {
  type uint8 {
   range "0..28";
  }
  mandatory false;
 }
 leaf ULMINMCS {
  type uint8 {
   range "0..28";
  }
  mandatory false;
 }
 leaf ULPREALLOCATIONDATAVOLUME {
  type uint16 {
   range "70..10000";
  }
  mandatory false;
 }
 leaf ULPREALLOCATIONINTERVAL {
  type uint16 {
   range "1..400";
  }
  mandatory false;
 }
 leaf ULSMARTPREALLOCATIONDUR {
  type uint16 {
   range "0..2000";
  }
  mandatory false;
 }
 leaf ULTARGETIBLER {
  type union {
   type uint32 {
    range "0..100000";
   }
  }
  mandatory false;
 }
 leaf URLLCMAXRANK {
  type enumeration {
   enum val-0;
   enum val-1;
   enum val-2;
  }
  mandatory false;
 }
 leaf URLLCPWRBOOSTMAXVALUE {
  type uint8 {
   range "0..15";
  }
  mandatory false;
 }
 }
 grouping GNBDUSPSGRP-attributes {
 leaf LTESPSGRPID {
  type uint16 {
   range "0..65535";
  }
  mandatory false;
 }
 leaf MULTIRATSPSPRI {
  type enumeration {
   enum val-0;
   enum val-1;
   enum val-2;
  }
  mandatory false;
 }
 leaf NRSPSAVGPRD {
  type uint32 {
   range "1..86400";
  }
  mandatory false;
 }
 leaf OLD_NRSPSGRPID {
  type union {
   type int32 {
    range "-1..65534";
   }
  }
  mandatory false;
 }
 leaf NRSPSGRPID {
  type union {
   type int32 {
    range "-1..65534";
   }
  }
  mandatory false;
 }
 leaf SPSALGOSWITCH {
  type string;
  mandatory false;
 }
 leaf SPSTYPE {
  type boolean;
  mandatory false;
 }
 }
 grouping GNBEUTRAEXTCELLPLMN-attributes {
 leaf OLD_CELLID {
  type union {
   type int16 {
    range "-1..255";
   }
  }
  mandatory false;
 }
 leaf CELLID {
  type union {
   type int16 {
    range "-1..255";
   }
  }
  mandatory false;
 }
 leaf OLD_ENODEBID {
  type union {
   type int32 {
    range "-1..1048575";
   }
  }
  mandatory false;
 }
 leaf ENODEBID {
  type union {
   type int32 {
    range "-1..1048575";
   }
  }
  mandatory false;
 }
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf OLD_SHAREDMCC {
  type string {
   length "3";
  }
  mandatory false;
 }
 leaf SHAREDMCC {
  type string {
   length "3";
  }
  mandatory false;
 }
 leaf OLD_SHAREDMNC {
  type string {
   length "2..3";
  }
  mandatory false;
 }
 leaf SHAREDMNC {
  type string {
   length "2..3";
  }
  mandatory false;
 }
 }
 grouping GNBEUTRAEXTERNALCELL-attributes {
 leaf AGGREGATIONATTRIBUTE {
  type string;
  mandatory false;
 }
 leaf OLD_CELLID {
  type union {
   type int16 {
    range "-1..255";
   }
  }
  mandatory false;
 }
 leaf CELLID {
  type union {
   type int16 {
    range "-1..255";
   }
  }
  mandatory false;
 }
 leaf CELLNAME {
  type string {
   length "0..99";
  }
  mandatory false;
 }
 leaf DLEARFCN {
  type union {
   type uint32 {
    range "0..229575";
   }
  }
  mandatory false;
 }
 leaf OLD_ENODEBID {
  type union {
   type int32 {
    range "-1..1048575";
   }
  }
  mandatory false;
 }
 leaf ENODEBID {
  type union {
   type int32 {
    range "-1..1048575";
   }
  }
  mandatory false;
 }
 leaf HIGHSPEEDFLAG {
  type boolean;
  mandatory false;
 }
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf PHYSICALCELLID {
  type uint16 {
   range "0..503";
  }
  mandatory false;
 }
 leaf TAC {
  type uint16 {
   range "0..65535";
  }
  mandatory false;
 }
 }
 grouping GNBEUTRANBLACKLIST-attributes {
 leaf OLD_ENODEBID {
  type union {
   type int32 {
    range "-1..1048575";
   }
  }
  mandatory false;
 }
 leaf ENODEBID {
  type union {
   type int32 {
    range "-1..1048575";
   }
  }
  mandatory false;
 }
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 }
 grouping GNBFREQPRIORITYGROUP-attributes {
 leaf CELLRESELPRI {
  type union {
   type uint8 {
    range "0..255";
   }
  }
  mandatory false;
 }
 leaf CELLRESELSUBPRI {
  type enumeration {
   enum val-0;
   enum val-2;
   enum val-4;
   enum val-6;
   enum val-8;
  }
  mandatory false;
 }
 leaf CONNDEDFREQPRIORITY {
  type uint8 {
   range "0..16";
  }
  mandatory false;
 }
 leaf CONNFREQPRIORITY {
  type union {
   type uint16 {
    range "0..65535";
   }
  }
  mandatory false;
 }
 leaf DLEARFCN {
  type union {
   type uint32 {
    range "0..229575";
   }
  }
  mandatory false;
 }
 leaf OLD_FREQINDEX {
  type union {
   type int8 {
    range "-1..15";
   }
  }
  mandatory false;
 }
 leaf FREQINDEX {
  type union {
   type int8 {
    range "-1..15";
   }
  }
  mandatory false;
 }
 leaf RATTYPE {
  type boolean;
  mandatory false;
 }
 leaf ROAMINGUEHPLMNFREQFLAG {
  type boolean;
  mandatory false;
 }
 leaf ROAMINGUEHPLMNINTERFHOFLAG {
  type boolean;
  mandatory false;
 }
 leaf SSBDESCMETHOD {
  type boolean;
  mandatory false;
 }
 leaf SSBFREQPOS {
  type uint32 {
   range "0..3279165";
  }
  mandatory false;
 }
 leaf TRAFFICPRIORITY {
  type uint8 {
   range "0..16";
  }
  mandatory false;
 }
 leaf VOLTEPRIORITY {
  type union {
   type uint16 {
    range "0..65535";
   }
  }
  mandatory false;
 }
 leaf OLD_GNBFREQPRIORITYGROUPID {
  type union {
   type int16 {
    range "-1..254";
   }
  }
  mandatory false;
 }
 leaf GNBFREQPRIORITYGROUPID {
  type union {
   type int16 {
    range "-1..254";
   }
  }
  mandatory false;
 }
 }
 grouping GNBINCRCFG-attributes {
 leaf DHCPSERVERIPV4 {
  type inet:ipv4-address;
  mandatory false;
 }
 leaf DHCPSERVERIPV6 {
  type inet:ipv6-address;
  mandatory false;
 }
 leaf INCRACCESSENHSW {
  type string;
  mandatory false;
 }
 leaf OLD_INCRCFGID {
  type union {
   type int32 {
    range "-1..65535";
   }
  }
  mandatory false;
 }
 leaf INCRCFGID {
  type union {
   type int32 {
    range "-1..65535";
   }
  }
  mandatory false;
 }
 leaf NR5QI {
  type union {
   type uint8 {
    range "3..255";
   }
  }
  mandatory false;
 }
 }
 grouping GNBINTEGRITYCAPB-attributes {
 leaf INTEGRITYALGO {
  type enumeration {
   enum val-1;
   enum val-2;
   enum val-3;
   enum val-4;
  }
  mandatory false;
 }
 leaf INTEGRITYALGOPRIORITY {
  type enumeration {
   enum val--1;
   enum val-0;
   enum val-1;
   enum val-2;
  }
  mandatory false;
 }
 }
 grouping GNBINTERFACEPARAM-attributes {
 leaf EXNUPAGINGTIMER {
  type enumeration {
   enum val-0;
   enum val-1;
   enum val-2;
   enum val-3;
   enum val-4;
   enum val-5;
   enum val-6;
  }
  mandatory false;
 }
 leaf INTERFACEOMSW {
  type string;
  mandatory false;
 }
 leaf INTERFACEPOLICYSWITCH {
  type string;
  mandatory false;
 }
 leaf INTERFACESELFCFGOPTSW {
  type string;
  mandatory false;
 }
 leaf MAXXNTRANSRATE {
  type union {
   type uint16 {
    range "1..65535";
   }
  }
  mandatory false;
 }
 leaf NGFAULTCELLDEACTVWAITTIME {
  type uint8 {
   range "0..3";
  }
  mandatory false;
 }
 leaf NGRANDOMREESTSW {
  type boolean;
  mandatory false;
 }
 leaf S1UFAULTCELLDEACTVWAITTIME {
  type uint8 {
   range "0..3";
  }
  mandatory false;
 }
 leaf X2CONFIGSW {
  type string;
  mandatory false;
 }
 leaf X2XNSYNCDIFFDETECTSWITCH {
  type boolean;
  mandatory false;
 }
 }
 grouping GNBLICENSECONFIG-attributes {
 leaf ANTBWLICENSEPOLICY {
  type boolean;
  mandatory false;
 }
 }
 grouping GNBMIMOCLUSTERCELL-attributes {
 leaf OLD_CELLID {
  type union {
   type int16 {
    range "-1..16383";
   }
  }
  mandatory false;
 }
 leaf CELLID {
  type union {
   type int16 {
    range "-1..16383";
   }
  }
  mandatory false;
 }
 leaf OLD_CLUSTERID {
  type union {
   type int32 {
    range "-1..49999";
   }
  }
  mandatory false;
 }
 leaf CLUSTERID {
  type union {
   type int32 {
    range "-1..49999";
   }
  }
  mandatory false;
 }
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf OLD_GNODEBID {
  type union {
   type int64 {
    range "-1..4294967295";
   }
  }
  mandatory false;
 }
 leaf GNODEBID {
  type union {
   type int64 {
    range "-1..4294967295";
   }
  }
  mandatory false;
 }
 }
 grouping GNBMOBILITYCOMMPARAM-attributes {
 leaf ADAPTCOVRSRPTHLD {
  type int16 {
   range "-156..-31";
  }
  mandatory false;
 }
 leaf CONTOINACCELLTHDINCELLLIST {
  type uint8 {
   range "0..32";
  }
  mandatory false;
 }
 leaf DAPSHOWAITUEPDCPSTSRPTTMR {
  type uint8 {
   range "20..200";
  }
  mandatory false;
 }
 leaf EUTRANHOUECAPBCONFIG {
  type string;
  mandatory false;
 }
 leaf HOPDUSESSCONFLHANDLINGSW {
  type string;
  mandatory false;
 }
 leaf INTERFREQHOUECAPBCONFIG {
  type string;
  mandatory false;
 }
 leaf INTERRATHOREQUECAPBSIZE {
  type uint16 {
   range "0..480";
  }
  mandatory false;
 }
 leaf INTRARATHOREQUECAPBSIZE {
  type uint16 {
   range "0..480";
  }
  mandatory false;
 }
 leaf MAXNONINTRAFREQMEASOBJNUM {
  type uint8 {
   range "7..21";
  }
  mandatory false;
 }
 leaf MAXNUMHOFWDPDCPPKTWITHSN {
  type uint16 {
   range "1..2000";
  }
  mandatory false;
 }
 leaf MEASALGOSWITCH {
  type string;
  mandatory false;
 }
 leaf MOBILITYALGOSWITCH {
  type string;
  mandatory false;
 }
 leaf NECHOPREPFAILPUNISHTIMER {
  type uint8 {
   range "0..50";
  }
  mandatory false;
 }
 leaf NONRESHOPREPFAILPUNISHTIMES {
  type uint8 {
   range "0..200";
  }
  mandatory false;
 }
 leaf NSAINTERFREQMEASWAITTIMER {
  type uint8 {
   range "0..15";
  }
  mandatory false;
 }
 leaf OPTHOPREPFAILPUNISHTIMER {
  type uint16 {
   range "0..600";
  }
  mandatory false;
 }
 leaf PROTOCOLCOMPATIBILITYSW {
  type string;
  mandatory false;
 }
 leaf RESNOTAVAILFORSLICETIMER {
  type uint16 {
   range "0..600";
  }
  mandatory false;
 }
 leaf SIGUERELINTRAFREQRSRPOFS {
  type uint8 {
   range "0..30";
  }
  mandatory false;
 }
 leaf SLICENOTSUPPORTEDTIMER {
  type uint8 {
   range "0..100";
  }
  mandatory false;
 }
 leaf SSBSINRINTERFHOPUNISHTIMER {
  type enumeration {
   enum val-0;
   enum val-1;
   enum val-2;
   enum val-3;
   enum val-4;
   enum val-5;
   enum val-6;
  }
  mandatory false;
 }
 leaf WAITNSADCUEPDCPSTSRPTTMR {
  type uint8 {
   range "20..200";
  }
  mandatory false;
 }
 leaf WAITSAUEPDCPSTSRPTTMR {
  type uint8 {
   range "20..200";
  }
  mandatory false;
 }
 }
 grouping GNBMOBILITYCTRLLIST-attributes {
 leaf MCC {
  type string {
   length "3";
  }
  mandatory false;
 }
 leaf MNC {
  type string {
   length "2..3";
  }
  mandatory false;
 }
 leaf OLD_MOBILITYCTRLLISTID {
  type union {
   type int8 {
    range "-1..15";
   }
  }
  mandatory false;
 }
 leaf MOBILITYCTRLLISTID {
  type union {
   type int8 {
    range "-1..15";
   }
  }
  mandatory false;
 }
 leaf GNODEBENDID {
  type uint32 {
   range "0..4294967295";
  }
  mandatory false;
 }
 leaf GNODEBSTARTID {
  type uint32 {
   range "0..4294967295";
  }
  mandatory false;
 }
 }
 grouping GNBNCELLPLMNLIST-attributes {
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf PLMNLISTTYPE {
  type enumeration {
   enum val-0;
   enum val-1;
   enum val-2;
  }
  mandatory false;
 }
 leaf OLD_RATTYPE {
  type enumeration {
   enum val--1;
   enum val-0;
   enum val-1;
  }
  mandatory false;
 }
 leaf RATTYPE {
  type enumeration {
   enum val--1;
   enum val-0;
   enum val-1;
  }
  mandatory false;
 }
 }
 grouping GNBNETWORKSLICE-attributes {
 leaf OLD_OPERATORID {
  type union {
   type int8 {
    range "-1..11";
   }
  }
  mandatory false;
 }
 leaf OPERATORID {
  type union {
   type int8 {
    range "-1..11";
   }
  }
  mandatory false;
 }
 leaf SLICEDESCRIPTION {
  type string {
   length "0..127";
  }
  mandatory false;
 }
 leaf OLD_SLICEDIFFERENTIATOR {
  type union {
   type int32 {
    range "-1..16777215";
   }
  }
  mandatory false;
 }
 leaf SLICEDIFFERENTIATOR {
  type union {
   type int32 {
    range "-1..16777215";
   }
  }
  mandatory false;
 }
 leaf OLD_SLICESERVICETYPE {
  type union {
   type int16 {
    range "-1..255";
   }
  }
  mandatory false;
 }
 leaf SLICESERVICETYPE {
  type union {
   type int16 {
    range "-1..255";
   }
  }
  mandatory false;
 }
 }
 grouping GNBNGHOFREQRELATION-attributes {
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf OLD_SOURCECELLSSBFREQPOS {
  type union {
   type int32 {
    range "-1..3279165";
   }
  }
  mandatory false;
 }
 leaf SOURCECELLSSBFREQPOS {
  type union {
   type int32 {
    range "-1..3279165";
   }
  }
  mandatory false;
 }
 leaf SSBDESCMETHOD {
  type boolean;
  mandatory false;
 }
 leaf OLD_TARGETCELLSSBFREQPOS {
  type union {
   type int32 {
    range "-1..3279165";
   }
  }
  mandatory false;
 }
 leaf TARGETCELLSSBFREQPOS {
  type union {
   type int32 {
    range "-1..3279165";
   }
  }
  mandatory false;
 }
 }
 grouping GNBNGSONCONFIG-attributes {
 leaf NGCSONSWITCH {
  type string;
  mandatory false;
 }
 }
 grouping GNBNRBLACKLIST-attributes {
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf OLD_GNODEBID {
  type union {
   type int64 {
    range "-1..4294967295";
   }
  }
  mandatory false;
 }
 leaf GNODEBID {
  type union {
   type int64 {
    range "-1..4294967295";
   }
  }
  mandatory false;
 }
 }
 grouping GNBNRLTECELLCOMB-attributes {
 leaf AGGREGATIONATTRIBUTE {
  type string;
  mandatory false;
 }
 leaf OLD_CELLID {
  type union {
   type int16 {
    range "-1..16383";
   }
  }
  mandatory false;
 }
 leaf CELLID {
  type union {
   type int16 {
    range "-1..16383";
   }
  }
  mandatory false;
 }
 leaf OLD_LTECELLID {
  type union {
   type int16 {
    range "-1..255";
   }
  }
  mandatory false;
 }
 leaf LTECELLID {
  type union {
   type int16 {
    range "-1..255";
   }
  }
  mandatory false;
 }
 leaf OLD_LTEMCC {
  type string {
   length "3";
  }
  mandatory false;
 }
 leaf LTEMCC {
  type string {
   length "3";
  }
  mandatory false;
 }
 leaf OLD_LTEMNC {
  type string {
   length "2..3";
  }
  mandatory false;
 }
 leaf LTEMNC {
  type string {
   length "2..3";
  }
  mandatory false;
 }
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf OLD_ENODEBID {
  type union {
   type int32 {
    range "-1..1048575";
   }
  }
  mandatory false;
 }
 leaf ENODEBID {
  type union {
   type int32 {
    range "-1..1048575";
   }
  }
  mandatory false;
 }
 leaf OLD_GNODEBID {
  type union {
   type int64 {
    range "-1..4294967295";
   }
  }
  mandatory false;
 }
 leaf GNODEBID {
  type union {
   type int64 {
    range "-1..4294967295";
   }
  }
  mandatory false;
 }
 }
 grouping GNBOAMPARAM-attributes {
 leaf ABNUEULDATAERRORJUDGETHLD {
  type uint8 {
   range "0..100";
  }
  mandatory false;
 }
 leaf ALARMSWITCH {
  type string;
  mandatory false;
 }
 leaf BEARERACTIVITYTHLD {
  type uint8 {
   range "0..80";
  }
  mandatory false;
 }
 leaf CFGINTERCEPTPOLICYSW {
  type string;
  mandatory false;
 }
 leaf CODRALGOSWITCH {
  type string;
  mandatory false;
 }
 leaf DEVABNCELLUNAVBLNOTIFYSW {
  type string;
  mandatory false;
 }
 leaf DLRSRPDSTRCOUNTERTHLD0 {
  type int16 {
   range "-156..-31";
  }
  mandatory false;
 }
 leaf DLRSRPDSTRCOUNTERTHLD1 {
  type int16 {
   range "-156..-31";
  }
  mandatory false;
 }
 leaf DLRSRPDSTRCOUNTERTHLD2 {
  type int16 {
   range "-156..-31";
  }
  mandatory false;
 }
 leaf DLRSRPDSTRCOUNTERTHLD3 {
  type int16 {
   range "-156..-31";
  }
  mandatory false;
 }
 leaf DLRSRPDSTRCOUNTERTHLD4 {
  type union {
   type int16 {
    range "-156..0";
   }
  }
  mandatory false;
 }
 leaf DLRSRPDSTRCOUNTERTHLD5 {
  type union {
   type int16 {
    range "-156..0";
   }
  }
  mandatory false;
 }
 leaf DLRSRPDSTRCOUNTERTHLD6 {
  type union {
   type int16 {
    range "-156..0";
   }
  }
  mandatory false;
 }
 leaf DLRSRPDSTRCOUNTERTHLD7 {
  type union {
   type int16 {
    range "-156..0";
   }
  }
  mandatory false;
 }
 leaf DLRSRPDSTRCOUNTERTHLD8 {
  type union {
   type int16 {
    range "-156..0";
   }
  }
  mandatory false;
 }
 leaf FAULTRPTMOD {
  type boolean;
  mandatory false;
 }
 leaf MTTCOUNTERSAMPLEPRD1 {
  type uint8 {
   range "1..200";
  }
  mandatory false;
 }
 leaf MTTCOUNTERSAMPLEPRD2 {
  type uint8 {
   range "1..10";
  }
  mandatory false;
 }
 leaf MTTCOUNTERSAMPLEPRD3 {
  type uint8 {
   range "1..10";
  }
  mandatory false;
 }
 leaf NOTFCALMULRXFAULTDURTHLD {
  type union {
   type uint16 {
    range "15..65535";
   }
  }
  mandatory false;
 }
 leaf REPRRCREESTPROTECTTIMER {
  type uint16 {
   range "0..3600";
  }
  mandatory false;
 }
 leaf RRCREESTPROTECTTHLD {
  type uint8 {
   range "0..30";
  }
  mandatory false;
 }
 leaf SCGADDMAXACCESSDUR {
  type enumeration {
   enum val-0;
   enum val-1;
   enum val-2;
   enum val-3;
   enum val-4;
   enum val-5;
   enum val-6;
   enum val-7;
  }
  mandatory false;
 }
 leaf SCGFAILULDATARXERRRATETHLD {
  type union {
   type uint8 {
    range "1..255";
   }
  }
  mandatory false;
 }
 leaf SLCALMDETECTDURATIONTHLD {
  type union {
   type uint8 {
    range "1..255";
   }
  }
  mandatory false;
 }
 leaf STATISTICSSTRATEGYSWITCH {
  type string;
  mandatory false;
 }
 leaf TRACESWITCH {
  type string;
  mandatory false;
 }
 leaf VIRTUALUETRACESAMPLINGRATE {
  type uint16 {
   range "1..1000";
  }
  mandatory false;
 }
 leaf VONRCONTINUOUSPKTLOSSTHLD {
  type uint16 {
   range "3..1024";
  }
  mandatory false;
 }
 leaf VONRINCOMEPKTLOSSPOORTHLD {
  type uint8 {
   range "0..100";
  }
  mandatory false;
 }
 leaf VONRPKTLOSSMUTETHLD {
  type uint8 {
   range "0..100";
  }
  mandatory false;
 }
 leaf VONRRADIOPKTLOSSPOORTHLD {
  type uint8 {
   range "0..100";
  }
  mandatory false;
 }
 }
 grouping GNBOP5QICONFIG-attributes {
 leaf NR5QI {
  type union {
   type uint8 {
    range "0..255";
   }
  }
  mandatory false;
 }
 leaf OLD_OP5QICONFIGINDEX {
  type union {
   type int16 {
    range "-1..511";
   }
  }
  mandatory false;
 }
 leaf OP5QICONFIGINDEX {
  type union {
   type int16 {
    range "-1..511";
   }
  }
  mandatory false;
 }
 leaf OPERATORID {
  type uint8 {
   range "0..11";
  }
  mandatory false;
 }
 leaf QCI {
  type union {
   type uint16 {
    range "201..65535";
   }
  }
  mandatory false;
 }
 leaf REDCAPQCI {
  type union {
   type uint16 {
    range "201..65535";
   }
  }
  mandatory false;
 }
 leaf SLICEDIFFERENTIATOR {
  type uint32 {
   range "0..16777215";
  }
  mandatory false;
 }
 leaf SLICESERVICETYPE {
  type uint8 {
   range "0..255";
  }
  mandatory false;
 }
 }
 grouping GNBOPERATOR-attributes {
 leaf CMASBROADCASTSWITCH {
  type boolean;
  mandatory false;
 }
 leaf HPLMNALGOSWITCH {
  type string;
  mandatory false;
 }
 leaf MCC {
  type string {
   length "3";
  }
  mandatory false;
 }
 leaf MNC {
  type string {
   length "2..3";
  }
  mandatory false;
 }
 leaf NRNETWORKINGOPTION {
  type enumeration {
   enum val-0;
   enum val-1;
   enum val-2;
  }
  mandatory false;
 }
 leaf OPERATORALGOSWITCH {
  type string;
  mandatory false;
 }
 leaf OPERATORID {
  type union {
   type int8 {
    range "-1..11";
   }
  }
  mandatory false;
 }
 leaf OPERATORINTERRATPOLICYSW {
  type string;
  mandatory false;
 }
 leaf OPERATORNAME {
  type string {
   length "1..32";
  }
  mandatory false;
 }
 leaf OPERATORTYPE {
  type boolean;
  mandatory false;
 }
 leaf PAGINGRESRATIO {
  type uint8 {
   range "0..100";
  }
  mandatory false;
 }
 leaf RELICPERCENTAGE {
  type union {
   type uint8 {
    range "0..255";
   }
  }
  mandatory false;
 }
 leaf ROAMINGPLMNFLAG {
  type boolean;
  mandatory false;
 }
 leaf RRCCONNUSERLICPERCENTAGE {
  type union {
   type uint8 {
    range "0..255";
   }
  }
  mandatory false;
 }
 leaf TRAFFICRATIO {
  type uint8 {
   range "0..100";
  }
  mandatory false;
 }
 leaf USERLABEL {
  type string {
   length "0..256";
  }
  mandatory false;
 }
 leaf GNBID {
  type uint32 {
   range "0..4294967295";
  }
  mandatory false;
 }
 leaf GNBIDLENGTH {
  type union {
   type uint8 {
    range "22..255";
   }
  }
  mandatory false;
 }
 }
 grouping GNBOPERATORQCIPARAM-attributes {
 leaf EPSFBB1RSRPTHLDOFFSET {
  type int8 {
   range "-20..20";
  }
  mandatory false;
 }
 leaf EUTRANA1RSRPTHLDOFFSET {
  type int8 {
   range "-20..20";
  }
  mandatory false;
 }
 leaf EUTRANA2B2RSRPTHLDOFFSET {
  type int8 {
   range "-20..20";
  }
  mandatory false;
 }
 leaf EUTRANB1B2RSRPTHLDOFFSET {
  type int8 {
   range "-20..20";
  }
  mandatory false;
 }
 leaf INTERFREQA1RSRPTHLDOFS {
  type int8 {
   range "-20..20";
  }
  mandatory false;
 }
 leaf INTERFREQA2RSRPTHLDOFS {
  type int8 {
   range "-20..20";
  }
  mandatory false;
 }
 leaf INTERFREQA5RSRPTHLD2OFS {
  type int8 {
   range "-20..20";
  }
  mandatory false;
 }
 leaf OLD_OPERATORID {
  type union {
   type int8 {
    range "-1..11";
   }
  }
  mandatory false;
 }
 leaf OPERATORID {
  type union {
   type int8 {
    range "-1..11";
   }
  }
  mandatory false;
 }
 leaf PLATINUMUSERFLAG {
  type boolean;
  mandatory false;
 }
 leaf OLD_QCI {
  type union {
   type int16 {
    range "-1..255";
   }
  }
  mandatory false;
 }
 leaf QCI {
  type union {
   type int16 {
    range "-1..255";
   }
  }
  mandatory false;
 }
 leaf RACSWITCH {
  type string;
  mandatory false;
 }
 leaf UDTNO {
  type union {
   type uint16 {
    range "0..65535";
   }
  }
  mandatory false;
 }
 leaf GNBSRVINTERFHOFREQGROUPID {
  type union {
   type uint8 {
    range "0..255";
   }
  }
  mandatory false;
 }
 }
 grouping GNBPDCPPARAMGROUP-attributes {
 leaf DLDATAPDCPSPLITMODE {
  type enumeration {
   enum val-0;
   enum val-1;
   enum val-2;
   enum val-3;
   enum val-4;
  }
  mandatory false;
 }
 leaf DLDISTIMERFORLOWIMPORTANCE {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf DLPDCPDISCARDTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
  }
  mandatory false;
 }
 leaf DLPDCPSNSIZE {
  type boolean;
  mandatory false;
 }
 leaf GNBPDCPOUTOFORDERDELIVERYIND {
  type enumeration {
   enum val-0;
   enum val-1;
   enum val-2;
  }
  mandatory false;
 }
 leaf NRDCDLSPLITMODE {
  type enumeration {
   enum val-0;
   enum val-1;
   enum val-2;
   enum val-3;
   enum val-4;
  }
  mandatory false;
 }
 leaf NRDCULSPLITPRIMARYPATH {
  type boolean;
  mandatory false;
 }
 leaf NRDCULSPLITTHRESHOLD {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
  }
  mandatory false;
 }
 leaf PDCPDUPLICATIONIND {
  type enumeration {
   enum val-0;
   enum val-1;
   enum val-2;
  }
  mandatory false;
 }
 leaf OLD_PDCPPARAMGROUPID {
  type union {
   type int16 {
    range "-1..165";
   }
  }
  mandatory false;
 }
 leaf PDCPPARAMGROUPID {
  type union {
   type int16 {
    range "-1..165";
   }
  }
  mandatory false;
 }
 leaf PDCPREPORTPOLLINGPERIOD {
  type enumeration {
   enum val-0;
   enum val-1;
   enum val-2;
   enum val-3;
   enum val-4;
   enum val-5;
  }
  mandatory false;
 }
 leaf UEPDCPOUTOFORDERDELIVERYIND {
  type boolean;
  mandatory false;
 }
 leaf UEPDCPREORDERINGTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
  }
  mandatory false;
 }
 leaf ULDATASPLITPRIMARYPATH {
  type boolean;
  mandatory false;
 }
 leaf ULDATASPLITTHRESHOLD {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
  }
  mandatory false;
 }
 leaf ULPDCPDISCARDTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf ULPDCPSNSIZE {
  type boolean;
  mandatory false;
 }
 leaf GNBPDCPREORDERINGTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
  }
  mandatory false;
 }
 }
 grouping GNBPIMINTRFDETECTION-attributes {
 leaf PIMINTERFDETECTDURATION {
  type uint16 {
   range "5..480";
  }
  mandatory false;
 }
 leaf PIMINTERFDETECTINTERVAL {
  type uint8 {
   range "1..90";
  }
  mandatory false;
 }
 leaf PIMINTERFDETECTSTARTTIME {
  type hwat:HH_MM_SS_Time;
  mandatory false;
 }
 leaf PIMINTRFCANCTRAININGINTVL {
  type enumeration {
   enum val-5;
   enum val-10;
   enum val-20;
   enum val-30;
   enum val-60;
   enum val-360;
   enum val-720;
   enum val-1440;
  }
  mandatory false;
 }
 }
 grouping GNBPWRSAVINGALGO-attributes {
 leaf CELLLOADFILTERMODE {
  type boolean;
  mandatory false;
 }
 leaf DORMANCYSWITCH {
  type string;
  mandatory false;
 }
 leaf PWRSAVINGALGOSWITCH {
  type string;
  mandatory false;
 }
 leaf SPEEDTURBOPWRSAVENDTIME {
  type hwat:HH_MM_SS_Time;
  mandatory false;
 }
 leaf SPEEDTURBOPWRSAVSTARTTIME {
  type hwat:HH_MM_SS_Time;
  mandatory false;
 }
 leaf STATICSTPWRSAVENDTIME {
  type hwat:HH_MM_SS_Time;
  mandatory false;
 }
 leaf STATICSTPWRSAVSTARTTIME {
  type hwat:HH_MM_SS_Time;
  mandatory false;
 }
 }
 grouping GNBQCIALGOPARAMGRP-attributes {
 leaf OLD_QCIALGOPARAMGROUPID {
  type union {
   type int16 {
    range "-1..143";
   }
  }
  mandatory false;
 }
 leaf QCIALGOPARAMGROUPID {
  type union {
   type int16 {
    range "-1..143";
   }
  }
  mandatory false;
 }
 leaf QCIALGOSWITCH {
  type string;
  mandatory false;
 }
 leaf SERVPLREVALPERIOD {
  type uint8 {
   range "1..10";
  }
  mandatory false;
 }
 leaf SERVQLTYEUTRANHOPLRTHLD {
  type uint8 {
   range "1..100";
  }
  mandatory false;
 }
 leaf SERVQLTYRECOVERYPLRTHLD {
  type uint8 {
   range "0..100";
  }
  mandatory false;
 }
 leaf SERVQLTYLNTERFREQHOPLRTHLD {
  type uint8 {
   range "1..100";
  }
  mandatory false;
 }
 }
 grouping GNBQCIBEARER-attributes {
 leaf ANBRINTERVAL {
  type uint8 {
   range "1..100";
  }
  mandatory false;
 }
 leaf ANBRMODE {
  type enumeration {
   enum val-0;
   enum val-1;
   enum val-2;
  }
  mandatory false;
 }
 leaf AVERAGINGWINDOWDUR {
  type uint16 {
   range "0..4095";
  }
  mandatory false;
 }
 leaf CHRRPTIND {
  type boolean;
  mandatory false;
 }
 leaf CLOUDSERVSPLITCOEF {
  type uint8 {
   range "0..10";
  }
  mandatory false;
 }
 leaf CLOUDSERVSPLITDURPROP {
  type uint8 {
   range "0..10";
  }
  mandatory false;
 }
 leaf CLOUDXFRMLOSSDELAYTHLD {
  type uint8 {
   range "10..200";
  }
  mandatory false;
 }
 leaf CORENETDELAYBUDGET {
  type uint16 {
   range "1..5000";
  }
  mandatory false;
 }
 leaf COUNTEROBJSUBSCRIPTIONIND {
  type boolean;
  mandatory false;
 }
 leaf DLLAYEREDQOSSWITCH {
  type string;
  mandatory false;
 }
 leaf ENDMARKERTIMER {
  type uint16 {
   range "0..1000";
  }
  mandatory false;
 }
 leaf FIRSTFORWARDEDPACKETTIMER {
  type uint16 {
   range "0..1000";
  }
  mandatory false;
 }
 leaf FRAMELARGEPACKETLENGTHTHLD {
  type uint16 {
   range "800..1500";
  }
  mandatory false;
 }
 leaf IDENTIFICATIONMODE {
  type boolean;
  mandatory false;
 }
 leaf INTERFRAMEPKTINTERVALTHLD {
  type uint8 {
   range "5..8";
  }
  mandatory false;
 }
 leaf INTRAFRAMEPKTINTERVALTHLD {
  type uint8 {
   range "2..5";
  }
  mandatory false;
 }
 leaf L4SCONGESTCHECKPERIOD {
  type uint16 {
   range "1..2000";
  }
  mandatory false;
 }
 leaf L4SCONGESTDETECTALGORITHM {
  type boolean;
  mandatory false;
 }
 leaf L4SCONGESTMARKPERIOD {
  type uint16 {
   range "1..2000";
  }
  mandatory false;
 }
 leaf L4SDLCONGESTCHECKCOEFF {
  type uint8 {
   range "1..20";
  }
  mandatory false;
 }
 leaf L4SDLDELAYLOWERTHLD {
  type uint16 {
   range "1..1000";
  }
  mandatory false;
 }
 leaf L4SDLDELAYUPPERTHLD {
  type uint16 {
   range "1..1000";
  }
  mandatory false;
 }
 leaf L4SFLAG {
  type boolean;
  mandatory false;
 }
 leaf L4SPLUSDLHEADROOMMINPCT {
  type uint8 {
   range "1..100";
  }
  mandatory false;
 }
 leaf L4SPLUSDLMINRATE {
  type uint32 {
   range "0..1000000";
  }
  mandatory false;
 }
 leaf L4SPLUSDLRELATIVEPRIWEIGHT {
  type uint8 {
   range "1..20";
  }
  mandatory false;
 }
 leaf L4SPLUSDLTARGETRATEOFFSET {
  type uint8 {
   range "0..100";
  }
  mandatory false;
 }
 leaf L4SPLUSMAXDURATION {
  type uint16 {
   range "1..10000";
  }
  mandatory false;
 }
 leaf L4SPLUSMININTERVALTIME {
  type uint16 {
   range "1..10000";
  }
  mandatory false;
 }
 leaf L4SPLUSULHEADROOMMINPCT {
  type uint8 {
   range "1..100";
  }
  mandatory false;
 }
 leaf L4SPLUSULMINRATE {
  type uint32 {
   range "0..1000000";
  }
  mandatory false;
 }
 leaf L4SPLUSULRELATIVEPRIWEIGHT {
  type uint8 {
   range "1..20";
  }
  mandatory false;
 }
 leaf L4SPLUSULTARGETRATEOFFSET {
  type uint8 {
   range "0..100";
  }
  mandatory false;
 }
 leaf L4SULCONGESTCHECKCOEFF {
  type uint8 {
   range "1..20";
  }
  mandatory false;
 }
 leaf L4SULDELAYLOWERTHLD {
  type uint16 {
   range "1..1000";
  }
  mandatory false;
 }
 leaf L4SULDELAYUPPERTHLD {
  type uint16 {
   range "1..1000";
  }
  mandatory false;
 }
 leaf MAXSCHTIMEBUDGET {
  type uint16 {
   range "1..1000";
  }
  mandatory false;
 }
 leaf MOBILITYFUNIND {
  type string;
  mandatory false;
 }
 leaf NETWORKINGOPTIONOPTFLAG {
  type enumeration {
   enum val-0;
   enum val-1;
   enum val-2;
  }
  mandatory false;
 }
 leaf NOTIFCTRLRESFACTOR {
  type uint8 {
   range "1..100";
  }
  mandatory false;
 }
 leaf NSAENDMARKERTIMER {
  type uint16 {
   range "0..1000";
  }
  mandatory false;
 }
 leaf NSAFIRSTFORWARDEDPACKETTMR {
  type uint16 {
   range "0..1000";
  }
  mandatory false;
 }
 leaf PACKETDELAYBUDGET {
  type uint16 {
   range "0..1023";
  }
  mandatory false;
 }
 leaf PDBDIFFSCHPOLICY {
  type enumeration {
   enum val-0;
   enum val-1;
   enum val-2;
   enum val-3;
   enum val-4;
   enum val-5;
  }
  mandatory false;
 }
 leaf PDCPALGOSWITCH {
  type string;
  mandatory false;
 }
 leaf PDCPREORDERTMRADAPTFACTOR {
  type uint8 {
   range "0..10";
  }
  mandatory false;
 }
 leaf POWERSAVINGPOLICYGRPINDEX {
  type union {
   type uint8 {
    range "0..255";
   }
  }
  mandatory false;
 }
 leaf PRIORITYLEVEL {
  type uint8 {
   range "1..127";
  }
  mandatory false;
 }
 leaf PWRSAVINGALGOSWITCH {
  type string;
  mandatory false;
 }
 leaf PWRSAVINGPROTECTMODE {
  type boolean;
  mandatory false;
 }
 leaf OLD_QCI {
  type union {
   type int16 {
    range "-1..255";
   }
  }
  mandatory false;
 }
 leaf QCI {
  type union {
   type int16 {
    range "-1..255";
   }
  }
  mandatory false;
 }
 leaf QCIPRIORITYFORHO {
  type union {
   type uint8 {
    range "1..255";
   }
  }
  mandatory false;
 }
 leaf QCIPRIORITYFORREDCAPHO {
  type union {
   type uint8 {
    range "1..255";
   }
  }
  mandatory false;
 }
 leaf RLCDLDELAYSTATTHLD {
  type union {
   type uint8 {
    range "0..20";
   }
  }
  mandatory false;
 }
 leaf RLCULDELAYSTATTHLD {
  type union {
   type uint8 {
    range "0..20";
   }
  }
  mandatory false;
 }
 leaf SCHADAPTTOTFCMODELPOL {
  type enumeration {
   enum val-0;
   enum val-1;
   enum val-2;
  }
  mandatory false;
 }
 leaf SERVICEDIFFALGOSWITCH {
  type string;
  mandatory false;
 }
 leaf SERVICETYPE {
  type enumeration {
   enum val-0;
   enum val-1;
   enum val-2;
   enum val-3;
   enum val-10;
   enum val-11;
   enum val-12;
   enum val-13;
   enum val-14;
   enum val-15;
   enum val-16;
   enum val-17;
   enum val-18;
  }
  mandatory false;
 }
 leaf SRVINTERFHOPRIJUDGEFLAG {
  type boolean;
  mandatory false;
 }
 leaf ULLIVEWEBCASTMEASTRFTHLD {
  type uint8 {
   range "1..40";
  }
  mandatory false;
 }
 leaf ULPACKETDELAYSTATTHLD {
  type uint8 {
   range "1..100";
  }
  mandatory false;
 }
 leaf ULPDCPSNBITS12ABNDETTHLD {
  type uint16 {
   range "512..2048";
  }
  mandatory false;
 }
 leaf ULPDCPSNBITS18ABNDETTHLD {
  type uint32 {
   range "2048..131072";
  }
  mandatory false;
 }
 }
 grouping GNBREDCAPSERVIDENCFG-attributes {
 leaf OLD_SERVPARAMGROUPID {
  type union {
   type int8 {
    range "-1..1";
   }
  }
  mandatory false;
 }
 leaf SERVPARAMGROUPID {
  type union {
   type int8 {
    range "-1..1";
   }
  }
  mandatory false;
 }
 leaf ULBIGPKTDATAVOLTHLD {
  type boolean;
  mandatory false;
 }
 }
 grouping GNBRFSPCONFIG-attributes {
 leaf BACKTOHPLMNHOA5RSRPTHLD1 {
  type int16 {
   range "-156..-31";
  }
  mandatory false;
 }
 leaf BACKTOHPLMNHOA5RSRPTHLD2 {
  type int16 {
   range "-156..-31";
  }
  mandatory false;
 }
 leaf BACKTOHPLMNHORETRYPERIOD {
  type union {
   type uint8 {
    range "10..255";
   }
  }
  mandatory false;
 }
 leaf DRXPARAMGROUPID {
  type union {
   type uint8 {
    range "0..255";
   }
  }
  mandatory false;
 }
 leaf FREQPRIHOA1A2RSRPTHLDOFS {
  type int8 {
   range "-40..0";
  }
  mandatory false;
 }
 leaf INTERFREQA1A2A5RSRPTHD1OFS {
  type int8 {
   range "-20..20";
  }
  mandatory false;
 }
 leaf INTERFREQA5RSRPTHD2OFS {
  type int8 {
   range "-20..20";
  }
  mandatory false;
 }
 leaf INTERRATA1A2B2RSRPTHLDOFS {
  type int8 {
   range "-20..20";
  }
  mandatory false;
 }
 leaf MLBALGOSWITCH {
  type string;
  mandatory false;
 }
 leaf NETWORKINGOPTIONOPTFLAG {
  type boolean;
  mandatory false;
 }
 leaf OLD_OPERATORID {
  type union {
   type int8 {
    range "-1..11";
   }
  }
  mandatory false;
 }
 leaf OPERATORID {
  type union {
   type int8 {
    range "-1..11";
   }
  }
  mandatory false;
 }
 leaf REDCAPGNBFREQPRIGROUPID {
  type uint8 {
   range "0..255";
  }
  mandatory false;
 }
 leaf RFSPALGOSWITCH {
  type string;
  mandatory false;
 }
 leaf OLD_RFSPINDEX {
  type union {
   type int16 {
    range "-1..256";
   }
  }
  mandatory false;
 }
 leaf RFSPINDEX {
  type union {
   type int16 {
    range "-1..256";
   }
  }
  mandatory false;
 }
 leaf ULDATASPLITTHRESHOLD {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
  }
  mandatory false;
 }
 leaf ULPRIMARYPATHSELMODE {
  type enumeration {
   enum val-0;
   enum val-1;
   enum val-2;
  }
  mandatory false;
 }
 leaf USERSERVICETYPE {
  type enumeration {
   enum val-0;
   enum val-1;
   enum val-2;
   enum val-3;
   enum val-4;
  }
  mandatory false;
 }
 leaf GNBFREQPRIORITYGROUPID {
  type uint8 {
   range "0..255";
  }
  mandatory false;
 }
 }
 grouping GNBSHARINGMODE-attributes {
 leaf ACCESSPENALTYTIMER {
  type uint8 {
   range "0..60";
  }
  mandatory false;
 }
 leaf AMFINFOCONFLICTCHECKSW {
  type boolean;
  mandatory false;
 }
 leaf MULTIPLENCISWITCH {
  type boolean;
  mandatory false;
 }
 leaf MULTIPLENCIENHANCESW {
  type boolean;
  mandatory false;
 }
 leaf OPPAGINGRESADAPTSW {
  type enumeration {
   enum val-0;
   enum val-1;
   enum val-2;
  }
  mandatory false;
 }
 leaf RRCCONNUSERLICDYNSHRSW {
  type boolean;
  mandatory false;
 }
 leaf GNBMULTIOPSHARINGMODE {
  type enumeration {
   enum val-0;
   enum val-1;
   enum val-2;
  }
  mandatory false;
 }
 }
 grouping GNBSIBCONFIG-attributes {
 leaf OLD_SIBCONFIGID {
  type union {
   type int8 {
    range "-1..10";
   }
  }
  mandatory false;
 }
 leaf SIBCONFIGID {
  type union {
   type int8 {
    range "-1..10";
   }
  }
  mandatory false;
 }
 leaf SIBTRANSPERIOD {
  type enumeration {
   enum val-1;
   enum val-2;
   enum val-3;
  }
  mandatory false;
 }
 leaf SIBTRANSPOLICY {
  type enumeration {
   enum val-0;
   enum val-1;
   enum val-2;
  }
  mandatory false;
 }
 leaf OLD_SIBTYPE {
  type enumeration {
   enum val--1;
   enum val-2;
   enum val-3;
   enum val-4;
   enum val-5;
   enum val-8;
   enum val-9;
   enum val-10;
   enum val-17;
   enum val-20;
   enum val-21;
   enum val-254;
  }
  mandatory false;
 }
 leaf SIBTYPE {
  type enumeration {
   enum val--1;
   enum val-2;
   enum val-3;
   enum val-4;
   enum val-5;
   enum val-8;
   enum val-9;
   enum val-10;
   enum val-17;
   enum val-20;
   enum val-21;
   enum val-254;
  }
  mandatory false;
 }
 }
 grouping GNBSRVINTERHOFREQGRP-attributes {
 leaf SSBDESCMETHOD {
  type boolean;
  mandatory false;
 }
 leaf OLD_SSBFREQINDEX {
  type union {
   type int8 {
    range "-1..15";
   }
  }
  mandatory false;
 }
 leaf SSBFREQINDEX {
  type union {
   type int8 {
    range "-1..15";
   }
  }
  mandatory false;
 }
 leaf SSBFREQPOS {
  type uint32 {
   range "0..3279165";
  }
  mandatory false;
 }
 leaf OLD_GNBSRVINTERFHOFREQGROUPID {
  type union {
   type int8 {
    range "-1..89";
   }
  }
  mandatory false;
 }
 leaf GNBSRVINTERFHOFREQGROUPID {
  type union {
   type int8 {
    range "-1..89";
   }
  }
  mandatory false;
 }
 }
 grouping GNBTANS-attributes {
 leaf NSSTATE {
  type boolean;
  mandatory false;
 }
 leaf OPERATORID {
  type union {
   type int8 {
    range "-1..11";
   }
  }
  mandatory false;
 }
 leaf SLICEDIFFERENTIATOR {
  type union {
   type int32 {
    range "-1..16777215";
   }
  }
  mandatory false;
 }
 leaf SLICESERVICETYPE {
  type union {
   type int16 {
    range "-1..255";
   }
  }
  mandatory false;
 }
 leaf TRACKINGAREAID {
  type union {
   type int32 {
    range "-1..65535";
   }
  }
  mandatory false;
 }
 }
 grouping GNBTRACKINGAREA-attributes {
 leaf TAC {
  type union {
   type uint32 {
    range "0..4294967295";
   }
  }
  mandatory false;
 }
 leaf OLD_TRACKINGAREAID {
  type union {
   type int32 {
    range "-1..65535";
   }
  }
  mandatory false;
 }
 leaf TRACKINGAREAID {
  type union {
   type int32 {
    range "-1..65535";
   }
  }
  mandatory false;
 }
 }
 grouping GNBUACPARAMGROUP-attributes {
 leaf OLD_ACCESSCONTROLPARAMGRPID {
  type union {
   type int8 {
    range "-1..127";
   }
  }
  mandatory false;
 }
 leaf ACCESSCONTROLPARAMGRPID {
  type union {
   type int8 {
    range "-1..127";
   }
  }
  mandatory false;
 }
 leaf BARSTATEFORSPECIALACSID {
  type string;
  mandatory false;
 }
 leaf BARRINGFACTOR {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf BARRINGTIME {
  type enumeration {
   enum val-0;
   enum val-1;
   enum val-2;
   enum val-3;
   enum val-4;
   enum val-5;
   enum val-6;
   enum val-7;
  }
  mandatory false;
 }
 leaf MINBARRINGFACTOR {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 }
 grouping GNBUEOPERATORDIFFGRP-attributes {
 leaf INTERFREQHOMEASGROUPID {
  type union {
   type uint8 {
    range "0..255";
   }
  }
  mandatory false;
 }
 leaf INTERRHOTOEUTRANMEASGRPID {
  type union {
   type uint8 {
    range "0..255";
   }
  }
  mandatory false;
 }
 leaf INTERRATHOMEASGROUPID {
  type union {
   type uint8 {
    range "0..255";
   }
  }
  mandatory false;
 }
 leaf OLD_OPERATORID {
  type union {
   type int8 {
    range "-1..11";
   }
  }
  mandatory false;
 }
 leaf OPERATORID {
  type union {
   type int8 {
    range "-1..11";
   }
  }
  mandatory false;
 }
 leaf OLD_UEDIFFCONFIGGRPID {
  type union {
   type int8 {
    range "-1..49";
   }
  }
  mandatory false;
 }
 leaf UEDIFFCONFIGGRPID {
  type union {
   type int8 {
    range "-1..49";
   }
  }
  mandatory false;
 }
 leaf OLD_UEINFOINDEX {
  type union {
   type int16 {
    range "-1..128";
   }
  }
  mandatory false;
 }
 leaf UEINFOINDEX {
  type union {
   type int16 {
    range "-1..128";
   }
  }
  mandatory false;
 }
 leaf GNBFREQPRIORITYGROUPID {
  type uint8 {
   range "0..255";
  }
  mandatory false;
 }
 }
 grouping GNBWTCPPARAGROUP-attributes {
 leaf MAXACCPKTNUM {
  type uint16 {
   range "200..2000";
  }
  mandatory false;
 }
 leaf MAXACCSTREAM {
  type uint8 {
   range "1..100";
  }
  mandatory false;
 }
 leaf MAXRTTSTATISTICSTHD {
  type uint16 {
   range "100..30000";
  }
  mandatory false;
 }
 leaf RTOPROTECTIONBUFFERTHLD {
  type uint8 {
   range "1..20";
  }
  mandatory false;
 }
 leaf WTCPDLRTTTIMER {
  type uint8 {
   range "0..20";
  }
  mandatory false;
 }
 leaf OLD_WTCPPARAGROUPID {
  type union {
   type int8 {
    range "-1..9";
   }
  }
  mandatory false;
 }
 leaf WTCPPARAGROUPID {
  type union {
   type int8 {
    range "-1..9";
   }
  }
  mandatory false;
 }
 }
 grouping GNBX2SONCONFIG-attributes {
 leaf X2SONCONFIGSWITCH {
  type string;
  mandatory false;
 }
 leaf X2SONDELETEGNBADDCNTTHLD {
  type uint16 {
   range "0..65535";
  }
  mandatory false;
 }
 leaf X2SONDELETETIMERFORX2FAULT {
  type uint16 {
   range "1..50400";
  }
  mandatory false;
 }
 leaf X2SONDELETETIMERFORX2USAGE {
  type uint16 {
   range "60..50400";
  }
  mandatory false;
 }
 }
 grouping GNBXNSONCONFIG-attributes {
 leaf XNSONCONFIGSWITCH {
  type string;
  mandatory false;
 }
 leaf XNSONDELETETIMERFORXNFAULT {
  type uint16 {
   range "1..50400";
  }
  mandatory false;
 }
 leaf XNSONDELETETIMERFORXNUSAGE {
  type uint16 {
   range "60..50400";
  }
  mandatory false;
 }
 }
 grouping GNODEBALGO-attributes {
 leaf CHNCALIBPOLSW {
  type string;
  mandatory false;
 }
 leaf DEDICATEDNETWORKFUNCSW {
  type string;
  mandatory false;
 }
 leaf DLSCHSWITCH {
  type string;
  mandatory false;
 }
 leaf HPLMNALGOSWITCH {
  type string;
  mandatory false;
 }
 leaf INTRFAVOIDSW {
  type string;
  mandatory false;
 }
 leaf JTFLOWCTRLLEVEL {
  type enumeration {
   enum val-0;
   enum val-1;
   enum val-2;
   enum val-3;
  }
  mandatory false;
 }
 leaf KEEPALIVEPKTTXPERIOD {
  type uint8 {
   range "0..60";
  }
  mandatory false;
 }
 leaf MAXTOBEDUPPKTNUM {
  type uint8 {
   range "20..150";
  }
  mandatory false;
 }
 leaf MULTICARRIERFLOWCTRLLEVEL {
  type enumeration {
   enum val-0;
   enum val-1;
   enum val-2;
   enum val-3;
  }
  mandatory false;
 }
 leaf MULTICARRIERMEASWAITTIMER {
  type uint8 {
   range "3..30";
  }
  mandatory false;
 }
 leaf NPNALGOSWITCH {
  type string;
  mandatory false;
 }
 leaf NRSMARTMULTICARRSW {
  type string;
  mandatory false;
 }
 leaf PAGINGALGOSWITCH {
  type string;
  mandatory false;
 }
 leaf POSTRPIDSWITCH {
  type boolean;
  mandatory false;
 }
 leaf PUCCHSWITCH {
  type string;
  mandatory false;
 }
 leaf RANSHARINGALGOSW {
  type string;
  mandatory false;
 }
 leaf RFMODULEALGOSWITCH {
  type string;
  mandatory false;
 }
 leaf RFNETWORKINGRELIABILITYSW {
  type string;
  mandatory false;
 }
 leaf SSLOTSCHOPT {
  type enumeration {
   enum val-0;
   enum val-1;
   enum val-2;
   enum val-3;
   enum val-4;
   enum val-5;
   enum val-6;
  }
  mandatory false;
 }
 leaf SELFCONFIGSWITCH {
  type string;
  mandatory false;
 }
 leaf TIMEINTRFAVOIDSW {
  type string;
  mandatory false;
 }
 leaf ULPATHCHANGEPKTLOSSNUMTHLD {
  type uint32 {
   range "1..131072";
  }
  mandatory false;
 }
 leaf ULSCHOPTSWITCH {
  type string;
  mandatory false;
 }
 leaf ULSCHSWITCH {
  type string;
  mandatory false;
 }
 leaf VOICESW {
  type string;
  mandatory false;
 }
 leaf GNBISALGOSW {
  type string;
  mandatory false;
 }
 }
 grouping GNODEBAMFCONFIG-attributes {
 leaf OLD_AMFCONFIGINDEX {
  type union {
   type int8 {
    range "-1..31";
   }
  }
  mandatory false;
 }
 leaf AMFCONFIGINDEX {
  type union {
   type int8 {
    range "-1..31";
   }
  }
  mandatory false;
 }
 leaf AMFNAME {
  type string {
   length "1..150";
  }
  mandatory false;
 }
 leaf AMFPRIORITY {
  type uint8 {
   range "0..255";
  }
  mandatory false;
 }
 leaf MCC {
  type string {
   length "3";
  }
  mandatory false;
 }
 leaf MNC {
  type string {
   length "2..3";
  }
  mandatory false;
 }
 }
 grouping GNODEBCARRMGMT-attributes {
 leaf CAENHANCEDALGOSWITCH {
  type string;
  mandatory false;
 }
 leaf DLSPLITSTOPPENALTYPRD {
  type uint16 {
   range "1..600";
  }
  mandatory false;
 }
 leaf NRDCOPTSWITCH {
  type string;
  mandatory false;
 }
 }
 grouping GNODEBFUNCTION-attributes {
 leaf TEMPLATENAME {
  type string;
  mandatory false;
 }
 leaf REFERENCEDAPPLICATIONID {
  type uint8 {
   range "1..255";
  }
  mandatory false;
 }
 leaf USERLABEL {
  type string {
   length "0..256";
  }
  mandatory false;
 }
 leaf GNBID {
  type uint32 {
   range "0..4294967295";
  }
  mandatory false;
 }
 leaf GNBIDLENGTH {
  type uint8 {
   range "22..32";
  }
  mandatory false;
 }
 leaf GNODEBFUNCTIONNAME {
  type string {
   length "1..128";
  }
  mandatory false;
 }
 }
 grouping GNODEBPARAM-attributes {
 leaf ABNDLDATASPLITPENALTYPRD {
  type uint16 {
   range "1..600";
  }
  mandatory false;
 }
 leaf AOAMEASSNRTHLD {
  type int16 {
   range "-10000..2000";
  }
  mandatory false;
 }
 leaf APPPKTSIZETHLD {
  type uint16 {
   range "1..1500";
  }
  mandatory false;
 }
 leaf AUTOCELLBINDBASEBANDEQMSW {
  type boolean;
  mandatory false;
 }
 leaf BASESTATIONDEEPDORMANCYSW {
  type string;
  mandatory false;
 }
 leaf BBRESALLOCATEMODE {
  type enumeration {
   enum val-0;
   enum val-1;
   enum val-2;
   enum val-3;
  }
  mandatory false;
 }
 leaf BOARDPROCESSINGPOLICYSW {
  type string;
  mandatory false;
 }
 leaf CELLSTATEPOLICYSWITCH {
  type string;
  mandatory false;
 }
 leaf CHRSWITCH {
  type string;
  mandatory false;
 }
 leaf CLKOUTOFSYNCCINTRFRPTINTVL {
  type enumeration {
   enum val-0;
   enum val-1;
   enum val-2;
   enum val-3;
   enum val-4;
   enum val-5;
   enum val-6;
   enum val-7;
   enum val-8;
   enum val-9;
  }
  mandatory false;
 }
 leaf CLKOUTOFSYNCDETSWITCH {
  type string;
  mandatory false;
 }
 leaf CLKOUTOFSYNCINTRFRPTTHLD {
  type int16 {
   range "-130..-50";
  }
  mandatory false;
 }
 leaf COMPATIBILITYALGOSWITCH {
  type string;
  mandatory false;
 }
 leaf DRBLOADSHARINGTHLD {
  type uint8 {
   range "10..100";
  }
  mandatory false;
 }
 leaf EQVPLMNALGOSWITCH {
  type string;
  mandatory false;
 }
 leaf ETHPORTSTATEAUTODEACELLSW {
  type boolean;
  mandatory false;
 }
 leaf FRAMEOFFSET {
  type union {
   type uint32 {
    range "0..307200";
   }
  }
  mandatory false;
 }
 leaf GNSSFAILLFHOLDOVERDURATION {
  type boolean;
  mandatory false;
 }
 leaf HIGHSPEEDDEDPOLICYSW {
  type string;
  mandatory false;
 }
 leaf INTRASITEMAXX2TRANSRATE {
  type uint8 {
   range "0..100";
  }
  mandatory false;
 }
 leaf L4SALGOSWITCH {
  type string;
  mandatory false;
 }
 leaf L4SCONGESTCHECKPERIOD {
  type uint8 {
   range "1..20";
  }
  mandatory false;
 }
 leaf L4SULDELAYLOWERTHLD {
  type uint16 {
   range "1..1000";
  }
  mandatory false;
 }
 leaf L4SULDELAYUPPERTHLD {
  type uint16 {
   range "1..1000";
  }
  mandatory false;
 }
 leaf LTEHANDOVERALGOSWITCH {
  type string;
  mandatory false;
 }
 leaf MAXFHFIBERLENGTHADAPTSW {
  type boolean;
  mandatory false;
 }
 leaf MAXNRTSTUENCELLNUM {
  type uint16 {
   range "1..384";
  }
  mandatory false;
 }
 leaf MAXX2TRANSRATE {
  type uint8 {
   range "1..100";
  }
  mandatory false;
 }
 leaf MDTEXTENDMEASSW {
  type string;
  mandatory false;
 }
 leaf MOBILITYOPTSWITCH {
  type string;
  mandatory false;
 }
 leaf MODULEPROOPTSWITCH {
  type string;
  mandatory false;
 }
 leaf MULTICARRIERCALIBFACTOR {
  type uint8 {
   range "1..4";
  }
  mandatory false;
 }
 leaf NETWORKINGOPTIONOPTSW {
  type string;
  mandatory false;
 }
 leaf NGINTERFACEALGOSW {
  type string;
  mandatory false;
 }
 leaf NOTIFCTRLCHECKINTERVAL {
  type uint8 {
   range "1..20";
  }
  mandatory false;
 }
 leaf NRBOARDPERFORMANCESW {
  type string;
  mandatory false;
 }
 leaf NRCOORDSERVICEFLOWCTRLLVL {
  type enumeration {
   enum val-0;
   enum val-1;
   enum val-2;
  }
  mandatory false;
 }
 leaf NRCOORDSERVICEFLOWCTRLSW {
  type boolean;
  mandatory false;
 }
 leaf NRUPLOADBALANCETHLD {
  type uint8 {
   range "0..100";
  }
  mandatory false;
 }
 leaf NRUSERPROCESSINGLOADMODE {
  type enumeration {
   enum val-0;
   enum val-1;
   enum val-2;
  }
  mandatory false;
 }
 leaf NSADCOPTSWITCH {
  type string;
  mandatory false;
 }
 leaf NSADCRESCOORDSCENARIO {
  type enumeration {
   enum val-0;
   enum val-1;
   enum val-2;
  }
  mandatory false;
 }
 leaf NSASASELOPTPERIOD {
  type uint8 {
   range "5..60";
  }
  mandatory false;
 }
 leaf PACKETMEASUREMENTSWITCH {
  type string;
  mandatory false;
 }
 leaf PDCPPROCOPTSWITCH {
  type string;
  mandatory false;
 }
 leaf PROCESSSWITCH {
  type string;
  mandatory false;
 }
 leaf PWSINDICATIONSWITCH {
  type string;
  mandatory false;
 }
 leaf RLCMACPERFORMANCESWITCH {
  type yang:mac-address;
  mandatory false;
 }
 leaf RRCSETUPREQPUNISHTHLD {
  type union {
   type uint8 {
    range "0..15";
   }
  }
  mandatory false;
 }
 leaf SCHGROUPPERIOD {
  type enumeration {
   enum val-0;
   enum val-1;
   enum val-2;
   enum val-3;
   enum val-4;
  }
  mandatory false;
 }
 leaf SERVINTERFACEALMCONFIGSW {
  type string;
  mandatory false;
 }
 leaf SERVICEDIFFPROCSWITCH {
  type string;
  mandatory false;
 }
 leaf SERVICEEXPALGOSWITCH {
  type string;
  mandatory false;
 }
 leaf SFSSWITCH {
  type string;
  mandatory false;
 }
 leaf SILDETINTRFDIFFTHLD {
  type int8 {
   range "-10..30";
  }
  mandatory false;
 }
 leaf STNCELLPROCSW {
  type string;
  mandatory false;
 }
 leaf STUEIDENTSW {
  type string;
  mandatory false;
 }
 leaf SYNCDIFFDETECTSWITCH {
  type string;
  mandatory false;
 }
 leaf TLLOSTPKTMEASSWITCH {
  type string;
  mandatory false;
 }
 leaf TLLOSTPKTMEASUSERTYPE {
  type boolean;
  mandatory false;
 }
 leaf UEOPTIMIZATIONSWITCH {
  type string;
  mandatory false;
 }
 leaf ULABNPDCPSNPKTNUMTHLD {
  type uint32 {
   range "1..131072";
  }
  mandatory false;
 }
 leaf ULFLOWCTRLALGOSWITCH {
  type string;
  mandatory false;
 }
 leaf ULPDCPSNOUTROWINPKTNUMTHLD {
  type uint32 {
   range "1..131072";
  }
  mandatory false;
 }
 leaf VIRTUALUSERTRACERATETHLD {
  type uint16 {
   range "0..1000";
  }
  mandatory false;
 }
 leaf X2UTRANSMISSIONTYPE {
  type boolean;
  mandatory false;
 }
 }
 grouping NRCELL-attributes {
 leaf TEMPLATENAME {
  type string;
  mandatory false;
 }
 leaf CELLACTIVESTATE {
  type boolean;
  mandatory false;
 }
 leaf CELLID {
  type uint16 {
   range "0..16383";
  }
  mandatory false;
 }
 leaf CELLNAME {
  type string {
   length "1..99";
  }
  mandatory false;
 }
 leaf DUPLEXMODE {
  type enumeration {
   enum val-0;
   enum val-1;
   enum val-3;
  }
  mandatory false;
 }
 leaf FREQUENCYBAND {
  type enumeration {
   enum val-1;
   enum val-2;
   enum val-3;
   enum val-5;
   enum val-7;
   enum val-8;
   enum val-12;
   enum val-13;
   enum val-20;
   enum val-25;
   enum val-28;
   enum val-38;
   enum val-39;
   enum val-40;
   enum val-41;
   enum val-66;
   enum val-71;
   enum val-75;
   enum val-77;
   enum val-78;
   enum val-79;
   enum val-257;
   enum val-258;
   enum val-260;
   enum val-261;
  }
  mandatory false;
 }
 leaf OLD_NRCELLID {
  type union {
   type int32 {
    range "-1..65534";
   }
  }
  mandatory false;
 }
 leaf NRCELLID {
  type union {
   type int32 {
    range "-1..65534";
   }
  }
  mandatory false;
 }
 leaf USERLABEL {
  type string {
   length "0..256";
  }
  mandatory false;
 }
 }
 grouping NRCELLALGOSWITCH-attributes {
 leaf AIINTERFREQHOOPTSWITCH {
  type string;
  mandatory false;
 }
 leaf ANRSWITCH {
  type string;
  mandatory false;
 }
 leaf CLOUDPHONESWITCH {
  type string;
  mandatory false;
 }
 leaf CLOUDVRSWITCH {
  type string;
  mandatory false;
 }
 leaf EXTENDEDCELLRANGEPOLSW {
  type string;
  mandatory false;
 }
 leaf FWAALGOSWITCH {
  type string;
  mandatory false;
 }
 leaf HIGHSPEEDDEDPOLICYSW {
  type string;
  mandatory false;
 }
 leaf HOCOMPATIBILITYSWITCH {
  type string;
  mandatory false;
 }
 leaf INACTIVESTRATEGYSWITCH {
  type string;
  mandatory false;
 }
 leaf INTERFREQHOSWITCH {
  type string;
  mandatory false;
 }
 leaf INTERRATSERVICEMOBILITYSW {
  type string;
  mandatory false;
 }
 leaf INTRAFREQCOORDHOMODE {
  type enumeration {
   enum val-0;
   enum val-1;
   enum val-2;
  }
  mandatory false;
 }
 leaf INTRAFREQHOALGOSW {
  type string;
  mandatory false;
 }
 leaf INTRAFREQHOSWITCH {
  type string;
  mandatory false;
 }
 leaf LCSSWITCH {
  type string;
  mandatory false;
 }
 leaf LIVEVIDEOSWITCH {
  type string;
  mandatory false;
 }
 leaf MEASPOLICYSWITCH {
  type string;
  mandatory false;
 }
 leaf MLBALGOSWITCH {
  type string;
  mandatory false;
 }
 leaf MULTIFREQALGOSWITCH {
  type string;
  mandatory false;
 }
 leaf MULTIFREQSMARTSELMODE {
  type enumeration {
   enum val-0;
   enum val-1;
   enum val-2;
  }
  mandatory false;
 }
 leaf NCELLINFOCTRLSWITCH {
  type string;
  mandatory false;
 }
 leaf NEIGHBORCELLOPTSWITCH {
  type string;
  mandatory false;
 }
 leaf NETWORKSLICEALGOSWITCH {
  type string;
  mandatory false;
 }
 leaf NRCELLID {
  type union {
   type int32 {
    range "-1..65534";
   }
  }
  mandatory false;
 }
 leaf NRDCSWITCH {
  type string;
  mandatory false;
 }
 leaf NSADCSWITCH {
  type boolean;
  mandatory false;
 }
 leaf PROCESSSWITCH {
  type string;
  mandatory false;
 }
 leaf RACALGOSWITCH {
  type string;
  mandatory false;
 }
 leaf RFSPALGOSWITCH {
  type string;
  mandatory false;
 }
 leaf ROHCMODE {
  type enumeration {
   enum val-0;
   enum val-1;
   enum val-2;
  }
  mandatory false;
 }
 leaf ROHCPROFILES {
  type string;
  mandatory false;
 }
 leaf ROHCSWITCH {
  type string;
  mandatory false;
 }
 leaf RRCRECONFIGMSGTRANSINTVL {
  type uint16 {
   range "0..1000";
  }
  mandatory false;
 }
 leaf SERVICEFUNCTIONSWITCH {
  type string;
  mandatory false;
 }
 leaf SPECUECOLLABSWITCH {
  type string;
  mandatory false;
 }
 leaf SPEEDTURBOSW {
  type string;
  mandatory false;
 }
 leaf TOBUSINESSSERVICESWITCH {
  type string;
  mandatory false;
 }
 leaf UEASSISTANCEINFOSWITCH {
  type string;
  mandatory false;
 }
 leaf UEPWRSAVINGSWITCH {
  type string;
  mandatory false;
 }
 leaf VOICESTRATEGYSWITCH {
  type string;
  mandatory false;
 }
 leaf VONRSWITCH {
  type string;
  mandatory false;
 }
 }
 grouping NRCELLCAMGMTCONFIG-attributes {
 leaf CAA2RSRPTHLD {
  type int16 {
   range "-156..-31";
  }
  mandatory false;
 }
 leaf CAA5RSRPTHLD2 {
  type int16 {
   range "-156..-31";
  }
  mandatory false;
 }
 leaf CAA5TIMETOTRIG {
  type enumeration {
   enum val-0;
   enum val-1;
   enum val-2;
   enum val-3;
   enum val-4;
   enum val-5;
   enum val-6;
   enum val-7;
   enum val-8;
   enum val-9;
   enum val-10;
   enum val-11;
  }
  mandatory false;
 }
 leaf CAA6OFFSET {
  type int8 {
   range "-30..30";
  }
  mandatory false;
 }
 leaf CAA6TIMETOTRIG {
  type enumeration {
   enum val-0;
   enum val-1;
   enum val-2;
   enum val-3;
   enum val-4;
   enum val-5;
   enum val-6;
   enum val-7;
   enum val-8;
   enum val-9;
   enum val-10;
   enum val-11;
  }
  mandatory false;
 }
 leaf CABANDCOMBSELECTIONSTRAT {
  type enumeration {
   enum val-0;
   enum val-1;
   enum val-2;
   enum val-3;
  }
  mandatory false;
 }
 leaf CACOMPATIBILITYSWITCH {
  type string;
  mandatory false;
 }
 leaf CASCELLCONFIGPRBUSAGETHLD {
  type uint8 {
   range "0..100";
  }
  mandatory false;
 }
 leaf CASTRATEGYSWITCH {
  type string;
  mandatory false;
 }
 leaf CARRSELMININTERVAL {
  type union {
   type uint16 {
    range "30..65535";
   }
  }
  mandatory false;
 }
 leaf DLEXPEVALHYST {
  type uint8 {
   range "10..100";
  }
  mandatory false;
 }
 leaf EXPEVALNSIMPACTFACTOR {
  type uint8 {
   range "0..100";
  }
  mandatory false;
 }
 leaf HETNETDLEXPEVALHYST {
  type uint16 {
   range "0..1000";
  }
  mandatory false;
 }
 leaf INTERFRCARRSELSTRAT {
  type boolean;
  mandatory false;
 }
 leaf INTERGNBEXPEVALCOEFF {
  type uint8 {
   range "0..100";
  }
  mandatory false;
 }
 leaf MULTIFREQOPTALGOSWITCH {
  type string;
  mandatory false;
 }
 leaf NRCELLID {
  type union {
   type int32 {
    range "-1..65534";
   }
  }
  mandatory false;
 }
 leaf NSASCELLMEASWAITTIMER {
  type uint8 {
   range "5..20";
  }
  mandatory false;
 }
 leaf SCCCOVADAPTCCEFAILTHLD {
  type uint8 {
   range "0..100";
  }
  mandatory false;
 }
 leaf SCCCOVADAPTPRBUSAGETHLD {
  type uint8 {
   range "0..100";
  }
  mandatory false;
 }
 leaf SCCCOVADAPTRSRPTHLDOFFSET {
  type int8 {
   range "-20..0";
  }
  mandatory false;
 }
 leaf SMARTCARRSELPOLICY {
  type boolean;
  mandatory false;
 }
 leaf SPECUEPCELLPOLICY {
  type enumeration {
   enum val-0;
   enum val-1;
   enum val-2;
  }
  mandatory false;
 }
 leaf ULCAA2RSRPTHLD {
  type int16 {
   range "-156..-31";
  }
  mandatory false;
 }
 leaf ULEXPEVALHYST {
  type uint8 {
   range "10..100";
  }
  mandatory false;
 }
 }
 grouping NRCELLCOMP-attributes {
 leaf COMPGUARANTEESW {
  type string;
  mandatory false;
 }
 leaf DLCOMPRSRPOFFSET {
  type int8 {
   range "-30..30";
  }
  mandatory false;
 }
 leaf HYSTERESIS {
  type uint8 {
   range "0..30";
  }
  mandatory false;
 }
 leaf INTRAFREQNCELLSTATA3OFFSET {
  type int8 {
   range "-30..30";
  }
  mandatory false;
 }
 leaf NRCELLID {
  type union {
   type int32 {
    range "-1..65534";
   }
  }
  mandatory false;
 }
 leaf OVERLAPPINGRSRPOFFSET {
  type int8 {
   range "-30..30";
  }
  mandatory false;
 }
 leaf TIMETOTRIGGER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf ULCOMPRSRPOFFSET {
  type int8 {
   range "-30..30";
  }
  mandatory false;
 }
 }
 grouping NRCELLEUTRANNFREQ-attributes {
 leaf AGGREGATIONATTRIBUTE {
  type string;
  mandatory false;
 }
 leaf AUTOEUTRANFREQRELNRSRPTHLD {
  type int16 {
   range "-140..-43";
  }
  mandatory false;
 }
 leaf CONNFREQPRIORITY {
  type uint8 {
   range "0..16";
  }
  mandatory false;
 }
 leaf COVHOA1A2B21FREQOFFSET {
  type int8 {
   range "-30..30";
  }
  mandatory false;
 }
 leaf OLD_DLEARFCN {
  type union {
   type int32 {
    range "-1..229575";
   }
  }
  mandatory false;
 }
 leaf DLEARFCN {
  type union {
   type int32 {
    range "-1..229575";
   }
  }
  mandatory false;
 }
 leaf EPSFBB1RSRPTHLD {
  type int16 {
   range "-140..-43";
  }
  mandatory false;
 }
 leaf EUTRANEXCLUDEDCELLLISTID {
  type uint16 {
   range "0..65535";
  }
  mandatory false;
 }
 leaf EUTRANFREQHIGHPRIRESELTHLD {
  type uint8 {
   range "0..31";
  }
  mandatory false;
 }
 leaf EUTRANFREQLOWPRIRESELTHLD {
  type uint8 {
   range "0..31";
  }
  mandatory false;
 }
 leaf EUTRANFREQRESELPRIORITY {
  type union {
   type uint8 {
    range "0..255";
   }
  }
  mandatory false;
 }
 leaf EUTRANFREQRESELSUBPRIORITY {
  type enumeration {
   enum val-0;
   enum val-2;
   enum val-4;
   enum val-6;
   enum val-8;
  }
  mandatory false;
 }
 leaf EUTRANHIGHPRIRESELRSRQTHLD {
  type uint8 {
   range "0..31";
  }
  mandatory false;
 }
 leaf EUTRANLOWPRIRESELRSRQTHLD {
  type uint8 {
   range "0..31";
  }
  mandatory false;
 }
 leaf FREQINTRFFLAG {
  type boolean;
  mandatory false;
 }
 leaf FREQRELATIONSHIP {
  type enumeration {
   enum val-0;
   enum val-1;
   enum val-2;
   enum val-3;
  }
  mandatory false;
 }
 leaf FREQSPECIFICOFFSET {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf FREQUENCYCTRLSWITCH {
  type string;
  mandatory false;
 }
 leaf HIGHSPEEDFLAG {
  type boolean;
  mandatory false;
 }
 leaf MAXIMUMTRANSMITPOWER {
  type int8 {
   range "-30..33";
  }
  mandatory false;
 }
 leaf MEASACTVFLAG {
  type boolean;
  mandatory false;
 }
 leaf MEASURETYPE {
  type boolean;
  mandatory false;
 }
 leaf MEASUREMENTBANDWIDTH {
  type enumeration {
   enum val-0;
   enum val-1;
   enum val-2;
   enum val-3;
   enum val-4;
   enum val-5;
  }
  mandatory false;
 }
 leaf MINIMUMRXLEVEL {
  type int8 {
   range "-70..-22";
  }
  mandatory false;
 }
 leaf MINIMUMRXQLTY {
  type int8 {
   range "-34..-3";
  }
  mandatory false;
 }
 leaf OLD_NRCELLID {
  type union {
   type int32 {
    range "-1..65534";
   }
  }
  mandatory false;
 }
 leaf NRCELLID {
  type union {
   type int32 {
    range "-1..65534";
   }
  }
  mandatory false;
 }
 leaf NSAPCCFREQPRIORITY {
  type uint8 {
   range "0..16";
  }
  mandatory false;
 }
 leaf VOLTEPRIORITY {
  type union {
   type uint8 {
    range "0..255";
   }
  }
  mandatory false;
 }
 }
 grouping NRCELLEUTRANRELATION-attributes {
 leaf ANRFLAG {
  type boolean;
  mandatory false;
 }
 leaf BLINDHOFLAG {
  type string;
  mandatory false;
 }
 leaf CELLID {
  type union {
   type int16 {
    range "-1..255";
   }
  }
  mandatory false;
 }
 leaf ENODEBID {
  type union {
   type int32 {
    range "-1..1048575";
   }
  }
  mandatory false;
 }
 leaf EUTRANCELLINDIVIDUALOFFSET {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf MCC {
  type string {
   length "3";
  }
  mandatory false;
 }
 leaf MINIMUMRXLEVELOFFSET {
  type uint8 {
   range "0..8";
  }
  mandatory false;
 }
 leaf MNC {
  type string {
   length "2..3";
  }
  mandatory false;
 }
 leaf NOHOFLAG {
  type boolean;
  mandatory false;
 }
 leaf NORMVFLAG {
  type boolean;
  mandatory false;
 }
 leaf NRCELLID {
  type union {
   type int32 {
    range "-1..65534";
   }
  }
  mandatory false;
 }
 leaf POWERSAVINGOVERLAPIND {
  type string;
  mandatory false;
 }
 }
 grouping NRCELLFEATURESWITCH-attributes {
 leaf CELLMEASCOLLECTSWITCH {
  type string;
  mandatory false;
 }
 leaf INTELLIGENTEXPGUARSWITCH {
  type string;
  mandatory false;
 }
 leaf INTERFREQHOEXPSWITCH {
  type string;
  mandatory false;
 }
 leaf MBSSWITCH {
  type string;
  mandatory false;
 }
 leaf NRCELLID {
  type union {
   type int32 {
    range "-1..65534";
   }
  }
  mandatory false;
 }
 }
 grouping NRCELLFREQRELATION-attributes {
 leaf ADDITIONALFREQUENCYBAND {
  type enumeration {
   enum val-0;
   enum val-2;
   enum val-5;
   enum val-8;
   enum val-12;
   enum val-18;
   enum val-25;
   enum val-26;
   enum val-31;
   enum val-38;
   enum val-41;
   enum val-48;
   enum val-71;
   enum val-72;
   enum val-77;
   enum val-78;
   enum val-85;
   enum val-90;
   enum val-96;
   enum val-102;
   enum val-104;
   enum val-105;
   enum val-106;
   enum val-257;
   enum val-258;
   enum val-259;
   enum val-260;
   enum val-261;
  }
  mandatory false;
 }
 leaf AGGREGATIONATTRIBUTE {
  type string;
  mandatory false;
 }
 leaf ANRIND {
  type boolean;
  mandatory false;
 }
 leaf AUTONRFREQRELATIONRSRPTHLD {
  type int16 {
   range "-156..-31";
  }
  mandatory false;
 }
 leaf BLINDREDIRECTPRIORITY {
  type uint8 {
   range "0..16";
  }
  mandatory false;
 }
 leaf CAANCHORFREQPRIORITY {
  type uint8 {
   range "0..16";
  }
  mandatory false;
 }
 leaf CELLRESELPRIORITY {
  type union {
   type uint8 {
    range "0..255";
   }
  }
  mandatory false;
 }
 leaf CELLRESELSUBPRIORITY {
  type enumeration {
   enum val-0;
   enum val-2;
   enum val-4;
   enum val-6;
   enum val-8;
  }
  mandatory false;
 }
 leaf CONNFREQOFFSET {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf CONNFREQPRIORITY {
  type uint8 {
   range "0..16";
  }
  mandatory false;
 }
 leaf EXPBASEDPCCFREQSELRSRPOFS {
  type int8 {
   range "-100..100";
  }
  mandatory false;
 }
 leaf EXTENDEDRANGECELLFLAG {
  type boolean;
  mandatory false;
 }
 leaf FREQINTRFFLAG {
  type enumeration {
   enum val-0;
   enum val-1;
   enum val-2;
  }
  mandatory false;
 }
 leaf FREQOFFSET {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf FREQUENCYBAND {
  type enumeration {
   enum val-1;
   enum val-2;
   enum val-3;
   enum val-5;
   enum val-7;
   enum val-8;
   enum val-12;
   enum val-13;
   enum val-14;
   enum val-18;
   enum val-20;
   enum val-24;
   enum val-25;
   enum val-26;
   enum val-28;
   enum val-30;
   enum val-31;
   enum val-34;
   enum val-38;
   enum val-39;
   enum val-40;
   enum val-41;
   enum val-46;
   enum val-48;
   enum val-50;
   enum val-51;
   enum val-53;
   enum val-54;
   enum val-65;
   enum val-66;
   enum val-70;
   enum val-71;
   enum val-72;
   enum val-74;
   enum val-75;
   enum val-77;
   enum val-78;
   enum val-79;
   enum val-85;
   enum val-90;
   enum val-91;
   enum val-92;
   enum val-93;
   enum val-94;
   enum val-96;
   enum val-100;
   enum val-101;
   enum val-102;
   enum val-104;
   enum val-105;
   enum val-106;
   enum val-109;
   enum val-257;
   enum val-258;
   enum val-259;
   enum val-260;
   enum val-261;
   enum val-262;
   enum val-263;
  }
  mandatory false;
 }
 leaf FREQUENCYCTRLSWITCH {
  type string;
  mandatory false;
 }
 leaf HIGHPRIRESELRSRQTHLD {
  type uint8 {
   range "0..31";
  }
  mandatory false;
 }
 leaf HIGHPRIRESELTHLD {
  type uint8 {
   range "0..31";
  }
  mandatory false;
 }
 leaf HIGHSPEEDFLAG {
  type enumeration {
   enum val-0;
   enum val-1;
   enum val-2;
  }
  mandatory false;
 }
 leaf IDLEMLBUERELEASERATIO {
  type uint8 {
   range "0..90";
  }
  mandatory false;
 }
 leaf INTERFEXCLUDEDCELLLISTID {
  type uint16 {
   range "0..65535";
  }
  mandatory false;
 }
 leaf INTERFREQHOA1A2A51FREQOFS {
  type int8 {
   range "-30..30";
  }
  mandatory false;
 }
 leaf INTERFREQHOEVENTTYPE {
  type boolean;
  mandatory false;
 }
 leaf INTERFREQPRDCMRTYPE {
  type enumeration {
   enum val-0;
   enum val-1;
   enum val-2;
  }
  mandatory false;
 }
 leaf INTRFFREQPRIORITY {
  type uint8 {
   range "0..16";
  }
  mandatory false;
 }
 leaf LOWPRIRESELRSRQTHLD {
  type uint8 {
   range "0..31";
  }
  mandatory false;
 }
 leaf LOWPRIRESELTHLD {
  type uint8 {
   range "0..31";
  }
  mandatory false;
 }
 leaf MAXUETRANSMITPOWER {
  type union {
   type int16 {
    range "-30..255";
   }
  }
  mandatory false;
 }
 leaf MEASACTVFLAG {
  type boolean;
  mandatory false;
 }
 leaf MINIMUMRXLEVEL {
  type int8 {
   range "-70..-22";
  }
  mandatory false;
 }
 leaf MINIMUMRXQLTY {
  type int8 {
   range "-43..-12";
  }
  mandatory false;
 }
 leaf MLBFREQPRIORITY {
  type uint8 {
   range "0..16";
  }
  mandatory false;
 }
 leaf OLD_NRCELLID {
  type union {
   type int32 {
    range "-1..65534";
   }
  }
  mandatory false;
 }
 leaf NRCELLID {
  type union {
   type int32 {
    range "-1..65534";
   }
  }
  mandatory false;
 }
 leaf PCCANCHORFLAG {
  type boolean;
  mandatory false;
 }
 leaf PERIODICMRLAYER {
  type enumeration {
   enum val-0;
   enum val-1;
   enum val-2;
   enum val-3;
  }
  mandatory false;
 }
 leaf REDCAPACCESSALLOWEDFLAG {
  type boolean;
  mandatory false;
 }
 leaf REDCAPMEASACTVFLAG {
  type boolean;
  mandatory false;
 }
 leaf REDCAPULEXPFREQPRIORITY {
  type uint8 {
   range "0..16";
  }
  mandatory false;
 }
 leaf SMTCDURATION {
  type enumeration {
   enum val-0;
   enum val-1;
   enum val-2;
   enum val-3;
   enum val-4;
  }
  mandatory false;
 }
 leaf SMTCOFFSET {
  type uint8 {
   range "0..159";
  }
  mandatory false;
 }
 leaf SMTCPERIOD {
  type enumeration {
   enum val-0;
   enum val-1;
   enum val-2;
   enum val-3;
   enum val-4;
   enum val-5;
  }
  mandatory false;
 }
 leaf SSBDESCMETHOD {
  type boolean;
  mandatory false;
 }
 leaf OLD_SSBFREQPOS {
  type union {
   type int32 {
    range "-1..3279165";
   }
  }
  mandatory false;
 }
 leaf SSBFREQPOS {
  type union {
   type int32 {
    range "-1..3279165";
   }
  }
  mandatory false;
 }
 leaf SUBCARRIERSPACING {
  type enumeration {
   enum val-0;
   enum val-1;
   enum val-3;
   enum val-4;
   enum val-5;
   enum val-6;
  }
  mandatory false;
 }
 leaf SYNCDDAPSHOFLAG {
  type boolean;
  mandatory false;
 }
 leaf TRAFFICPRIORITY {
  type uint8 {
   range "0..16";
  }
  mandatory false;
 }
 leaf ULTRAFFICFREQPRIORITY {
  type uint8 {
   range "0..16";
  }
  mandatory false;
 }
 leaf VONRQUALITYFREQPRIORITY {
  type union {
   type uint8 {
    range "0..255";
   }
  }
  mandatory false;
 }
 }
 grouping NRCELLHOEUTRANMEAGRP-attributes {
 leaf COVBASEDHOB1B2HYST {
  type uint8 {
   range "0..30";
  }
  mandatory false;
 }
 leaf COVBASEDHOB1B2TIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf COVBASEDHOB1RSRPTHLD {
  type int16 {
   range "-140..-43";
  }
  mandatory false;
 }
 leaf COVBASEDHOB1RSRQTHLD {
  type int8 {
   range "-40..-6";
  }
  mandatory false;
 }
 leaf EPSFBB1HYST {
  type uint8 {
   range "0..30";
  }
  mandatory false;
 }
 leaf EPSFBB1RSRPTHLD {
  type int16 {
   range "-140..-43";
  }
  mandatory false;
 }
 leaf EPSFBB1RSRQTHLD {
  type int8 {
   range "-40..-6";
  }
  mandatory false;
 }
 leaf EPSFBB1TIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf OLD_INTERRHOTOEUTRANMEASGRPID {
  type union {
   type int8 {
    range "-1..14";
   }
  }
  mandatory false;
 }
 leaf INTERRHOTOEUTRANMEASGRPID {
  type union {
   type int8 {
    range "-1..14";
   }
  }
  mandatory false;
 }
 leaf LNRCARRSHUTDOWNB1RSRPTHLD {
  type int16 {
   range "-140..-43";
  }
  mandatory false;
 }
 leaf LOADMOBTOEUTRANB1RSRPTHLD {
  type int16 {
   range "-140..-43";
  }
  mandatory false;
 }
 leaf NETWORKINGOPTIONOPTB1THLD {
  type int16 {
   range "-140..-43";
  }
  mandatory false;
 }
 leaf OLD_NRCELLID {
  type union {
   type int32 {
    range "-1..65534";
   }
  }
  mandatory false;
 }
 leaf NRCELLID {
  type union {
   type int32 {
    range "-1..65534";
   }
  }
  mandatory false;
 }
 leaf STCOVBASEDHOB1RSRPTHLD {
  type int16 {
   range "-140..-43";
  }
  mandatory false;
 }
 }
 grouping NRCELLINTERFHOMEAGRP-attributes {
 leaf A3INTERFREQHOA1RSRPTHLD {
  type int16 {
   range "-156..-31";
  }
  mandatory false;
 }
 leaf A3INTERFREQHOA2RSRPTHLD {
  type int16 {
   range "-156..-31";
  }
  mandatory false;
 }
 leaf BWPSWITCHINGA1RSRPTHLD {
  type int16 {
   range "-156..-31";
  }
  mandatory false;
 }
 leaf BWPSWITCHINGA2RSRPTHLD {
  type int16 {
   range "-156..-31";
  }
  mandatory false;
 }
 leaf CENTERUEINTERFA5RSRPTHLD2 {
  type int16 {
   range "-156..-31";
  }
  mandatory false;
 }
 leaf COVINTERFREQA1RSRPTHLD {
  type int16 {
   range "-156..-31";
  }
  mandatory false;
 }
 leaf COVINTERFREQA1RSRQTHLD {
  type int8 {
   range "-87..40";
  }
  mandatory false;
 }
 leaf COVINTERFREQA2RSRPTHLD {
  type int16 {
   range "-156..-31";
  }
  mandatory false;
 }
 leaf COVINTERFREQA2RSRQTHLD {
  type int8 {
   range "-87..40";
  }
  mandatory false;
 }
 leaf COVINTERFREQA5RSRPTHLD1 {
  type int16 {
   range "-156..-31";
  }
  mandatory false;
 }
 leaf COVINTERFREQA5RSRPTHLD2 {
  type int16 {
   range "-156..-31";
  }
  mandatory false;
 }
 leaf COVINTERFREQA5RSRQTHLD2 {
  type int8 {
   range "-87..40";
  }
  mandatory false;
 }
 leaf COVINTERFREQA5SINRTHLD2 {
  type int8 {
   range "-46..80";
  }
  mandatory false;
 }
 leaf DLDLYINTERFREQA5RSRPTHLD2 {
  type int16 {
   range "-156..-31";
  }
  mandatory false;
 }
 leaf FREQPRIINTERFA1RSRPTHLD {
  type int16 {
   range "-156..-31";
  }
  mandatory false;
 }
 leaf FREQPRIINTERFA2RSRPTHLD {
  type int16 {
   range "-156..-31";
  }
  mandatory false;
 }
 leaf FREQPRIINTERFA4RSRPTHLD {
  type int16 {
   range "-156..-31";
  }
  mandatory false;
 }
 leaf HIGHSPEEDUEA2THLDOFS {
  type int8 {
   range "-50..0";
  }
  mandatory false;
 }
 leaf INTERFBLINDREDIRA2SINRTHLD {
  type int8 {
   range "-46..80";
  }
  mandatory false;
 }
 leaf INTERFREQA1A2HYST {
  type uint8 {
   range "0..30";
  }
  mandatory false;
 }
 leaf INTERFREQA1A2TIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf INTERFREQA4A5HYST {
  type uint8 {
   range "0..30";
  }
  mandatory false;
 }
 leaf INTERFREQA4A5TIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf INTERFREQHOA3OFFSET {
  type int8 {
   range "-30..30";
  }
  mandatory false;
 }
 leaf OLD_INTERFREQHOMEASGROUPID {
  type union {
   type int8 {
    range "-1..14";
   }
  }
  mandatory false;
 }
 leaf INTERFREQHOMEASGROUPID {
  type union {
   type int8 {
    range "-1..14";
   }
  }
  mandatory false;
 }
 leaf INTERFREQMLBA4RSRPTHLD {
  type int16 {
   range "-156..-31";
  }
  mandatory false;
 }
 leaf INTRFINTERFREQHOA3RSRPOFS {
  type int8 {
   range "-20..20";
  }
  mandatory false;
 }
 leaf INTRFINTERFREQHORSRPTHLD {
  type int16 {
   range "-156..-31";
  }
  mandatory false;
 }
 leaf INTRFISOINTERFA5RSRPTHLD1 {
  type int16 {
   range "-156..-31";
  }
  mandatory false;
 }
 leaf LOWSPEEDUEOUTA2RSRPTHLD {
  type int16 {
   range "-156..-31";
  }
  mandatory false;
 }
 leaf MIIINTERFREQHOA5RSRPTHLD2 {
  type int16 {
   range "-156..-31";
  }
  mandatory false;
 }
 leaf MULTIFREQSMTSELA5RSRPTHLD2 {
  type union {
   type int16 {
    range "-156..255";
   }
  }
  mandatory false;
 }
 leaf OLD_NRCELLID {
  type union {
   type int32 {
    range "-1..65534";
   }
  }
  mandatory false;
 }
 leaf NRCELLID {
  type union {
   type int32 {
    range "-1..65534";
   }
  }
  mandatory false;
 }
 leaf OPDEDPRIHOA4RSRPTHLD {
  type int16 {
   range "-156..-31";
  }
  mandatory false;
 }
 leaf REDCAPNCDSSBA1RSRPTHLD {
  type int16 {
   range "-156..-31";
  }
  mandatory false;
 }
 leaf REDCAPNCDSSBA1SINRTHLD {
  type int8 {
   range "-46..80";
  }
  mandatory false;
 }
 leaf REDCAPNCDSSBA2RSRPTHLD {
  type int16 {
   range "-156..-31";
  }
  mandatory false;
 }
 leaf REDCAPNCDSSBA2SINRTHLD {
  type int8 {
   range "-46..80";
  }
  mandatory false;
 }
 leaf REDCAPNCDSSBA3OFFSET {
  type int8 {
   range "-30..30";
  }
  mandatory false;
 }
 leaf SPLUEFREQPRIHOA1RSRPTHLD {
  type int16 {
   range "-156..-31";
  }
  mandatory false;
 }
 leaf SPLUEFREQPRIHOA2RSRPTHLD {
  type int16 {
   range "-156..-31";
  }
  mandatory false;
 }
 leaf SPLUEFREQPRIHOA4RSRPTHLD {
  type int16 {
   range "-156..-31";
  }
  mandatory false;
 }
 leaf SPLUEULFREQPRIHOA1RSRPTHLD {
  type int16 {
   range "-156..-31";
  }
  mandatory false;
 }
 leaf SPLUEULFREQPRIHOA2RSRPTHLD {
  type int16 {
   range "-156..-31";
  }
  mandatory false;
 }
 leaf SPLUEULFREQPRIHOA4RSRPTHLD {
  type int16 {
   range "-156..-31";
  }
  mandatory false;
 }
 leaf SRVINTERFREQA4RSRPTHLD {
  type int16 {
   range "-156..-31";
  }
  mandatory false;
 }
 leaf SSBSINRINTERFREQHOA1THLD {
  type int8 {
   range "-46..80";
  }
  mandatory false;
 }
 leaf SSBSINRINTERFREQHOA2THLD {
  type int8 {
   range "-46..80";
  }
  mandatory false;
 }
 leaf ULCOVINTERFREQA5RSRPTHLD1 {
  type int16 {
   range "-156..-31";
  }
  mandatory false;
 }
 }
 grouping NRCELLINTERRHOMEAGRP-attributes {
 leaf COVHOTOEUTRANB2RSRPTHLD1 {
  type int16 {
   range "-156..-31";
  }
  mandatory false;
 }
 leaf COVHOTOEUTRANBLINDA2THLD {
  type int16 {
   range "-156..-31";
  }
  mandatory false;
 }
 leaf COVHOTOLTEBLINDA2RSRQTHLD {
  type int8 {
   range "-87..40";
  }
  mandatory false;
 }
 leaf INTERRATHOA1A2HYST {
  type uint8 {
   range "0..30";
  }
  mandatory false;
 }
 leaf INTERRATHOA1A2TIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf INTERRATHOA1RSRPTHLD {
  type int16 {
   range "-156..-31";
  }
  mandatory false;
 }
 leaf INTERRATHOA1RSRQTHLD {
  type int8 {
   range "-87..40";
  }
  mandatory false;
 }
 leaf INTERRATHOA2RSRPTHLD {
  type int16 {
   range "-156..-31";
  }
  mandatory false;
 }
 leaf INTERRATHOA2RSRQTHLD {
  type int8 {
   range "-87..40";
  }
  mandatory false;
 }
 leaf OLD_INTERRATHOMEASGROUPID {
  type union {
   type int8 {
    range "-1..14";
   }
  }
  mandatory false;
 }
 leaf INTERRATHOMEASGROUPID {
  type union {
   type int8 {
    range "-1..14";
   }
  }
  mandatory false;
 }
 leaf OLD_NRCELLID {
  type union {
   type int32 {
    range "-1..65534";
   }
  }
  mandatory false;
 }
 leaf NRCELLID {
  type union {
   type int32 {
    range "-1..65534";
   }
  }
  mandatory false;
 }
 leaf ULSINRHOEUTRANB2RSRPTHLD1 {
  type int16 {
   range "-156..-31";
  }
  mandatory false;
 }
 leaf VONREPSFBADAPTA2TIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf VONREPSFBADAPTA2RSRPTHLD {
  type int16 {
   range "-156..-31";
  }
  mandatory false;
 }
 }
 grouping NRCELLINTRAFHOMEAGRP-attributes {
 leaf HETNETINTRAFREQA3OFFSET {
  type int8 {
   range "-30..30";
  }
  mandatory false;
 }
 leaf INDROUTDROVERLAPA3OFFSET {
  type int8 {
   range "-30..30";
  }
  mandatory false;
 }
 leaf INTRAFREQCHOCANDCELLA3OFS {
  type int8 {
   range "-20..-1";
  }
  mandatory false;
 }
 leaf INTRAFREQHOA3HYST {
  type uint8 {
   range "0..30";
  }
  mandatory false;
 }
 leaf INTRAFREQHOA3OFFSET {
  type int8 {
   range "-30..30";
  }
  mandatory false;
 }
 leaf INTRAFREQHOA3TIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf INTRAFREQHOCOVEXTENDA3OFS {
  type int8 {
   range "-30..30";
  }
  mandatory false;
 }
 leaf OLD_INTRAFREQHOMEASGROUPID {
  type union {
   type int8 {
    range "-1..14";
   }
  }
  mandatory false;
 }
 leaf INTRAFREQHOMEASGROUPID {
  type union {
   type int8 {
    range "-1..14";
   }
  }
  mandatory false;
 }
 leaf OLD_NRCELLID {
  type union {
   type int32 {
    range "-1..65534";
   }
  }
  mandatory false;
 }
 leaf NRCELLID {
  type union {
   type int32 {
    range "-1..65534";
   }
  }
  mandatory false;
 }
 }
 grouping NRCELLMLB-attributes {
 leaf ARPTHLDBASEDUESELPOLICYPRI {
  type uint8 {
   range "0..255";
  }
  mandatory false;
 }
 leaf CELLDLCAPBSCALEFACTOR {
  type uint16 {
   range "1..1000";
  }
  mandatory false;
 }
 leaf CELLULCAPBSCALEFACTOR {
  type uint16 {
   range "1..1000";
  }
  mandatory false;
 }
 leaf CONNMLBUENUMTHLD {
  type uint8 {
   range "1..40";
  }
  mandatory false;
 }
 leaf DLLOADDIFFTHLD {
  type uint8 {
   range "1..100";
  }
  mandatory false;
 }
 leaf FARPOINTTHLDUESELPOLICYPRI {
  type uint8 {
   range "0..255";
  }
  mandatory false;
 }
 leaf FREQSELECTIONPOLICY {
  type boolean;
  mandatory false;
 }
 leaf IDLEMLBPOLICY {
  type boolean;
  mandatory false;
 }
 leaf IDLEMLBUENUMTHLD {
  type uint16 {
   range "1..10000";
  }
  mandatory false;
 }
 leaf INTERFREQMLBUENUMTHLD {
  type uint16 {
   range "1..10000";
  }
  mandatory false;
 }
 leaf INTERFREQMLBULUENUMTHLD {
  type uint16 {
   range "1..10000";
  }
  mandatory false;
 }
 leaf INTERRATMLBDLPRBUSAGETHLD {
  type uint8 {
   range "0..100";
  }
  mandatory false;
 }
 leaf INTERRATMLBUENUMTHLD {
  type uint16 {
   range "0..2000";
  }
  mandatory false;
 }
 leaf INTERRATMLBULPRBUSAGETHLD {
  type uint8 {
   range "0..100";
  }
  mandatory false;
 }
 leaf LOADEVALUATIONPOLICY {
  type boolean;
  mandatory false;
 }
 leaf MIMOLAYERNUMPOLICY {
  type enumeration {
   enum val-0;
   enum val-7;
  }
  mandatory false;
 }
 leaf MLBALGOENHSWITCH {
  type string;
  mandatory false;
 }
 leaf MLBDIRECTION {
  type enumeration {
   enum val-0;
   enum val-1;
   enum val-2;
  }
  mandatory false;
 }
 leaf MLBDLCCEUSAGETHLD {
  type uint8 {
   range "20..100";
  }
  mandatory false;
 }
 leaf MLBDLPRBUSAGECALCALPHA {
  type uint8 {
   range "1..240";
  }
  mandatory false;
 }
 leaf MLBDLPRBUSAGEOFFSET {
  type uint8 {
   range "0..50";
  }
  mandatory false;
 }
 leaf MLBDLPRBUSAGETHLD {
  type uint8 {
   range "1..100";
  }
  mandatory false;
 }
 leaf MLBHOADMISSIONTHLD {
  type uint8 {
   range "50..99";
  }
  mandatory false;
 }
 leaf MLBJUDGEPERIOD {
  type uint8 {
   range "0..60";
  }
  mandatory false;
 }
 leaf MLBTRIGGERMODE {
  type enumeration {
   enum val-0;
   enum val-1;
   enum val-2;
   enum val-3;
   enum val-4;
   enum val-5;
  }
  mandatory false;
 }
 leaf MLBUE5QI {
  type uint8 {
   range "0..255";
  }
  mandatory false;
 }
 leaf MLBUEDLPRBHIGHTHLDOFS {
  type int16 {
   range "-1000..1000";
  }
  mandatory false;
 }
 leaf MLBUEDLPRBLOWTHLDOFS {
  type int16 {
   range "-1000..1000";
  }
  mandatory false;
 }
 leaf MLBUENUMJUDGEFACTOR {
  type uint16 {
   range "10..1000";
  }
  mandatory false;
 }
 leaf MLBUENUMOFFSET {
  type uint16 {
   range "0..10000";
  }
  mandatory false;
 }
 leaf MLBUESELDISTANCEPOLICY {
  type boolean;
  mandatory false;
 }
 leaf MLBUESELDLPRBUSAGETHLD {
  type uint8 {
   range "0..100";
  }
  mandatory false;
 }
 leaf MLBUESELULPRBUSAGETHLD {
  type uint8 {
   range "0..100";
  }
  mandatory false;
 }
 leaf MLBUESELECTIONARPTHLD {
  type uint8 {
   range "1..15";
  }
  mandatory false;
 }
 leaf MLBUESELECTIONPOLICY {
  type string;
  mandatory false;
 }
 leaf MLBUESELECTIONRSRPTHLD {
  type int16 {
   range "-156..-31";
  }
  mandatory false;
 }
 leaf MLBUEULPRBHIGHTHLDOFS {
  type int16 {
   range "-1000..1000";
  }
  mandatory false;
 }
 leaf MLBUEULPRBLOWTHLDOFS {
  type int16 {
   range "-1000..1000";
  }
  mandatory false;
 }
 leaf MLBULCCEUSAGETHLD {
  type uint8 {
   range "20..100";
  }
  mandatory false;
 }
 leaf MLBULPRBUSAGECALCALPHA {
  type uint8 {
   range "1..120";
  }
  mandatory false;
 }
 leaf MLBULPRBUSAGEOFFSET {
  type uint8 {
   range "0..50";
  }
  mandatory false;
 }
 leaf MLBULPRBUSAGETHLD {
  type uint8 {
   range "1..100";
  }
  mandatory false;
 }
 leaf MLBULUENUMOFFSET {
  type uint16 {
   range "0..10000";
  }
  mandatory false;
 }
 leaf NRCELLID {
  type union {
   type int32 {
    range "-1..65534";
   }
  }
  mandatory false;
 }
 leaf OFFLOADMAXUENUM {
  type uint8 {
   range "1..80";
  }
  mandatory false;
 }
 leaf PRBUSAGEMLBMINUENUM {
  type uint16 {
   range "1..10000";
  }
  mandatory false;
 }
 leaf PRBUSAGETHLDUESELPOLICYPRI {
  type uint8 {
   range "0..255";
  }
  mandatory false;
 }
 leaf QCISWBASEDUESELPOLICYPRI {
  type uint8 {
   range "0..255";
  }
  mandatory false;
 }
 leaf QCITHLDBASEDUESELPOLICYPRI {
  type uint8 {
   range "0..255";
  }
  mandatory false;
 }
 leaf UENUMDIFFTHLD {
  type uint8 {
   range "0..100";
  }
  mandatory false;
 }
 leaf ULLOADDIFFTHLD {
  type uint8 {
   range "1..100";
  }
  mandatory false;
 }
 leaf ULUENUMDIFFTHLD {
  type uint8 {
   range "0..100";
  }
  mandatory false;
 }
 }
 grouping NRCELLMOBILITYCONFIG-attributes {
 leaf ABNBLINDREDIRECTA2RSRPTHLD {
  type union {
   type int16 {
    range "-156..255";
   }
  }
  mandatory false;
 }
 leaf AERIALCELLOFFSET {
  type uint8 {
   range "0..30";
  }
  mandatory false;
 }
 leaf AERIALHOALGOSWITCH {
  type string;
  mandatory false;
 }
 leaf BEAMRSRPFILTERCOEFF {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf CARRSHUTUSERMEASTIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf CELLCENTERUSERDISTHLD {
  type uint32 {
   range "0..100000";
  }
  mandatory false;
 }
 leaf CELLRSRPFILTERCOEFF {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf CHNQLTYHODELAYDIFFTHLD {
  type uint8 {
   range "0..255";
  }
  mandatory false;
 }
 leaf CHNQLTYHOMCSTHLD {
  type uint8 {
   range "0..28";
  }
  mandatory false;
 }
 leaf DAPSHOALGOSWITCH {
  type string;
  mandatory false;
 }
 leaf ENERGYEFFINTERFHODLRATETHD {
  type uint16 {
   range "0..1000";
  }
  mandatory false;
 }
 leaf FREQPRIHOTRIGGERMODE {
  type boolean;
  mandatory false;
 }
 leaf FREQPRIINTERFHORETRYINTVL {
  type enumeration {
   enum val-5;
   enum val-10;
   enum val-15;
   enum val-30;
   enum val-60;
   enum val-90;
   enum val-120;
   enum val-200;
  }
  mandatory false;
 }
 leaf HETNETDLPRBUSAGETHLD {
  type uint8 {
   range "0..100";
  }
  mandatory false;
 }
 leaf HSCELLADAPTHOOFFSETLEVEL {
  type uint8 {
   range "0..15";
  }
  mandatory false;
 }
 leaf HSCELLHOPROTECTTIMER {
  type uint8 {
   range "0..120";
  }
  mandatory false;
 }
 leaf INDROUTDRCODLPRBUSAGETHLD {
  type uint8 {
   range "0..100";
  }
  mandatory false;
 }
 leaf INTERFREQHOWAITTIME {
  type uint8 {
   range "0..120";
  }
  mandatory false;
 }
 leaf INTERFREQMEASDELAY {
  type uint8 {
   range "0..120";
  }
  mandatory false;
 }
 leaf INTERFREQMEASEVENTCONFIG {
  type boolean;
  mandatory false;
 }
 leaf INTERFREQMEASWAITTIME {
  type uint8 {
   range "1..6";
  }
  mandatory false;
 }
 leaf INTRAFEXCLUDEDCELLLISTID {
  type uint16 {
   range "0..65535";
  }
  mandatory false;
 }
 leaf INTRAFRESELCELLBLACKLISTID {
  type uint16 {
   range "0..65535";
  }
  mandatory false;
 }
 leaf INTRFISODLPRBUSAGETHLD {
  type uint8 {
   range "0..100";
  }
  mandatory false;
 }
 leaf LOWSPEEDUEOUTGOINGPOLICY {
  type enumeration {
   enum val-0;
   enum val-1;
   enum val-2;
   enum val-3;
  }
  mandatory false;
 }
 leaf MEASEXCLUDEDCELLLISTSWITCH {
  type boolean;
  mandatory false;
 }
 leaf MEASTRIGQUANTITY {
  type enumeration {
   enum val-0;
   enum val-1;
   enum val-2;
  }
  mandatory false;
 }
 leaf NRCELLDLEXPERIENCECOEFF {
  type uint16 {
   range "10..6400";
  }
  mandatory false;
 }
 leaf NRCELLID {
  type union {
   type int32 {
    range "-1..65534";
   }
  }
  mandatory false;
 }
 leaf NRCELLULEXPERIENCECOEFF {
  type uint16 {
   range "10..6400";
  }
  mandatory false;
 }
 leaf PCCANCHORFLAG {
  type boolean;
  mandatory false;
 }
 leaf PROCESSOPTSW {
  type string;
  mandatory false;
 }
 leaf SSBCONSOLIDATIONTHLD {
  type uint8 {
   range "0..127";
  }
  mandatory false;
 }
 leaf SSBNUMTOAVERAGE {
  type uint8 {
   range "2..16";
  }
  mandatory false;
 }
 leaf VOICEULCOVBASEDHOSINRTHLD {
  type int16 {
   range "-100..350";
  }
  mandatory false;
 }
 leaf VONREPSFBADAPTULSINRTHLD {
  type int8 {
   range "-100..100";
  }
  mandatory false;
 }
 }
 grouping NRCELLMULTIFSCHCOORD-attributes {
 leaf BEAMCOORDLCCETHLD {
  type uint8 {
   range "1..100";
  }
  mandatory false;
 }
 leaf BEAMCOORDEXPEVALUATEHYST {
  type int8 {
   range "-100..100";
  }
  mandatory false;
 }
 leaf BEAMCOORDLOADDIFFTHLD {
  type uint8 {
   range "0..100";
  }
  mandatory false;
 }
 leaf BEAMCOORDLOADOFFSET {
  type uint16 {
   range "1..10000";
  }
  mandatory false;
 }
 leaf BEAMCOORDLOADTHLD {
  type uint16 {
   range "1..10000";
  }
  mandatory false;
 }
 leaf BEAMCOORDPRBDIFFTHLD {
  type uint8 {
   range "0..100";
  }
  mandatory false;
 }
 leaf BEAMCOORDPRBUSAGETHLD {
  type uint8 {
   range "0..100";
  }
  mandatory false;
 }
 leaf NRCELLID {
  type union {
   type int32 {
    range "-1..65534";
   }
  }
  mandatory false;
 }
 leaf ULNIDIFFTHLD {
  type int8 {
   range "-30..30";
  }
  mandatory false;
 }
 }
 grouping NRCELLNSADCCONFIG-attributes {
 leaf CACAPUEPSCELLA2RSRPTHLDOFS {
  type int8 {
   range "-100..100";
  }
  mandatory false;
 }
 leaf DLDATASPLITDELAYTHLD {
  type uint8 {
   range "0..100";
  }
  mandatory false;
 }
 leaf DLDATASPLITPENALTYPERIOD {
  type uint16 {
   range "1..600";
  }
  mandatory false;
 }
 leaf DLDATASPLITSNOFFSET {
  type uint8 {
   range "1..100";
  }
  mandatory false;
 }
 leaf DLSPLITPREFERREDDUR {
  type uint8 {
   range "0..100";
  }
  mandatory false;
 }
 leaf HIGHDELAYSPLITPENALTYPRD {
  type uint16 {
   range "1..600";
  }
  mandatory false;
 }
 leaf NRCELLID {
  type union {
   type int32 {
    range "-1..65534";
   }
  }
  mandatory false;
 }
 leaf NRDATAVOLUMERPTCFG {
  type union {
   type uint16 {
    range "0..65535";
   }
  }
  mandatory false;
 }
 leaf NSADCALGOSWITCH {
  type string;
  mandatory false;
 }
 leaf NSADCDLSPLITLTEINITRATE {
  type uint16 {
   range "1..1000";
  }
  mandatory false;
 }
 leaf NSADCDLSPLITNRINITRATE {
  type uint8 {
   range "1..10";
  }
  mandatory false;
 }
 leaf NSADCFASTRETRANSTRIGTHLD {
  type uint16 {
   range "0..5000";
  }
  mandatory false;
 }
 leaf NSADCULFBRSRPTHLD {
  type int16 {
   range "-156..-31";
  }
  mandatory false;
 }
 leaf PSCELLA2RSRPTHLD {
  type int16 {
   range "-156..-31";
  }
  mandatory false;
 }
 leaf STOPSPLITRATERATIOTHLD {
  type uint8 {
   range "1..100";
  }
  mandatory false;
 }
 leaf STOPSPLITTIMETOTRIGGER {
  type uint8 {
   range "1..200";
  }
  mandatory false;
 }
 leaf TFCBASEDSCGRELULSINRTHLD {
  type int16 {
   range "-500..500";
  }
  mandatory false;
 }
 leaf USEREXPSCGRELA1RSRPTHLD {
  type int16 {
   range "-156..-31";
  }
  mandatory false;
 }
 leaf USEREXPSCGRELA2RSRPTHLD {
  type int16 {
   range "-156..-31";
  }
  mandatory false;
 }
 }
 grouping NRCELLNSADCCONFIGGRP-attributes {
 leaf OLD_NRCELLID {
  type union {
   type int32 {
    range "-1..65534";
   }
  }
  mandatory false;
 }
 leaf NRCELLID {
  type union {
   type int32 {
    range "-1..65534";
   }
  }
  mandatory false;
 }
 leaf OLD_NSADCCONFIGGROUPID {
  type union {
   type int8 {
    range "-1..14";
   }
  }
  mandatory false;
 }
 leaf NSADCCONFIGGROUPID {
  type union {
   type int8 {
    range "-1..14";
   }
  }
  mandatory false;
 }
 leaf PSCELLA2RSRPTHLDOFFSET {
  type int8 {
   range "-100..100";
  }
  mandatory false;
 }
 leaf PSCELLA2RSRQTHLD {
  type int8 {
   range "-87..40";
  }
  mandatory false;
 }
 leaf PSCELLA2SINRTHLD {
  type int8 {
   range "-46..80";
  }
  mandatory false;
 }
 leaf PSCELLA2TIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 }
 grouping NRCELLNSGRP-attributes {
 leaf CELLRESID {
  type union {
   type uint8 {
    range "0..255";
   }
  }
  mandatory false;
 }
 leaf OLD_NRCELLID {
  type union {
   type int32 {
    range "-1..65534";
   }
  }
  mandatory false;
 }
 leaf NRCELLID {
  type union {
   type int32 {
    range "-1..65534";
   }
  }
  mandatory false;
 }
 leaf NSGRPDESCRIPTION {
  type string {
   length "0..127";
  }
  mandatory false;
 }
 leaf OLD_NSGRPID {
  type union {
   type int8 {
    range "-1..31";
   }
  }
  mandatory false;
 }
 leaf NSGRPID {
  type union {
   type int8 {
    range "-1..31";
   }
  }
  mandatory false;
 }
 }
 grouping NRCELLNSGRPNS-attributes {
 leaf NRCELLID {
  type union {
   type int32 {
    range "-1..65534";
   }
  }
  mandatory false;
 }
 leaf NSGRPID {
  type union {
   type int8 {
    range "-1..31";
   }
  }
  mandatory false;
 }
 leaf OPERATORID {
  type union {
   type int8 {
    range "-1..11";
   }
  }
  mandatory false;
 }
 leaf SLICEDIFFERENTIATOR {
  type union {
   type int32 {
    range "-1..16777215";
   }
  }
  mandatory false;
 }
 leaf SLICESERVICETYPE {
  type union {
   type int16 {
    range "-1..255";
   }
  }
  mandatory false;
 }
 }
 grouping NRCELLOAMPARAM-attributes {
 leaf NRCELLID {
  type union {
   type int32 {
    range "-1..65534";
   }
  }
  mandatory false;
 }
 leaf SERVICETYPETAG {
  type enumeration {
   enum val-0;
   enum val-1;
   enum val-2;
   enum val-3;
  }
  mandatory false;
 }
 leaf SIGCHRCTRLSTATESELMAXUENUM {
  type uint16 {
   range "0..400";
  }
  mandatory false;
 }
 leaf SIGCHRCTRLSTATEUENUMTHLD {
  type union {
   type uint16 {
    range "0..65535";
   }
  }
  mandatory false;
 }
 }
 grouping NRCELLOPPOLICY-attributes {
 leaf EPSFBMODE {
  type enumeration {
   enum val-0;
   enum val-1;
   enum val-2;
  }
  mandatory false;
 }
 leaf EUTRANA1A2B2RSRPTHLDOFS {
  type int8 {
   range "-100..100";
  }
  mandatory false;
 }
 leaf EUTRANCIOOFFSET {
  type int8 {
   range "-20..20";
  }
  mandatory false;
 }
 leaf FREQCONFIGPOLICYSWITCH {
  type string;
  mandatory false;
 }
 leaf INTERRATHOPOLICYSWITCH {
  type string;
  mandatory false;
 }
 leaf OLD_NRCELLID {
  type union {
   type int32 {
    range "-1..65534";
   }
  }
  mandatory false;
 }
 leaf NRCELLID {
  type union {
   type int32 {
    range "-1..65534";
   }
  }
  mandatory false;
 }
 leaf OLD_OPERATORID {
  type union {
   type int8 {
    range "-1..11";
   }
  }
  mandatory false;
 }
 leaf OPERATORID {
  type union {
   type int8 {
    range "-1..11";
   }
  }
  mandatory false;
 }
 leaf PSCELLA2RSRPTHLDOFFSET {
  type int8 {
   range "-20..20";
  }
  mandatory false;
 }
 leaf REDCAPGNBFREQPRIGROUPID {
  type uint8 {
   range "0..255";
  }
  mandatory false;
 }
 leaf ULVOICEALIVECONTDUR {
  type uint16 {
   range "1..3600";
  }
  mandatory false;
 }
 leaf ULVOICEALIVEINTERV {
  type uint8 {
   range "3..30";
  }
  mandatory false;
 }
 leaf ULVOICEJITTERELIMINATETIME {
  type uint8 {
   range "0..10";
  }
  mandatory false;
 }
 leaf VOICEPOLICYSWITCH {
  type string;
  mandatory false;
 }
 leaf GNBDIFFUSEREXPGROUPID {
  type union {
   type uint8 {
    range "0..255";
   }
  }
  mandatory false;
 }
 leaf GNBFREQPRIORITYGROUPID {
  type uint8 {
   range "0..255";
  }
  mandatory false;
 }
 }
 grouping NRCELLOPQCIBEARER-attributes {
 leaf AMPDCPPARAMGROUPID {
  type uint8 {
   range "0..165";
  }
  mandatory false;
 }
 leaf OLD_NRCELLID {
  type union {
   type int32 {
    range "-1..65534";
   }
  }
  mandatory false;
 }
 leaf NRCELLID {
  type union {
   type int32 {
    range "-1..65534";
   }
  }
  mandatory false;
 }
 leaf OLD_OPERATORID {
  type union {
   type int8 {
    range "-1..11";
   }
  }
  mandatory false;
 }
 leaf OPERATORID {
  type union {
   type int8 {
    range "-1..11";
   }
  }
  mandatory false;
 }
 leaf OLD_QCI {
  type union {
   type int16 {
    range "-1..255";
   }
  }
  mandatory false;
 }
 leaf QCI {
  type union {
   type int16 {
    range "-1..255";
   }
  }
  mandatory false;
 }
 leaf RLCMODE {
  type enumeration {
   enum val-1;
   enum val-2;
  }
  mandatory false;
 }
 leaf UMPDCPPARAMGROUPID {
  type uint8 {
   range "0..165";
  }
  mandatory false;
 }
 }
 grouping NRCELLOPRFSP-attributes {
 leaf OLD_NRCELLID {
  type union {
   type int32 {
    range "-1..65534";
   }
  }
  mandatory false;
 }
 leaf NRCELLID {
  type union {
   type int32 {
    range "-1..65534";
   }
  }
  mandatory false;
 }
 leaf OLD_OPERATORID {
  type union {
   type int8 {
    range "-1..11";
   }
  }
  mandatory false;
 }
 leaf OPERATORID {
  type union {
   type int8 {
    range "-1..11";
   }
  }
  mandatory false;
 }
 leaf RFSPGRPCELLRESID {
  type union {
   type uint8 {
    range "0..255";
   }
  }
  mandatory false;
 }
 leaf OLD_RFSPINDEX {
  type union {
   type int16 {
    range "-1..256";
   }
  }
  mandatory false;
 }
 leaf RFSPINDEX {
  type union {
   type int16 {
    range "-1..256";
   }
  }
  mandatory false;
 }
 }
 grouping NRCELLPSPOLICYGRP-attributes {
 leaf OLD_NRCELLID {
  type union {
   type int32 {
    range "-1..65534";
   }
  }
  mandatory false;
 }
 leaf NRCELLID {
  type union {
   type int32 {
    range "-1..65534";
   }
  }
  mandatory false;
 }
 leaf OLD_POWERSAVINGPOLICYGRPINDEX {
  type union {
   type int8 {
    range "-1..4";
   }
  }
  mandatory false;
 }
 leaf POWERSAVINGPOLICYGRPINDEX {
  type union {
   type int8 {
    range "-1..4";
   }
  }
  mandatory false;
 }
 leaf SERVTYPEDYNEXITPWRSAVINGSW {
  type string;
  mandatory false;
 }
 leaf USERIDENTMETHOD {
  type boolean;
  mandatory false;
 }
 }
 grouping NRCELLQCIBEARER-attributes {
 leaf AMPDCPPARAMGROUPID {
  type uint8 {
   range "0..165";
  }
  mandatory false;
 }
 leaf DRXPARAMGROUPID {
  type union {
   type uint8 {
    range "0..255";
   }
  }
  mandatory false;
 }
 leaf FLOWCTRLPARAMGROUPID {
  type uint8 {
   range "0..160";
  }
  mandatory false;
 }
 leaf HOQOSFLOWCONFLPROCSTRAT {
  type string;
  mandatory false;
 }
 leaf INTERFREQHOMEASGROUPID {
  type uint8 {
   range "0..14";
  }
  mandatory false;
 }
 leaf INTERRHOTOEUTRANMEASGRPID {
  type uint8 {
   range "0..14";
  }
  mandatory false;
 }
 leaf INTERRATHOMEASGROUPID {
  type uint8 {
   range "0..14";
  }
  mandatory false;
 }
 leaf INTRAFREQHOMEASGROUPID {
  type uint8 {
   range "0..14";
  }
  mandatory false;
 }
 leaf LSUEINTERFREQHOMEASGRPID {
  type union {
   type uint8 {
    range "0..255";
   }
  }
  mandatory false;
 }
 leaf LSUEINTRAFREQHOMEASGRPID {
  type union {
   type uint8 {
    range "0..255";
   }
  }
  mandatory false;
 }
 leaf MLBALGOSWITCH {
  type string;
  mandatory false;
 }
 leaf MLBDETECTTIME {
  type uint8 {
   range "1..60";
  }
  mandatory false;
 }
 leaf MLBDLBFRSIZE {
  type uint32 {
   range "1..4294967295";
  }
  mandatory false;
 }
 leaf MLBDLTHPTTHLD {
  type uint32 {
   range "1..4294967295";
  }
  mandatory false;
 }
 leaf MLBULBSRDATASIZE {
  type uint32 {
   range "1..4294967295";
  }
  mandatory false;
 }
 leaf MLBULTHPTTHLD {
  type uint32 {
   range "1..4294967295";
  }
  mandatory false;
 }
 leaf OLD_NRCELLID {
  type union {
   type int32 {
    range "-1..65534";
   }
  }
  mandatory false;
 }
 leaf NRCELLID {
  type union {
   type int32 {
    range "-1..65534";
   }
  }
  mandatory false;
 }
 leaf NSADCCONFIGGROUPID {
  type uint8 {
   range "0..14";
  }
  mandatory false;
 }
 leaf NSAINTERFREQHOMEASGROUPID {
  type uint8 {
   range "0..14";
  }
  mandatory false;
 }
 leaf OLD_QCI {
  type union {
   type int16 {
    range "-1..255";
   }
  }
  mandatory false;
 }
 leaf QCI {
  type union {
   type int16 {
    range "-1..255";
   }
  }
  mandatory false;
 }
 leaf QCIALGOPARAMGROUPID {
  type union {
   type uint16 {
    range "0..65535";
   }
  }
  mandatory false;
 }
 leaf QCICAFREQGRPIDLIST {
  type uint32 {
   range "0..4294967295";
  }
  mandatory false;
 }
 leaf REDCAPDRXPARAMGROUPID {
  type union {
   type uint8 {
    range "0..255";
   }
  }
  mandatory false;
 }
 leaf REDCAPGNBFREQPRIGROUPID {
  type uint8 {
   range "0..255";
  }
  mandatory false;
 }
 leaf RLCMODE {
  type enumeration {
   enum val-1;
   enum val-2;
  }
  mandatory false;
 }
 leaf SERVICEDIFFALGOSWITCH {
  type string;
  mandatory false;
 }
 leaf TRAFFICRELDELAYTMR {
  type uint16 {
   range "0..65000";
  }
  mandatory false;
 }
 leaf UEDIFFCONFIGGRPID {
  type union {
   type uint8 {
    range "0..255";
   }
  }
  mandatory false;
 }
 leaf UMPDCPPARAMGROUPID {
  type uint8 {
   range "0..165";
  }
  mandatory false;
 }
 leaf WTCPALGOSW {
  type string;
  mandatory false;
 }
 leaf WTCPPARAGROUPID {
  type uint8 {
   range "0..9";
  }
  mandatory false;
 }
 leaf GNBFREQPRIORITYGROUPID {
  type uint8 {
   range "0..255";
  }
  mandatory false;
 }
 }
 grouping NRCELLREDCAP-attributes {
 leaf CONNMEASRELAXSINRTHLD {
  type uint8 {
   range "3..10";
  }
  mandatory false;
 }
 leaf FASTMOVEUECAMPCELLNUMTHLD {
  type uint8 {
   range "1..10";
  }
  mandatory false;
 }
 leaf FASTMOVEUECAMPDURTHLD {
  type uint16 {
   range "0..300";
  }
  mandatory false;
 }
 leaf NRCELLID {
  type union {
   type int32 {
    range "-1..65534";
   }
  }
  mandatory false;
 }
 leaf REDCAPALGOSWITCH {
  type string;
  mandatory false;
 }
 leaf REDCAPULEXPINTERFA5RSRPTH1 {
  type int16 {
   range "-156..-31";
  }
  mandatory false;
 }
 leaf REDCAPULEXPINTERFA5RSRPTH2 {
  type int8 {
   range "-110..-31";
  }
  mandatory false;
 }
 leaf ULEXPBASEDINTERFHOSINRTHLD {
  type int16 {
   range "-100..380";
  }
  mandatory false;
 }
 leaf ULEXPIFHOCCEALLOCULFAILTH {
  type uint8 {
   range "0..30";
  }
  mandatory false;
 }
 leaf ULEXPIFHOSERVPARAMGROUPID {
  type uint8 {
   range "0..1";
  }
  mandatory false;
 }
 leaf ULEXPIFHOULPRBUSAGETHLD {
  type uint8 {
   range "0..70";
  }
  mandatory false;
 }
 }
 grouping NRCELLRELATION-attributes {
 leaf ANRFLAG {
  type boolean;
  mandatory false;
 }
 leaf BLINDHOFLAG {
  type string;
  mandatory false;
 }
 leaf BLINDHOPRIORITY {
  type uint8 {
   range "0..16";
  }
  mandatory false;
 }
 leaf BLINDSCELLCONFIGFLAG {
  type boolean;
  mandatory false;
 }
 leaf CELLID {
  type union {
   type int16 {
    range "-1..16383";
   }
  }
  mandatory false;
 }
 leaf CELLINDIVIDUALOFFSET {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf COOPCELLPRI {
  type uint8 {
   range "0..10";
  }
  mandatory false;
 }
 leaf CTRLMODE {
  type boolean;
  mandatory false;
 }
 leaf HETNETCOORDCELLFLAG {
  type enumeration {
   enum val-0;
   enum val-1;
   enum val-2;
  }
  mandatory false;
 }
 leaf HIGHSPEEDINTRFAVOIDFLAG {
  type boolean;
  mandatory false;
 }
 leaf HOALGOSWITCH {
  type string;
  mandatory false;
 }
 leaf INTERGNODEBFLAG {
  type boolean;
  mandatory false;
 }
 leaf INTERGNODEBSULFLAG {
  type boolean;
  mandatory false;
 }
 leaf MCC {
  type string {
   length "3";
  }
  mandatory false;
 }
 leaf MLBHOFLAG {
  type boolean;
  mandatory false;
 }
 leaf MNC {
  type string {
   length "2..3";
  }
  mandatory false;
 }
 leaf NCELLCLASSLABEL {
  type boolean;
  mandatory false;
 }
 leaf NCELLRESELOFFSET {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf NOHOFLAG {
  type enumeration {
   enum val-0;
   enum val-1;
   enum val-2;
   enum val-3;
   enum val-4;
  }
  mandatory false;
 }
 leaf NORMVFLAG {
  type boolean;
  mandatory false;
 }
 leaf NRCELLID {
  type union {
   type int32 {
    range "-1..65534";
   }
  }
  mandatory false;
 }
 leaf OVERLAPRATE {
  type uint8 {
   range "10..100";
  }
  mandatory false;
 }
 leaf POWERSAVINGCELLFLAG {
  type enumeration {
   enum val-0;
   enum val-1;
   enum val-2;
  }
  mandatory false;
 }
 leaf GNBID {
  type union {
   type int64 {
    range "-1..4294967295";
   }
  }
  mandatory false;
 }
 }
 grouping NRCELLRES-attributes {
 leaf OLD_CELLRESID {
  type union {
   type int8 {
    range "-1..31";
   }
  }
  mandatory false;
 }
 leaf CELLRESID {
  type union {
   type int8 {
    range "-1..31";
   }
  }
  mandatory false;
 }
 leaf MAXRRCCONNUSERNUM {
  type uint16 {
   range "0..65534";
  }
  mandatory false;
 }
 leaf OLD_NRCELLID {
  type union {
   type int32 {
    range "-1..65534";
   }
  }
  mandatory false;
 }
 leaf NRCELLID {
  type union {
   type int32 {
    range "-1..65534";
   }
  }
  mandatory false;
 }
 }
 grouping NRCELLRESELCONFIG-attributes {
 leaf ADDLHYSTFORHIGHMOB {
  type enumeration {
   enum val-0;
   enum val-1;
   enum val-2;
   enum val-3;
  }
  mandatory false;
 }
 leaf ADDLHYSTFORMEDIUMMOB {
  type enumeration {
   enum val-0;
   enum val-1;
   enum val-2;
   enum val-3;
  }
  mandatory false;
 }
 leaf CANDIDATECELLTHLD {
  type enumeration {
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf CELLRESELHYSTERESIS {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf CELLRESELPRIORITY {
  type uint8 {
   range "0..7";
  }
  mandatory false;
 }
 leaf CELLRESELSUBPRIORITY {
  type enumeration {
   enum val-0;
   enum val-2;
   enum val-4;
   enum val-6;
   enum val-8;
  }
  mandatory false;
 }
 leaf EUTRANCELLRESELTIMER {
  type union {
   type uint8 {
    range "0..255";
   }
  }
  mandatory false;
 }
 leaf INTRAFREQMEASSTARTTHLD {
  type uint8 {
   range "0..31";
  }
  mandatory false;
 }
 leaf MAXUETRANSMITPOWER {
  type union {
   type int16 {
    range "-30..255";
   }
  }
  mandatory false;
 }
 leaf MINIMUMRXLEVEL {
  type int8 {
   range "-70..-22";
  }
  mandatory false;
 }
 leaf MOBSTATEEVALPERIOD {
  type enumeration {
   enum val-0;
   enum val-1;
   enum val-2;
   enum val-3;
   enum val-4;
  }
  mandatory false;
 }
 leaf NONINTRAFREQMEASRSRPTHLD {
  type uint8 {
   range "0..31";
  }
  mandatory false;
 }
 leaf NONINTRAFREQMEASRSRQTHLD {
  type uint8 {
   range "0..31";
  }
  mandatory false;
 }
 leaf NRCELLID {
  type union {
   type int32 {
    range "-1..65534";
   }
  }
  mandatory false;
 }
 leaf RESELTHLDFORHIGHMOB {
  type uint8 {
   range "1..16";
  }
  mandatory false;
 }
 leaf RESELTHLDFORMEDIUMMOB {
  type uint8 {
   range "1..16";
  }
  mandatory false;
 }
 leaf RESELTIMESFFORHIGHMOB {
  type enumeration {
   enum val-0;
   enum val-1;
   enum val-2;
   enum val-3;
  }
  mandatory false;
 }
 leaf RESELTIMESFFORMEDIUMMOB {
  type enumeration {
   enum val-0;
   enum val-1;
   enum val-2;
   enum val-3;
  }
  mandatory false;
 }
 leaf RRMRELAXLSUEJUDGETIMER {
  type enumeration {
   enum val-0;
   enum val-1;
   enum val-2;
   enum val-3;
   enum val-4;
   enum val-5;
   enum val-6;
   enum val-7;
   enum val-8;
  }
  mandatory false;
 }
 leaf RRMRELAXLSUERSRPDIFFTHLD {
  type enumeration {
   enum val-0;
   enum val-1;
   enum val-2;
   enum val-3;
   enum val-4;
  }
  mandatory false;
 }
 leaf RRMRELAXNONEDGERSRPTHLD {
  type uint8 {
   range "0..31";
  }
  mandatory false;
 }
 leaf SERVFREQLOWPRIRSRPRESELTHD {
  type uint8 {
   range "0..31";
  }
  mandatory false;
 }
 leaf SERVFREQLOWPRIRSRQRESELTHD {
  type uint8 {
   range "0..31";
  }
  mandatory false;
 }
 leaf SIBOPTIONALIEIND {
  type string;
  mandatory false;
 }
 leaf SSBCONSOLIDATIONTHLD {
  type uint8 {
   range "0..127";
  }
  mandatory false;
 }
 leaf SSBNUMTOAVERAGE {
  type uint8 {
   range "2..16";
  }
  mandatory false;
 }
 }
 grouping NRCELLSERVEXP-attributes {
 leaf HIGHLOADUSERNUMTHLD {
  type union {
   type uint16 {
    range "100..65535";
   }
  }
  mandatory false;
 }
 leaf INTERHONOGAPRSRPOFS {
  type uint8 {
   range "0..20";
  }
  mandatory false;
 }
 leaf NRCELLID {
  type union {
   type int32 {
    range "-1..65534";
   }
  }
  mandatory false;
 }
 leaf NRCELLUSAGESCENARIO {
  type enumeration {
   enum val-0;
   enum val-1;
   enum val-2;
   enum val-3;
   enum val-4;
   enum val-5;
   enum val-6;
   enum val-7;
  }
  mandatory false;
 }
 leaf RRCRESUMEMEASDELAY {
  type uint8 {
   range "0..80";
  }
  mandatory false;
 }
 leaf SIPTIMEOUTPROTECTTIMER {
  type uint8 {
   range "3..15";
  }
  mandatory false;
 }
 leaf SPDTURBOALGOSWITCH {
  type string;
  mandatory false;
 }
 leaf SPDTURBOFLAGVALIDITYPERIOD {
  type uint16 {
   range "2..900";
  }
  mandatory false;
 }
 leaf STINTERFREQMEASDELAY {
  type union {
   type uint8 {
    range "0..255";
   }
  }
  mandatory false;
 }
 leaf UDCBUFFERSIZE {
  type enumeration {
   enum val-0;
   enum val-1;
   enum val-2;
  }
  mandatory false;
 }
 leaf VINRDLJITTERELIMINATEDUR {
  type enumeration {
   enum val-0;
   enum val-1;
   enum val-2;
   enum val-3;
  }
  mandatory false;
 }
 leaf VOICEALGOSWITCH {
  type string;
  mandatory false;
 }
 leaf VONRAIRTIMEOUTEPSFBTIMER {
  type uint8 {
   range "0..50";
  }
  mandatory false;
 }
 leaf VONRQLTYEUTRANB1RSRPTHLD {
  type int16 {
   range "-140..-43";
  }
  mandatory false;
 }
 leaf VONRQLTYEUTRANB1RSRQTHLD {
  type int8 {
   range "-40..-6";
  }
  mandatory false;
 }
 leaf VONRQLTYINTERFA5RSRQTHLD {
  type int8 {
   range "-87..40";
  }
  mandatory false;
 }
 leaf VONRQLTYINTERFA5SINRTHLD {
  type int8 {
   range "-46..80";
  }
  mandatory false;
 }
 leaf VONRQLTYLNTERFA5RSRPTHLD2 {
  type int16 {
   range "-156..-31";
  }
  mandatory false;
 }
 }
 grouping NRCELLSMARTMULTICARR-attributes {
 leaf COVGRIDMODELAPPPOLICY {
  type boolean;
  mandatory false;
 }
 leaf HOPROTECTALGOSWITCH {
  type string;
  mandatory false;
 }
 leaf LNRHOSUCCRATEPROTECTTHLD {
  type uint16 {
   range "0..1000";
  }
  mandatory false;
 }
 leaf LNRMULTICARRIERALGOSWITCH {
  type string;
  mandatory false;
 }
 leaf MODELBUILDINGSWITCH {
  type string;
  mandatory false;
 }
 leaf NRCELLID {
  type union {
   type int32 {
    range "-1..65534";
   }
  }
  mandatory false;
 }
 leaf NRIFHOSUCCRATEPROTECTTHLD {
  type uint16 {
   range "0..1000";
  }
  mandatory false;
 }
 leaf NRMULTICARRIERALGOSWITCH {
  type string;
  mandatory false;
 }
 leaf PREDACCUFORDATATHLD {
  type enumeration {
   enum val-0;
   enum val-1;
   enum val-2;
   enum val-3;
  }
  mandatory false;
 }
 leaf PREDACCUFORVOICETHLD {
  type enumeration {
   enum val-0;
   enum val-1;
   enum val-2;
  }
  mandatory false;
 }
 leaf ULSPCTEFFPREDACCUTHLD {
  type uint8 {
   range "10..90";
  }
  mandatory false;
 }
 }
 grouping NRCELLSULFREQUENCY-attributes {
 leaf OLD_NRCELLID {
  type union {
   type int32 {
    range "-1..65534";
   }
  }
  mandatory false;
 }
 leaf NRCELLID {
  type union {
   type int32 {
    range "-1..65534";
   }
  }
  mandatory false;
 }
 leaf SSBFREQPOS {
  type union {
   type uint32 {
    range "1901..434000";
   }
  }
  mandatory false;
 }
 leaf OLD_SULFREQINDEX {
  type union {
   type int8 {
    range "-1..0";
   }
  }
  mandatory false;
 }
 leaf SULFREQINDEX {
  type union {
   type int8 {
    range "-1..0";
   }
  }
  mandatory false;
 }
 leaf SULINTERFREQA5RSRPTHLD2 {
  type int16 {
   range "-156..-31";
  }
  mandatory false;
 }
 leaf SULSSBSINROFFSET {
  type uint8 {
   range "5..50";
  }
  mandatory false;
 }
 leaf SULSSBSINRTHLD {
  type enumeration {
   enum val-0;
   enum val-1;
   enum val-2;
   enum val-3;
   enum val-4;
   enum val-5;
   enum val-6;
   enum val-7;
   enum val-8;
   enum val-9;
   enum val-10;
   enum val-11;
   enum val-12;
   enum val-13;
  }
  mandatory false;
 }
 }
 grouping NRCELLUSERMEASCFG-attributes {
 leaf OLD_ALGOEVENTTYPE {
  type enumeration {
   enum val--1;
   enum val-0;
   enum val-1;
  }
  mandatory false;
 }
 leaf ALGOEVENTTYPE {
  type enumeration {
   enum val--1;
   enum val-0;
   enum val-1;
  }
  mandatory false;
 }
 leaf OLD_NRCELLID {
  type union {
   type int32 {
    range "-1..65534";
   }
  }
  mandatory false;
 }
 leaf NRCELLID {
  type union {
   type int32 {
    range "-1..65534";
   }
  }
  mandatory false;
 }
 leaf RSRPTHLDOFFSET {
  type int8 {
   range "-50..50";
  }
  mandatory false;
 }
 leaf TIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf OLD_USERTYPE {
  type enumeration {
   enum val--1;
   enum val-0;
  }
  mandatory false;
 }
 leaf USERTYPE {
  type enumeration {
   enum val--1;
   enum val-0;
  }
  mandatory false;
 }
 }
 grouping NRDUCELL-attributes {
 leaf TEMPLATENAME {
  type string;
  mandatory false;
 }
 leaf ADDITIONALFREQUENCYBAND {
  type enumeration {
   enum val-0;
   enum val-2;
   enum val-25;
   enum val-38;
   enum val-41;
   enum val-77;
   enum val-78;
   enum val-257;
   enum val-258;
   enum val-261;
  }
  mandatory false;
 }
 leaf AERIALCELLFLAG {
  type enumeration {
   enum val-0;
   enum val-1;
   enum val-2;
  }
  mandatory false;
 }
 leaf CELLADMINSTATE {
  type enumeration {
   enum val-0;
   enum val-1;
   enum val-2;
   enum val-3;
  }
  mandatory false;
 }
 leaf CELLBARRED {
  type boolean;
  mandatory false;
 }
 leaf CELLID {
  type union {
   type uint16 {
    range "0..65535";
   }
  }
  mandatory false;
 }
 leaf CELLRADIUS {
  type uint32 {
   range "1..100000";
  }
  mandatory false;
 }
 leaf CUSTOMIZEDBWCONFIGIND {
  type enumeration {
   enum val-0;
   enum val-1;
   enum val-2;
   enum val-3;
  }
  mandatory false;
 }
 leaf CUSTOMIZEDDLBANDWIDTH {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf CUSTOMIZEDULBANDWIDTH {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf CYCLICPREFIXLENGTH {
  type boolean;
  mandatory false;
 }
 leaf DEPLOYPOSITION {
  type boolean;
  mandatory false;
 }
 leaf DLBANDWIDTH {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf DLNARFCN {
  type union {
   type uint32 {
    range "123400..2279165";
   }
  }
  mandatory false;
 }
 leaf DUPLEXMODE {
  type enumeration {
   enum val-0;
   enum val-1;
   enum val-2;
   enum val-3;
  }
  mandatory false;
 }
 leaf FREQUENCYBAND {
  type enumeration {
   enum val-1;
   enum val-2;
   enum val-3;
   enum val-5;
   enum val-7;
   enum val-8;
   enum val-12;
   enum val-13;
   enum val-20;
   enum val-25;
   enum val-28;
   enum val-38;
   enum val-39;
   enum val-40;
   enum val-41;
   enum val-66;
   enum val-71;
   enum val-75;
   enum val-77;
   enum val-78;
   enum val-79;
   enum val-80;
   enum val-81;
   enum val-82;
   enum val-83;
   enum val-84;
   enum val-86;
   enum val-89;
   enum val-97;
   enum val-197;
   enum val-198;
   enum val-199;
   enum val-257;
   enum val-258;
   enum val-260;
   enum val-261;
  }
  mandatory false;
 }
 leaf HIGHSPEEDFLAG {
  type boolean;
  mandatory false;
 }
 leaf IABNODEID {
  type uint16 {
   range "0..65534";
  }
  mandatory false;
 }
 leaf LAMPSITECELLFLAG {
  type boolean;
  mandatory false;
 }
 leaf LOGICALROOTSEQUENCEINDEX {
  type union {
   type uint16 {
    range "0..65535";
   }
  }
  mandatory false;
 }
 leaf OLD_NRDUCELLID {
  type union {
   type int32 {
    range "-1..65534";
   }
  }
  mandatory false;
 }
 leaf NRDUCELLID {
  type union {
   type int32 {
    range "-1..65534";
   }
  }
  mandatory false;
 }
 leaf NRDUCELLNAME {
  type string {
   length "1..99";
  }
  mandatory false;
 }
 leaf NRDUCELLNETWORKINGMODE {
  type enumeration {
   enum val-0;
   enum val-1;
   enum val-2;
   enum val-3;
  }
  mandatory false;
 }
 leaf PEERCELLSLOTASSIGNMENT {
  type enumeration {
   enum val-0;
   enum val-1;
   enum val-2;
  }
  mandatory false;
 }
 leaf PHYSICALCELLID {
  type uint16 {
   range "0..1007";
  }
  mandatory false;
 }
 leaf PRACHFREQSTARTPOSITION {
  type union {
   type uint16 {
    range "0..65535";
   }
  }
  mandatory false;
 }
 leaf RANNOTIFICATIONAREAID {
  type union {
   type uint16 {
    range "0..65535";
   }
  }
  mandatory false;
 }
 leaf SCENARIOPOLICY {
  type enumeration {
   enum val-0;
   enum val-1;
   enum val-2;
  }
  mandatory false;
 }
 leaf SIB1PERIOD {
  type enumeration {
   enum val-0;
   enum val-1;
   enum val-2;
   enum val-3;
  }
  mandatory false;
 }
 leaf SIBCONFIGID {
  type uint8 {
   range "0..10";
  }
  mandatory false;
 }
 leaf SLOTASSIGNMENT {
  type enumeration {
   enum val-1;
   enum val-2;
   enum val-3;
   enum val-4;
   enum val-5;
   enum val-7;
   enum val-8;
  }
  mandatory false;
 }
 leaf SLOTSTRUCTURE {
  type enumeration {
   enum val-1;
   enum val-2;
   enum val-3;
   enum val-4;
   enum val-5;
   enum val-6;
   enum val-18;
   enum val-21;
   enum val-22;
   enum val-23;
   enum val-32;
   enum val-51;
   enum val-52;
   enum val-53;
   enum val-54;
   enum val-55;
   enum val-56;
   enum val-81;
   enum val-82;
   enum val-83;
   enum val-84;
   enum val-85;
   enum val-86;
   enum val-101;
   enum val-102;
   enum val-103;
   enum val-104;
   enum val-105;
   enum val-106;
   enum val-201;
   enum val-202;
   enum val-203;
   enum val-204;
   enum val-205;
   enum val-206;
   enum val-207;
   enum val-208;
   enum val-209;
   enum val-210;
   enum val-221;
   enum val-518;
   enum val-602;
   enum val-818;
   enum val-1017;
   enum val-4108;
   enum val-6660;
   enum val-19458;
  }
  mandatory false;
 }
 leaf SMTCDURATION {
  type enumeration {
   enum val-0;
   enum val-1;
   enum val-2;
   enum val-3;
   enum val-4;
  }
  mandatory false;
 }
 leaf SMTCPERIOD {
  type enumeration {
   enum val-0;
   enum val-1;
   enum val-2;
   enum val-3;
   enum val-4;
   enum val-5;
  }
  mandatory false;
 }
 leaf SSBDESCMETHOD {
  type boolean;
  mandatory false;
 }
 leaf SSBFREQPOS {
  type union {
   type uint32 {
    range "2..2279165";
   }
  }
  mandatory false;
 }
 leaf SSBPERIOD {
  type enumeration {
   enum val-5;
   enum val-10;
   enum val-20;
   enum val-40;
   enum val-80;
   enum val-160;
  }
  mandatory false;
 }
 leaf SSBSUBCARRIERSPACING {
  type enumeration {
   enum val-0;
   enum val-1;
   enum val-3;
   enum val-4;
  }
  mandatory false;
 }
 leaf SSBTIMEPOS {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf SUBCARRIERSPACING {
  type enumeration {
   enum val-0;
   enum val-1;
   enum val-3;
  }
  mandatory false;
 }
 leaf SUPPLEMENTARYCELLIND {
  type enumeration {
   enum val-0;
   enum val-1;
   enum val-2;
   enum val-3;
  }
  mandatory false;
 }
 leaf TAOFFSET {
  type enumeration {
   enum val-0;
   enum val-1;
   enum val-2;
  }
  mandatory false;
 }
 leaf TRACKINGAREAID {
  type uint16 {
   range "0..65535";
  }
  mandatory false;
 }
 leaf TRIDCOMMMODE {
  type enumeration {
   enum val-0;
   enum val-1;
   enum val-2;
  }
  mandatory false;
 }
 leaf ULBANDWIDTH {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-4294967295;
  }
  mandatory false;
 }
 leaf ULNARFCN {
  type union {
   type uint32 {
    range "0..2279165";
   }
  }
  mandatory false;
 }
 leaf ULPUNCTUREDRBNUMOFFSET {
  type uint8 {
   range "0..2";
  }
  mandatory false;
 }
 }
 grouping NRDUCELL3DEIRPTHLD-attributes {
 leaf ABSOLUTEEIRPCONTROLTHLD {
  type union {
   type uint16 {
    range "0..65535";
   }
  }
  mandatory false;
 }
 leaf ABSOLUTEPOWERCONTROLTHLD {
  type union {
   type uint32 {
    range "0..4294967295";
   }
  }
  mandatory false;
 }
 leaf OLD_GRIDGROUPNO {
  type union {
   type int8 {
    range "-1..27";
   }
  }
  mandatory false;
 }
 leaf GRIDGROUPNO {
  type union {
   type int8 {
    range "-1..27";
   }
  }
  mandatory false;
 }
 leaf OLD_NRDUCELLTRPID {
  type union {
   type int32 {
    range "-1..65534";
   }
  }
  mandatory false;
 }
 leaf NRDUCELLTRPID {
  type union {
   type int32 {
    range "-1..65534";
   }
  }
  mandatory false;
 }
 leaf POWERCONTROLTHRESHOLD {
  type uint8 {
   range "0..100";
  }
  mandatory false;
 }
 }
 grouping NRDUCELLAIALGO-attributes {
 leaf AIAMCALGOSWITCH {
  type string;
  mandatory false;
 }
 leaf DLSUPREDICTERRORUPPERLIMIT {
  type uint8 {
   range "3..10";
  }
  mandatory false;
 }
 leaf NRDUCELLID {
  type union {
   type int32 {
    range "-1..65534";
   }
  }
  mandatory false;
 }
 leaf ULSUMCSPREDICTERRUPLIMIT {
  type uint8 {
   range "0..15";
  }
  mandatory false;
 }
 leaf ULSUMIMOMODELSUSPENDTHLD {
  type uint8 {
   range "15..100";
  }
  mandatory false;
 }
 leaf ULSUPREDICTERRORUPPERLIMIT {
  type uint8 {
   range "10..30";
  }
  mandatory false;
 }
 }
 grouping NRDUCELLALGOSWITCH-attributes {
 leaf ADAPTIVEEDGEEXPENHSWITCH {
  type string;
  mandatory false;
 }
 leaf ALGOCOMPATIBILITYSWITCH {
  type string;
  mandatory false;
 }
 leaf ALGOCOMPATIBILITYSWITCHEXT {
  type string;
  mandatory false;
 }
 leaf BEAMMULTIPLEXSWITCH {
  type inet:ip-address;
  mandatory false;
 }
 leaf BEAMOPTSWITCH {
  type string;
  mandatory false;
 }
 leaf BWPCONFIGPOLICYSWITCH {
  type string;
  mandatory false;
 }
 leaf CAALGOSWITCH {
  type string;
  mandatory false;
 }
 leaf CHNCALIBSWITCH {
  type string;
  mandatory false;
 }
 leaf CLOUDVRSCHSWITCH {
  type string;
  mandatory false;
 }
 leaf COMMCHNINTRFAVOIDSWITCH {
  type string;
  mandatory false;
 }
 leaf COMPSWITCH {
  type string;
  mandatory false;
 }
 leaf COORDTRSRESOURCESWITCH {
  type string;
  mandatory false;
 }
 leaf CPLATENCYSWITCH {
  type string;
  mandatory false;
 }
 leaf DL256QAMSWITCH {
  type boolean;
  mandatory false;
 }
 leaf DMMIMOSWITCH {
  type string;
  mandatory false;
 }
 leaf DYNPOWERSHARINGSWITCH {
  type string;
  mandatory false;
 }
 leaf FULLCHANNELCOVENHSWITCH {
  type string;
  mandatory false;
 }
 leaf FWAALGOSWITCH {
  type string;
  mandatory false;
 }
 leaf HIGHRELIABILITYSWITCH {
  type string;
  mandatory false;
 }
 leaf HIGHSPEEDINTRFRANDOMSCHSW {
  type boolean;
  mandatory false;
 }
 leaf INDOOROUTDOORCOOPERATESW {
  type string;
  mandatory false;
 }
 leaf LOWLATENCYSWITCH {
  type string;
  mandatory false;
 }
 leaf MUMIMOOPTSWITH {
  type boolean;
  mandatory false;
 }
 leaf MUMIMOSWITCH {
  type string;
  mandatory false;
 }
 leaf MULTIDCIALGOSWITCH {
  type string;
  mandatory false;
 }
 leaf MULTITRSMEASSWITCH {
  type boolean;
  mandatory false;
 }
 leaf NETWORKSLICEALGOSWITCH {
  type string;
  mandatory false;
 }
 leaf NRDUCELLID {
  type union {
   type int32 {
    range "-1..65534";
   }
  }
  mandatory false;
 }
 leaf NSADCALGOSWITCH {
  type string;
  mandatory false;
 }
 leaf NSATDMPATTERNTYPESTRATEGY {
  type boolean;
  mandatory false;
 }
 leaf POWERSAVINGEXTSWITCH {
  type string;
  mandatory false;
 }
 leaf POWERSAVINGSWITCH {
  type string;
  mandatory false;
 }
 leaf RACALGOSWITCH {
  type string;
  mandatory false;
 }
 leaf RANSHARINGALGOSWITCH {
  type string;
  mandatory false;
 }
 leaf RANKSELECTALGOSW {
  type string;
  mandatory false;
 }
 leaf RIMALGOSWITCH {
  type string;
  mandatory false;
 }
 leaf SERVICEDIFFSWITCH {
  type string;
  mandatory false;
 }
 leaf SHORTTACOMMANDPERIODSW {
  type string;
  mandatory false;
 }
 leaf SPECRFMODULENRADAPTSWITCH {
  type string;
  mandatory false;
 }
 leaf SPECTRUMCLOUDENHSWITCH {
  type string;
  mandatory false;
 }
 leaf SPECTRUMCLOUDSWITCH {
  type string;
  mandatory false;
 }
 leaf SUMIMOMULTIPLELAYERSW {
  type inet:ip-address;
  mandatory false;
 }
 leaf SUPERUPLINKSWITCH {
  type string;
  mandatory false;
 }
 leaf SYMBOLSHUTDOWNSWITCH {
  type boolean;
  mandatory false;
 }
 leaf UEFEATUREBASEDPAIRENHSW {
  type string;
  mandatory false;
 }
 leaf UELINKABNORMALDETECTSWITCH {
  type boolean;
  mandatory false;
 }
 leaf UL256QAMSWITCH {
  type enumeration {
   enum val-0;
   enum val-1;
   enum val-2;
  }
  mandatory false;
 }
 leaf ULDLDECOUPLINGSWITCH {
  type boolean;
  mandatory false;
 }
 leaf ULINCONSECUTIVESCHSWITCH {
  type string;
  mandatory false;
 }
 leaf ULINTRFRANDOMSCHSWITCH {
  type boolean;
  mandatory false;
 }
 leaf ULPREALLOCPWRCTRLENHSW {
  type boolean;
  mandatory false;
 }
 leaf VMIMOSWITCH {
  type boolean;
  mandatory false;
 }
 }
 grouping NRDUCELLASSIST-attributes {
 leaf OLD_ASSISTANCETYPE {
  type enumeration {
   enum val--1;
   enum val-0;
  }
  mandatory false;
 }
 leaf ASSISTANCETYPE {
  type enumeration {
   enum val--1;
   enum val-0;
  }
  mandatory false;
 }
 leaf OLD_ASSISTANTNRDUCELLID {
  type union {
   type int32 {
    range "-1..65534";
   }
  }
  mandatory false;
 }
 leaf ASSISTANTNRDUCELLID {
  type union {
   type int32 {
    range "-1..65534";
   }
  }
  mandatory false;
 }
 leaf OLD_NRDUCELLID {
  type union {
   type int32 {
    range "-1..65534";
   }
  }
  mandatory false;
 }
 leaf NRDUCELLID {
  type union {
   type int32 {
    range "-1..65534";
   }
  }
  mandatory false;
 }
 }
 grouping NRDUCELLBICARRIER-attributes {
 leaf CONRDUCELLID {
  type uint16 {
   range "0..65534";
  }
  mandatory false;
 }
 leaf NRDUCELLID {
  type union {
   type int32 {
    range "-1..65534";
   }
  }
  mandatory false;
 }
 leaf PDCCHRMPOLICY {
  type boolean;
  mandatory false;
 }
 leaf PRBTHLD {
  type uint8 {
   range "0..100";
  }
  mandatory false;
 }
 leaf RESALLOCATIONPOLICY {
  type enumeration {
   enum val-0;
   enum val-1;
   enum val-2;
  }
  mandatory false;
 }
 leaf SRSINTRFDIFFTHLD {
  type uint8 {
   range "0..60";
  }
  mandatory false;
 }
 }
 grouping NRDUCELLCARRMGMT-attributes {
 leaf CACOMPATIBILITYSWITCH {
  type string;
  mandatory false;
 }
 leaf CADLMAXCCNUM {
  type enumeration {
   enum val-0;
   enum val-1;
   enum val-2;
   enum val-3;
  }
  mandatory false;
 }
 leaf CADLSCELLACTTHLDSLOTNUM {
  type uint8 {
   range "0..80";
  }
  mandatory false;
 }
 leaf CADLSCELLDEACTTHLDSLOTNUM {
  type uint8 {
   range "0..40";
  }
  mandatory false;
 }
 leaf CAENHANCEDALGOEXTSWITCH {
  type string;
  mandatory false;
 }
 leaf CAENHANCEDALGOSWITCH {
  type string;
  mandatory false;
 }
 leaf CAULSCELLACTTHLDSLOTNUM {
  type uint8 {
   range "0..80";
  }
  mandatory false;
 }
 leaf CAULSCELLDEACTTHLDSLOTNUM {
  type uint8 {
   range "0..40";
  }
  mandatory false;
 }
 leaf DLINTRAGNBCASPLITPOLICY {
  type boolean;
  mandatory false;
 }
 leaf DLSTATETRANSITBUFVOLTHLD {
  type union {
   type uint16 {
    range "1..65535";
   }
  }
  mandatory false;
 }
 leaf DYNCODEBOOKCAUENUMTHLD {
  type uint8 {
   range "0..255";
  }
  mandatory false;
 }
 leaf FLEXSPCTACCESSEXPEVALHYST {
  type uint8 {
   range "10..100";
  }
  mandatory false;
 }
 leaf FR1CADLTBSPARAMOH {
  type uint8 {
   range "0..14";
  }
  mandatory false;
 }
 leaf FR2CACARRMGMTPOLICY {
  type boolean;
  mandatory false;
 }
 leaf FR2CADLTBSPARAMOH {
  type uint8 {
   range "0..18";
  }
  mandatory false;
 }
 leaf FR2NOSPLITSCHDATARATIOTHLD {
  type uint8 {
   range "1..200";
  }
  mandatory false;
 }
 leaf INTERFRCA100MFR2CCMAXNUM {
  type boolean;
  mandatory false;
 }
 leaf INTERFRCAENHSW {
  type string;
  mandatory false;
 }
 leaf INTERFRCAFR1DLMAXCCNUM {
  type boolean;
  mandatory false;
 }
 leaf INTERGNODEBDELAY {
  type enumeration {
   enum val-0;
   enum val-1;
   enum val-2;
   enum val-3;
   enum val-4;
  }
  mandatory false;
 }
 leaf INTRAGNBCADLSPLITTHLD {
  type enumeration {
   enum val-0;
   enum val-1;
   enum val-2;
   enum val-3;
   enum val-4;
   enum val-5;
  }
  mandatory false;
 }
 leaf MULTIBANDFLEXSCHSWITCH {
  type string;
  mandatory false;
 }
 leaf NRDUCELLID {
  type union {
   type int32 {
    range "-1..65534";
   }
  }
  mandatory false;
 }
 leaf NSASASELOPTHIGHTRAFFICTHLD {
  type uint8 {
   range "1..20";
  }
  mandatory false;
 }
 leaf NSASASELOPTLOWTRAFFICTHLD {
  type uint8 {
   range "0..10";
  }
  mandatory false;
 }
 leaf RLCBUFFERFILTERCOEFF {
  type uint8 {
   range "1..20";
  }
  mandatory false;
 }
 leaf RLCDLTHROUGHPUTTHLD {
  type uint16 {
   range "0..50000";
  }
  mandatory false;
 }
 leaf RLCULTHROUGHPUTTHLD {
  type uint16 {
   range "0..50000";
  }
  mandatory false;
 }
 leaf SCCCFGINTERVAL {
  type uint8 {
   range "5..60";
  }
  mandatory false;
 }
 leaf SCCDEACTVCQITHLD {
  type uint8 {
   range "0..15";
  }
  mandatory false;
 }
 leaf SCELLDEACTVWAITTIMER {
  type uint8 {
   range "0..20";
  }
  mandatory false;
 }
 leaf SPLITSTOPSCHCAPBRATIOTHLD {
  type uint8 {
   range "0..200";
  }
  mandatory false;
 }
 leaf SRSCARRSWITCHINGTIMEDLTHLD {
  type enumeration {
   enum val-0;
   enum val-1;
   enum val-2;
   enum val-3;
  }
  mandatory false;
 }
 leaf SRSCARRSWITCHINGTIMEULTHLD {
  type enumeration {
   enum val-0;
   enum val-1;
   enum val-2;
   enum val-3;
  }
  mandatory false;
 }
 leaf SRSCARRSWITCHINGULSYMCFG {
  type enumeration {
   enum val-0;
   enum val-1;
   enum val-2;
   enum val-3;
  }
  mandatory false;
 }
 leaf SRSONLYWEIGHTPRESINRTHLD {
  type int8 {
   range "-20..20";
  }
  mandatory false;
 }
 leaf SRSSWITCHINGSCCSSLOTUNUM {
  type string;
  mandatory false;
 }
 leaf ULCELLEXPEVALUATIONFACTOR {
  type int16 {
   range "-100..200";
  }
  mandatory false;
 }
 leaf ULMULTICCABSTADIFFTHLD {
  type uint8 {
   range "0..64";
  }
  mandatory false;
 }
 }
 grouping NRDUCELLCHNCOVALGO-attributes {
 leaf DLCOVERAGEALGOSWITCH {
  type string;
  mandatory false;
 }
 leaf NRDUCELLID {
  type union {
   type int32 {
    range "-1..65534";
   }
  }
  mandatory false;
 }
 leaf ULCOVERAGEALGOSWITCH {
  type string;
  mandatory false;
 }
 leaf ULWEAKCOVFREQSELSCHMETHOD {
  type boolean;
  mandatory false;
 }
 leaf ULWEAKCOVSCHALGOSW {
  type string;
  mandatory false;
 }
 }
 grouping NRDUCELLCHNPWR-attributes {
 leaf AIRCONTROLMSGMAXPWROFFSET {
  type int8 {
   range "-15..15";
  }
  mandatory false;
 }
 leaf BSEVMHIGHRANKMCSTHLD {
  type uint8 {
   range "0..29";
  }
  mandatory false;
 }
 leaf BSEVMLOWRANKMCSTHLD {
  type uint8 {
   range "0..29";
  }
  mandatory false;
 }
 leaf CFARPWRTHLDFACTOR {
  type uint16 {
   range "200..1000";
  }
  mandatory false;
 }
 leaf CHNPWRALGOSWITCH {
  type string;
  mandatory false;
 }
 leaf CHNRSSITHLD {
  type int8 {
   range "-80..-40";
  }
  mandatory false;
 }
 leaf CSIRSMAXPWROFFSET {
  type int8 {
   range "-15..15";
  }
  mandatory false;
 }
 leaf DLMUMIMOPWROPTPOLICY {
  type enumeration {
   enum val-0;
   enum val-1;
   enum val-2;
  }
  mandatory false;
 }
 leaf DSSPDCCHMAXPWROFS {
  type boolean;
  mandatory false;
 }
 leaf HIGHRANKPWRREDUCEMCSTHLD {
  type uint8 {
   range "0..29";
  }
  mandatory false;
 }
 leaf HOSIGMAXPWROFFSET {
  type uint8 {
   range "0..30";
  }
  mandatory false;
 }
 leaf LOWRANKPWRREDUCEMCSTHLD {
  type uint8 {
   range "0..29";
  }
  mandatory false;
 }
 leaf LTENRSPCTSHRPWRAGGSWITCH {
  type string;
  mandatory false;
 }
 leaf MAX1024QAMPWROFFSET {
  type uint8 {
   range "0..40";
  }
  mandatory false;
 }
 leaf MAXBSEVMPWROFFSET {
  type uint8 {
   range "0..40";
  }
  mandatory false;
 }
 leaf MAXCOMMONDCIPWROFFSET {
  type int8 {
   range "-15..15";
  }
  mandatory false;
 }
 leaf MAXPDCCHAGGPWROFFSET {
  type uint8 {
   range "0..150";
  }
  mandatory false;
 }
 leaf MAXPDSCHCONVPWROFFSET {
  type uint8 {
   range "0..15";
  }
  mandatory false;
 }
 leaf MAXUESATPRECODEPWROFFSET {
  type uint8 {
   range "0..6";
  }
  mandatory false;
 }
 leaf MAXUESATPWROFFSET {
  type uint8 {
   range "0..40";
  }
  mandatory false;
 }
 leaf MSG2MAXPWROFFSET {
  type int8 {
   range "-15..15";
  }
  mandatory false;
 }
 leaf MSG4MAXPWROFFSET {
  type int8 {
   range "-15..15";
  }
  mandatory false;
 }
 leaf MULTILAYERPWRCTRLMCSTHLD {
  type uint8 {
   range "0..27";
  }
  mandatory false;
 }
 leaf MULTILAYERPWRCTRLPOL {
  type enumeration {
   enum val-0;
   enum val-1;
   enum val-2;
  }
  mandatory false;
 }
 leaf MULTILAYERPWRDISCOUNTCOEFF {
  type uint8 {
   range "0..100";
  }
  mandatory false;
 }
 leaf MULTILAYERPWROFSLOWERLMT {
  type int8 {
   range "-30..0";
  }
  mandatory false;
 }
 leaf NRDUCELLID {
  type union {
   type int32 {
    range "-1..65534";
   }
  }
  mandatory false;
 }
 leaf OSIMAXPWROFFSET {
  type int8 {
   range "-15..15";
  }
  mandatory false;
 }
 leaf PAGINGMAXPWROFFSET {
  type int8 {
   range "-15..15";
  }
  mandatory false;
 }
 leaf PDSCHPWROPTSWITCH {
  type string;
  mandatory false;
 }
 leaf PWRAGGLEVEL {
  type enumeration {
   enum val-0;
   enum val-1;
   enum val-2;
   enum val-100;
  }
  mandatory false;
 }
 leaf PWROPTSENSITIVITY {
  type uint8 {
   range "0..10";
  }
  mandatory false;
 }
 leaf PWRREDUCTIONVALUE {
  type uint8 {
   range "0..50";
  }
  mandatory false;
 }
 leaf RMSIMAXPWROFFSET {
  type int8 {
   range "-15..15";
  }
  mandatory false;
 }
 leaf SENSINGSAMPLENUMTHLD {
  type uint8 {
   range "0..255";
  }
  mandatory false;
 }
 leaf SIGINITTRANSPDCCHMAXPWROFS {
  type uint8 {
   range "0..150";
  }
  mandatory false;
 }
 leaf SIGINITTRANSPDSCHMAXPWROFS {
  type uint8 {
   range "0..150";
  }
  mandatory false;
 }
 leaf SIGRETRANSPDCCHMAXPWROFS {
  type uint8 {
   range "0..150";
  }
  mandatory false;
 }
 leaf SIGRETRANSPDSCHMAXPWROFS {
  type uint8 {
   range "0..150";
  }
  mandatory false;
 }
 leaf SMARTPWRCTRLNCELLRSRPTHLD {
  type int8 {
   range "-125..-80";
  }
  mandatory false;
 }
 leaf SPECUERSSISATOFFSET {
  type int8 {
   range "-100..100";
  }
  mandatory false;
 }
 leaf SUPWRCOFFTHLD {
  type uint8 {
   range "0..10";
  }
  mandatory false;
 }
 leaf SUPWRCOFFVALUE {
  type uint8 {
   range "1..10";
  }
  mandatory false;
 }
 leaf TRSPWROFFSET {
  type uint8 {
   range "0..3";
  }
  mandatory false;
 }
 leaf UEPWRSATRANK1OFFSET {
  type int8 {
   range "-100..100";
  }
  mandatory false;
 }
 leaf UEPWRSATRANK2OFFSET {
  type int8 {
   range "-100..100";
  }
  mandatory false;
 }
 leaf UEPWRSATRANK3OFFSET {
  type int8 {
   range "-100..100";
  }
  mandatory false;
 }
 leaf UEPWRSATRANK4OFFSET {
  type int8 {
   range "-100..100";
  }
  mandatory false;
 }
 leaf UEPWRSATRBTHD {
  type uint8 {
   range "0..100";
  }
  mandatory false;
 }
 leaf UESATPWROFFSETTHLD {
  type int8 {
   range "-100..100";
  }
  mandatory false;
 }
 leaf UESATPWRRANKTHLD {
  type enumeration {
   enum val-0;
   enum val-1;
   enum val-2;
   enum val-3;
  }
  mandatory false;
 }
 }
 grouping NRDUCELLCOLLABCOOP-attributes {
 leaf INTERGNBSULMAXRBPCT {
  type uint8 {
   range "1..100";
  }
  mandatory false;
 }
 leaf INTERGNBSULMINRBPCT {
  type uint8 {
   range "0..100";
  }
  mandatory false;
 }
 leaf MSG3RSVDRBNUM {
  type uint16 {
   range "0..273";
  }
  mandatory false;
 }
 leaf NRDUCELLID {
  type union {
   type int32 {
    range "-1..65534";
   }
  }
  mandatory false;
 }
 leaf NULSULMAXINTERGNBDELAY {
  type enumeration {
   enum val-5;
   enum val-20;
   enum val-40;
  }
  mandatory false;
 }
 leaf SULALGOSWITCH {
  type string;
  mandatory false;
 }
 leaf ULDLDECOUPLESWITCHTIME {
  type boolean;
  mandatory false;
 }
 }
 grouping NRDUCELLCOLLABSERV-attributes {
 leaf ASSISTANCESRSRSRPTHLD {
  type int16 {
   range "-156..-31";
  }
  mandatory false;
 }
 leaf CARRSELTDDSRSRSRPTHLD {
  type int16 {
   range "-156..-31";
  }
  mandatory false;
 }
 leaf CBFSRSPRESINRTHLD {
  type int8 {
   range "-100..100";
  }
  mandatory false;
 }
 leaf COCELLRSRPTHLD {
  type int16 {
   range "-156..-31";
  }
  mandatory false;
 }
 leaf COMMALGOSWITCH {
  type string;
  mandatory false;
 }
 leaf COOPCELLPRESINRTHLD {
  type int8 {
   range "-20..40";
  }
  mandatory false;
 }
 leaf COORDMIMOCLUSTERID {
  type union {
   type uint16 {
    range "0..65535";
   }
  }
  mandatory false;
 }
 leaf COORDMIMOCLUSTERMGNBID {
  type uint32 {
   range "0..4294967295";
  }
  mandatory false;
 }
 leaf COORDMIMOCLUSTERMGNBMCC {
  type string {
   length "3";
  }
  mandatory false;
 }
 leaf COORDMIMOCLUSTERMGNBMNC {
  type string {
   length "2..3";
  }
  mandatory false;
 }
 leaf DMIMOINTRFSINRTHLD {
  type union {
   type uint16 {
    range "30..65535";
   }
  }
  mandatory false;
 }
 leaf DLCOMMINITIALMCSADJVALUE {
  type int8 {
   range "-27..27";
  }
  mandatory false;
 }
 leaf INTRAGNBSULUEPDCCHPROTTIME {
  type uint8 {
   range "0..3";
  }
  mandatory false;
 }
 leaf INTRFAVOIDDLTARGETIBLER {
  type uint8 {
   range "10..30";
  }
  mandatory false;
 }
 leaf MULTICARRMGMTSW {
  type string;
  mandatory false;
 }
 leaf MULTICELLMIMOSWITCH {
  type string;
  mandatory false;
 }
 leaf NEIGHBORNRCELLMGMTSW {
  type string;
  mandatory false;
 }
 leaf NRDUCELLID {
  type union {
   type int32 {
    range "-1..65534";
   }
  }
  mandatory false;
 }
 leaf NUL1TXTOSUL1TXSWITCHTIME {
  type enumeration {
   enum val-0;
   enum val-1;
   enum val-2;
  }
  mandatory false;
 }
 leaf NUL2TXTOSUL1TXSWITCHTIME {
  type enumeration {
   enum val-0;
   enum val-1;
   enum val-2;
  }
  mandatory false;
 }
 leaf NULSULMAXINTERGNBDELAY {
  type enumeration {
   enum val-5;
   enum val-20;
   enum val-40;
  }
  mandatory false;
 }
 leaf RSRPTHLD {
  type int16 {
   range "-156..-31";
  }
  mandatory false;
 }
 leaf SRSRSRPDIFFTHLD {
  type int8 {
   range "-100..100";
  }
  mandatory false;
 }
 leaf SRSRSRPTHLD {
  type int16 {
   range "-156..-31";
  }
  mandatory false;
 }
 leaf SRSTADIFFTHLD {
  type uint8 {
   range "0..90";
  }
  mandatory false;
 }
 leaf SULALGOSWITCH {
  type string;
  mandatory false;
 }
 leaf SULDTXSINRLOWERLIMIT {
  type int8 {
   range "-100..100";
  }
  mandatory false;
 }
 leaf SULESTTHPTGAINFACTOR {
  type uint8 {
   range "12..32";
  }
  mandatory false;
 }
 leaf SULSINRLOWERLIMIT {
  type int16 {
   range "-200..100";
  }
  mandatory false;
 }
 leaf SULSINRLOWERLIMITOFFSET {
  type uint8 {
   range "5..50";
  }
  mandatory false;
 }
 leaf SULTAOPTALGOTHLD {
  type uint8 {
   range "0..8";
  }
  mandatory false;
 }
 leaf ULSPLITSLOTNUMTHLD {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
  }
  mandatory false;
 }
 }
 grouping NRDUCELLCOMMONSW-attributes {
 leaf NRDUCELLID {
  type union {
   type int32 {
    range "-1..65534";
   }
  }
  mandatory false;
 }
 leaf RFSPALGOSWITCH {
  type string;
  mandatory false;
 }
 leaf SERVICEDIFFALGOSWITCH {
  type string;
  mandatory false;
 }
 }
 grouping NRDUCELLCOMP-attributes {
 leaf CBFSPECEFFICIENCYJUDGETHLD {
  type uint16 {
   range "0..1000";
  }
  mandatory false;
 }
 leaf CBFUEFRESELFACTORTHLD {
  type uint8 {
   range "0..20";
  }
  mandatory false;
 }
 leaf COMPOPTSWITCH {
  type string;
  mandatory false;
 }
 leaf CSCBFALGOSWITCH {
  type string;
  mandatory false;
 }
 leaf CSCBFCHANNELCORRTHLD {
  type uint8 {
   range "0..20";
  }
  mandatory false;
 }
 leaf CSCBFSRSRSRPOFFSET {
  type uint8 {
   range "0..100";
  }
  mandatory false;
 }
 leaf CSMCSTHLD {
  type uint8 {
   range "0..27";
  }
  mandatory false;
 }
 leaf CSSPCTEFFICIENCYTHLD {
  type uint16 {
   range "0..1000";
  }
  mandatory false;
 }
 leaf DLCOMPALGOEXTSWITCH {
  type string;
  mandatory false;
 }
 leaf DLCOMPALGOSWITCH {
  type string;
  mandatory false;
 }
 leaf DLCOMPCOCELLPRBTHLD {
  type uint8 {
   range "0..100";
  }
  mandatory false;
 }
 leaf DLCOMPENHANCEDTRANSMITMODE {
  type enumeration {
   enum val-0;
   enum val-1;
   enum val-2;
  }
  mandatory false;
 }
 leaf DLCOMPRISUBSETCONFIG {
  type uint8 {
   range "0..255";
  }
  mandatory false;
 }
 leaf INTERGNBCLUSTERID {
  type uint8 {
   range "0..100";
  }
  mandatory false;
 }
 leaf INTERGNBCONNLATENCYMODE {
  type boolean;
  mandatory false;
 }
 leaf JTAVAILPRBPROPTHLD {
  type uint8 {
   range "10..100";
  }
  mandatory false;
 }
 leaf JTCSIRSTXMODE {
  type enumeration {
   enum val-0;
   enum val-1;
   enum val-2;
   enum val-3;
  }
  mandatory false;
 }
 leaf JTDELAYCOMPENSATIONTHLD {
  type uint8 {
   range "0..96";
  }
  mandatory false;
 }
 leaf JTMODEPROBEOFFSET {
  type uint16 {
   range "0..1000";
  }
  mandatory false;
 }
 leaf JTMODESPECEFFTHLD {
  type uint16 {
   range "1..1000";
  }
  mandatory false;
 }
 leaf JTMULTIPOINTTRANSMITMODE {
  type enumeration {
   enum val-0;
   enum val-1;
   enum val-2;
   enum val-3;
  }
  mandatory false;
 }
 leaf JTPMITYPE {
  type enumeration {
   enum val-0;
   enum val-1;
   enum val-2;
   enum val-3;
   enum val-4;
  }
  mandatory false;
 }
 leaf JTPWRBACKOFFOFFSET {
  type uint8 {
   range "0..20";
  }
  mandatory false;
 }
 leaf JTQUICKROLLBACKSPCTEFFTHLD {
  type uint16 {
   range "0..1000";
  }
  mandatory false;
 }
 leaf JTSPCTEFFICIENCYTHLD {
  type uint16 {
   range "0..1000";
  }
  mandatory false;
 }
 leaf JTSRSRSRPDIFFTHLD {
  type uint8 {
   range "0..20";
  }
  mandatory false;
 }
 leaf NRDUCELLID {
  type union {
   type int32 {
    range "-1..65534";
   }
  }
  mandatory false;
 }
 leaf QUICKCBFSPCTEFFTHLD {
  type uint16 {
   range "0..1100";
  }
  mandatory false;
 }
 leaf SINGLECELLTRANSPROBEOFFSET {
  type uint16 {
   range "0..1000";
  }
  mandatory false;
 }
 leaf ULCOMPALGOSWITCH {
  type string;
  mandatory false;
 }
 leaf ULCOMPPRESINRTHLD {
  type int8 {
   range "-20..0";
  }
  mandatory false;
 }
 leaf USERCSIRSBEAMTYPE {
  type enumeration {
   enum val-0;
   enum val-1;
   enum val-2;
   enum val-3;
   enum val-4;
   enum val-5;
   enum val-6;
   enum val-7;
   enum val-8;
   enum val-9;
   enum val-10;
   enum val-11;
  }
  mandatory false;
 }
 }
 grouping NRDUCELLCORESET-attributes {
 leaf COMMONCTRLRESRBNUM {
  type enumeration {
   enum val-0;
   enum val-1;
   enum val-2;
  }
  mandatory false;
 }
 leaf COMMONCTRLRESSTARTSYMBOL {
  type enumeration {
   enum val-0;
   enum val-1;
   enum val-2;
   enum val-255;
  }
  mandatory false;
 }
 leaf NRDUCELLID {
  type union {
   type int32 {
    range "-1..65534";
   }
  }
  mandatory false;
 }
 }
 grouping NRDUCELLCOVERAGE-attributes {
 leaf ANTENNAPORTMAPPING {
  type enumeration {
   enum val-0;
   enum val-1;
   enum val-2;
   enum val-3;
   enum val-4;
   enum val-5;
   enum val-6;
   enum val-50;
   enum val-51;
   enum val-52;
   enum val-53;
   enum val-54;
   enum val-55;
   enum val-56;
   enum val-57;
   enum val-58;
   enum val-59;
   enum val-60;
   enum val-61;
   enum val-62;
   enum val-63;
   enum val-64;
  }
  mandatory false;
 }
 leaf ANTENNAPORTMAPPINGEXT {
  type string {
   length "0..8";
  }
  mandatory false;
 }
 leaf FRONTHAULSWITCH {
  type string;
  mandatory false;
 }
 leaf MAXTRANSMITPOWER {
  type union {
   type uint16 {
    range "0..65535";
   }
  }
  mandatory false;
 }
 leaf MAXTRANSMITPOWERMW {
  type uint32 {
   range "1..1000000";
  }
  mandatory false;
 }
 leaf OLD_NRDUCELLCOVERAGEID {
  type union {
   type int16 {
    range "-1..255";
   }
  }
  mandatory false;
 }
 leaf NRDUCELLCOVERAGEID {
  type union {
   type int16 {
    range "-1..255";
   }
  }
  mandatory false;
 }
 leaf OLD_NRDUCELLTRPID {
  type union {
   type int32 {
    range "-1..65534";
   }
  }
  mandatory false;
 }
 leaf NRDUCELLTRPID {
  type union {
   type int32 {
    range "-1..65534";
   }
  }
  mandatory false;
 }
 leaf POWERCONFIGMODE {
  type boolean;
  mandatory false;
 }
 leaf SECTOREQMID {
  type uint16 {
   range "0..65535";
  }
  mandatory false;
 }
 leaf TRANSMITPOWEROFFSETCHN0 {
  type int8 {
   range "-100..100";
  }
  mandatory false;
 }
 leaf TRANSMITPOWEROFFSETCHN1 {
  type int8 {
   range "-100..100";
  }
  mandatory false;
 }
 leaf TRANSMITPOWEROFFSETCHN2 {
  type int8 {
   range "-100..100";
  }
  mandatory false;
 }
 leaf TRANSMITPOWEROFFSETCHN3 {
  type int8 {
   range "-100..100";
  }
  mandatory false;
 }
 leaf TRANSMITPOWEROFFSETCHN4 {
  type int8 {
   range "-100..100";
  }
  mandatory false;
 }
 leaf TRANSMITPOWEROFFSETCHN5 {
  type int8 {
   range "-100..100";
  }
  mandatory false;
 }
 leaf TRANSMITPOWEROFFSETCHN6 {
  type int8 {
   range "-100..100";
  }
  mandatory false;
 }
 leaf TRANSMITPOWEROFFSETCHN7 {
  type int8 {
   range "-100..100";
  }
  mandatory false;
 }
 }
 grouping NRDUCELLCSIRS-attributes {
 leaf APERIODICCSIMINSCHINTVL {
  type enumeration {
   enum val-1;
   enum val-2;
   enum val-3;
   enum val-4;
   enum val-5;
   enum val-6;
   enum val-7;
  }
  mandatory false;
 }
 leaf BEAMRPTNUMCHANGETHLD {
  type enumeration {
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
  }
  mandatory false;
 }
 leaf CSIPERIOD {
  type enumeration {
   enum val-3;
   enum val-5;
   enum val-6;
   enum val-7;
   enum val-8;
   enum val-9;
  }
  mandatory false;
 }
 leaf CSIRSBEAMMEASPERIOD {
  type enumeration {
   enum val-1;
   enum val-2;
   enum val-3;
  }
  mandatory false;
 }
 leaf CSIRSDFTBMSWEEPPATTERN {
  type uint16 {
   range "255..65280";
  }
  mandatory false;
 }
 leaf CSIRSEXTSWITCH {
  type string;
  mandatory false;
 }
 leaf CSIRSVAMBMSWEEPPATTERN {
  type uint8 {
   range "1..127";
  }
  mandatory false;
 }
 leaf CSIRSRPFILTERCOEFF {
  type uint8 {
   range "0..100";
  }
  mandatory false;
 }
 leaf CSISUBBANDSIZE {
  type boolean;
  mandatory false;
 }
 leaf CSISWITCH {
  type string;
  mandatory false;
 }
 leaf CSITYPE2SUBBANDSIZE {
  type boolean;
  mandatory false;
 }
 leaf CSIUSERPERIOD {
  type enumeration {
   enum val-0;
   enum val-6;
   enum val-7;
   enum val-8;
   enum val-9;
   enum val-10;
  }
  mandatory false;
 }
 leaf CSIUSERPORTNUM {
  type enumeration {
   enum val-0;
   enum val-1;
   enum val-2;
  }
  mandatory false;
 }
 leaf CSIRS4P8PADAPTIVESWTHLD {
  type uint8 {
   range "0..110";
  }
  mandatory false;
 }
 leaf CSIRSBEAMSWITCHTHLD {
  type uint8 {
   range "0..10";
  }
  mandatory false;
 }
 leaf CSIRSBEAMSWITCHTHLDOFS {
  type uint8 {
   range "0..10";
  }
  mandatory false;
 }
 leaf CSIRSBEAMTYPE {
  type enumeration {
   enum val-0;
   enum val-1;
   enum val-2;
  }
  mandatory false;
 }
 leaf CSIRSCELLRESOURCENUM {
  type enumeration {
   enum val-0;
   enum val-1;
   enum val-2;
   enum val-3;
   enum val-4;
  }
  mandatory false;
 }
 leaf CSIRSRESFULLBUFFERUENUM {
  type uint8 {
   range "0..32";
  }
  mandatory false;
 }
 leaf CSIRSRPTBASEDSCCDEACTVTHLD {
  type uint8 {
   range "1..50";
  }
  mandatory false;
 }
 leaf FR1MAXCELLCSIRSPORTNUM {
  type enumeration {
   enum val-0;
   enum val-1;
   enum val-2;
  }
  mandatory false;
 }
 leaf FR2MAXCELLCSIRSPORTNUM {
  type enumeration {
   enum val-0;
   enum val-1;
   enum val-2;
  }
  mandatory false;
 }
 leaf FDCSIPERIOD {
  type enumeration {
   enum val-6;
   enum val-7;
   enum val-8;
   enum val-9;
  }
  mandatory false;
 }
 leaf FDCSIRSACTIVEUETHLD {
  type uint8 {
   range "0..60";
  }
  mandatory false;
 }
 leaf FDCSIRSPATHLOSSTHLD {
  type uint8 {
   range "80..140";
  }
  mandatory false;
 }
 leaf FDD8TNARROWCSISPCTEFFCOEFF {
  type uint16 {
   range "105..1000";
  }
  mandatory false;
 }
 leaf INCOMPATIBLEUECSIRSPERIOD {
  type enumeration {
   enum val-5;
   enum val-6;
   enum val-7;
   enum val-8;
   enum val-9;
  }
  mandatory false;
 }
 leaf INTERTRPCSIRSSTAGGERMODE {
  type boolean;
  mandatory false;
 }
 leaf INTERTRPHOCSIRSRPEVALTIMES {
  type uint8 {
   range "1..50";
  }
  mandatory false;
 }
 leaf INTERTRPHODELTACSIRSRPTHLD {
  type uint8 {
   range "0..30";
  }
  mandatory false;
 }
 leaf JTUECSIRSMEASTHLD {
  type uint8 {
   range "0..100";
  }
  mandatory false;
 }
 leaf LAMPATHLOSSTHLD {
  type uint8 {
   range "80..140";
  }
  mandatory false;
 }
 leaf MUMIMOCSIRSBEAMSWEEPMODE {
  type enumeration {
   enum val-0;
   enum val-1;
   enum val-2;
  }
  mandatory false;
 }
 leaf NCELLCSIRSINTRFAVOID {
  type enumeration {
   enum val-0;
   enum val-1;
   enum val-2;
   enum val-3;
   enum val-4;
   enum val-5;
   enum val-6;
  }
  mandatory false;
 }
 leaf NRDUCELLID {
  type union {
   type int32 {
    range "-1..65534";
   }
  }
  mandatory false;
 }
 leaf POWERCONTROLOFFSET {
  type int8 {
   range "-8..15";
  }
  mandatory false;
 }
 leaf SSBBEAMSWITCHINGMODE {
  type enumeration {
   enum val-0;
   enum val-1;
   enum val-2;
  }
  mandatory false;
 }
 leaf TIMETOSENDFIRSTCSIRSFORBM {
  type enumeration {
   enum val-0;
   enum val-1;
   enum val-2;
   enum val-3;
  }
  mandatory false;
 }
 leaf TRSALLOCATIONSTRATEGY {
  type boolean;
  mandatory false;
 }
 leaf TRSBEAMTYPE {
  type boolean;
  mandatory false;
 }
 leaf TRSPERIOD {
  type enumeration {
   enum val-0;
   enum val-1;
   enum val-2;
   enum val-3;
   enum val-4;
  }
  mandatory false;
 }
 leaf USERCSIRSBEAMTYPE {
  type enumeration {
   enum val-0;
   enum val-1;
   enum val-2;
   enum val-3;
   enum val-4;
   enum val-5;
   enum val-6;
   enum val-7;
   enum val-8;
   enum val-9;
   enum val-10;
   enum val-11;
  }
  mandatory false;
 }
 }
 grouping NRDUCELLDLAMC-attributes {
 leaf DL1024QAMADJOFFSET {
  type uint8 {
   range "0..50";
  }
  mandatory false;
 }
 leaf DLAMCALGOSW {
  type string;
  mandatory false;
 }
 leaf DLBASEAMCADJWEIGHTFACTOR {
  type uint8 {
   range "0..100";
  }
  mandatory false;
 }
 leaf DLCHNFLCTNWEIGHTFACTOR {
  type uint16 {
   range "1..600";
  }
  mandatory false;
 }
 leaf DLFIXEDMCS {
  type uint8 {
   range "0..28";
  }
  mandatory false;
 }
 leaf DLIBLERTARGETOFFSET {
  type int8 {
   range "-100..100";
  }
  mandatory false;
 }
 leaf DLINITTRANSNACKNUMTHLD {
  type uint8 {
   range "0..150";
  }
  mandatory false;
 }
 leaf DLLEVEL1IBLERTARGETTHLD {
  type int8 {
   range "-100..100";
  }
  mandatory false;
 }
 leaf DLLEVEL2IBLERTARGETTHLD {
  type int8 {
   range "-100..100";
  }
  mandatory false;
 }
 leaf DLLEVEL3IBLERTARGETTHLD {
  type int8 {
   range "-100..100";
  }
  mandatory false;
 }
 leaf DLMCSADJOFFSET {
  type int8 {
   range "-5..0";
  }
  mandatory false;
 }
 leaf DLMCSPOLICY {
  type boolean;
  mandatory false;
 }
 leaf DLMCSSELALGOSW {
  type string;
  mandatory false;
 }
 leaf DLMODULATIONSCHEMESW {
  type string;
  mandatory false;
 }
 leaf DLMUMIMOSIRSCALEFACTOR {
  type uint8 {
   range "0..100";
  }
  mandatory false;
 }
 leaf LAMSPCTEFFTHLD {
  type uint16 {
   range "0..1000";
  }
  mandatory false;
 }
 leaf NRDUCELLID {
  type union {
   type int32 {
    range "-1..65534";
   }
  }
  mandatory false;
 }
 leaf PRECISEMCSADJPART1 {
  type uint32 {
   range "0..4294967295";
  }
  mandatory false;
 }
 leaf PRECISEMCSADJPART2 {
  type uint32 {
   range "0..4294967295";
  }
  mandatory false;
 }
 leaf PRECISEMCSADJPART3 {
  type uint32 {
   range "0..4294967295";
  }
  mandatory false;
 }
 leaf PRECISEMCSADJPART4 {
  type uint32 {
   range "0..4294967295";
  }
  mandatory false;
 }
 leaf SRSWEIGHTINITIALMCSOFFSET {
  type int8 {
   range "-1..19";
  }
  mandatory false;
 }
 leaf SUMIMOPWRCTRLPROTECTTHLD {
  type uint8 {
   range "0..100";
  }
  mandatory false;
 }
 leaf VOICEDLCQIADJVALUE {
  type uint8 {
   range "0..150";
  }
  mandatory false;
 }
 }
 grouping NRDUCELLDLMIMO-attributes {
 leaf DLMUMIMOSCHSUPPLEMENTSW {
  type string;
  mandatory false;
 }
 leaf DLMUBACKTOSUSETHLD {
  type uint8 {
   range "0..30";
  }
  mandatory false;
 }
 leaf DLMUCORRACCELERATORMODE {
  type boolean;
  mandatory false;
 }
 leaf DLMUISOLATIONMEASTHLD {
  type uint16 {
   range "0..500";
  }
  mandatory false;
 }
 leaf DLMUMIMOPRECISEPAIRMODE {
  type enumeration {
   enum val-0;
   enum val-1;
   enum val-2;
  }
  mandatory false;
 }
 leaf DLMUMIMOSRSPRESINRTHLD {
  type int8 {
   range "-100..100";
  }
  mandatory false;
 }
 leaf DLMUPMIBEAMNUMTHLD {
  type uint8 {
   range "1..16";
  }
  mandatory false;
 }
 leaf DLMUPRBUSAGETHLD {
  type uint8 {
   range "0..100";
  }
  mandatory false;
 }
 leaf HIGHLAYERMUMIMOSW {
  type string;
  mandatory false;
 }
 leaf MUMIMOIBLERTARGET {
  type uint8 {
   range "10..20";
  }
  mandatory false;
 }
 leaf NRDUCELLID {
  type union {
   type int32 {
    range "-1..65534";
   }
  }
  mandatory false;
 }
 }
 grouping NRDUCELLDLRANK-attributes {
 leaf AIRANKPARAOPTSWITCH {
  type string;
  mandatory false;
 }
 leaf AMCMCSDWSHIFAMPLIFACTOR {
  type uint8 {
   range "1..10";
  }
  mandatory false;
 }
 leaf AMCMCSUPSHIFAMPLIFACTOR {
  type uint8 {
   range "1..10";
  }
  mandatory false;
 }
 leaf DLFIXEDRANK {
  type uint8 {
   range "0..8";
  }
  mandatory false;
 }
 leaf DLHIGHRANKDECSPCTEFFTHLD {
  type uint8 {
   range "0..200";
  }
  mandatory false;
 }
 leaf DLHIGHRANKINCSPCTEFFTHLD {
  type uint8 {
   range "0..200";
  }
  mandatory false;
 }
 leaf DLMAXRANKLIMITLAYERGAPTHLD {
  type uint16 {
   range "1..1000";
  }
  mandatory false;
 }
 leaf DLMUMIMOPAIRGAINTHLD {
  type uint8 {
   range "100..200";
  }
  mandatory false;
 }
 leaf DLMUMIMORANKDETECTPERIOD {
  type enumeration {
   enum val-0;
   enum val-1;
   enum val-2;
   enum val-3;
   enum val-4;
   enum val-5;
   enum val-6;
   enum val-7;
   enum val-8;
   enum val-9;
  }
  mandatory false;
 }
 leaf DLMUMIMORANKDETECTPOLICY {
  type enumeration {
   enum val-0;
   enum val-1;
   enum val-2;
  }
  mandatory false;
 }
 leaf DLNONPCRANKDECSPCTEFFTHLD {
  type uint8 {
   range "0..200";
  }
  mandatory false;
 }
 leaf DLNONPCRANKINCSPCTEFFTHLD {
  type uint8 {
   range "0..200";
  }
  mandatory false;
 }
 leaf DLPMIMUMIMORANK {
  type enumeration {
   enum val-0;
   enum val-1;
   enum val-2;
   enum val-3;
  }
  mandatory false;
 }
 leaf DLRANK2INCSPCTEFFTHLD {
  type uint8 {
   range "0..200";
  }
  mandatory false;
 }
 leaf DLRANK3DECSPCTEFFTHLD {
  type uint8 {
   range "0..200";
  }
  mandatory false;
 }
 leaf DLRANK3INCSPCTEFFTHLD {
  type uint8 {
   range "0..200";
  }
  mandatory false;
 }
 leaf DLRANK4DECSPCTEFFTHLD {
  type uint8 {
   range "0..200";
  }
  mandatory false;
 }
 leaf DLRANKADAPTLAYERGAPTHLD {
  type uint8 {
   range "0..30";
  }
  mandatory false;
 }
 leaf DLRANKADAPTMCSTHLD {
  type uint8 {
   range "0..27";
  }
  mandatory false;
 }
 leaf DLRANKADAPTPERIOD {
  type uint16 {
   range "3..1000";
  }
  mandatory false;
 }
 leaf DLRANKADAPTSPCTEFFCOEFF {
  type uint8 {
   range "0..20";
  }
  mandatory false;
 }
 leaf DLRANKADAPTSRSPRESINRTHLD {
  type int8 {
   range "-20..-1";
  }
  mandatory false;
 }
 leaf DLRANKDETECTCORRTHLD {
  type uint8 {
   range "0..101";
  }
  mandatory false;
 }
 leaf DLRANKSELALGOSW {
  type string;
  mandatory false;
 }
 leaf DLSRSMUMIMORANK {
  type enumeration {
   enum val-0;
   enum val-1;
   enum val-2;
   enum val-3;
  }
  mandatory false;
 }
 leaf DLSRSMUMIMORANKMODE {
  type enumeration {
   enum val-0;
   enum val-1;
   enum val-2;
  }
  mandatory false;
 }
 leaf HIGHRANKADJMCSTHLD {
  type uint8 {
   range "1..27";
  }
  mandatory false;
 }
 leaf LOWRANKADJMCSTHLD {
  type uint8 {
   range "1..27";
  }
  mandatory false;
 }
 leaf MEDIUMRANKADJMCSLOWERTHLD {
  type uint8 {
   range "1..27";
  }
  mandatory false;
 }
 leaf MEDIUMRANKADJMCSUPPERTHLD {
  type uint8 {
   range "0..27";
  }
  mandatory false;
 }
 leaf MUMIMORANKENHEQVSINRTHLD {
  type int16 {
   range "-50..250";
  }
  mandatory false;
 }
 leaf MULTILAYERPCHIGHRANKMCSTHD {
  type uint8 {
   range "0..28";
  }
  mandatory false;
 }
 leaf NONASRANK1INCMCSTHLD {
  type uint8 {
   range "0..27";
  }
  mandatory false;
 }
 leaf NONASRANK2DECMCSTHLD {
  type uint8 {
   range "0..27";
  }
  mandatory false;
 }
 leaf NONASRANKSELPOL {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
  }
  mandatory false;
 }
 leaf NRDUCELLID {
  type union {
   type int32 {
    range "-1..65534";
   }
  }
  mandatory false;
 }
 leaf RANKSELHIGHSPCTEFFTHLD {
  type uint16 {
   range "1..300";
  }
  mandatory false;
 }
 leaf RANKSELLOWSPCTEFFTHLD {
  type uint16 {
   range "1..300";
  }
  mandatory false;
 }
 leaf ROBUSTWEIGHTRANK1FACTOR {
  type uint8 {
   range "0..200";
  }
  mandatory false;
 }
 leaf SPECTRALEFFIVARITHLD {
  type uint8 {
   range "0..100";
  }
  mandatory false;
 }
 leaf SRSDIFFBASEDDLRANKSELTHLD {
  type uint8 {
   range "1..40";
  }
  mandatory false;
 }
 }
 grouping NRDUCELLDLSCH-attributes {
 leaf ABNUELINKDETECTTHLD {
  type uint8 {
   range "50..100";
  }
  mandatory false;
 }
 leaf AERIALUSERDLSCHRBRATIO {
  type union {
   type uint8 {
    range "0..50";
   }
  }
  mandatory false;
 }
 leaf CLOUDSERVSPLITPRBTHLD {
  type uint8 {
   range "0..100";
  }
  mandatory false;
 }
 leaf CLOUDXFRAMELOSSRATETARGET {
  type uint8 {
   range "0..20";
  }
  mandatory false;
 }
 leaf CLOUDXRESCTRLDLPRBTHLD {
  type uint8 {
   range "50..100";
  }
  mandatory false;
 }
 leaf CONVERGENCEDELAYTHLD {
  type uint8 {
   range "0..100";
  }
  mandatory false;
 }
 leaf DLADAPTSCHPRBTHLD {
  type uint8 {
   range "20..100";
  }
  mandatory false;
 }
 leaf DLADAPTSCHTIMETHLD {
  type uint16 {
   range "0..300";
  }
  mandatory false;
 }
 leaf DLBEAMPRIBASEDSCH {
  type boolean;
  mandatory false;
 }
 leaf DLCCEBASEDSCHPRIFACTOR {
  type enumeration {
   enum val-0;
   enum val-1;
   enum val-2;
   enum val-3;
   enum val-4;
   enum val-5;
   enum val-6;
   enum val-7;
   enum val-8;
   enum val-9;
   enum val-10;
   enum val-11;
  }
  mandatory false;
 }
 leaf DLFLOWCTRLPRBUSAGETHLD0 {
  type uint8 {
   range "0..100";
  }
  mandatory false;
 }
 leaf DLFLOWCTRLPRBUSAGETHLD1 {
  type uint8 {
   range "0..100";
  }
  mandatory false;
 }
 leaf DLINITMCSADJAFTERHO {
  type int8 {
   range "-10..27";
  }
  mandatory false;
 }
 leaf DLINTRFBASEDIBLERTARGET {
  type uint8 {
   range "0..100";
  }
  mandatory false;
 }
 leaf DLINTRFRANDSTARTSECTION {
  type uint8 {
   range "0..3";
  }
  mandatory false;
 }
 leaf DLPOORQUALITYCQITHLD {
  type uint8 {
   range "0..15";
  }
  mandatory false;
 }
 leaf DLRETRANSMINRBREDUCECOEFF {
  type uint8 {
   range "0..100";
  }
  mandatory false;
 }
 leaf DLSCHALGOENHSWITCH {
  type string;
  mandatory false;
 }
 leaf DLSCHALGOSWITCH {
  type string;
  mandatory false;
 }
 leaf DLSCHHEAVYLOADPRBTHLD {
  type uint8 {
   range "50..100";
  }
  mandatory false;
 }
 leaf DLSCHPERFORMANCESWITCH {
  type string;
  mandatory false;
 }
 leaf DLSCHPOLICY {
  type boolean;
  mandatory false;
 }
 leaf DLSRBDRBSCHPOLICY {
  type enumeration {
   enum val-0;
   enum val-1;
   enum val-2;
  }
  mandatory false;
 }
 leaf FIRSTPKTEXPIMPRBPCTTHLD {
  type uint8 {
   range "1..100";
  }
  mandatory false;
 }
 leaf FREQSELSCHACTIVEUENUMTHLD {
  type uint8 {
   range "0..100";
  }
  mandatory false;
 }
 leaf FSSUESUBBANDCQIVALIDPRD {
  type uint8 {
   range "10..50";
  }
  mandatory false;
 }
 leaf HDSSAPERCSIINTVLADAPTCOEFF {
  type uint8 {
   range "120..200";
  }
  mandatory false;
 }
 leaf HDSSSPCTEFFCOEFFICIENT {
  type uint8 {
   range "90..110";
  }
  mandatory false;
 }
 leaf HIGHQUALITYUSERCSITHLD {
  type uint8 {
   range "2..20";
  }
  mandatory false;
 }
 leaf MINEXPECTEDDLUERATE {
  type uint32 {
   range "0..1000000";
  }
  mandatory false;
 }
 leaf NRDUCELLID {
  type union {
   type int32 {
    range "-1..65534";
   }
  }
  mandatory false;
 }
 leaf PAGINGANDRARTBSCALFACTOR {
  type enumeration {
   enum val-0;
   enum val-1;
   enum val-2;
   enum val-3;
  }
  mandatory false;
 }
 leaf PDSCHRMMCSTHLD {
  type uint8 {
   range "0..28";
  }
  mandatory false;
 }
 leaf POORCOVPDCCHRMMCSTHLD {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
  }
  mandatory false;
 }
 leaf RATEMATCHCODERATEMAXOFFSET {
  type uint8 {
   range "0..10";
  }
  mandatory false;
 }
 leaf RMSISPARSIFIEDSCHPOLICY {
  type enumeration {
   enum val-0;
   enum val-1;
   enum val-2;
   enum val-3;
   enum val-4;
   enum val-5;
   enum val-6;
   enum val-7;
   enum val-8;
   enum val-9;
  }
  mandatory false;
 }
 leaf SHORTVIDEODLSCHSW {
  type string;
  mandatory false;
 }
 leaf SIPDLINITTRANSMCSDECREASE {
  type uint8 {
   range "0..28";
  }
  mandatory false;
 }
 leaf SPECIFIEDUESRSPRESINRTHLD {
  type int8 {
   range "-100..100";
  }
  mandatory false;
 }
 leaf STOPSPLITRESBLKERRCNTTHID {
  type uint8 {
   range "0..100";
  }
  mandatory false;
 }
 leaf VINRDLINITTRANSMCSDECREASE {
  type uint8 {
   range "0..28";
  }
  mandatory false;
 }
 leaf VINRDLSCHSWITCH {
  type string;
  mandatory false;
 }
 leaf VOICEDLSCHSWITCH {
  type string;
  mandatory false;
 }
 }
 grouping NRDUCELLDMRS-attributes {
 leaf DLADDLDMRSADAPTMCSTHLD {
  type uint8 {
   range "0..27";
  }
  mandatory false;
 }
 leaf DLADPADDDMRSFREQOFSLOWTHLD {
  type uint16 {
   range "0..1500";
  }
  mandatory false;
 }
 leaf DLADPADDDMRSFREQOFSUPTHLD {
  type uint16 {
   range "0..2500";
  }
  mandatory false;
 }
 leaf DLADPADDDMRSPOSFALLCNTTHLD {
  type uint16 {
   range "1..10000";
  }
  mandatory false;
 }
 leaf DLADPADDDMRSPOSRISECNTTHLD {
  type uint16 {
   range "1..10000";
  }
  mandatory false;
 }
 leaf DLDMRSSWITCH {
  type string;
  mandatory false;
 }
 leaf DLDMRSTYPEADAPTMCSTHLD {
  type uint8 {
   range "0..27";
  }
  mandatory false;
 }
 leaf DLMUESTRBPOLICY {
  type enumeration {
   enum val-0;
   enum val-1;
   enum val-2;
  }
  mandatory false;
 }
 leaf DLPOSADAPTOPTALGOSW {
  type string;
  mandatory false;
 }
 leaf DMRSTYPEAPOS {
  type enumeration {
   enum val-0;
   enum val-1;
   enum val-2;
  }
  mandatory false;
 }
 leaf INITDMRSRSRPWEAKCOVTHLD {
  type int16 {
   range "-140..-120";
  }
  mandatory false;
 }
 leaf INITDMRSSINRWEAKCOVTHLD {
  type int8 {
   range "-15..10";
  }
  mandatory false;
 }
 leaf NRDUCELLID {
  type union {
   type int32 {
    range "-1..65534";
   }
  }
  mandatory false;
 }
 leaf PDSCHDMRSFDMMCSTHID {
  type uint8 {
   range "0..27";
  }
  mandatory false;
 }
 leaf ULDMRSNONORTHMUXMCSADJVAL {
  type uint8 {
   range "0..5";
  }
  mandatory false;
 }
 leaf ULDMRSNONORTHMUXPORTISOTHD {
  type uint8 {
   range "0..29";
  }
  mandatory false;
 }
 leaf ULDMRSNONORTHMUXRESPOLICY {
  type enumeration {
   enum val-0;
   enum val-1;
   enum val-2;
  }
  mandatory false;
 }
 leaf ULDMRSNONORTHMUXSUSPENDNUM {
  type uint8 {
   range "0..9";
  }
  mandatory false;
 }
 leaf ULDMRSSWITCH {
  type string;
  mandatory false;
 }
 }
 grouping NRDUCELLFEATURESW-attributes {
 leaf AHRSWITCH {
  type string;
  mandatory false;
 }
 leaf CUSTOMIZEDSPCTSWITCH {
  type string;
  mandatory false;
 }
 leaf DLEHRSWITCH {
  type boolean;
  mandatory false;
 }
 leaf DMNSWITCH {
  type string;
  mandatory false;
 }
 leaf HDVIDEOACCELERATORSWITCH {
  type string;
  mandatory false;
 }
 leaf HIGHPRECISIONBEAMPHASE2SW {
  type boolean;
  mandatory false;
 }
 leaf HIGHPRECISIONBEAMSWITCH {
  type boolean;
  mandatory false;
 }
 leaf HIGHRELIABILITYEXTSWITCH {
  type string;
  mandatory false;
 }
 leaf MIMOFEATURESWITCH {
  type string;
  mandatory false;
 }
 leaf MULTICARRIERSWITCH {
  type string;
  mandatory false;
 }
 leaf NRDUCELLID {
  type union {
   type int32 {
    range "-1..65534";
   }
  }
  mandatory false;
 }
 leaf PERFORMANCEALGOSWITCH {
  type string;
  mandatory false;
 }
 leaf PWSSWITCH {
  type string;
  mandatory false;
 }
 leaf QCIBASEDDIFFSERVEXPSW {
  type string;
  mandatory false;
 }
 leaf SHORTVIDEOIDENTPOLICY {
  type boolean;
  mandatory false;
 }
 leaf STABLEULSERVICEEXPSWITCH {
  type string;
  mandatory false;
 }
 leaf UECAPBBASEDFUNSW {
  type string;
  mandatory false;
 }
 leaf V2XSWITCH {
  type string;
  mandatory false;
 }
 }
 grouping NRDUCELLFWAQOS-attributes {
 leaf ACTIVEUENUMRATIOTHLD {
  type uint16 {
   range "1..1000";
  }
  mandatory false;
 }
 leaf DLAMBR {
  type uint8 {
   range "1..100";
  }
  mandatory false;
 }
 leaf DLPRBUSAGETHRESHOLD {
  type uint8 {
   range "0..100";
  }
  mandatory false;
 }
 leaf EMBBCONGESTDELAYTHLD {
  type uint8 {
   range "30..100";
  }
  mandatory false;
 }
 leaf EMBBPRIORITIZEDYNPRBTHLD {
  type uint8 {
   range "1..100";
  }
  mandatory false;
 }
 leaf EXPBASEDSCHMAXWEIGHT {
  type uint8 {
   range "10..100";
  }
  mandatory false;
 }
 leaf FWAINTERNETUSERRESID {
  type union {
   type uint8 {
    range "0..255";
   }
  }
  mandatory false;
 }
 leaf FWAPRIVATELINEUSERRESID {
  type union {
   type uint8 {
    range "0..255";
   }
  }
  mandatory false;
 }
 leaf FWARESALLOCCOEFF {
  type uint8 {
   range "20..100";
  }
  mandatory false;
 }
 leaf NONFWAINTERNETUSERRESID {
  type union {
   type uint8 {
    range "0..255";
   }
  }
  mandatory false;
 }
 leaf NRDUCELLID {
  type union {
   type int32 {
    range "-1..65534";
   }
  }
  mandatory false;
 }
 leaf PRIREDUCTION {
  type union {
   type uint16 {
    range "2..1024";
   }
  }
  mandatory false;
 }
 leaf UECOOPMAXPREALLOCRBRATIO {
  type uint8 {
   range "1..100";
  }
  mandatory false;
 }
 leaf UECOOPMINPREALLOCPERIOD {
  type uint8 {
   range "1..255";
  }
  mandatory false;
 }
 leaf ULAMBR {
  type uint8 {
   range "1..100";
  }
  mandatory false;
 }
 leaf ULPRBUSAGETHRESHOLD {
  type uint8 {
   range "0..100";
  }
  mandatory false;
 }
 leaf USERNUMTHRESHOLD {
  type uint8 {
   range "0..100";
  }
  mandatory false;
 }
 }
 grouping NRDUCELLHIGHSPEEDMOB-attributes {
 leaf CHANNELBASEDDLMCSADJMAXOFS {
  type int8 {
   range "-5..0";
  }
  mandatory false;
 }
 leaf DLAFCMAXSTEP {
  type uint16 {
   range "10..600";
  }
  mandatory false;
 }
 leaf DLAFCPERIOD {
  type uint8 {
   range "1..16";
  }
  mandatory false;
 }
 leaf DLAFCTYPE {
  type enumeration {
   enum val-0;
   enum val-1;
   enum val-2;
  }
  mandatory false;
 }
 leaf DLINTRFBASEDPWROFFSET {
  type uint8 {
   range "0..20";
  }
  mandatory false;
 }
 leaf DLINTRFLIMITRBSCHRATIO {
  type uint8 {
   range "0..100";
  }
  mandatory false;
 }
 leaf DLRBESTINTRFRANDOMPRBTHLD {
  type uint8 {
   range "0..100";
  }
  mandatory false;
 }
 leaf FREQOFSMEASENHPOOFFSET {
  type uint8 {
   range "0..15";
  }
  mandatory false;
 }
 leaf HSINTRFRANDOMSCHPRBTHLD {
  type uint8 {
   range "0..100";
  }
  mandatory false;
 }
 leaf HSTRAINTEMPSTOPUENUMTHLD {
  type uint16 {
   range "20..1200";
  }
  mandatory false;
 }
 leaf HIGHSPEEDALGOOPTSW {
  type string;
  mandatory false;
 }
 leaf HIGHSPEEDDLMCSFILTERCOEFF {
  type uint8 {
   range "0..100";
  }
  mandatory false;
 }
 leaf HIGHSPEEDFREQOFFSETNUMTHLD {
  type uint8 {
   range "4..255";
  }
  mandatory false;
 }
 leaf HIGHSPEEDFREQOFFSETTHLD {
  type uint16 {
   range "1..2000";
  }
  mandatory false;
 }
 leaf HIGHSPEEDULAMCADJUSTSTEP {
  type uint8 {
   range "0..100";
  }
  mandatory false;
 }
 leaf HIGHSPEEDULSINRFILTERCOEFF {
  type uint8 {
   range "0..100";
  }
  mandatory false;
 }
 leaf HIGHSPEEDUSERNUMTHLD {
  type uint8 {
   range "5..100";
  }
  mandatory false;
 }
 leaf LOWSPEEDFREQOFFSETTHLD {
  type uint16 {
   range "1..2000";
  }
  mandatory false;
 }
 leaf LOWSPEEDSTAYTIMETHLD {
  type uint16 {
   range "1..900";
  }
  mandatory false;
 }
 leaf NEARPOLEDOPPLERSHIFTTHLD {
  type uint16 {
   range "1..1500";
  }
  mandatory false;
 }
 leaf NRDUCELLID {
  type union {
   type int32 {
    range "-1..65534";
   }
  }
  mandatory false;
 }
 leaf REDCAPUESRSRESALLOCPOL {
  type enumeration {
   enum val-0;
   enum val-1;
   enum val-2;
  }
  mandatory false;
 }
 leaf ROBUSTWEIGHTFILTERCOEFF {
  type uint8 {
   range "1..10";
  }
  mandatory false;
 }
 leaf ROBUSTWEIGHTKFACTORTHLD {
  type int8 {
   range "-10..15";
  }
  mandatory false;
 }
 leaf SRSRESMULTIPLEXPOLICY {
  type boolean;
  mandatory false;
 }
 leaf TRPHOINITIALMCSOPTOFFSET {
  type uint8 {
   range "0..10";
  }
  mandatory false;
 }
 leaf ULINTRFBASEDPWROFFSET {
  type uint8 {
   range "0..20";
  }
  mandatory false;
 }
 leaf ULINTRFLIMITRBSCHRATIO {
  type uint8 {
   range "0..100";
  }
  mandatory false;
 }
 leaf ULRBESTINTRFRANDOMPRBTHLD {
  type uint8 {
   range "0..100";
  }
  mandatory false;
 }
 }
 grouping NRDUCELLINTRFAVOID-attributes {
 leaf OLD_INTRFCELLIINTRFRESTYPE {
  type enumeration {
   enum val--1;
   enum val-0;
   enum val-1;
  }
  mandatory false;
 }
 leaf INTRFCELLIINTRFRESTYPE {
  type enumeration {
   enum val--1;
   enum val-0;
   enum val-1;
  }
  mandatory false;
 }
 leaf OLD_INTRFCELLINTRFBANDINDEX {
  type union {
   type int8 {
    range "-1..0";
   }
  }
  mandatory false;
 }
 leaf INTRFCELLINTRFBANDINDEX {
  type union {
   type int8 {
    range "-1..0";
   }
  }
  mandatory false;
 }
 leaf INTRFCELLINTRFENDRB {
  type uint16 {
   range "0..272";
  }
  mandatory false;
 }
 leaf INTRFCELLINTRFSLOT {
  type uint16 {
   range "0..1023";
  }
  mandatory false;
 }
 leaf INTRFCELLINTRFSTARTRB {
  type uint16 {
   range "0..272";
  }
  mandatory false;
 }
 leaf OLD_NRDUCELLID {
  type union {
   type int32 {
    range "-1..65534";
   }
  }
  mandatory false;
 }
 leaf NRDUCELLID {
  type union {
   type int32 {
    range "-1..65534";
   }
  }
  mandatory false;
 }
 }
 grouping NRDUCELLISOLATIONDET-attributes {
 leaf OLD_CONFIGPARAID {
  type union {
   type int8 {
    range "-1..1";
   }
  }
  mandatory false;
 }
 leaf CONFIGPARAID {
  type union {
   type int8 {
    range "-1..1";
   }
  }
  mandatory false;
 }
 leaf ENDFREQOFFSET {
  type uint8 {
   range "1..150";
  }
  mandatory false;
 }
 leaf INITIALISOLATION {
  type uint16 {
   range "0..1000";
  }
  mandatory false;
 }
 leaf MAXBLOCKEDRBNUM {
  type union {
   type uint8 {
    range "1..255";
   }
  }
  mandatory false;
 }
 leaf NARROWBANDTXPOWER {
  type int16 {
   range "-1000..1000";
  }
  mandatory false;
 }
 leaf OLD_NRDUCELLID {
  type union {
   type int32 {
    range "-1..65534";
   }
  }
  mandatory false;
 }
 leaf NRDUCELLID {
  type union {
   type int32 {
    range "-1..65534";
   }
  }
  mandatory false;
 }
 leaf POWERPROFILE {
  type boolean;
  mandatory false;
 }
 leaf RBEXTENDDETECTNUM {
  type uint16 {
   range "1..1000";
  }
  mandatory false;
 }
 leaf RBSHRINKDETECTNUM {
  type uint16 {
   range "1..1000";
  }
  mandatory false;
 }
 leaf STARTFREQOFFSET {
  type uint8 {
   range "0..149";
  }
  mandatory false;
 }
 leaf ULBLOCKTHLD {
  type int16 {
   range "-1000..1000";
  }
  mandatory false;
 }
 leaf WIDEBANDTXPOWER {
  type int16 {
   range "-1000..1000";
  }
  mandatory false;
 }
 leaf WORKMODE {
  type boolean;
  mandatory false;
 }
 }
 grouping NRDUCELLMEAS-attributes {
 leaf MEASALGOSWITCH {
  type string;
  mandatory false;
 }
 leaf NRDUCELLID {
  type union {
   type int32 {
    range "-1..65534";
   }
  }
  mandatory false;
 }
 leaf SSBMEASPOLICYSWITCH {
  type string;
  mandatory false;
 }
 }
 grouping NRDUCELLNONCONSPCT-attributes {
 leaf ENDRB {
  type uint16 {
   range "0..272";
  }
  mandatory false;
 }
 leaf NONCONTIGSPCTDIRECTION {
  type boolean;
  mandatory false;
 }
 leaf OLD_NONCONTIGSPCTINDEX {
  type union {
   type int8 {
    range "-1..5";
   }
  }
  mandatory false;
 }
 leaf NONCONTIGSPCTINDEX {
  type union {
   type int8 {
    range "-1..5";
   }
  }
  mandatory false;
 }
 leaf OLD_NRDUCELLID {
  type union {
   type int32 {
    range "-1..65534";
   }
  }
  mandatory false;
 }
 leaf NRDUCELLID {
  type union {
   type int32 {
    range "-1..65534";
   }
  }
  mandatory false;
 }
 leaf PRIMARYSPCTFLAG {
  type boolean;
  mandatory false;
 }
 leaf STARTRB {
  type uint16 {
   range "0..272";
  }
  mandatory false;
 }
 }
 grouping NRDUCELLNSADCCONFIG-attributes {
 leaf EXCEPTIONTIMESTHLD {
  type uint16 {
   range "0..300";
  }
  mandatory false;
 }
 leaf FIRSTACKRLCPDUDELAYTHLD {
  type uint8 {
   range "0..30";
  }
  mandatory false;
 }
 leaf HARMONICINTRFAVOIDRANGE {
  type boolean;
  mandatory false;
 }
 leaf LOWCORPEAKPREAMSCGRELTIMER {
  type uint16 {
   range "10..500";
  }
  mandatory false;
 }
 leaf NRDUCELLID {
  type union {
   type int32 {
    range "-1..65534";
   }
  }
  mandatory false;
 }
 leaf NRULESTRATEMAXSINROFS {
  type int16 {
   range "-200..300";
  }
  mandatory false;
 }
 leaf NRULESTRATESINROFSADJPRD {
  type uint16 {
   range "1..5000";
  }
  mandatory false;
 }
 leaf NSADCDLSPLITRLCRATE {
  type uint16 {
   range "0..1000";
  }
  mandatory false;
 }
 leaf PERCEIVEDRATETHLD {
  type uint16 {
   range "0..10000";
  }
  mandatory false;
 }
 leaf SCGRELDLCQITHLD {
  type uint8 {
   range "0..15";
  }
  mandatory false;
 }
 leaf SCGRELPREAMBLECORPEAKTHLD {
  type uint16 {
   range "0..1000";
  }
  mandatory false;
 }
 leaf SCGRELULSRSSINRTHLD {
  type int16 {
   range "-200..200";
  }
  mandatory false;
 }
 leaf ULCONSECRESIDUALERRBLOCKS {
  type uint16 {
   range "1..500";
  }
  mandatory false;
 }
 leaf ULPATHCHANGERATERATIOTHLD {
  type uint8 {
   range "1..200";
  }
  mandatory false;
 }
 leaf USEREXPSCGRELMEASNUM {
  type uint8 {
   range "5..25";
  }
  mandatory false;
 }
 }
 grouping NRDUCELLNSGRP-attributes {
 leaf CELLRESID {
  type union {
   type uint8 {
    range "0..255";
   }
  }
  mandatory false;
 }
 leaf OLD_NRDUCELLID {
  type union {
   type int32 {
    range "-1..65534";
   }
  }
  mandatory false;
 }
 leaf NRDUCELLID {
  type union {
   type int32 {
    range "-1..65534";
   }
  }
  mandatory false;
 }
 leaf NSGRPDESCRIPTION {
  type string {
   length "0..127";
  }
  mandatory false;
 }
 leaf OLD_NSGRPID {
  type union {
   type int8 {
    range "-1..31";
   }
  }
  mandatory false;
 }
 leaf NSGRPID {
  type union {
   type int8 {
    range "-1..31";
   }
  }
  mandatory false;
 }
 }
 grouping NRDUCELLNSGRPNS-attributes {
 leaf NRDUCELLID {
  type union {
   type int32 {
    range "-1..65534";
   }
  }
  mandatory false;
 }
 leaf NSGRPID {
  type union {
   type int8 {
    range "-1..31";
   }
  }
  mandatory false;
 }
 leaf OPERATORID {
  type union {
   type int8 {
    range "-1..11";
   }
  }
  mandatory false;
 }
 leaf SLICEDIFFERENTIATOR {
  type union {
   type int32 {
    range "-1..16777215";
   }
  }
  mandatory false;
 }
 leaf SLICESERVICETYPE {
  type union {
   type int16 {
    range "-1..255";
   }
  }
  mandatory false;
 }
 }
 grouping NRDUCELLNSMGMTCONFIG-attributes {
 leaf NETSLICERFSPGRPPREEMPTPOL {
  type boolean;
  mandatory false;
 }
 leaf NETSLICERFSPGRPSHAREPOL {
  type boolean;
  mandatory false;
 }
 leaf NRDUCELLID {
  type union {
   type int32 {
    range "-1..65534";
   }
  }
  mandatory false;
 }
 }
 grouping NRDUCELLOP-attributes {
 leaf CAGCELLID {
  type uint16 {
   range "0..16383";
  }
  mandatory false;
 }
 leaf CAGGRPID {
  type uint8 {
   range "0..143";
  }
  mandatory false;
 }
 leaf CELLID {
  type union {
   type uint16 {
    range "0..65535";
   }
  }
  mandatory false;
 }
 leaf CELLPRIMARYOPFLAG {
  type boolean;
  mandatory false;
 }
 leaf CELLRESID {
  type union {
   type uint8 {
    range "0..255";
   }
  }
  mandatory false;
 }
 leaf CELLRESERVEDFOROP {
  type boolean;
  mandatory false;
 }
 leaf NRDUCELLID {
  type union {
   type int32 {
    range "-1..65534";
   }
  }
  mandatory false;
 }
 leaf NRNETWORKINGOPTION {
  type enumeration {
   enum val-0;
   enum val-1;
   enum val-2;
   enum val-3;
  }
  mandatory false;
 }
 leaf OPCAGEXISTFLAG {
  type boolean;
  mandatory false;
 }
 leaf OPERATORID {
  type union {
   type int8 {
    range "-1..11";
   }
  }
  mandatory false;
 }
 leaf PLMNROUNDROBINPERIOD {
  type uint16 {
   range "1..720";
  }
  mandatory false;
 }
 leaf POLICYSWITCH {
  type string;
  mandatory false;
 }
 leaf RANNOTIFICATIONAREAID {
  type union {
   type uint16 {
    range "0..65535";
   }
  }
  mandatory false;
 }
 leaf TRACKINGAREAID {
  type union {
   type uint32 {
    range "0..4294967295";
   }
  }
  mandatory false;
 }
 leaf USERLABEL {
  type string {
   length "0..256";
  }
  mandatory false;
 }
 }
 grouping NRDUCELLOPFWAQOS-attributes {
 leaf FWAINTERNETUSERRESID {
  type union {
   type uint8 {
    range "0..255";
   }
  }
  mandatory false;
 }
 leaf FWAPRIVATELINEUSERRESID {
  type union {
   type uint8 {
    range "0..255";
   }
  }
  mandatory false;
 }
 leaf NONFWAINTERNETUSERRESID {
  type union {
   type uint8 {
    range "0..255";
   }
  }
  mandatory false;
 }
 leaf OLD_NRDUCELLID {
  type union {
   type int32 {
    range "-1..65534";
   }
  }
  mandatory false;
 }
 leaf NRDUCELLID {
  type union {
   type int32 {
    range "-1..65534";
   }
  }
  mandatory false;
 }
 leaf OLD_OPERATORID {
  type union {
   type int8 {
    range "-1..11";
   }
  }
  mandatory false;
 }
 leaf OPERATORID {
  type union {
   type int8 {
    range "-1..11";
   }
  }
  mandatory false;
 }
 }
 grouping NRDUCELLOPQCI-attributes {
 leaf OLD_NRDUCELLID {
  type union {
   type int32 {
    range "-1..65534";
   }
  }
  mandatory false;
 }
 leaf NRDUCELLID {
  type union {
   type int32 {
    range "-1..65534";
   }
  }
  mandatory false;
 }
 leaf OLD_OPERATORID {
  type union {
   type int8 {
    range "-1..11";
   }
  }
  mandatory false;
 }
 leaf OPERATORID {
  type union {
   type int8 {
    range "-1..11";
   }
  }
  mandatory false;
 }
 leaf OLD_QCI {
  type union {
   type int16 {
    range "-1..255";
   }
  }
  mandatory false;
 }
 leaf QCI {
  type union {
   type int16 {
    range "-1..255";
   }
  }
  mandatory false;
 }
 leaf QCIGRPCELLRESID {
  type union {
   type uint8 {
    range "0..255";
   }
  }
  mandatory false;
 }
 leaf QCIPRILVL {
  type uint8 {
   range "0..255";
  }
  mandatory false;
 }
 }
 grouping NRDUCELLOPRFSP-attributes {
 leaf OLD_NRDUCELLID {
  type union {
   type int32 {
    range "-1..65534";
   }
  }
  mandatory false;
 }
 leaf NRDUCELLID {
  type union {
   type int32 {
    range "-1..65534";
   }
  }
  mandatory false;
 }
 leaf OLD_OPERATORID {
  type union {
   type int8 {
    range "-1..11";
   }
  }
  mandatory false;
 }
 leaf OPERATORID {
  type union {
   type int8 {
    range "-1..11";
   }
  }
  mandatory false;
 }
 leaf RFSPGRPCELLRESID {
  type union {
   type uint8 {
    range "0..255";
   }
  }
  mandatory false;
 }
 leaf OLD_RFSPINDEX {
  type union {
   type int16 {
    range "-1..256";
   }
  }
  mandatory false;
 }
 leaf RFSPINDEX {
  type union {
   type int16 {
    range "-1..256";
   }
  }
  mandatory false;
 }
 }
 grouping NRDUCELLPAGINGCONFIG-attributes {
 leaf DEFAULTPAGINGCYCLE {
  type enumeration {
   enum val-0;
   enum val-1;
   enum val-2;
   enum val-3;
  }
  mandatory false;
 }
 leaf MAXGROUPPAGINGMSGNUM {
  type uint8 {
   range "1..32";
  }
  mandatory false;
 }
 leaf MAXPAGINGMSGNUM {
  type uint8 {
   range "1..32";
  }
  mandatory false;
 }
 leaf NRDUCELLID {
  type union {
   type int32 {
    range "-1..65534";
   }
  }
  mandatory false;
 }
 leaf PAGINGCAPACITYMODE {
  type boolean;
  mandatory false;
 }
 leaf PAGINGFRAMETRANSPOLICY {
  type uint8 {
   range "0..4";
  }
  mandatory false;
 }
 leaf PAGINGSCHALGOSWITCH {
  type string;
  mandatory false;
 }
 leaf PAGINGTIMEOUTDISCARDTIMER {
  type uint8 {
   range "3..12";
  }
  mandatory false;
 }
 leaf PAGINGTRANSPOLICY {
  type boolean;
  mandatory false;
 }
 leaf PRIBASEDPAGINGRETRANSPOL {
  type enumeration {
   enum val-0;
   enum val-1;
   enum val-2;
   enum val-3;
   enum val-4;
   enum val-5;
   enum val-6;
   enum val-7;
   enum val-8;
  }
  mandatory false;
 }
 leaf SIMODEDRXPAGINGTIME {
  type enumeration {
   enum val-0;
   enum val-1;
   enum val-2;
   enum val-3;
   enum val-4;
   enum val-5;
   enum val-6;
   enum val-7;
   enum val-8;
   enum val-9;
   enum val-10;
   enum val-11;
   enum val-12;
   enum val-13;
  }
  mandatory false;
 }
 }
 grouping NRDUCELLPDCCH-attributes {
 leaf ANTIDROPRSVDRESDUR {
  type enumeration {
   enum val-5;
   enum val-10;
   enum val-15;
   enum val-20;
  }
  mandatory false;
 }
 leaf ANTIDROPRSVDRESPRD {
  type enumeration {
   enum val-0;
   enum val-5;
   enum val-10;
   enum val-20;
   enum val-40;
   enum val-60;
   enum val-80;
   enum val-100;
   enum val-120;
   enum val-140;
   enum val-160;
  }
  mandatory false;
 }
 leaf CCERATIOADAPTADJPRD {
  type uint16 {
   range "1..360";
  }
  mandatory false;
 }
 leaf COMMULRESRSVMODE {
  type boolean;
  mandatory false;
 }
 leaf COMMULRSVPCT {
  type union {
   type uint8 {
    range "0..100";
   }
  }
  mandatory false;
 }
 leaf CQIFREESINRADJSTEP {
  type uint8 {
   range "1..50";
  }
  mandatory false;
 }
 leaf ENHRESALLOCCCETHLD {
  type uint8 {
   range "1..100";
  }
  mandatory false;
 }
 leaf GUARANTEEDRBNUM {
  type uint8 {
   range "0..17";
  }
  mandatory false;
 }
 leaf HEAVYLOADCCEUSAGETHLD {
  type uint8 {
   range "50..100";
  }
  mandatory false;
 }
 leaf HEAVYLOADULCCEADJPOLICY {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf HIGHLOADINITSINROFFSET {
  type int8 {
   range "-30..30";
  }
  mandatory false;
 }
 leaf IBLERPDCCHSINROFFSET {
  type int8 {
   range "-30..15";
  }
  mandatory false;
 }
 leaf LIGHTLOADINITSINROFFSET {
  type int8 {
   range "-30..30";
  }
  mandatory false;
 }
 leaf MAXCOMMONPDCCHAGGLVL {
  type enumeration {
   enum val-2;
   enum val-3;
   enum val-4;
  }
  mandatory false;
 }
 leaf MAXPAIRLAYERNUM {
  type enumeration {
   enum val-0;
   enum val-1;
   enum val-2;
  }
  mandatory false;
 }
 leaf MAXPDCCHSINRCHANGE {
  type uint8 {
   range "1..10";
  }
  mandatory false;
 }
 leaf NONDTXSINRINCREASESTEP {
  type uint8 {
   range "0..50";
  }
  mandatory false;
 }
 leaf NRDUCELLID {
  type union {
   type int32 {
    range "-1..65534";
   }
  }
  mandatory false;
 }
 leaf NRPREFERENTIALPDCCHRBNUM {
  type uint8 {
   range "0..100";
  }
  mandatory false;
 }
 leaf OCCUPIEDRBNUM {
  type uint8 {
   range "0..22";
  }
  mandatory false;
 }
 leaf OCCUPIEDSYMBOLNUM {
  type enumeration {
   enum val-0;
   enum val-1;
   enum val-2;
   enum val-3;
   enum val-4;
  }
  mandatory false;
 }
 leaf PDCCHADJREFRESTYPE {
  type string;
  mandatory false;
 }
 leaf PDCCHAGGLEVEL1STRATEGY {
  type enumeration {
   enum val-0;
   enum val-1;
   enum val-2;
  }
  mandatory false;
 }
 leaf PDCCHAGGLVLADAPTPOL {
  type boolean;
  mandatory false;
 }
 leaf PDCCHALGOENHSWITCH {
  type string;
  mandatory false;
 }
 leaf PDCCHALGOEXTSWITCH {
  type string;
  mandatory false;
 }
 leaf PDCCHALGOSWITCH {
  type string;
  mandatory false;
 }
 leaf PDCCHBLERTARGET {
  type uint8 {
   range "0..200";
  }
  mandatory false;
 }
 leaf PDCCHCOVENHDTXTHLD {
  type uint8 {
   range "0..100";
  }
  mandatory false;
 }
 leaf PDCCHMUMIMOSPACEISOTHLD {
  type uint8 {
   range "1..30";
  }
  mandatory false;
 }
 leaf PDCCHSYMMINADJINTVL {
  type uint16 {
   range "1..3600";
  }
  mandatory false;
 }
 leaf PWRSAVEBWPCCEADJUSTPOLICY {
  type boolean;
  mandatory false;
 }
 leaf SEARCHSPACEZERO {
  type enumeration {
   enum val-0;
   enum val-1;
   enum val-3;
  }
  mandatory false;
 }
 leaf SGLDCISCCCCEFAILRATETHLD {
  type uint8 {
   range "15..100";
  }
  mandatory false;
 }
 leaf SINGLEDCIAVAILCCERATIO {
  type uint8 {
   range "0..100";
  }
  mandatory false;
 }
 leaf SPCTSHRSTARTSYMBOL {
  type enumeration {
   enum val-0;
   enum val-1;
   enum val-2;
  }
  mandatory false;
 }
 leaf SULCCEADJPOLICY {
  type enumeration {
   enum val-0;
   enum val-1;
   enum val-2;
   enum val-3;
   enum val-4;
   enum val-5;
   enum val-6;
   enum val-7;
   enum val-8;
   enum val-9;
   enum val-10;
   enum val-11;
  }
  mandatory false;
 }
 leaf SULMAXCCEPCT {
  type uint8 {
   range "0..100";
  }
  mandatory false;
 }
 leaf UECTRLMSGAGGLVL {
  type enumeration {
   enum val-0;
   enum val-1;
   enum val-2;
   enum val-3;
   enum val-4;
  }
  mandatory false;
 }
 leaf UEPDCCHADAPTMAXSYMNUM {
  type boolean;
  mandatory false;
 }
 leaf UESPECIFICPDCCHAGGLVL {
  type enumeration {
   enum val-0;
   enum val-1;
   enum val-2;
   enum val-3;
   enum val-4;
   enum val-255;
  }
  mandatory false;
 }
 leaf ULCCEPCTMAXADJSTEP {
  type uint8 {
   range "5..100";
  }
  mandatory false;
 }
 leaf ULCCERATIOUPPERLIMIT {
  type uint8 {
   range "0..100";
  }
  mandatory false;
 }
 leaf ULMAXCCEPCT {
  type uint8 {
   range "0..100";
  }
  mandatory false;
 }
 }
 grouping NRDUCELLPDCCHALGO-attributes {
 leaf AGGLVLCOMPRCCEUSAGETHLD {
  type enumeration {
   enum val-30;
   enum val-40;
   enum val-50;
   enum val-60;
   enum val-70;
   enum val-80;
   enum val-90;
   enum val-100;
  }
  mandatory false;
 }
 leaf AVAILABLECCERATIOTHLD {
  type uint8 {
   range "0..20";
  }
  mandatory false;
 }
 leaf CCE4PWRAGGSINROFFSET {
  type uint8 {
   range "0..50";
  }
  mandatory false;
 }
 leaf CONTINUOUSCCEALLOCFAILTHLD {
  type enumeration {
   enum val-0;
   enum val-5;
   enum val-10;
   enum val-20;
   enum val-40;
   enum val-80;
   enum val-160;
   enum val-320;
  }
  mandatory false;
 }
 leaf EXTULDLSLOTULCCEPCT {
  type uint8 {
   range "0..100";
  }
  mandatory false;
 }
 leaf NRDUCELLID {
  type union {
   type int32 {
    range "-1..65534";
   }
  }
  mandatory false;
 }
 leaf PDCCHEDGEPWRCTRLMAXOFFSET {
  type union {
   type uint8 {
    range "0..250";
   }
  }
  mandatory false;
 }
 leaf PDCCHEDGEPWRCTRLPOLICY {
  type enumeration {
   enum val-0;
   enum val-1;
   enum val-2;
  }
  mandatory false;
 }
 leaf PDCCHMAXAGGLEVEL {
  type enumeration {
   enum val-0;
   enum val-1;
   enum val-2;
   enum val-3;
  }
  mandatory false;
 }
 leaf PDCCHNULCCERSVPERIOD {
  type enumeration {
   enum val-10;
   enum val-20;
   enum val-30;
   enum val-40;
   enum val-50;
   enum val-60;
   enum val-70;
   enum val-80;
   enum val-255;
  }
  mandatory false;
 }
 leaf PDCCHOUTERLOOPADJUPLIMIT {
  type uint8 {
   range "0..40";
  }
  mandatory false;
 }
 leaf PDCCHPRECODEENHPOLICY {
  type boolean;
  mandatory false;
 }
 leaf PDCCHPRECODEENHPRESINRTHLD {
  type int8 {
   range "-20..21";
  }
  mandatory false;
 }
 leaf PDCCHULCCEPCTADJPOLICY {
  type boolean;
  mandatory false;
 }
 leaf PDCCHULCCERSVPERIOD {
  type enumeration {
   enum val-0;
   enum val-5;
   enum val-10;
   enum val-20;
   enum val-40;
   enum val-80;
   enum val-160;
   enum val-320;
   enum val-640;
   enum val-1000;
  }
  mandatory false;
 }
 leaf PDCCHUSAGEIMPPOLICY {
  type enumeration {
   enum val-0;
   enum val-1;
   enum val-2;
   enum val-3;
   enum val-4;
  }
  mandatory false;
 }
 leaf PDCCHUSERNUMBERTHLDCOEFF {
  type uint8 {
   range "10..40";
  }
  mandatory false;
 }
 leaf RARSCHACCELERATESW {
  type boolean;
  mandatory false;
 }
 leaf VOICEPDCCHSINROFFSET {
  type uint8 {
   range "0..150";
  }
  mandatory false;
 }
 }
 grouping NRDUCELLPDSCH-attributes {
 leaf CLOUDVRMUMCSDECREASEVALUE {
  type uint8 {
   range "0..5";
  }
  mandatory false;
 }
 leaf CLOUDVRMUSCHDURPROP {
  type uint8 {
   range "0..10";
  }
  mandatory false;
 }
 leaf COMMONCTRLINFOMINIMUMMCS {
  type uint8 {
   range "0..9";
  }
  mandatory false;
 }
 leaf DEBFOPTFACTOR {
  type uint8 {
   range "0..10";
  }
  mandatory false;
 }
 leaf DLADDITIONALDMRSPOS {
  type enumeration {
   enum val-0;
   enum val-1;
   enum val-2;
   enum val-4;
  }
  mandatory false;
 }
 leaf DLDELAYSCHBUFFERTHLD {
  type uint8 {
   range "0..10";
  }
  mandatory false;
 }
 leaf DLDMRSCDMGROUPNUMBER {
  type enumeration {
   enum val-0;
   enum val-1;
   enum val-2;
  }
  mandatory false;
 }
 leaf DLDMRSCONFIGTYPE {
  type enumeration {
   enum val-0;
   enum val-1;
   enum val-2;
  }
  mandatory false;
 }
 leaf DLDMRSMAXLENGTH {
  type enumeration {
   enum val-0;
   enum val-1;
   enum val-2;
  }
  mandatory false;
 }
 leaf DLINITMCS {
  type uint8 {
   range "0..27";
  }
  mandatory false;
 }
 leaf DLINITMCSAFTERHO {
  type uint8 {
   range "0..27";
  }
  mandatory false;
 }
 leaf DLINITRANK {
  type enumeration {
   enum val-0;
   enum val-1;
   enum val-2;
   enum val-3;
  }
  mandatory false;
 }
 leaf DLINITRANKAFTERHO {
  type enumeration {
   enum val-0;
   enum val-1;
   enum val-2;
   enum val-3;
  }
  mandatory false;
 }
 leaf DLINITIALMCSADJVALUE {
  type int8 {
   range "-27..27";
  }
  mandatory false;
 }
 leaf DLLINKADAPTALGOSWITCH {
  type string;
  mandatory false;
 }
 leaf DLLINKADAPTENHANCEMENTSW {
  type string;
  mandatory false;
 }
 leaf DLLOWTIMECORRMUSW {
  type boolean;
  mandatory false;
 }
 leaf DLMIMOMCSOPTPOLICY {
  type enumeration {
   enum val-0;
   enum val-1;
   enum val-2;
   enum val-3;
   enum val-4;
   enum val-5;
  }
  mandatory false;
 }
 leaf DLMUGATHEROPTSW {
  type boolean;
  mandatory false;
 }
 leaf DLMUIRPRECODINGMCSTHLD {
  type uint8 {
   range "0..27";
  }
  mandatory false;
 }
 leaf DLMUINITIALMCSADJVALUE {
  type int8 {
   range "-27..27";
  }
  mandatory false;
 }
 leaf DLMUMIMOGROUPMODE {
  type enumeration {
   enum val-0;
   enum val-1;
   enum val-2;
   enum val-3;
   enum val-4;
   enum val-5;
  }
  mandatory false;
 }
 leaf DLMUSMALLGRANPRECODEDSTHLD {
  type uint8 {
   range "0..16";
  }
  mandatory false;
 }
 leaf DLNONSLOTSTARTSYMBOL {
  type uint8 {
   range "0..12";
  }
  mandatory false;
 }
 leaf DLPDSCHALGOSWITCH {
  type string;
  mandatory false;
 }
 leaf DLPMICODEBOOKMODE {
  type boolean;
  mandatory false;
 }
 leaf DLPMIMUMIMOSPACEISOTHLD {
  type uint16 {
   range "0..300";
  }
  mandatory false;
 }
 leaf DLPTRSFREQDENSITYNRB0 {
  type uint16 {
   range "1..276";
  }
  mandatory false;
 }
 leaf DLPTRSFREQDENSITYNRB1 {
  type uint16 {
   range "1..276";
  }
  mandatory false;
 }
 leaf DLPTRSTIMEDENSITYMCS1 {
  type uint8 {
   range "0..29";
  }
  mandatory false;
 }
 leaf DLPTRSTIMEDENSITYMCS2 {
  type uint8 {
   range "0..29";
  }
  mandatory false;
 }
 leaf DLPTRSTIMEDENSITYMCS3 {
  type uint8 {
   range "0..29";
  }
  mandatory false;
 }
 leaf DLSCHOPTTIMETHLD {
  type uint16 {
   range "0..10000";
  }
  mandatory false;
 }
 leaf DLSPARSESERVSCHDATAADJVAL {
  type uint16 {
   range "0..1000";
  }
  mandatory false;
 }
 leaf DLSRSMUMIMOCHANISOTHLD {
  type uint8 {
   range "0..100";
  }
  mandatory false;
 }
 leaf DLSRSMUMIMOFREQSELTHLD {
  type uint8 {
   range "0..20";
  }
  mandatory false;
 }
 leaf DLSRSMUMIMOPRESINRTHLD {
  type int8 {
   range "-20..20";
  }
  mandatory false;
 }
 leaf DLSRSMUMIMOSPACEISOTHLD {
  type uint16 {
   range "0..300";
  }
  mandatory false;
 }
 leaf DLTARGETIBLER {
  type uint8 {
   range "0..100";
  }
  mandatory false;
 }
 leaf FIXEDAMCSTEPVALUE {
  type uint8 {
   range "0..200";
  }
  mandatory false;
 }
 leaf FIXEDWEIGHTTYPE {
  type boolean;
  mandatory false;
 }
 leaf FWADLADDDMRSMCSTHLDOFFSET {
  type int8 {
   range "-10..10";
  }
  mandatory false;
 }
 leaf HIGHSPEEDCELLRIRESTR {
  type uint8 {
   range "0..15";
  }
  mandatory false;
 }
 leaf INTRAFDAPSDLMCSADJVALUE {
  type int8 {
   range "-10..0";
  }
  mandatory false;
 }
 leaf LTECRSALLSYMRMADAPTOFFSET {
  type uint8 {
   range "0..20";
  }
  mandatory false;
 }
 leaf LTECRSALLSYMRMADAPTTHLD {
  type int8 {
   range "-60..60";
  }
  mandatory false;
 }
 leaf MAXCLOUDVRSCHTRANSTIME {
  type uint8 {
   range "1..40";
  }
  mandatory false;
 }
 leaf MAXDLHARQTRANSNUM {
  type uint8 {
   range "1..8";
  }
  mandatory false;
 }
 leaf MAXMIMOLAYERNUM {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-255;
  }
  mandatory false;
 }
 leaf MCSADJUSTSWITCH {
  type string;
  mandatory false;
 }
 leaf MUMIMOPWRALLOCSWITCH {
  type boolean;
  mandatory false;
 }
 leaf NRDUCELLID {
  type union {
   type int32 {
    range "-1..65534";
   }
  }
  mandatory false;
 }
 leaf RATEMATCHSWITCH {
  type string;
  mandatory false;
 }
 leaf ROBUSTWTPHASECALCMETHOD {
  type boolean;
  mandatory false;
 }
 leaf SPARSESERVDLMCSDECVALUE {
  type uint8 {
   range "0..6";
  }
  mandatory false;
 }
 leaf SRSPRESINRJUDGETHLD {
  type int8 {
   range "-100..100";
  }
  mandatory false;
 }
 leaf SRSPRESINRTHLD {
  type int8 {
   range "-20..20";
  }
  mandatory false;
 }
 leaf SUBALSCHUENUMTHLD {
  type uint16 {
   range "1..10000";
  }
  mandatory false;
 }
 leaf SUMULTILAYERPWRCTRLMCSTHLD {
  type uint8 {
   range "0..27";
  }
  mandatory false;
 }
 leaf VMIMODLJTSCHTHLD {
  type uint8 {
   range "0..100";
  }
  mandatory false;
 }
 }
 grouping NRDUCELLPDSCHPRECODE-attributes {
 leaf CHNEIGDIFFTHLD {
  type uint8 {
   range "0..100";
  }
  mandatory false;
 }
 leaf CORRCALCSRSWEIGHTVALIDPRD {
  type uint8 {
   range "10..60";
  }
  mandatory false;
 }
 leaf DLADAPTPRECODECORROFFSET {
  type uint8 {
   range "1..100";
  }
  mandatory false;
 }
 leaf DLADAPTPRECODECORRTHLD {
  type uint8 {
   range "0..100";
  }
  mandatory false;
 }
 leaf DLCHNPREDCORRHYST {
  type uint8 {
   range "0..60";
  }
  mandatory false;
 }
 leaf DLCHNPREDCORRUPPERTHLD {
  type uint8 {
   range "1..100";
  }
  mandatory false;
 }
 leaf DLCHNPREDPRESINRTHLD {
  type int8 {
   range "-20..20";
  }
  mandatory false;
 }
 leaf DLCODEBOOKTYPESPCTEFFCOEFF {
  type uint16 {
   range "0..1000";
  }
  mandatory false;
 }
 leaf DLCODEBOOKTYPESWITCH {
  type string;
  mandatory false;
 }
 leaf DLLINKADAPTKFACTORTHLD {
  type int8 {
   range "-100..100";
  }
  mandatory false;
 }
 leaf DLMOBENHINTRFOPTPOL {
  type enumeration {
   enum val-0;
   enum val-1;
   enum val-2;
   enum val-3;
  }
  mandatory false;
 }
 leaf DLMUIRPRECODEPOL {
  type enumeration {
   enum val-1;
   enum val-2;
   enum val-3;
  }
  mandatory false;
 }
 leaf DLMUMOBPRECODECORRUPRTHLD {
  type uint8 {
   range "61..100";
  }
  mandatory false;
 }
 leaf DLMUPRECODEIRCOEFF {
  type union {
   type uint8 {
    range "0..50";
   }
  }
  mandatory false;
 }
 leaf DLPRECODEOPTONSRSDTXSW {
  type string;
  mandatory false;
 }
 leaf DLSUMIMOJTMOBPRECODEMODE {
  type enumeration {
   enum val-0;
   enum val-1;
   enum val-255;
  }
  mandatory false;
 }
 leaf DLSUMIMOMOBPRECODEMODE {
  type enumeration {
   enum val-0;
   enum val-1;
   enum val-2;
   enum val-255;
  }
  mandatory false;
 }
 leaf HORIZONTALCOVCONFIGPOLICY {
  type enumeration {
   enum val-0;
   enum val-1;
   enum val-2;
   enum val-3;
   enum val-4;
   enum val-5;
  }
  mandatory false;
 }
 leaf INTRFBASEDROBUSTWTRHOTHLD {
  type uint8 {
   range "50..110";
  }
  mandatory false;
 }
 leaf NONASFIXEDPRECODETYPE {
  type boolean;
  mandatory false;
 }
 leaf NONASPRECODEENHMCSTHLD {
  type uint8 {
   range "0..28";
  }
  mandatory false;
 }
 leaf NRDUCELLID {
  type union {
   type int32 {
    range "-1..65534";
   }
  }
  mandatory false;
 }
 leaf PRECODINGALGOSWITCH {
  type string;
  mandatory false;
 }
 leaf PRECODINGINTRFSUPPRVALUE {
  type enumeration {
   enum val-0;
   enum val-1;
   enum val-2;
   enum val-3;
   enum val-4;
   enum val-5;
   enum val-6;
  }
  mandatory false;
 }
 leaf ROBUSTWTFULLBANDSRSPRDTHLD {
  type uint16 {
   range "240..2000";
  }
  mandatory false;
 }
 leaf ROBUSTWTSRSPRESINRTHLD {
  type int8 {
   range "-20..5";
  }
  mandatory false;
 }
 leaf SRS1TNONASPRECODEENHCOEFF {
  type uint8 {
   range "0..14";
  }
  mandatory false;
 }
 leaf SRS2TNONASPRECODEENHCOEFF {
  type uint8 {
   range "0..14";
  }
  mandatory false;
 }
 leaf SRSNONASFIXEDWEIGHTTYPE {
  type boolean;
  mandatory false;
 }
 leaf SRSPRDSHORTONLINEUENUMTHLD {
  type uint16 {
   range "1..65535";
  }
  mandatory false;
 }
 leaf SRSPRECODEUPTDELAYREDUPOL {
  type enumeration {
   enum val-0;
   enum val-1;
   enum val-2;
  }
  mandatory false;
 }
 leaf SRSWEIGHTVALIDITYPERIOD {
  type enumeration {
   enum val-50;
   enum val-100;
   enum val-150;
   enum val-200;
   enum val-250;
   enum val-300;
   enum val-350;
   enum val-400;
   enum val-450;
   enum val-500;
   enum val-550;
   enum val-600;
   enum val-650;
   enum val-700;
   enum val-1000;
   enum val-1500;
   enum val-2000;
   enum val-2500;
   enum val-3000;
  }
  mandatory false;
 }
 leaf SUMIMOSRSPERIODSHORTSW {
  type string;
  mandatory false;
 }
 leaf SUNONASPRECODESW {
  type string;
  mandatory false;
 }
 leaf TRIDBEAMAVOID {
  type uint32 {
   range "0..4294967295";
  }
  mandatory false;
 }
 leaf TRIDBEAMAVOIDEXT {
  type uint32 {
   range "0..4294967295";
  }
  mandatory false;
 }
 leaf TYPE2CBCHNTIMESPREADTHLD {
  type uint16 {
   range "0..700";
  }
  mandatory false;
 }
 leaf TYPE2CODEBOOKSPCTEFFCOEFF {
  type uint16 {
   range "100..1000";
  }
  mandatory false;
 }
 leaf VERTICALCOVCONFIGPOLICY {
  type enumeration {
   enum val-0;
   enum val-1;
   enum val-2;
   enum val-3;
  }
  mandatory false;
 }
 }
 grouping NRDUCELLPIMINTRFAVD-attributes {
 leaf NRDUCELLID {
  type union {
   type int32 {
    range "-1..65534";
   }
  }
  mandatory false;
 }
 leaf PIMALGOSWITCH {
  type string;
  mandatory false;
 }
 leaf PIMCHNSHUTDOWNINTRFTHLD {
  type uint8 {
   range "0..100";
  }
  mandatory false;
 }
 leaf PIMDLPWRREDUCTIONLEVEL {
  type enumeration {
   enum val-0;
   enum val-1;
   enum val-2;
   enum val-3;
  }
  mandatory false;
 }
 leaf PIMDLPWRREDUCTIONTHLD {
  type uint8 {
   range "0..100";
  }
  mandatory false;
 }
 leaf PIMDLRBAVOIDRATIO {
  type uint8 {
   range "0..30";
  }
  mandatory false;
 }
 leaf PIMINTERFTHLD {
  type uint8 {
   range "0..50";
  }
  mandatory false;
 }
 leaf PIMINTRFDETECTPRBUSAGETHLD {
  type uint8 {
   range "5..20";
  }
  mandatory false;
 }
 }
 grouping NRDUCELLPOSALGO-attributes {
 leaf APPLICATIONSCENARIO {
  type enumeration {
   enum val-0;
   enum val-1;
   enum val-2;
  }
  mandatory false;
 }
 leaf BIGDATATAESWITCH {
  type string;
  mandatory false;
 }
 leaf DIELECTRICCONSTANT {
  type uint8 {
   range "100..200";
  }
  mandatory false;
 }
 leaf INTERTRPTRANSMAXDISTANCE {
  type uint16 {
   range "0..300";
  }
  mandatory false;
 }
 leaf INTERTRPTRANSRSRPTHLD {
  type int8 {
   range "-125..-40";
  }
  mandatory false;
 }
 leaf INTERTRPTRANSSEARCHSCALE {
  type enumeration {
   enum val-0;
   enum val-1;
   enum val-2;
   enum val-3;
  }
  mandatory false;
 }
 leaf INTERTRPTRANSMISSIONSWITCH {
  type boolean;
  mandatory false;
 }
 leaf LCSMEASUREALGOSW {
  type string;
  mandatory false;
 }
 leaf LCSSCENARIO {
  type enumeration {
   enum val-1;
   enum val-2;
   enum val-3;
   enum val-4;
   enum val-5;
   enum val-6;
   enum val-7;
   enum val-100;
   enum val-101;
   enum val-102;
   enum val-103;
   enum val-104;
   enum val-105;
   enum val-106;
   enum val-107;
   enum val-108;
   enum val-109;
   enum val-110;
   enum val-111;
   enum val-112;
   enum val-113;
   enum val-114;
   enum val-115;
   enum val-116;
   enum val-117;
   enum val-118;
   enum val-119;
   enum val-120;
   enum val-121;
   enum val-122;
   enum val-123;
   enum val-124;
   enum val-125;
   enum val-126;
   enum val-127;
   enum val-128;
   enum val-129;
   enum val-130;
   enum val-131;
   enum val-132;
   enum val-133;
   enum val-134;
   enum val-135;
   enum val-136;
   enum val-137;
   enum val-138;
   enum val-139;
   enum val-140;
   enum val-141;
   enum val-142;
   enum val-143;
   enum val-144;
   enum val-145;
   enum val-146;
   enum val-147;
   enum val-148;
   enum val-149;
   enum val-150;
   enum val-151;
   enum val-152;
   enum val-153;
   enum val-154;
   enum val-155;
   enum val-156;
   enum val-157;
   enum val-158;
   enum val-159;
   enum val-160;
   enum val-161;
   enum val-162;
   enum val-163;
   enum val-164;
   enum val-165;
   enum val-166;
   enum val-167;
   enum val-168;
   enum val-169;
   enum val-170;
   enum val-171;
   enum val-172;
   enum val-173;
   enum val-174;
   enum val-175;
   enum val-176;
   enum val-177;
   enum val-178;
   enum val-179;
   enum val-180;
   enum val-181;
   enum val-182;
   enum val-183;
   enum val-184;
   enum val-185;
   enum val-186;
   enum val-187;
   enum val-188;
   enum val-189;
  }
  mandatory false;
 }
 leaf NRDUCELLID {
  type union {
   type int32 {
    range "-1..65534";
   }
  }
  mandatory false;
 }
 }
 grouping NRDUCELLPOWERSAVING-attributes {
 leaf BACKUPPWRSAVINGPOLICY {
  type enumeration {
   enum val-1;
   enum val-2;
   enum val-3;
   enum val-4;
  }
  mandatory false;
 }
 leaf BEAMMAPPEDDLPRBTHLD {
  type uint8 {
   range "0..50";
  }
  mandatory false;
 }
 leaf BEAMMAPPEDUENUMTHLD {
  type uint8 {
   range "0..100";
  }
  mandatory false;
 }
 leaf CARRSHUTDSERVICEASSURLEVEL {
  type enumeration {
   enum val-0;
   enum val-1;
   enum val-2;
   enum val-3;
   enum val-4;
  }
  mandatory false;
 }
 leaf CARRSHUTDOWNPENALTYTIME {
  type uint16 {
   range "0..360";
  }
  mandatory false;
 }
 leaf CARRIERSHUTDOWNMODE {
  type boolean;
  mandatory false;
 }
 leaf CELLAVGDLTHPTOFFSET {
  type uint16 {
   range "0..1000";
  }
  mandatory false;
 }
 leaf CELLAVGDLTHPTTHLD {
  type union {
   type uint16 {
    range "0..65535";
   }
  }
  mandatory false;
 }
 leaf COMCHNDYNSHUTDOWNSWITCH {
  type boolean;
  mandatory false;
 }
 leaf COMB8TDYNRFCHNSHUTDOWNMODE {
  type enumeration {
   enum val-0;
   enum val-1;
   enum val-2;
  }
  mandatory false;
 }
 leaf COVCOMPENSATIONMODE {
  type boolean;
  mandatory false;
 }
 leaf DLPRBLOWERTHLD {
  type uint8 {
   range "0..100";
  }
  mandatory false;
 }
 leaf DLPRBLOWERTHLDOFFSET {
  type uint8 {
   range "0..100";
  }
  mandatory false;
 }
 leaf DLPRBOFFSET {
  type uint8 {
   range "0..100";
  }
  mandatory false;
 }
 leaf DLPRBTHLD {
  type uint8 {
   range "0..100";
  }
  mandatory false;
 }
 leaf EUTRANCARRSHUTDOWNEXITOFS {
  type uint8 {
   range "0..100";
  }
  mandatory false;
 }
 leaf EUTRANCARRSHUTDOWNRATIO {
  type uint8 {
   range "51..100";
  }
  mandatory false;
 }
 leaf EUTRANDLPRBOFFSET {
  type uint8 {
   range "0..100";
  }
  mandatory false;
 }
 leaf EUTRANDLPRBTHLD {
  type uint8 {
   range "0..100";
  }
  mandatory false;
 }
 leaf EUTRANNRUSERDLPRBTHLD {
  type union {
   type uint8 {
    range "0..255";
   }
  }
  mandatory false;
 }
 leaf EUTRANNRUSERDLPRBTHLDOFS {
  type uint8 {
   range "0..100";
  }
  mandatory false;
 }
 leaf EUTRANNRUSERNUMTHLD {
  type uint16 {
   range "0..65535";
  }
  mandatory false;
 }
 leaf EUTRANNRUSERNUMTHLDOFS {
  type uint16 {
   range "0..32767";
  }
  mandatory false;
 }
 leaf EUTRANNRUSERULPRBTHLD {
  type union {
   type uint8 {
    range "0..255";
   }
  }
  mandatory false;
 }
 leaf EUTRANNRUSERULPRBTHLDOFS {
  type uint8 {
   range "0..100";
  }
  mandatory false;
 }
 leaf EVALPERIODGRANULARITY {
  type boolean;
  mandatory false;
 }
 leaf EXITEVALUATIONPERIOD {
  type uint8 {
   range "1..10";
  }
  mandatory false;
 }
 leaf FLEXFREQSCHMODE {
  type enumeration {
   enum val-0;
   enum val-1;
   enum val-2;
  }
  mandatory false;
 }
 leaf LOWPOWERTHLD {
  type uint8 {
   range "1..20";
  }
  mandatory false;
 }
 leaf LOWPWRMODEALGOSWITCH {
  type string;
  mandatory false;
 }
 leaf MAXPOWERREDUCTION {
  type uint8 {
   range "0..100";
  }
  mandatory false;
 }
 leaf MMWAVEUSERNUMTHLD {
  type uint16 {
   range "0..5000";
  }
  mandatory false;
 }
 leaf NCELLULPRBOFFSET {
  type uint8 {
   range "0..100";
  }
  mandatory false;
 }
 leaf NCELLULPRBTHLD {
  type uint8 {
   range "0..100";
  }
  mandatory false;
 }
 leaf OLD_NRDUCELLID {
  type union {
   type int32 {
    range "-1..65534";
   }
  }
  mandatory false;
 }
 leaf NRDUCELLID {
  type union {
   type int32 {
    range "-1..65534";
   }
  }
  mandatory false;
 }
 leaf NRMULTICARRPROTSWITCH {
  type boolean;
  mandatory false;
 }
 leaf OPUSERNUMOFFSET {
  type uint16 {
   range "0..65535";
  }
  mandatory false;
 }
 leaf OPUSERNUMTHLD {
  type uint16 {
   range "0..65535";
  }
  mandatory false;
 }
 leaf PMIWTUEDYNSHUTDOWNSWITCH {
  type boolean;
  mandatory false;
 }
 leaf OLD_POWERSAVINGPOLICYINDEX {
  type union {
   type int8 {
    range "-1..31";
   }
  }
  mandatory false;
 }
 leaf POWERSAVINGPOLICYINDEX {
  type union {
   type int8 {
    range "-1..31";
   }
  }
  mandatory false;
 }
 leaf POWERSAVINGTYPE {
  type enumeration {
   enum val-0;
   enum val-1;
   enum val-2;
   enum val-3;
   enum val-5;
   enum val-7;
   enum val-8;
   enum val-9;
   enum val-10;
   enum val-11;
   enum val-12;
   enum val-15;
   enum val-16;
   enum val-17;
   enum val-18;
   enum val-19;
   enum val-21;
   enum val-22;
   enum val-23;
   enum val-24;
   enum val-25;
   enum val-26;
   enum val-27;
   enum val-28;
   enum val-29;
   enum val-31;
  }
  mandatory false;
 }
 leaf PROTECTDLPRBOFFSET {
  type uint8 {
   range "0..100";
  }
  mandatory false;
 }
 leaf PROTECTDLPRBTHLD {
  type uint8 {
   range "0..100";
  }
  mandatory false;
 }
 leaf PROTECTULPRBOFFSET {
  type uint8 {
   range "0..100";
  }
  mandatory false;
 }
 leaf PROTECTULPRBTHLD {
  type uint8 {
   range "0..100";
  }
  mandatory false;
 }
 leaf PWRCOMPENSATIONOFFSET {
  type uint8 {
   range "0..120";
  }
  mandatory false;
 }
 leaf PWRSAVINGPENALTYTIME {
  type uint16 {
   range "0..360";
  }
  mandatory false;
 }
 leaf RFCHNSHUTDOWNDURATION {
  type uint16 {
   range "0..1440";
  }
  mandatory false;
 }
 leaf RFCHNSHUTDOWNMODE {
  type enumeration {
   enum val-0;
   enum val-1;
   enum val-2;
  }
  mandatory false;
 }
 leaf RFRESTOREDLPRBUSAGETHLD {
  type uint8 {
   range "0..100";
  }
  mandatory false;
 }
 leaf RFRSTRDLHIGHLOADTTINUMTHLD {
  type uint8 {
   range "0..40";
  }
  mandatory false;
 }
 leaf RFSHDNDLHIGHLOADTTINUMTHLD {
  type uint8 {
   range "0..40";
  }
  mandatory false;
 }
 leaf RFSHUTDOWNDLPRBUSAGETHLD {
  type uint8 {
   range "0..100";
  }
  mandatory false;
 }
 leaf RFSHUTDOWNNUM {
  type boolean;
  mandatory false;
 }
 leaf RLCFIRSTPKTDELAYTHLD {
  type uint8 {
   range "0..100";
  }
  mandatory false;
 }
 leaf RMSIADJUSTMODE {
  type boolean;
  mandatory false;
 }
 leaf RRUCHIPPOWERSAVING {
  type boolean;
  mandatory false;
 }
 leaf SECONDLEVELEXITEVALPRD {
  type uint8 {
   range "1..60";
  }
  mandatory false;
 }
 leaf SECONDLEVELTRIGEVALPRD {
  type uint8 {
   range "1..30";
  }
  mandatory false;
 }
 leaf SHUTDOWNTRIGJUDGEPERIOD {
  type uint8 {
   range "1..10";
  }
  mandatory false;
 }
 leaf SLOTPRBTHLD {
  type uint8 {
   range "1..100";
  }
  mandatory false;
 }
 leaf SMARTPWRCTRLIMPACTFACTOR {
  type enumeration {
   enum val-0;
   enum val-1;
   enum val-2;
   enum val-3;
   enum val-4;
   enum val-5;
   enum val-6;
  }
  mandatory false;
 }
 leaf SMARTPWRCTRLMAXPDSCHOFFSET {
  type uint8 {
   range "1..2";
  }
  mandatory false;
 }
 leaf SMARTPWRCTRLMCSTHLD {
  type enumeration {
   enum val-0;
   enum val-1;
   enum val-2;
   enum val-3;
   enum val-4;
   enum val-5;
   enum val-6;
   enum val-7;
   enum val-8;
   enum val-9;
   enum val-10;
  }
  mandatory false;
 }
 leaf SMARTPWRCTRLNCELLLOADTHLD {
  type uint8 {
   range "0..100";
  }
  mandatory false;
 }
 leaf SSBDYNSHUTDOWNSWITCH {
  type boolean;
  mandatory false;
 }
 leaf STARTTIME {
  type hwat:HH_MM_SS_Time;
  mandatory false;
 }
 leaf STOPTIME {
  type hwat:HH_MM_SS_Time;
  mandatory false;
 }
 leaf SYMBOLCOMPRESSLENGTH {
  type boolean;
  mandatory false;
 }
 leaf TIMETOTRIGGER {
  type uint16 {
   range "1..1440";
  }
  mandatory false;
 }
 leaf TTIRFSHUTDOWNMODE {
  type boolean;
  mandatory false;
 }
 leaf UEAVGDLTHPTOFFSET {
  type uint16 {
   range "0..1000";
  }
  mandatory false;
 }
 leaf UEAVGDLTHPTTHLD {
  type union {
   type uint16 {
    range "0..65535";
   }
  }
  mandatory false;
 }
 leaf ULPRBOFFSET {
  type uint8 {
   range "0..100";
  }
  mandatory false;
 }
 leaf ULPRBTHLD {
  type uint8 {
   range "0..100";
  }
  mandatory false;
 }
 leaf USERNUMOFFSET {
  type uint16 {
   range "0..5000";
  }
  mandatory false;
 }
 leaf USERNUMTHLD {
  type uint16 {
   range "0..5000";
  }
  mandatory false;
 }
 }
 grouping NRDUCELLPRACH-attributes {
 leaf CBRAPREAMBLEPCT {
  type union {
   type uint8 {
    range "6..255";
   }
  }
  mandatory false;
 }
 leaf CFRAPRACHCONFIGINDEX {
  type union {
   type uint16 {
    range "0..65535";
   }
  }
  mandatory false;
 }
 leaf MAXPREAMBLETRANSCNT {
  type enumeration {
   enum val-0;
   enum val-1;
   enum val-2;
   enum val-3;
   enum val-4;
   enum val-5;
   enum val-6;
   enum val-7;
   enum val-8;
   enum val-9;
   enum val-10;
  }
  mandatory false;
 }
 leaf NARROWBEAMPROBETHLD {
  type int16 {
   range "-140..-43";
  }
  mandatory false;
 }
 leaf NRDUCELLID {
  type union {
   type int32 {
    range "-1..65534";
   }
  }
  mandatory false;
 }
 leaf PRACHALGOEXTSWITCH {
  type string;
  mandatory false;
 }
 leaf PRACHCONFIGPATTERN {
  type enumeration {
   enum val-0;
   enum val-1;
   enum val-2;
  }
  mandatory false;
 }
 leaf PRACHCONFIGURATIONINDEX {
  type union {
   type uint16 {
    range "0..65535";
   }
  }
  mandatory false;
 }
 leaf PRACHFALSEALMDETDISTHLD {
  type uint32 {
   range "0..100000";
  }
  mandatory false;
 }
 leaf PRACHTHLDINCREASERATE {
  type uint16 {
   range "0..1000";
  }
  mandatory false;
 }
 leaf PUSCHPRACHFDMSWITCH {
  type enumeration {
   enum val-0;
   enum val-1;
   enum val-2;
  }
  mandatory false;
 }
 leaf RASDTPREAMBLEMAXNUM {
  type uint8 {
   range "1..16";
  }
  mandatory false;
 }
 leaf RACHALGOOPTSWITCH {
  type string;
  mandatory false;
 }
 leaf RSRPTHLDFORSSBSELECTION {
  type uint8 {
   range "0..127";
  }
  mandatory false;
 }
 }
 grouping NRDUCELLPSPOLICYGRP-attributes {
 leaf OLD_NRDUCELLID {
  type union {
   type int32 {
    range "-1..65534";
   }
  }
  mandatory false;
 }
 leaf NRDUCELLID {
  type union {
   type int32 {
    range "-1..65534";
   }
  }
  mandatory false;
 }
 leaf OLD_POWERSAVINGPOLICYGRPINDEX {
  type union {
   type int8 {
    range "-1..4";
   }
  }
  mandatory false;
 }
 leaf POWERSAVINGPOLICYGRPINDEX {
  type union {
   type int8 {
    range "-1..4";
   }
  }
  mandatory false;
 }
 leaf SERVTYPEDYNEXITPWRSAVINGSW {
  type string;
  mandatory false;
 }
 leaf USERIDENTMETHOD {
  type boolean;
  mandatory false;
 }
 }
 grouping NRDUCELLPUCCH-attributes {
 leaf CSIDEDICATEDRBNUM {
  type enumeration {
   enum val-0;
   enum val-2;
   enum val-4;
   enum val-6;
   enum val-8;
   enum val-10;
  }
  mandatory false;
 }
 leaf CSIREPORTPERIOD {
  type enumeration {
   enum val-3;
   enum val-5;
   enum val-6;
   enum val-7;
   enum val-8;
   enum val-9;
  }
  mandatory false;
 }
 leaf CSIRESOUREALGOSWITCH {
  type string;
  mandatory false;
 }
 leaf F3ANDF4HARQRESFAILRATIO {
  type uint8 {
   range "0..50";
  }
  mandatory false;
 }
 leaf F3ANDF4HARQRESUSERATIO {
  type uint8 {
   range "5..95";
  }
  mandatory false;
 }
 leaf F3ANDF4HARQSINRTHLD {
  type int8 {
   range "-50..50";
  }
  mandatory false;
 }
 leaf F3RBRSVINSHAREDMODE {
  type enumeration {
   enum val-0;
   enum val-2;
   enum val-4;
   enum val-6;
   enum val-8;
   enum val-10;
   enum val-12;
   enum val-14;
   enum val-16;
   enum val-255;
  }
  mandatory false;
 }
 leaf FORMAT1RBNUM {
  type enumeration {
   enum val-0;
   enum val-2;
   enum val-4;
   enum val-6;
   enum val-8;
   enum val-10;
  }
  mandatory false;
 }
 leaf FORMAT3CSIDEDRBADAPTMODE {
  type enumeration {
   enum val-1;
   enum val-2;
  }
  mandatory false;
 }
 leaf FORMAT3RBNUM {
  type enumeration {
   enum val-2;
   enum val-4;
   enum val-6;
   enum val-8;
   enum val-10;
   enum val-12;
   enum val-14;
   enum val-16;
   enum val-18;
   enum val-20;
   enum val-22;
   enum val-24;
  }
  mandatory false;
 }
 leaf FORMAT4CSIDEDICATEDRBNUM {
  type enumeration {
   enum val-0;
   enum val-2;
   enum val-4;
   enum val-6;
   enum val-8;
   enum val-10;
  }
  mandatory false;
 }
 leaf FORMAT4DFTBMSRSPRESINRTHLD {
  type int16 {
   range "-200..200";
  }
  mandatory false;
 }
 leaf FORMAT4RBNUM {
  type enumeration {
   enum val-0;
   enum val-2;
   enum val-4;
   enum val-6;
   enum val-8;
   enum val-10;
   enum val-12;
   enum val-14;
  }
  mandatory false;
 }
 leaf NRDUCELLID {
  type union {
   type int32 {
    range "-1..65534";
   }
  }
  mandatory false;
 }
 leaf PUCCHALGOEXTSWITCH {
  type string;
  mandatory false;
 }
 leaf PUCCHALGOSWITCH {
  type string;
  mandatory false;
 }
 leaf PUCCHPERFORMANCESW {
  type string;
  mandatory false;
 }
 leaf PUCCHRECEIVEENHSWITCH {
  type string;
  mandatory false;
 }
 leaf PUCCHRESRCREDNMTHD {
  type enumeration {
   enum val-0;
   enum val-1;
   enum val-2;
  }
  mandatory false;
 }
 leaf PUCCHRXALLOCMODE {
  type boolean;
  mandatory false;
 }
 leaf SHORTPUCCHSYMBOLNUM {
  type enumeration {
   enum val-0;
   enum val-1;
   enum val-2;
   enum val-3;
   enum val-4;
  }
  mandatory false;
 }
 leaf SRPERIOD {
  type enumeration {
   enum val-2;
   enum val-3;
   enum val-4;
   enum val-5;
   enum val-6;
   enum val-7;
   enum val-8;
   enum val-9;
   enum val-10;
   enum val-11;
   enum val-12;
   enum val-13;
   enum val-14;
  }
  mandatory false;
 }
 leaf SRPROHIBITTIMER {
  type enumeration {
   enum val-0;
   enum val-1;
   enum val-2;
   enum val-3;
   enum val-4;
   enum val-5;
   enum val-6;
   enum val-7;
   enum val-8;
  }
  mandatory false;
 }
 leaf SRRESOUREALGOSWITCH {
  type string;
  mandatory false;
 }
 leaf STRUCTURETYPE {
  type boolean;
  mandatory false;
 }
 leaf UEPUCCHCAPABILITYALGOSW {
  type string;
  mandatory false;
 }
 }
 grouping NRDUCELLPUSCH-attributes {
 leaf ABNUEDATAVOLADJPADRATETHLD {
  type uint8 {
   range "1..100";
  }
  mandatory false;
 }
 leaf ABNUEDATAVOLUME {
  type union {
   type uint8 {
    range "1..60";
   }
  }
  mandatory false;
 }
 leaf ABNUEPRBUSAGETHLD {
  type uint8 {
   range "1..10";
  }
  mandatory false;
 }
 leaf ABNORMALUEPADDINGRATIOTHLD {
  type uint8 {
   range "5..10";
  }
  mandatory false;
 }
 leaf ALGOCOMPATIBILITYSWITCH {
  type string;
  mandatory false;
 }
 leaf CLOUDVRULSCHVOLCOEFF {
  type uint8 {
   range "1..50";
  }
  mandatory false;
 }
 leaf EXTSLOTDCIALLOCUEPCT {
  type uint8 {
   range "0..100";
  }
  mandatory false;
 }
 leaf GRANTFREEPERIOD {
  type enumeration {
   enum val-0;
   enum val-1;
   enum val-2;
   enum val-3;
   enum val-4;
   enum val-5;
   enum val-6;
   enum val-7;
  }
  mandatory false;
 }
 leaf GRANTFREERBNUM {
  type uint16 {
   range "0..273";
  }
  mandatory false;
 }
 leaf GRANTFREERESOURCEMODE {
  type boolean;
  mandatory false;
 }
 leaf GRANTFREETBSIZE {
  type uint16 {
   range "0..2000";
  }
  mandatory false;
 }
 leaf GTDHARQACKSCHRATIOTHLD {
  type uint8 {
   range "10..90";
  }
  mandatory false;
 }
 leaf GUARUEULPRBUSAGEUPPERLIMIT {
  type uint8 {
   range "0..100";
  }
  mandatory false;
 }
 leaf INITULSINRADJUST {
  type int8 {
   range "-40..60";
  }
  mandatory false;
 }
 leaf MAXMIMOLAYERCNT {
  type enumeration {
   enum val-0;
   enum val-1;
   enum val-2;
   enum val-3;
   enum val-4;
   enum val-5;
  }
  mandatory false;
 }
 leaf MINPREALLOCATIONPERIOD {
  type uint8 {
   range "1..255";
  }
  mandatory false;
 }
 leaf MSG3PAYLOADCONFIG {
  type enumeration {
   enum val-0;
   enum val-1;
   enum val-2;
   enum val-3;
   enum val-4;
  }
  mandatory false;
 }
 leaf NRDUCELLID {
  type union {
   type int32 {
    range "-1..65534";
   }
  }
  mandatory false;
 }
 leaf PERIODICBSRTIMER {
  type enumeration {
   enum val-1;
   enum val-5;
   enum val-10;
   enum val-16;
   enum val-20;
   enum val-32;
   enum val-40;
   enum val-64;
   enum val-80;
   enum val-128;
   enum val-160;
   enum val-320;
   enum val-640;
   enum val-1280;
   enum val-2560;
   enum val-2570;
  }
  mandatory false;
 }
 leaf PREALLOCATIONSIZE {
  type uint16 {
   range "1..65535";
  }
  mandatory false;
 }
 leaf PRESCHUENUMUPPERLIMIT {
  type uint8 {
   range "1..32";
  }
  mandatory false;
 }
 leaf PTUSERPRBUSAGEUPPERLIMIT {
  type uint8 {
   range "0..100";
  }
  mandatory false;
 }
 leaf PUSCHALGOEXTSWITCH {
  type string;
  mandatory false;
 }
 leaf PUSCHBEAMADAPTMCSTHD {
  type uint8 {
   range "0..31";
  }
  mandatory false;
 }
 leaf PUSCHBEAMADAPTRSRPRATIOTHD {
  type uint8 {
   range "0..100";
  }
  mandatory false;
 }
 leaf PUSCHDMRSFDM256QAMMCSTHLD {
  type uint8 {
   range "0..28";
  }
  mandatory false;
 }
 leaf PUSCHDMRSFDM64QAMMCSTHLD {
  type uint8 {
   range "0..29";
  }
  mandatory false;
 }
 leaf PUSCHDMRSFDMSWITCH {
  type boolean;
  mandatory false;
 }
 leaf PUSCHMEASSW {
  type string;
  mandatory false;
 }
 leaf PUSCHPERFORMANCESWITCH {
  type string;
  mandatory false;
 }
 leaf PUSCHSHAREPUCCHRESPOL {
  type enumeration {
   enum val-0;
   enum val-1;
   enum val-2;
   enum val-3;
  }
  mandatory false;
 }
 leaf RASDTMSG3MCS {
  type enumeration {
   enum val-0;
   enum val-1;
   enum val-2;
   enum val-3;
   enum val-4;
   enum val-5;
   enum val-6;
   enum val-7;
   enum val-8;
   enum val-9;
   enum val-10;
  }
  mandatory false;
 }
 leaf RBDIVIDEDUSERUPPERLIMIT {
  type uint8 {
   range "1..8";
  }
  mandatory false;
 }
 leaf RETRANSBSRTIMER {
  type enumeration {
   enum val-10;
   enum val-20;
   enum val-40;
   enum val-80;
   enum val-160;
   enum val-320;
   enum val-640;
   enum val-1280;
   enum val-2560;
   enum val-5120;
  }
  mandatory false;
 }
 leaf SCHMULTISLIVTYPEUESWITCH {
  type boolean;
  mandatory false;
 }
 leaf SINRTHLDFORWAVEFORMSEL {
  type int16 {
   range "-100..200";
  }
  mandatory false;
 }
 leaf SPARSESERVICETBSIZE {
  type union {
   type uint16 {
    range "1..65535";
   }
  }
  mandatory false;
 }
 leaf SPECIALUSERMCSIDXLOWAMOUNT {
  type uint8 {
   range "0..28";
  }
  mandatory false;
 }
 leaf SRSCHFIRSTTBSIZE {
  type uint16 {
   range "1..65535";
  }
  mandatory false;
 }
 leaf UELOFEEDTHROUGHOFS {
  type int8 {
   range "-3..3";
  }
  mandatory false;
 }
 leaf ULADDITIONALDMRSPOS {
  type enumeration {
   enum val-0;
   enum val-1;
   enum val-2;
  }
  mandatory false;
 }
 leaf ULAMCADJUSTSTEP {
  type uint16 {
   range "0..300";
  }
  mandatory false;
 }
 leaf ULCAULABNSCHRATIOTHLD {
  type uint8 {
   range "1..100";
  }
  mandatory false;
 }
 leaf ULCHNESTIMATIONTYPE {
  type boolean;
  mandatory false;
 }
 leaf ULDCIEXTRBUSAGETHLD {
  type uint8 {
   range "0..100";
  }
  mandatory false;
 }
 leaf ULDMRSTYPE {
  type enumeration {
   enum val-1;
   enum val-2;
  }
  mandatory false;
 }
 leaf ULLIVEVIDEOIBLER {
  type uint8 {
   range "1..30";
  }
  mandatory false;
 }
 leaf ULNONSLOTSTARTSYMBOL {
  type uint8 {
   range "0..12";
  }
  mandatory false;
 }
 leaf ULPREALLOCATIONSWITCH {
  type string;
  mandatory false;
 }
 leaf ULPUSCHALGOSWITCH {
  type string;
  mandatory false;
 }
 leaf ULSMARTPREALLOCATIONDUR {
  type uint16 {
   range "1..2000";
  }
  mandatory false;
 }
 leaf ULSPARSEMCSADJUSTRBTHLD {
  type uint16 {
   range "0..273";
  }
  mandatory false;
 }
 leaf ULSPARSESERVSCHDATAADJVAL {
  type uint16 {
   range "0..1000";
  }
  mandatory false;
 }
 leaf ULTARGETIBLER {
  type uint8 {
   range "0..100";
  }
  mandatory false;
 }
 leaf ULVONRCOMPENSATIONSCHPRD {
  type enumeration {
   enum val-0;
   enum val-1;
   enum val-2;
   enum val-3;
  }
  mandatory false;
 }
 leaf ULVONRRSVDRBNUM {
  type enumeration {
   enum val-2;
   enum val-3;
   enum val-4;
   enum val-5;
   enum val-10;
   enum val-15;
   enum val-20;
   enum val-25;
   enum val-30;
   enum val-35;
   enum val-40;
  }
  mandatory false;
 }
 leaf ULVONRRSVDRBSTARTPOS {
  type uint16 {
   range "0..273";
  }
  mandatory false;
 }
 leaf VMIMOULJTSCHTHLD {
  type uint8 {
   range "0..100";
  }
  mandatory false;
 }
 }
 grouping NRDUCELLPWRSAVEALGO-attributes {
 leaf NRDUCELLID {
  type union {
   type int32 {
    range "-1..65534";
   }
  }
  mandatory false;
 }
 leaf POWERSAVINGALGOSWITCH {
  type string;
  mandatory false;
 }
 }
 grouping NRDUCELLRAC-attributes {
 leaf CELLCAPACITYMODE {
  type boolean;
  mandatory false;
 }
 leaf DLADMISSIONTHLDFACTOR {
  type uint8 {
   range "0..10";
  }
  mandatory false;
 }
 leaf DLCONGESTPRBUSAGETHLD {
  type uint8 {
   range "50..100";
  }
  mandatory false;
 }
 leaf DLPRBUSAGETHLD {
  type uint8 {
   range "0..100";
  }
  mandatory false;
 }
 leaf NRDUCELLID {
  type union {
   type int32 {
    range "-1..65534";
   }
  }
  mandatory false;
 }
 leaf RACTRLCOMMPDCCHCCEUSAGETHD {
  type uint8 {
   range "50..100";
  }
  mandatory false;
 }
 leaf RACALGOSWITCH {
  type string;
  mandatory false;
 }
 leaf SPECSERVPVIMODE {
  type boolean;
  mandatory false;
 }
 leaf UENUMPREEMPTIONRANGE {
  type enumeration {
   enum val-0;
   enum val-1;
   enum val-2;
  }
  mandatory false;
 }
 leaf ULADMISSIONTHLDFACTOR {
  type uint8 {
   range "0..10";
  }
  mandatory false;
 }
 leaf ULCONGESTPRBUSAGETHLD {
  type uint8 {
   range "50..100";
  }
  mandatory false;
 }
 leaf ULPRBUSAGETHLD {
  type uint8 {
   range "0..100";
  }
  mandatory false;
 }
 leaf URLLCMODESWITCH {
  type string;
  mandatory false;
 }
 }
 grouping NRDUCELLRBRESERVE-attributes {
 leaf OLD_INDEX {
  type union {
   type int8 {
    range "-1..9";
   }
  }
  mandatory false;
 }
 leaf INDEX {
  type union {
   type int8 {
    range "-1..9";
   }
  }
  mandatory false;
 }
 leaf OLD_NRDUCELLID {
  type union {
   type int32 {
    range "-1..65534";
   }
  }
  mandatory false;
 }
 leaf NRDUCELLID {
  type union {
   type int32 {
    range "-1..65534";
   }
  }
  mandatory false;
 }
 leaf RBRSVENDINDEX {
  type uint16 {
   range "0..269";
  }
  mandatory false;
 }
 leaf RBRSVMODE {
  type enumeration {
   enum val-0;
   enum val-1;
   enum val-2;
   enum val-3;
   enum val-4;
  }
  mandatory false;
 }
 leaf RBRSVSTARTINDEX {
  type uint16 {
   range "0..269";
  }
  mandatory false;
 }
 leaf RBRSVTYPE {
  type boolean;
  mandatory false;
 }
 }
 grouping NRDUCELLREDCAP-attributes {
 leaf BWP0CCEAGGLVLCFGPOL {
  type boolean;
  mandatory false;
 }
 leaf BWP0FREQSELECTPOLICY {
  type enumeration {
   enum val-0;
   enum val-1;
   enum val-2;
  }
  mandatory false;
 }
 leaf BWPSHRINKWAITINGTIME {
  type enumeration {
   enum val-1;
   enum val-10;
   enum val-30;
   enum val-60;
  }
  mandatory false;
 }
 leaf CELLBARREDREDCAP {
  type enumeration {
   enum val-0;
   enum val-1;
   enum val-2;
   enum val-3;
  }
  mandatory false;
 }
 leaf CELLMEDIUMLOADUERATIOTHLD {
  type uint8 {
   range "1..100";
  }
  mandatory false;
 }
 leaf DLSCHOPTFACTOR {
  type union {
   type uint8 {
    range "5..255";
   }
  }
  mandatory false;
 }
 leaf EREDCAPULPEAKRATEFACTOR {
  type uint8 {
   range "0..8";
  }
  mandatory false;
 }
 leaf LSUEEVALTIMER {
  type enumeration {
   enum val-0;
   enum val-1;
   enum val-2;
   enum val-3;
   enum val-4;
   enum val-5;
   enum val-6;
   enum val-7;
   enum val-8;
  }
  mandatory false;
 }
 leaf LSUERSRPDIFFTHLD {
  type enumeration {
   enum val-0;
   enum val-1;
   enum val-2;
   enum val-3;
   enum val-4;
  }
  mandatory false;
 }
 leaf NCDSSBBWPPREFERMAXUENUM {
  type uint8 {
   range "0..10";
  }
  mandatory false;
 }
 leaf NRDUCELLID {
  type union {
   type int32 {
    range "-1..65534";
   }
  }
  mandatory false;
 }
 leaf PUCCHFORMAT4ACKRBNUM {
  type enumeration {
   enum val-0;
   enum val-1;
   enum val-2;
  }
  mandatory false;
 }
 leaf REDCAPALGOEXTSWITCH {
  type string;
  mandatory false;
 }
 leaf REDCAPALGOSWITCH {
  type string;
  mandatory false;
 }
 leaf REDCAPBWPCCEFAILRATIOTHLD {
  type uint8 {
   range "20..50";
  }
  mandatory false;
 }
 leaf REDCAPBWPDLPRBRATIOTHLD {
  type uint8 {
   range "20..70";
  }
  mandatory false;
 }
 leaf REDCAPBWPULPRBRATIOTHLD {
  type uint8 {
   range "20..70";
  }
  mandatory false;
 }
 leaf REDCAPCOVERAGEALGOSW {
  type string;
  mandatory false;
 }
 leaf REDCAPIDENTIFYSTRATEGY {
  type enumeration {
   enum val-0;
   enum val-1;
   enum val-2;
  }
  mandatory false;
 }
 leaf REDCAPINITBWPCONFIG {
  type enumeration {
   enum val-0;
   enum val-1;
   enum val-2;
  }
  mandatory false;
 }
 leaf REDCAPSCHALGOSWITCH {
  type string;
  mandatory false;
 }
 leaf REDCAPUEMAXAVAILBANDWIDTH {
  type enumeration {
   enum val-20;
   enum val-40;
   enum val-60;
   enum val-80;
   enum val-100;
  }
  mandatory false;
 }
 leaf REDCAPUENUMTHLD {
  type uint8 {
   range "1..200";
  }
  mandatory false;
 }
 leaf REDCAPULPREALLOCPOLICY {
  type boolean;
  mandatory false;
 }
 leaf SIB1MINTBSIZECOMPATSW {
  type boolean;
  mandatory false;
 }
 leaf SRREPETITIONSINRTHLD {
  type int16 {
   range "-100..300";
  }
  mandatory false;
 }
 leaf TBOMSSINRTHLD {
  type int16 {
   range "-100..160";
  }
  mandatory false;
 }
 leaf ULAVOIDPOL {
  type enumeration {
   enum val-0;
   enum val-1;
   enum val-2;
  }
  mandatory false;
 }
 leaf ULSLOTAGGFACTORTHLDOFS {
  type uint8 {
   range "0..100";
  }
  mandatory false;
 }
 leaf ULSLOTAGGSINRTHLD {
  type int16 {
   range "-150..100";
  }
  mandatory false;
 }
 }
 grouping NRDUCELLREINFLRNALGO-attributes {
 leaf DLPDCPFIRSTPKTLATTHLD {
  type uint8 {
   range "0..200";
  }
  mandatory false;
 }
 leaf DLPERCEIVEDRATETHLD {
  type uint8 {
   range "0..200";
  }
  mandatory false;
 }
 leaf NRDUCELLID {
  type union {
   type int32 {
    range "-1..65534";
   }
  }
  mandatory false;
 }
 leaf REINFLRNALGOSWITCH {
  type string;
  mandatory false;
 }
 }
 grouping NRDUCELLRES-attributes {
 leaf OLD_CELLRESID {
  type union {
   type int8 {
    range "-1..31";
   }
  }
  mandatory false;
 }
 leaf CELLRESID {
  type union {
   type int8 {
    range "-1..31";
   }
  }
  mandatory false;
 }
 leaf DLMINRBSTARTPOS {
  type union {
   type uint16 {
    range "0..65535";
   }
  }
  mandatory false;
 }
 leaf DLRBAVERAGERATIO {
  type union {
   type uint8 {
    range "1..255";
   }
  }
  mandatory false;
 }
 leaf DLRBMAXRATIO {
  type union {
   type uint8 {
    range "1..255";
   }
  }
  mandatory false;
 }
 leaf DLRBMINRATIO {
  type union {
   type uint8 {
    range "1..255";
   }
  }
  mandatory false;
 }
 leaf OLD_NRDUCELLID {
  type union {
   type int32 {
    range "-1..65534";
   }
  }
  mandatory false;
 }
 leaf NRDUCELLID {
  type union {
   type int32 {
    range "-1..65534";
   }
  }
  mandatory false;
 }
 leaf OPRBNUM {
  type union {
   type uint8 {
    range "27..53";
   }
  }
  mandatory false;
 }
 leaf QCIGRPRBCTRLARPTHLD {
  type uint8 {
   range "1..15";
  }
  mandatory false;
 }
 leaf QCIGRPRBCTRLMCSTHLD {
  type uint8 {
   range "0..28";
  }
  mandatory false;
 }
 leaf QCIGRPRBCTRLUESELPOL {
  type enumeration {
   enum val-0;
   enum val-1;
   enum val-2;
   enum val-3;
   enum val-4;
  }
  mandatory false;
 }
 leaf RBRATIODYNADJSWITCH {
  type string;
  mandatory false;
 }
 leaf RESSTRATEGYTYPE {
  type enumeration {
   enum val-0;
   enum val-1;
   enum val-2;
  }
  mandatory false;
 }
 leaf RESUSAGEOBJECT {
  type enumeration {
   enum val-0;
   enum val-1;
   enum val-2;
   enum val-3;
   enum val-4;
   enum val-5;
   enum val-6;
  }
  mandatory false;
 }
 leaf SCHEDULINGPOLICYSWITCH {
  type string;
  mandatory false;
 }
 leaf ULDLRESALLOCFACTOR {
  type uint8 {
   range "0..2";
  }
  mandatory false;
 }
 leaf ULMINRBSTARTPOS {
  type union {
   type uint16 {
    range "0..65535";
   }
  }
  mandatory false;
 }
 leaf ULRBAVERAGERATIO {
  type union {
   type uint8 {
    range "1..255";
   }
  }
  mandatory false;
 }
 leaf ULRBMAXRATIO {
  type union {
   type uint8 {
    range "1..255";
   }
  }
  mandatory false;
 }
 leaf ULRBMINRATIO {
  type union {
   type uint8 {
    range "1..255";
   }
  }
  mandatory false;
 }
 }
 grouping NRDUCELLRIMCONFIG-attributes {
 leaf INTRFAVOIDDETECTPRDNUM {
  type uint8 {
   range "0..3";
  }
  mandatory false;
 }
 leaf INTRFAVOIDDLEXTENSIONLEVEL {
  type enumeration {
   enum val-0;
   enum val-1;
   enum val-2;
   enum val-3;
   enum val-4;
  }
  mandatory false;
 }
 leaf INTRFAVOIDPUSCHSCHPRBTHLD {
  type enumeration {
   enum val-40;
   enum val-50;
   enum val-60;
   enum val-70;
   enum val-80;
   enum val-90;
   enum val-100;
  }
  mandatory false;
 }
 leaf INTRFAVOIDRSTRDETECTPRDNUM {
  type uint16 {
   range "3..288";
  }
  mandatory false;
 }
 leaf INTRFAVOIDULPWRDIFFTHLD {
  type int8 {
   range "-30..30";
  }
  mandatory false;
 }
 leaf INTRFULSLOTINITMCSOFFSET {
  type uint8 {
   range "0..28";
  }
  mandatory false;
 }
 leaf NRDUCELLID {
  type union {
   type int32 {
    range "-1..65534";
   }
  }
  mandatory false;
 }
 leaf RIMPOLICYSWITCH {
  type string;
  mandatory false;
 }
 leaf RIMRSFREQCANDNUM {
  type enumeration {
   enum val-1;
   enum val-2;
   enum val-3;
   enum val-4294967295;
  }
  mandatory false;
 }
 leaf RIMRSFUNCTIONSWITCH {
  type string;
  mandatory false;
 }
 leaf RIMRSSCRTIMERMULTIFACTOR {
  type uint32 {
   range "0..2147483647";
  }
  mandatory false;
 }
 leaf RIMRSSCRTIMEROFFSET {
  type uint32 {
   range "0..2147483647";
  }
  mandatory false;
 }
 leaf RIMRSSTARTFREQOFFSET {
  type uint8 {
   range "0..225";
  }
  mandatory false;
 }
 leaf RIMRSSTARTFREQREOFFSET {
  type uint8 {
   range "0..11";
  }
  mandatory false;
 }
 leaf RIMRSTYPE1INTRFTHLD {
  type int16 {
   range "-140..-50";
  }
  mandatory false;
 }
 leaf RIMRSTYPE1INTRFTHLDOFS {
  type int8 {
   range "-40..40";
  }
  mandatory false;
 }
 leaf RIMRSTYPE1SCIDFORIS0 {
  type union {
   type uint32 {
    range "0..4294967295";
   }
  }
  mandatory false;
 }
 leaf RIMRSTYPE1SCIDFORIS1 {
  type union {
   type uint32 {
    range "0..4294967295";
   }
  }
  mandatory false;
 }
 leaf RIMRSTYPE1SCIDFORIS2 {
  type union {
   type uint32 {
    range "0..4294967295";
   }
  }
  mandatory false;
 }
 leaf RIMRSTYPE1SCIDFORIS3 {
  type union {
   type uint32 {
    range "0..4294967295";
   }
  }
  mandatory false;
 }
 leaf RIMRSTYPE1SCIDFORIS4 {
  type union {
   type uint32 {
    range "0..4294967295";
   }
  }
  mandatory false;
 }
 leaf RIMRSTYPE1SCIDFORIS5 {
  type union {
   type uint32 {
    range "0..4294967295";
   }
  }
  mandatory false;
 }
 leaf RIMRSTYPE1SCIDFORIS6 {
  type union {
   type uint32 {
    range "0..4294967295";
   }
  }
  mandatory false;
 }
 leaf RIMRSTYPE1SCIDFORIS7 {
  type union {
   type uint32 {
    range "0..4294967295";
   }
  }
  mandatory false;
 }
 leaf RIMRSTYPE1SEQCANDNUM {
  type enumeration {
   enum val-1;
   enum val-2;
   enum val-3;
   enum val-4;
   enum val-4294967295;
  }
  mandatory false;
 }
 leaf RIMRSTYPE1SETID {
  type union {
   type uint32 {
    range "0..4294967295";
   }
  }
  mandatory false;
 }
 leaf RIMRSTYPE1SETIDSIZE {
  type union {
   type uint8 {
    range "15..255";
   }
  }
  mandatory false;
 }
 leaf RIMRSTYPE2SCIDFORIS0 {
  type union {
   type uint32 {
    range "0..4294967295";
   }
  }
  mandatory false;
 }
 leaf RIMRSTYPE2SCIDFORIS1 {
  type union {
   type uint32 {
    range "0..4294967295";
   }
  }
  mandatory false;
 }
 leaf RIMRSTYPE2SCIDFORIS2 {
  type union {
   type uint32 {
    range "0..4294967295";
   }
  }
  mandatory false;
 }
 leaf RIMRSTYPE2SCIDFORIS3 {
  type union {
   type uint32 {
    range "0..4294967295";
   }
  }
  mandatory false;
 }
 leaf RIMRSTYPE2SCIDFORIS4 {
  type union {
   type uint32 {
    range "0..4294967295";
   }
  }
  mandatory false;
 }
 leaf RIMRSTYPE2SCIDFORIS5 {
  type union {
   type uint32 {
    range "0..4294967295";
   }
  }
  mandatory false;
 }
 leaf RIMRSTYPE2SCIDFORIS6 {
  type union {
   type uint32 {
    range "0..4294967295";
   }
  }
  mandatory false;
 }
 leaf RIMRSTYPE2SCIDFORIS7 {
  type union {
   type uint32 {
    range "0..4294967295";
   }
  }
  mandatory false;
 }
 leaf RIMRSTYPE2SEQCANDNUM {
  type enumeration {
   enum val-1;
   enum val-2;
   enum val-3;
   enum val-4;
   enum val-4294967295;
  }
  mandatory false;
 }
 leaf RIMRSTYPE2SETID {
  type union {
   type uint32 {
    range "0..4294967295";
   }
  }
  mandatory false;
 }
 leaf RIMRSTYPE2SETIDSIZE {
  type union {
   type uint8 {
    range "15..255";
   }
  }
  mandatory false;
 }
 leaf ULPWRDIFFTHLD {
  type int8 {
   range "-30..30";
  }
  mandatory false;
 }
 leaf ULSLOTPWRDIFFTHLD {
  type int8 {
   range "-50..50";
  }
  mandatory false;
 }
 }
 grouping NRDUCELLSELCONFIG-attributes {
 leaf CELLRESERVEDFOROP {
  type boolean;
  mandatory false;
 }
 leaf MAXUETRANSMITPOWER {
  type union {
   type int16 {
    range "-30..255";
   }
  }
  mandatory false;
 }
 leaf MINIMUMRXLEVEL {
  type int8 {
   range "-70..-22";
  }
  mandatory false;
 }
 leaf MINIMUMRXQLTY {
  type int8 {
   range "-43..-12";
  }
  mandatory false;
 }
 leaf NRDUCELLID {
  type union {
   type int32 {
    range "-1..65534";
   }
  }
  mandatory false;
 }
 leaf RASDTDATAVOLUMETHLD {
  type enumeration {
   enum val-0;
   enum val-1;
   enum val-2;
   enum val-3;
  }
  mandatory false;
 }
 leaf RASDTRSRPTHLD {
  type int16 {
   range "-156..-31";
  }
  mandatory false;
 }
 leaf SIMODIFICATIONPERIOD {
  type enumeration {
   enum val-0;
   enum val-1;
   enum val-2;
   enum val-3;
   enum val-4;
   enum val-5;
  }
  mandatory false;
 }
 leaf SIB1PAYLOADREDUCTIONPOLICY {
  type enumeration {
   enum val-0;
   enum val-1;
   enum val-2;
  }
  mandatory false;
 }
 leaf SIBOPTIONALIEIND {
  type string;
  mandatory false;
 }
 }
 grouping NRDUCELLSERVEXP-attributes {
 leaf BITRATECONFIGSWITCH {
  type string;
  mandatory false;
 }
 leaf BWPSWITCHPRESCHTRANSDELAY {
  type uint8 {
   range "0..100";
  }
  mandatory false;
 }
 leaf COMMONLARGEPKTIDENTTHLD {
  type uint32 {
   range "0..1000000";
  }
  mandatory false;
 }
 leaf COMMONSMALLPKTEVALTIME {
  type uint16 {
   range "0..65535";
  }
  mandatory false;
 }
 leaf COMMONULLARGEPKTIDENTTHLD {
  type uint32 {
   range "0..1000000";
  }
  mandatory false;
 }
 leaf DLBITRATELIMIT {
  type uint32 {
   range "1..100000";
  }
  mandatory false;
 }
 leaf DLLARGEPKTFASTIDENTTHLD {
  type uint32 {
   range "0..1000000";
  }
  mandatory false;
 }
 leaf FULLBUFFERUEDLPRBUSAGETHLD {
  type uint8 {
   range "1..100";
  }
  mandatory false;
 }
 leaf FULLBUFFERUEDLTTIRATIOTHLD {
  type uint8 {
   range "1..100";
  }
  mandatory false;
 }
 leaf FULLBUFFERUEEVALPRD {
  type uint8 {
   range "1..100";
  }
  mandatory false;
 }
 leaf FULLBUFFERUEULPRBUSAGETHLD {
  type uint8 {
   range "1..100";
  }
  mandatory false;
 }
 leaf FULLBUFFERUEULTTIRATIOTHLD {
  type uint8 {
   range "1..100";
  }
  mandatory false;
 }
 leaf LIGHTLOADUENUMTHLD {
  type uint8 {
   range "0..200";
  }
  mandatory false;
 }
 leaf MINCCEAGGLEVEL {
  type enumeration {
   enum val-0;
   enum val-1;
   enum val-2;
   enum val-3;
  }
  mandatory false;
 }
 leaf NRDUCELLID {
  type union {
   type int32 {
    range "-1..65534";
   }
  }
  mandatory false;
 }
 leaf PLATINUMUSERNUMUPPERLIMIT {
  type uint8 {
   range "0..20";
  }
  mandatory false;
 }
 leaf POWERSAVINGOPTSWITCH {
  type string;
  mandatory false;
 }
 leaf RLCADAPTRETRANSTIME {
  type enumeration {
   enum val-100;
   enum val-200;
   enum val-300;
   enum val-400;
  }
  mandatory false;
 }
 leaf RLCSWITCH {
  type string;
  mandatory false;
 }
 leaf SSLOTOLLAOFFSET {
  type union {
   type int8 {
    range "-10..127";
   }
  }
  mandatory false;
 }
 leaf SERVICEEXPALGOSWITCH {
  type string;
  mandatory false;
 }
 leaf SPARSESERVDATARATETHLD {
  type uint16 {
   range "0..15000";
  }
  mandatory false;
 }
 leaf SPARSESERVEVALPRD {
  type uint8 {
   range "1..10";
  }
  mandatory false;
 }
 leaf SPDTURBOALGOEXTSWITCH {
  type string;
  mandatory false;
 }
 leaf SPDTURBOALGOSWITCH {
  type string;
  mandatory false;
 }
 leaf SPDTURBODLSLOTCONVPATTERN {
  type uint32 {
   range "0..1048575";
  }
  mandatory false;
 }
 leaf SPDTURBONCELLPDSCHSINROFS {
  type uint8 {
   range "0..40";
  }
  mandatory false;
 }
 leaf SPDTURBOSRSP0OFFSET {
  type uint8 {
   range "0..100";
  }
  mandatory false;
 }
 leaf SPDTURBOUEDLTYPE1RESALLOC {
  type enumeration {
   enum val-0;
   enum val-1;
   enum val-2;
  }
  mandatory false;
 }
 leaf SPDTURBOULRANKOPTSINRTHLD {
  type int16 {
   range "-100..350";
  }
  mandatory false;
 }
 leaf SPDTURBOULSLOTCONVPATTERN {
  type uint32 {
   range "0..1048575";
  }
  mandatory false;
 }
 leaf SPDTURBOVONRDLMAXMCS {
  type uint8 {
   range "0..28";
  }
  mandatory false;
 }
 leaf SPDTURBOVONRPUSCHPWROFFSET {
  type uint8 {
   range "0..12";
  }
  mandatory false;
 }
 leaf SPDTURBOVONRULMAXMCS {
  type uint8 {
   range "0..28";
  }
  mandatory false;
 }
 leaf SPEEDTURBONCELLSRSPERIOD {
  type enumeration {
   enum val-0;
   enum val-1;
   enum val-2;
   enum val-3;
   enum val-4;
   enum val-5;
  }
  mandatory false;
 }
 leaf SRSTAJUDGETIMES {
  type uint8 {
   range "0..50";
  }
  mandatory false;
 }
 leaf SRSTATHLD {
  type uint16 {
   range "119..496";
  }
  mandatory false;
 }
 leaf SRSWIDEBANDRESPERIOD {
  type enumeration {
   enum val-1;
   enum val-2;
   enum val-3;
   enum val-4;
   enum val-5;
   enum val-6;
   enum val-7;
  }
  mandatory false;
 }
 leaf STUEWAVEFORMADAPTSINRTHLD {
  type int16 {
   range "-100..350";
  }
  mandatory false;
 }
 leaf TBCQUEUE1STPKTWAITDLYTHLD {
  type uint8 {
   range "0..30";
  }
  mandatory false;
 }
 leaf ULAMCFILTERCOEFF {
  type union {
   type uint8 {
    range "0..255";
   }
  }
  mandatory false;
 }
 leaf ULBITRATELIMIT {
  type uint32 {
   range "40..100000";
  }
  mandatory false;
 }
 leaf ULRANKADAPTSINRTHLD {
  type uint16 {
   range "0..3000";
  }
  mandatory false;
 }
 leaf ULSPARSESERVPREALLOCDUR {
  type uint8 {
   range "1..200";
  }
  mandatory false;
 }
 leaf ULSPARSESERVPREALLOCINTVL {
  type uint16 {
   range "200..2000";
  }
  mandatory false;
 }
 leaf ULVONRRLCSEGNUM {
  type uint8 {
   range "0..30";
  }
  mandatory false;
 }
 leaf VOLBASEDSCCDEACTVTIMETHLD {
  type uint8 {
   range "2..60";
  }
  mandatory false;
 }
 leaf VONRDLJITTERELIMINATETIME {
  type uint8 {
   range "0..10";
  }
  mandatory false;
 }
 leaf VONRPUSCHPOWEROFFSET {
  type uint8 {
   range "0..12";
  }
  mandatory false;
 }
 }
 grouping NRDUCELLSMARTPWRLOCK-attributes {
 leaf ABSOLUTEEIRPCONTROLTHLD {
  type union {
   type uint16 {
    range "0..65535";
   }
  }
  mandatory false;
 }
 leaf ABSOLUTEPOWERCONTROLTHLD {
  type union {
   type uint32 {
    range "0..4294967295";
   }
  }
  mandatory false;
 }
 leaf AVERAGEPERIOD {
  type uint32 {
   range "1..86400";
  }
  mandatory false;
 }
 leaf MAXANTAMPLIFYFACTOR {
  type union {
   type uint16 {
    range "0..1000";
   }
  }
  mandatory false;
 }
 leaf NRDUCELLTRPID {
  type union {
   type int32 {
    range "-1..65534";
   }
  }
  mandatory false;
 }
 leaf NRSPSGRPID {
  type uint16 {
   range "0..65535";
  }
  mandatory false;
 }
 leaf POWERCONTROLTHRESHOLD {
  type uint8 {
   range "0..100";
  }
  mandatory false;
 }
 leaf PWRDENSITYREFLEVEL {
  type union {
   type uint32 {
    range "0..1000000";
   }
  }
  mandatory false;
 }
 leaf SMARTPOWERLOCKSW {
  type string;
  mandatory false;
 }
 leaf UPHEMITRPPOWERUPPERLIMIT {
  type uint16 {
   range "150..1000";
  }
  mandatory false;
 }
 leaf WRC19EIRPCONTROLTHLD {
  type uint16 {
   range "0..1000";
  }
  mandatory false;
 }
 }
 grouping NRDUCELLSPCTCLOUD-attributes {
 leaf NRDUCELLID {
  type union {
   type int32 {
    range "-1..65534";
   }
  }
  mandatory false;
 }
 leaf NRSPCTSHRCELLGRPID {
  type uint8 {
   range "0..23";
  }
  mandatory false;
 }
 }
 grouping NRDUCELLSRSMEAS-attributes {
 leaf DMMIMOTRPSELRSRPDIFFTHLD {
  type uint8 {
   range "0..100";
  }
  mandatory false;
 }
 leaf DMRSTASINRTHID {
  type int8 {
   range "-20..20";
  }
  mandatory false;
 }
 leaf EUTRANTONRSINRHIGHTHLD {
  type int16 {
   range "-100..350";
  }
  mandatory false;
 }
 leaf INCRSRSRSRPABSTHLD {
  type int16 {
   range "-165..-50";
  }
  mandatory false;
 }
 leaf INCRSRSRSRPDIFFTHLD {
  type uint8 {
   range "1..50";
  }
  mandatory false;
 }
 leaf INCRSRSRSRPFILTERCOEFF {
  type uint8 {
   range "10..90";
  }
  mandatory false;
 }
 leaf INCRUEIDENTIFICATIONSWITCH {
  type boolean;
  mandatory false;
 }
 leaf LOWSRSPRESINRTHLD {
  type int8 {
   range "-100..100";
  }
  mandatory false;
 }
 leaf NRDUCELLID {
  type union {
   type int32 {
    range "-1..65534";
   }
  }
  mandatory false;
 }
 leaf NRTOEUTRANSINRLOWTHLD {
  type int16 {
   range "-100..350";
  }
  mandatory false;
 }
 leaf NSASPKTULBACKTONRPENALTYTIME {
  type uint8 {
   range "1..60";
  }
  mandatory false;
 }
 leaf NSASPLITULPATHSELSINRTHLD {
  type int16 {
   range "-100..350";
  }
  mandatory false;
 }
 leaf NSATDMPCTRIGSINRHYST {
  type uint8 {
   range "0..100";
  }
  mandatory false;
 }
 leaf NSATDMPCTRIGSINRTHLD {
  type int8 {
   range "-100..100";
  }
  mandatory false;
 }
 leaf NSAULFACKTOLTESINRHYST {
  type uint8 {
   range "0..100";
  }
  mandatory false;
 }
 leaf NSAULFACKTOLTESINRTHLD {
  type int16 {
   range "-200..350";
  }
  mandatory false;
 }
 leaf NSAULFBTOLTESINROPTSW {
  type string;
  mandatory false;
 }
 leaf NSAULPATHSELSINRHIGHTHLD {
  type int16 {
   range "-100..350";
  }
  mandatory false;
 }
 leaf NSAULPATHSELSINRHYST {
  type uint8 {
   range "0..100";
  }
  mandatory false;
 }
 leaf NSAULPATHSELSINRLOWTHLD {
  type int16 {
   range "-100..350";
  }
  mandatory false;
 }
 leaf NSAULPATHSELSINRTIMETOTRIG {
  type uint8 {
   range "1..200";
  }
  mandatory false;
 }
 leaf NSAULPATHTOLTERATERATIO {
  type uint16 {
   range "1..50000";
  }
  mandatory false;
 }
 leaf NSAULPATHTONRRATERATIO {
  type uint16 {
   range "1..50000";
  }
  mandatory false;
 }
 leaf NSAULTOLTESINRTIMETOTRIG {
  type uint16 {
   range "1..300";
  }
  mandatory false;
 }
 leaf SRSDMRSTADIFFTHID {
  type uint8 {
   range "0..80";
  }
  mandatory false;
 }
 leaf SRSINTRFTAMEASOPTSW {
  type boolean;
  mandatory false;
 }
 leaf SRSINTRFTHLD {
  type uint8 {
   range "0..15";
  }
  mandatory false;
 }
 leaf SRSMEASEXTSW {
  type string;
  mandatory false;
 }
 leaf SRSMEASOPTPOL {
  type enumeration {
   enum val-0;
   enum val-1;
   enum val-2;
   enum val-3;
  }
  mandatory false;
 }
 leaf SRSMEASOPTSWITCH {
  type string;
  mandatory false;
 }
 leaf SRSRSRPEXCTHLD {
  type enumeration {
   enum val-0;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
  }
  mandatory false;
 }
 leaf SRSTAEXCEPTIONPROTECTTHLD {
  type enumeration {
   enum val-0;
   enum val-30;
   enum val-40;
   enum val-50;
   enum val-60;
   enum val-70;
   enum val-80;
  }
  mandatory false;
 }
 leaf SRSTAMEASSWITCH {
  type string;
  mandatory false;
 }
 leaf TIMECHNCORRTHLD {
  type union {
   type uint8 {
    range "0..100";
   }
  }
  mandatory false;
 }
 leaf ULROHCSINRHYST {
  type uint8 {
   range "0..100";
  }
  mandatory false;
 }
 leaf ULROHCSINRTHLD {
  type int16 {
   range "-200..200";
  }
  mandatory false;
 }
 leaf ULSRSMEASUSAGESWITCH {
  type enumeration {
   enum val-0;
   enum val-1;
   enum val-2;
  }
  mandatory false;
 }
 leaf ULVOICEROHCEXITSINRTHLD {
  type int16 {
   range "-200..0";
  }
  mandatory false;
 }
 }
 grouping NRDUCELLSULRELATION-attributes {
 leaf FDDCYCLICPREFIXLENGTH {
  type boolean;
  mandatory false;
 }
 leaf FDDFREQUENCYBAND {
  type enumeration {
   enum val-1;
   enum val-3;
   enum val-5;
   enum val-8;
   enum val-20;
   enum val-28;
   enum val-66;
  }
  mandatory false;
 }
 leaf FDDLTENRSPCTSHRFLAG {
  type boolean;
  mandatory false;
 }
 leaf FDDSUBCARRIERSPACING {
  type boolean;
  mandatory false;
 }
 leaf FDDULBANDWIDTH {
  type enumeration {
   enum val-0;
   enum val-1;
   enum val-2;
   enum val-4;
   enum val-5;
   enum val-6;
   enum val-7;
   enum val-8;
   enum val-9;
   enum val-10;
   enum val-11;
   enum val-12;
  }
  mandatory false;
 }
 leaf FDDULBWP0BANDWIDTH {
  type uint16 {
   range "11..273";
  }
  mandatory false;
 }
 leaf FDDULBWP0CONFIGMODE {
  type boolean;
  mandatory false;
 }
 leaf FDDULBWP0STARTPRB {
  type uint8 {
   range "0..245";
  }
  mandatory false;
 }
 leaf FDDULNRARFCN {
  type union {
   type uint32 {
    range "140600..396000";
   }
  }
  mandatory false;
 }
 leaf FDDULOFFSETTOCARRIER {
  type uint8 {
   range "0..140";
  }
  mandatory false;
 }
 leaf MULTIFREQULPRBUSAGETHLD {
  type uint8 {
   range "0..100";
  }
  mandatory false;
 }
 leaf NRDUCELLID {
  type union {
   type int32 {
    range "-1..65534";
   }
  }
  mandatory false;
 }
 leaf SULCARRCHANGESINRTHLD {
  type int8 {
   range "-20..10";
  }
  mandatory false;
 }
 leaf SULINDEX {
  type union {
   type int8 {
    range "-1..7";
   }
  }
  mandatory false;
 }
 leaf SULNRDUCELLID {
  type uint16 {
   range "0..65534";
  }
  mandatory false;
 }
 leaf SULTYPE {
  type boolean;
  mandatory false;
 }
 }
 grouping NRDUCELLTRP-attributes {
 leaf ANTPOLARIZATION {
  type enumeration {
   enum val-0;
   enum val-1;
   enum val-2;
   enum val-3;
  }
  mandatory false;
 }
 leaf BASEBANDEQMID {
  type union {
   type uint8 {
    range "0..255";
   }
  }
  mandatory false;
 }
 leaf BBRESMUTUALAIDSW {
  type boolean;
  mandatory false;
 }
 leaf BRANCHCPRICOMPRESSION {
  type enumeration {
   enum val-1;
   enum val-3;
   enum val-5;
   enum val-7;
   enum val-9;
   enum val-11;
  }
  mandatory false;
 }
 leaf CPRICOMPRESSION {
  type enumeration {
   enum val-1;
   enum val-2;
   enum val-3;
   enum val-5;
   enum val-7;
   enum val-8;
  }
  mandatory false;
 }
 leaf FRANDDUPLEXMODE {
  type enumeration {
   enum val-0;
   enum val-1;
   enum val-2;
   enum val-3;
   enum val-4;
  }
  mandatory false;
 }
 leaf MASTERTRPID {
  type uint16 {
   range "0..65534";
  }
  mandatory false;
 }
 leaf MAXEIRP {
  type uint16 {
   range "0..1000";
  }
  mandatory false;
 }
 leaf MAXTRANSMITPOWER {
  type uint16 {
   range "0..600";
  }
  mandatory false;
 }
 leaf MAXTRANSMITPOWERMW {
  type uint32 {
   range "1..1000000";
  }
  mandatory false;
 }
 leaf NRDUCELLID {
  type uint16 {
   range "0..65535";
  }
  mandatory false;
 }
 leaf OLD_NRDUCELLTRPID {
  type union {
   type int32 {
    range "-1..65534";
   }
  }
  mandatory false;
 }
 leaf NRDUCELLTRPID {
  type union {
   type int32 {
    range "-1..65534";
   }
  }
  mandatory false;
 }
 leaf POWERCONFIGMODE {
  type enumeration {
   enum val-0;
   enum val-1;
   enum val-2;
  }
  mandatory false;
 }
 leaf SECONDARYBASEBANDEQMID {
  type union {
   type uint8 {
    range "0..255";
   }
  }
  mandatory false;
 }
 leaf TRPAUXILIARYINDEX {
  type uint8 {
   range "0..255";
  }
  mandatory false;
 }
 leaf TRPTYPE {
  type enumeration {
   enum val-0;
   enum val-1;
   enum val-2;
   enum val-3;
   enum val-4;
   enum val-5;
   enum val-6;
  }
  mandatory false;
 }
 leaf TXRXMODE {
  type enumeration {
   enum val-0;
   enum val-1;
   enum val-2;
   enum val-3;
   enum val-4;
   enum val-5;
   enum val-6;
   enum val-7;
   enum val-8;
   enum val-9;
   enum val-10;
   enum val-11;
   enum val-12;
   enum val-13;
  }
  mandatory false;
 }
 leaf ULRXPOWERATTENUATIONVALUE {
  type uint8 {
   range "0..20";
  }
  mandatory false;
 }
 }
 grouping NRDUCELLTRPBEAM-attributes {
 leaf AIRCOVERAGESCENARIO {
  type enumeration {
   enum val-1;
   enum val-2;
   enum val-3;
   enum val-4;
  }
  mandatory false;
 }
 leaf AIRMAXSSBPWROFFSET {
  type int8 {
   range "-15..15";
  }
  mandatory false;
 }
 leaf AZIMUTH {
  type int8 {
   range "-47..47";
  }
  mandatory false;
 }
 leaf CONNMODECOVSCENARIOEXT {
  type enumeration {
   enum val-0;
   enum val-1;
   enum val-2;
   enum val-3;
   enum val-4;
  }
  mandatory false;
 }
 leaf CONNMODECOVERAGESCENARIO {
  type enumeration {
   enum val-0;
   enum val-1;
   enum val-2;
  }
  mandatory false;
 }
 leaf COVERAGESCENARIO {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-27;
   enum val-28;
   enum val-29;
   enum val-30;
   enum val-31;
   enum val-32;
   enum val-33;
   enum val-34;
   enum val-35;
   enum val-36;
   enum val-37;
   enum val-98;
   enum val-99;
  }
  mandatory false;
 }
 leaf GROUNDAIRCOVERAGEMODE {
  type enumeration {
   enum val-1;
   enum val-2;
   enum val-3;
   enum val-4;
  }
  mandatory false;
 }
 leaf MAXSSBPWROFFSET {
  type int8 {
   range "-15..15";
  }
  mandatory false;
 }
 leaf MAXSSBPWROFFSETEXT {
  type uint8 {
   range "0..3";
  }
  mandatory false;
 }
 leaf NRDUCELLTRPID {
  type union {
   type int32 {
    range "-1..65534";
   }
  }
  mandatory false;
 }
 leaf SCENARIOBEAMALGOSW {
  type string;
  mandatory false;
 }
 leaf TILT {
  type union {
   type int16 {
    range "-5..255";
   }
  }
  mandatory false;
 }
 leaf TRPANTTYPE {
  type enumeration {
   enum val-0;
   enum val-1;
   enum val-2;
   enum val-3;
  }
  mandatory false;
 }
 leaf TRPBEAMOPTSWITCH {
  type string;
  mandatory false;
 }
 }
 grouping NRDUCELLTRPCUSTBEAM-attributes {
 leaf AZIMUTH {
  type int8 {
   range "-47..47";
  }
  mandatory false;
 }
 leaf OLD_BEAMID {
  type enumeration {
   enum val--1;
   enum val-0;
   enum val-1;
   enum val-2;
   enum val-3;
   enum val-4;
   enum val-5;
   enum val-6;
   enum val-7;
  }
  mandatory false;
 }
 leaf BEAMID {
  type enumeration {
   enum val--1;
   enum val-0;
   enum val-1;
   enum val-2;
   enum val-3;
   enum val-4;
   enum val-5;
   enum val-6;
   enum val-7;
  }
  mandatory false;
 }
 leaf HORZLEFTPOLARIZATIONWTID {
  type uint16 {
   range "0..65535";
  }
  mandatory false;
 }
 leaf HORZRIGHTPOLARIZATIONWTID {
  type uint16 {
   range "0..65535";
  }
  mandatory false;
 }
 leaf MAXSSBPWROFFSET {
  type int8 {
   range "-15..15";
  }
  mandatory false;
 }
 leaf OLD_NRDUCELLTRPID {
  type union {
   type int32 {
    range "-1..65534";
   }
  }
  mandatory false;
 }
 leaf NRDUCELLTRPID {
  type union {
   type int32 {
    range "-1..65534";
   }
  }
  mandatory false;
 }
 leaf SSBBEAMHORIZWIDTH {
  type boolean;
  mandatory false;
 }
 leaf TILT {
  type int8 {
   range "-3..15";
  }
  mandatory false;
 }
 leaf VERTLEFTPOLARIZATIONWTID {
  type uint16 {
   range "0..65535";
  }
  mandatory false;
 }
 leaf VERTRIGHTPOLARIZATIONWTID {
  type uint16 {
   range "0..65535";
  }
  mandatory false;
 }
 }
 grouping NRDUCELLTRPDLSCH-attributes {
 leaf DLSCHPRIFACTOR {
  type uint16 {
   range "1..1000";
  }
  mandatory false;
 }
 leaf NRDUCELLTRPID {
  type union {
   type int32 {
    range "-1..65534";
   }
  }
  mandatory false;
 }
 }
 grouping NRDUCELLTRPDYNPWRSHR-attributes {
 leaf JTUETHLD {
  type uint8 {
   range "0..100";
  }
  mandatory false;
 }
 leaf MAXPOWERSHARINGRATE {
  type uint8 {
   range "1..100";
  }
  mandatory false;
 }
 leaf MULTIBANDPWRADAPTSCHPRI {
  type uint8 {
   range "0..7";
  }
  mandatory false;
 }
 leaf NRDUCELLTRPID {
  type union {
   type int32 {
    range "-1..65534";
   }
  }
  mandatory false;
 }
 }
 grouping NRDUCELLTRPIFINFO-attributes {
 leaf NRDUCELLTRPID {
  type union {
   type int32 {
    range "-1..65534";
   }
  }
  mandatory false;
 }
 leaf NRIFDLCENTERFREQ {
  type uint32 {
   range "63728..83728";
  }
  mandatory false;
 }
 leaf NRIFOUTPUTPOWER {
  type int16 {
   range "-200..-100";
  }
  mandatory false;
 }
 leaf NRIFULCENTERFREQ {
  type uint16 {
   range "14576..34576";
  }
  mandatory false;
 }
 leaf NRIFUPLINKRECEIVEGAIN {
  type uint16 {
   range "350..550";
  }
  mandatory false;
 }
 }
 grouping NRDUCELLTRPMMWAVBEAM-attributes {
 leaf AIRCOVERAGESCENARIO {
  type boolean;
  mandatory false;
 }
 leaf AZIMUTH {
  type int8 {
   range "-10..10";
  }
  mandatory false;
 }
 leaf BEAMALLOCATIONPOLICY {
  type boolean;
  mandatory false;
 }
 leaf BEAMPERFORMANCESW {
  type string;
  mandatory false;
 }
 leaf CSIBEAMALLOCATIONPOLICY {
  type boolean;
  mandatory false;
 }
 leaf COVERAGESCENARIO {
  type enumeration {
   enum val-100;
   enum val-101;
   enum val-102;
   enum val-103;
   enum val-104;
   enum val-105;
   enum val-106;
   enum val-151;
  }
  mandatory false;
 }
 leaf CUSTOMIZEDSSBBEAM0ID {
  type union {
   type uint8 {
    range "0..255";
   }
  }
  mandatory false;
 }
 leaf CUSTOMIZEDSSBBEAM10ID {
  type union {
   type uint8 {
    range "0..255";
   }
  }
  mandatory false;
 }
 leaf CUSTOMIZEDSSBBEAM11ID {
  type union {
   type uint8 {
    range "0..255";
   }
  }
  mandatory false;
 }
 leaf CUSTOMIZEDSSBBEAM12ID {
  type union {
   type uint8 {
    range "0..255";
   }
  }
  mandatory false;
 }
 leaf CUSTOMIZEDSSBBEAM13ID {
  type union {
   type uint8 {
    range "0..255";
   }
  }
  mandatory false;
 }
 leaf CUSTOMIZEDSSBBEAM14ID {
  type union {
   type uint8 {
    range "0..255";
   }
  }
  mandatory false;
 }
 leaf CUSTOMIZEDSSBBEAM15ID {
  type union {
   type uint8 {
    range "0..255";
   }
  }
  mandatory false;
 }
 leaf CUSTOMIZEDSSBBEAM1ID {
  type union {
   type uint8 {
    range "0..255";
   }
  }
  mandatory false;
 }
 leaf CUSTOMIZEDSSBBEAM2ID {
  type union {
   type uint8 {
    range "0..255";
   }
  }
  mandatory false;
 }
 leaf CUSTOMIZEDSSBBEAM3ID {
  type union {
   type uint8 {
    range "0..255";
   }
  }
  mandatory false;
 }
 leaf CUSTOMIZEDSSBBEAM4ID {
  type union {
   type uint8 {
    range "0..255";
   }
  }
  mandatory false;
 }
 leaf CUSTOMIZEDSSBBEAM5ID {
  type union {
   type uint8 {
    range "0..255";
   }
  }
  mandatory false;
 }
 leaf CUSTOMIZEDSSBBEAM6ID {
  type union {
   type uint8 {
    range "0..255";
   }
  }
  mandatory false;
 }
 leaf CUSTOMIZEDSSBBEAM7ID {
  type union {
   type uint8 {
    range "0..255";
   }
  }
  mandatory false;
 }
 leaf CUSTOMIZEDSSBBEAM8ID {
  type union {
   type uint8 {
    range "0..255";
   }
  }
  mandatory false;
 }
 leaf CUSTOMIZEDSSBBEAM9ID {
  type union {
   type uint8 {
    range "0..255";
   }
  }
  mandatory false;
 }
 leaf CUSTOMIZEDSSBBEAMNUMBER {
  type enumeration {
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
  }
  mandatory false;
 }
 leaf MAXSSBPWROFFSET {
  type int8 {
   range "-15..15";
  }
  mandatory false;
 }
 leaf NRDUCELLTRPID {
  type union {
   type int32 {
    range "-1..65534";
   }
  }
  mandatory false;
 }
 leaf PREFERREDBEAM1ID {
  type uint8 {
   range "0..255";
  }
  mandatory false;
 }
 leaf PREFERREDBEAM2ID {
  type uint8 {
   range "0..255";
  }
  mandatory false;
 }
 leaf TILT {
  type union {
   type int16 {
    range "-12..255";
   }
  }
  mandatory false;
 }
 }
 grouping NRDUCELLTRPSHARING-attributes {
 leaf OLD_NRDUCELLTRPID {
  type union {
   type int32 {
    range "-1..65534";
   }
  }
  mandatory false;
 }
 leaf NRDUCELLTRPID {
  type union {
   type int32 {
    range "-1..65534";
   }
  }
  mandatory false;
 }
 leaf OLD_SHRTRPID {
  type union {
   type int32 {
    range "-1..65534";
   }
  }
  mandatory false;
 }
 leaf SHRTRPID {
  type union {
   type int32 {
    range "-1..65534";
   }
  }
  mandatory false;
 }
 }
 grouping NRDUCELLTRPULSCH-attributes {
 leaf NRDUCELLTRPID {
  type union {
   type int32 {
    range "-1..65534";
   }
  }
  mandatory false;
 }
 leaf ULSCHPRIFACTOR {
  type uint16 {
   range "1..1000";
  }
  mandatory false;
 }
 }
 grouping NRDUCELLUACBAR-attributes {
 leaf OLD_ACCESSCATEGORY {
  type union {
   type int8 {
    range "-1..63";
   }
  }
  mandatory false;
 }
 leaf ACCESSCATEGORY {
  type union {
   type int8 {
    range "-1..63";
   }
  }
  mandatory false;
 }
 leaf ACCESSCONTROLPARAMGRPID {
  type uint8 {
   range "0..127";
  }
  mandatory false;
 }
 leaf ACCESSCONTROLTYPE {
  type boolean;
  mandatory false;
 }
 leaf FLOWCTRLUACENTERTHLD {
  type union {
   type uint8 {
    range "0..255";
   }
  }
  mandatory false;
 }
 leaf FLOWCTRLUACEXITTHLD {
  type union {
   type uint8 {
    range "0..255";
   }
  }
  mandatory false;
 }
 leaf OLD_NRDUCELLID {
  type union {
   type int32 {
    range "-1..65534";
   }
  }
  mandatory false;
 }
 leaf NRDUCELLID {
  type union {
   type int32 {
    range "-1..65534";
   }
  }
  mandatory false;
 }
 leaf OLD_OPERATORID {
  type union {
   type int16 {
    range "-1..255";
   }
  }
  mandatory false;
 }
 leaf OPERATORID {
  type union {
   type int16 {
    range "-1..255";
   }
  }
  mandatory false;
 }
 leaf RRCUSERNUMUACENTERTHLD {
  type union {
   type uint8 {
    range "0..255";
   }
  }
  mandatory false;
 }
 leaf RRCUSERNUMUACEXITTHLD {
  type union {
   type uint8 {
    range "0..255";
   }
  }
  mandatory false;
 }
 }
 grouping NRDUCELLUEPWRSAVING-attributes {
 leaf BWP1TOBWP2DLTHPTTHLD {
  type uint16 {
   range "0..50000";
  }
  mandatory false;
 }
 leaf BWP1TOBWP2EVALUATEPERIOD {
  type uint8 {
   range "1..50";
  }
  mandatory false;
 }
 leaf BWP1TOBWP2ULTHPTTHLD {
  type uint16 {
   range "0..50000";
  }
  mandatory false;
 }
 leaf BWP2DNSTOSPARSESSSGTHLDFAC {
  type uint8 {
   range "0..30";
  }
  mandatory false;
 }
 leaf BWP2MAXRBNUM {
  type enumeration {
   enum val-51;
   enum val-64;
   enum val-106;
  }
  mandatory false;
 }
 leaf BWP2NETWORKINGMODE {
  type boolean;
  mandatory false;
 }
 leaf BWP2SCHFAILRATETHLD {
  type uint8 {
   range "1..9";
  }
  mandatory false;
 }
 leaf BWP2SPARSETODNSSSSGTHLDFAC {
  type uint8 {
   range "50..70";
  }
  mandatory false;
 }
 leaf BWPPWRSAVINGSW {
  type string;
  mandatory false;
 }
 leaf BWPSWITCHINGMODE {
  type boolean;
  mandatory false;
 }
 leaf DNSTOSPARSESSSGDLTHPTTHLD {
  type uint16 {
   range "0..50000";
  }
  mandatory false;
 }
 leaf DNSTOSPARSESSSGULTHPTTHLD {
  type uint16 {
   range "0..50000";
  }
  mandatory false;
 }
 leaf DRXSLEEPSTATEDETECTTHLD {
  type uint32 {
   range "1..4294967295";
  }
  mandatory false;
 }
 leaf IAADAPTIVEALGOSWITCH {
  type boolean;
  mandatory false;
 }
 leaf IDLEUEPWRSAVINGSWITCH {
  type string;
  mandatory false;
 }
 leaf NRDUCELLDRXALGOSWITCH {
  type string;
  mandatory false;
 }
 leaf NRDUCELLID {
  type union {
   type int32 {
    range "-1..65534";
   }
  }
  mandatory false;
 }
 leaf PDCCHSKIPPINGDURATION {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
  }
  mandatory false;
 }
 leaf REDCAPSSSGSWTHPTTHLD {
  type uint16 {
   range "0..50000";
  }
  mandatory false;
 }
 leaf REDCAPSSSGSWVOLTHLDSLOTNUM {
  type uint8 {
   range "4..40";
  }
  mandatory false;
 }
 leaf RLMRELAXGOODSERVCELLEVAOFS {
  type enumeration {
   enum val-0;
   enum val-1;
   enum val-2;
   enum val-3;
  }
  mandatory false;
 }
 leaf SCHPWRSAVINGSW {
  type string;
  mandatory false;
 }
 leaf SSSGSWITCHINGLEVEL {
  type boolean;
  mandatory false;
 }
 leaf UEPOWERSAVINGSWITCH {
  type string;
  mandatory false;
 }
 leaf ULVONRSILENCECOMPENSCHPRD {
  type enumeration {
   enum val-0;
   enum val-1;
   enum val-2;
   enum val-3;
  }
  mandatory false;
 }
 leaf VONREXITBWP2USERNUMTHLD {
  type uint8 {
   range "0..100";
  }
  mandatory false;
 }
 leaf WEAKCOVERAGECQITHLD {
  type uint8 {
   range "0..15";
  }
  mandatory false;
 }
 leaf WEAKCOVERAGETHLDOFFSET {
  type uint8 {
   range "0..10";
  }
  mandatory false;
 }
 leaf WEAKCOVERAGEULSINRTHLD {
  type int8 {
   range "-5..10";
  }
  mandatory false;
 }
 }
 grouping NRDUCELLUETIMERCONST-attributes {
 leaf N310 {
  type enumeration {
   enum val-0;
   enum val-1;
   enum val-2;
   enum val-3;
   enum val-4;
   enum val-5;
   enum val-6;
   enum val-7;
  }
  mandatory false;
 }
 leaf N311 {
  type enumeration {
   enum val-0;
   enum val-1;
   enum val-2;
   enum val-3;
   enum val-4;
   enum val-5;
   enum val-6;
   enum val-7;
  }
  mandatory false;
 }
 leaf NRDUCELLID {
  type union {
   type int32 {
    range "-1..65534";
   }
  }
  mandatory false;
 }
 leaf T300 {
  type enumeration {
   enum val-0;
   enum val-1;
   enum val-2;
   enum val-3;
   enum val-4;
   enum val-5;
   enum val-6;
   enum val-7;
  }
  mandatory false;
 }
 leaf T301 {
  type enumeration {
   enum val-0;
   enum val-1;
   enum val-2;
   enum val-3;
   enum val-4;
   enum val-5;
   enum val-6;
   enum val-7;
  }
  mandatory false;
 }
 leaf T304 {
  type enumeration {
   enum val-0;
   enum val-1;
   enum val-2;
   enum val-3;
   enum val-4;
   enum val-5;
   enum val-6;
   enum val-7;
  }
  mandatory false;
 }
 leaf T310 {
  type enumeration {
   enum val-0;
   enum val-1;
   enum val-2;
   enum val-3;
   enum val-4;
   enum val-5;
   enum val-6;
   enum val-7;
   enum val-8;
  }
  mandatory false;
 }
 leaf T311 {
  type enumeration {
   enum val-0;
   enum val-1;
   enum val-2;
   enum val-3;
   enum val-4;
   enum val-5;
   enum val-6;
  }
  mandatory false;
 }
 leaf T319 {
  type enumeration {
   enum val-0;
   enum val-1;
   enum val-2;
   enum val-3;
   enum val-4;
   enum val-5;
   enum val-6;
   enum val-7;
  }
  mandatory false;
 }
 }
 grouping NRDUCELLULMIMO-attributes {
 leaf ALIGNPAIRBIGPKTRBREDRATIO {
  type uint8 {
   range "1..100";
  }
  mandatory false;
 }
 leaf ALIGNPAIRBIGSMLPKTRBTHLD {
  type uint8 {
   range "0..100";
  }
  mandatory false;
 }
 leaf ALIGNPAIRSMLPKTRBEXTRATIO {
  type uint16 {
   range "100..30000";
  }
  mandatory false;
 }
 leaf FLEXPAIRLRGPKTRBRATIOTHLD {
  type uint8 {
   range "20..100";
  }
  mandatory false;
 }
 leaf FLEXPAIRRBRATIOTHLD {
  type uint16 {
   range "0..1000";
  }
  mandatory false;
 }
 leaf FLEXPAIRSMLPKTRBRATIOTHLD {
  type uint8 {
   range "0..100";
  }
  mandatory false;
 }
 leaf MUDETECTIONSINROFFSET {
  type int8 {
   range "-99..100";
  }
  mandatory false;
 }
 leaf MUFREQSELSCHRBRATIOTHLD {
  type uint8 {
   range "0..100";
  }
  mandatory false;
 }
 leaf MUGRPPAIRNORMSUMINRBRATIO {
  type uint8 {
   range "0..100";
  }
  mandatory false;
 }
 leaf MURBRATIOTHLD {
  type uint8 {
   range "0..100";
  }
  mandatory false;
 }
 leaf MURBREDUCTIONSINROFFSET {
  type uint16 {
   range "0..1000";
  }
  mandatory false;
 }
 leaf MURBREDUCTIONSINRTHLD {
  type uint16 {
   range "0..1000";
  }
  mandatory false;
 }
 leaf MURBREDUCTIONUENUMTHLD {
  type uint8 {
   range "1..100";
  }
  mandatory false;
 }
 leaf NRDUCELLID {
  type union {
   type int32 {
    range "-1..65534";
   }
  }
  mandatory false;
 }
 leaf ULHIGHLAYERMUMIMOSWITCH {
  type string;
  mandatory false;
 }
 leaf ULMUGATHEROPTGAINTHLD {
  type uint8 {
   range "0..200";
  }
  mandatory false;
 }
 leaf ULMUMIMOALGOSWITCH {
  type string;
  mandatory false;
 }
 leaf ULMUMIMOCORRTHLD {
  type uint8 {
   range "1..10";
  }
  mandatory false;
 }
 leaf ULMUMIMOSINRTHLD {
  type int16 {
   range "-200..200";
  }
  mandatory false;
 }
 leaf ULMUMIMOSPCTEFFTHLD {
  type uint16 {
   range "100..4000";
  }
  mandatory false;
 }
 leaf ULMULTILAYERPAIRSINRTHLD {
  type int16 {
   range "-200..200";
  }
  mandatory false;
 }
 }
 grouping NRDUCELLULPCCONFIG-attributes {
 leaf CMPMSGPWRRAMPSTEP {
  type enumeration {
   enum val-0;
   enum val-1;
   enum val-2;
  }
  mandatory false;
 }
 leaf DELTAFPUCCHFORMAT1 {
  type int8 {
   range "-16..15";
  }
  mandatory false;
 }
 leaf DELTAFPUCCHFORMAT3 {
  type int8 {
   range "-16..15";
  }
  mandatory false;
 }
 leaf DELTAFPUCCHFORMAT4 {
  type int8 {
   range "-16..15";
  }
  mandatory false;
 }
 leaf DELTAPREAMBLEMSG3 {
  type int8 {
   range "-1..6";
  }
  mandatory false;
 }
 leaf INTRFUESRSPCMINSINRTARGET {
  type int8 {
   range "-20..100";
  }
  mandatory false;
 }
 leaf MAXSRSPOADJUSTAMOUNT {
  type uint8 {
   range "0..20";
  }
  mandatory false;
 }
 leaf NEARPOINTPUSCHSINRTHLDOFS {
  type uint8 {
   range "0..4";
  }
  mandatory false;
 }
 leaf NRDUCELLID {
  type union {
   type int32 {
    range "-1..65534";
   }
  }
  mandatory false;
 }
 leaf PATHLOSSCOEFF {
  type enumeration {
   enum val-0;
   enum val-1;
   enum val-2;
   enum val-3;
   enum val-4;
   enum val-5;
   enum val-6;
   enum val-7;
  }
  mandatory false;
 }
 leaf PATHLOSSCOEFFPOSSRS {
  type enumeration {
   enum val-0;
   enum val-1;
   enum val-2;
   enum val-3;
   enum val-4;
   enum val-5;
   enum val-6;
   enum val-7;
  }
  mandatory false;
 }
 leaf PHRPERIODICTIMER {
  type enumeration {
   enum val-10;
   enum val-20;
   enum val-50;
   enum val-100;
   enum val-200;
   enum val-500;
   enum val-600;
   enum val-610;
  }
  mandatory false;
 }
 leaf PHRPROHIBITTIMER {
  type enumeration {
   enum val-0;
   enum val-10;
   enum val-20;
   enum val-50;
   enum val-100;
   enum val-200;
   enum val-500;
   enum val-600;
  }
  mandatory false;
 }
 leaf PONOMINALPUCCH {
  type int8 {
   range "-101..12";
  }
  mandatory false;
 }
 leaf PONOMINALPUSCH {
  type int8 {
   range "-101..12";
  }
  mandatory false;
 }
 leaf POPOSSRS {
  type int8 {
   range "-101..12";
  }
  mandatory false;
 }
 leaf POSRS {
  type int8 {
   range "-101..12";
  }
  mandatory false;
 }
 leaf PREAMBLEINITRXTARGETPWR {
  type int8 {
   range "-101..-30";
  }
  mandatory false;
 }
 leaf PUCCHBERTARGETTHLD {
  type uint16 {
   range "3..1000";
  }
  mandatory false;
 }
 leaf PUCCHFORMAT1PCSINRTARGET {
  type uint8 {
   range "0..50";
  }
  mandatory false;
 }
 leaf PUCCHFORMAT3PCSINRTARGET {
  type uint8 {
   range "0..50";
  }
  mandatory false;
 }
 leaf PUCCHFORMAT4PCSINRTARGET {
  type uint8 {
   range "0..50";
  }
  mandatory false;
 }
 leaf PUCCHRSRPUPPERLIMIT {
  type int16 {
   range "-200..0";
  }
  mandatory false;
 }
 leaf PUSCHJOINTPCUEIOTTHLDOFS {
  type uint8 {
   range "0..50";
  }
  mandatory false;
 }
 leaf PUSCHJOINTPCCELLIOTTHLD {
  type uint8 {
   range "0..20";
  }
  mandatory false;
 }
 leaf PUSCHJOINTPCMCSTHLD {
  type uint8 {
   range "0..28";
  }
  mandatory false;
 }
 leaf PUSCHJOINTPCPRBTHLD {
  type enumeration {
   enum val-40;
   enum val-50;
   enum val-60;
   enum val-70;
   enum val-80;
   enum val-90;
   enum val-100;
  }
  mandatory false;
 }
 leaf PUSCHJOINTPCUSERIOTTHLD {
  type uint8 {
   range "0..20";
  }
  mandatory false;
 }
 leaf PUSCHOUTERLOOPPCTARGET {
  type uint16 {
   range "0..600";
  }
  mandatory false;
 }
 leaf PUSCHRSRPTHLD {
  type int16 {
   range "-202..24";
  }
  mandatory false;
 }
 leaf PWRRAMPINGSTEP {
  type enumeration {
   enum val-0;
   enum val-1;
   enum val-2;
   enum val-3;
  }
  mandatory false;
 }
 leaf SMALLPKTUEPUSCHPWROFFSET {
  type uint8 {
   range "0..10";
  }
  mandatory false;
 }
 leaf SMALLPKTUESRSPCSINRTARGET {
  type int16 {
   range "-100..300";
  }
  mandatory false;
 }
 leaf SMALLPKTUESRSSINRTHLD {
  type int16 {
   range "-200..200";
  }
  mandatory false;
 }
 leaf SRSPCSINRTARGET {
  type int16 {
   range "-100..300";
  }
  mandatory false;
 }
 leaf SRSPOADAPTPERIOD {
  type enumeration {
   enum val-500;
   enum val-1000;
   enum val-1500;
   enum val-2000;
  }
  mandatory false;
 }
 leaf SRSRSRPTHLD {
  type int16 {
   range "-202..24";
  }
  mandatory false;
 }
 leaf TPCVALUEINMSG2 {
  type enumeration {
   enum val-0;
   enum val-1;
   enum val-2;
   enum val-3;
   enum val-4;
   enum val-5;
   enum val-6;
   enum val-7;
  }
  mandatory false;
 }
 leaf ULCAPSDCOEFF {
  type uint8 {
   range "1..100";
  }
  mandatory false;
 }
 leaf ULPWRCTRLALGOEXTSWITCH {
  type string;
  mandatory false;
 }
 leaf ULPWRCTRLALGOSWITCH {
  type string;
  mandatory false;
 }
 leaf VONRHORAMPREAMBLEPWROFS {
  type uint8 {
   range "0..20";
  }
  mandatory false;
 }
 }
 grouping NRDUCELLULSCH-attributes {
 leaf AERIALUSERULSCHRBRATIO {
  type union {
   type uint8 {
    range "0..50";
   }
  }
  mandatory false;
 }
 leaf CMPMSGMCSUPPERLIMIT {
  type uint8 {
   range "0..28";
  }
  mandatory false;
 }
 leaf FARUEULSCHMININTVL {
  type uint8 {
   range "1..50";
  }
  mandatory false;
 }
 leaf NRDUCELLID {
  type union {
   type int32 {
    range "-1..65534";
   }
  }
  mandatory false;
 }
 leaf REDCAPSTABLEULEXPMAXUENUM {
  type union {
   type uint8 {
    range "0..255";
   }
  }
  mandatory false;
 }
 leaf RFCOMBSWITCH {
  type string;
  mandatory false;
 }
 leaf STABLEULEXPMAXUENUM {
  type union {
   type uint8 {
    range "0..255";
   }
  }
  mandatory false;
 }
 leaf ULBALANCEDSCHUENUMTHLD {
  type uint16 {
   range "1..20000";
  }
  mandatory false;
 }
 leaf ULBEAMPRIBASEDSCH {
  type boolean;
  mandatory false;
 }
 leaf ULCCEBASEDSCHPRIFACTOR {
  type uint16 {
   range "1..1024";
  }
  mandatory false;
 }
 leaf ULFIRSTRETRANSMINRBPCT {
  type uint8 {
   range "10..100";
  }
  mandatory false;
 }
 leaf ULFLOWCTRLPRBUSAGETHLD0 {
  type uint8 {
   range "0..100";
  }
  mandatory false;
 }
 leaf ULFLOWCTRLPRBUSAGETHLD1 {
  type uint8 {
   range "0..100";
  }
  mandatory false;
 }
 leaf ULGRANTFREEHARQPROCESSNUM {
  type uint8 {
   range "1..16";
  }
  mandatory false;
 }
 leaf ULGRANTFREEPDPTHLD {
  type uint16 {
   range "17..4000";
  }
  mandatory false;
 }
 leaf ULLARGEPKTUEDATAVOLUMETHLD {
  type uint32 {
   range "1..1000000";
  }
  mandatory false;
 }
 leaf ULLATENCYOPTPRBUSAGETHLD {
  type uint8 {
   range "10..60";
  }
  mandatory false;
 }
 leaf ULPREALLOCPOLENHSWITCH {
  type string;
  mandatory false;
 }
 leaf ULRBRESSCHPRIORITY {
  type enumeration {
   enum val-0;
   enum val-1;
   enum val-2;
  }
  mandatory false;
 }
 leaf ULRETRANSADJOCCASION {
  type enumeration {
   enum val-0;
   enum val-1;
   enum val-2;
   enum val-3;
   enum val-4;
   enum val-5;
   enum val-6;
   enum val-7;
   enum val-8;
  }
  mandatory false;
 }
 leaf ULSCHALGOSWITCH {
  type string;
  mandatory false;
 }
 leaf ULSCHDCIEXTEXITTHLD {
  type uint8 {
   range "0..100";
  }
  mandatory false;
 }
 leaf ULSCHDCIEXTUSRNUMTHLD {
  type uint16 {
   range "1..10000";
  }
  mandatory false;
 }
 leaf ULSCHGUARUSERRATE {
  type uint32 {
   range "0..100000";
  }
  mandatory false;
 }
 leaf ULVOICEMAXMCS {
  type uint8 {
   range "0..28";
  }
  mandatory false;
 }
 leaf VOICEULCCEALLOCFAILRATTHLD {
  type uint8 {
   range "0..100";
  }
  mandatory false;
 }
 leaf VOICEULSCHSWITCH {
  type string;
  mandatory false;
 }
 leaf VOICEULSLOTAGGPWRLMTRBTHLD {
  type uint8 {
   range "1..20";
  }
  mandatory false;
 }
 leaf VOICEULSLOTAGGRBTHLD {
  type uint16 {
   range "1..273";
  }
  mandatory false;
 }
 leaf VONRULSLOTAGGEXITSINRHYST {
  type uint8 {
   range "3..6";
  }
  mandatory false;
 }
 leaf VONRULSLOTAGGTRIGSINRTHLD {
  type int8 {
   range "-5..10";
  }
  mandatory false;
 }
 }
 grouping NRDUCELLULTACONFIG-attributes {
 leaf NRDUCELLID {
  type union {
   type int32 {
    range "-1..65534";
   }
  }
  mandatory false;
 }
 leaf TAALGOOPTSWITCH {
  type string;
  mandatory false;
 }
 leaf ULTIMEALIGNMENTTIMER {
  type enumeration {
   enum val-0;
   enum val-1;
   enum val-2;
   enum val-3;
   enum val-4;
   enum val-5;
   enum val-6;
   enum val-7;
  }
  mandatory false;
 }
 }
 grouping NRDUCELLVIRTUALRADAR-attributes {
 leaf ISOLATIONDETINTERVAL {
  type uint8 {
   range "7..60";
  }
  mandatory false;
 }
 leaf NRDUCELLID {
  type union {
   type int32 {
    range "-1..65534";
   }
  }
  mandatory false;
 }
 leaf VIRTUALRADARSWITCH {
  type string;
  mandatory false;
 }
 }
 grouping NRDUCELLVOICEALGO-attributes {
 leaf NRDUCELLID {
  type union {
   type int32 {
    range "-1..65534";
   }
  }
  mandatory false;
 }
 leaf TIMEDUPEXTCONTPKTLOSSTHLD {
  type uint8 {
   range "1..100";
  }
  mandatory false;
 }
 leaf ULVOICEMUTEDETECTPRD {
  type uint8 {
   range "1..10";
  }
  mandatory false;
 }
 leaf ULVOICEMUTERBLERTHLD {
  type uint8 {
   range "10..100";
  }
  mandatory false;
 }
 leaf VOICEUSERALGOSW {
  type string;
  mandatory false;
 }
 }
 grouping NRDUFDDCELLTRPBEAM-attributes {
 leaf AZIMUTH {
  type int8 {
   range "-47..47";
  }
  mandatory false;
 }
 leaf BEAMFORMINGCAPABILITY {
  type boolean;
  mandatory false;
 }
 leaf CDDALGODELAYSTEP {
  type uint8 {
   range "0..48";
  }
  mandatory false;
 }
 leaf COVERAGESCENARIO {
  type enumeration {
   enum val-200;
   enum val-201;
   enum val-202;
   enum val-203;
   enum val-204;
   enum val-205;
   enum val-206;
   enum val-207;
   enum val-208;
   enum val-210;
   enum val-220;
   enum val-240;
   enum val-241;
   enum val-242;
   enum val-290;
  }
  mandatory false;
 }
 leaf FDD8TNARROWCSIAZIMUTHOFS {
  type int8 {
   range "-20..20";
  }
  mandatory false;
 }
 leaf MAXSSBPWROFFSET {
  type int8 {
   range "-15..15";
  }
  mandatory false;
 }
 leaf NRDUCELLTRPID {
  type union {
   type int32 {
    range "-1..65534";
   }
  }
  mandatory false;
 }
 leaf SCENARIOBEAMALGOSW {
  type string;
  mandatory false;
 }
 leaf SCENARIOMODESW {
  type string;
  mandatory false;
 }
 leaf TILT {
  type union {
   type int16 {
    range "-3..255";
   }
  }
  mandatory false;
 }
 leaf TILTFRACTIONPART {
  type int8 {
   range "-9..9";
  }
  mandatory false;
 }
 }
 grouping NRDUSECTORSPLITGROUP-attributes {
 leaf BEAMDEPLOYMENTMODE {
  type boolean;
  mandatory false;
 }
 leaf DLRANKADAPTEVALUATIONPRD {
  type union {
   type uint16 {
    range "0..3600";
   }
  }
  mandatory false;
 }
 leaf GROUPMAXTRANSMITPWR {
  type union {
   type uint16 {
    range "0..65535";
   }
  }
  mandatory false;
 }
 leaf OLD_NRDUSECTORSPLITGROUPID {
  type union {
   type int16 {
    range "-1..255";
   }
  }
  mandatory false;
 }
 leaf NRDUSECTORSPLITGROUPID {
  type union {
   type int16 {
    range "-1..255";
   }
  }
  mandatory false;
 }
 }
 grouping NRDUSECTORSPLITTRP-attributes {
 leaf CELLBEAMINDEX {
  type uint8 {
   range "0..2";
  }
  mandatory false;
 }
 leaf FLEXIBLEWEIGHT {
  type uint16 {
   range "0..7070";
  }
  mandatory false;
 }
 leaf OLD_NRDUCELLTRPID {
  type union {
   type int32 {
    range "-1..65534";
   }
  }
  mandatory false;
 }
 leaf NRDUCELLTRPID {
  type union {
   type int32 {
    range "-1..65534";
   }
  }
  mandatory false;
 }
 leaf OLD_NRDUSECTORSPLITGROUPID {
  type union {
   type int16 {
    range "-1..255";
   }
  }
  mandatory false;
 }
 leaf NRDUSECTORSPLITGROUPID {
  type union {
   type int16 {
    range "-1..255";
   }
  }
  mandatory false;
 }
 }
 grouping NREXTERNALNCELL-attributes {
 leaf ADDITIONALFREQUENCYBAND {
  type enumeration {
   enum val-0;
   enum val-2;
   enum val-5;
   enum val-8;
   enum val-12;
   enum val-18;
   enum val-25;
   enum val-26;
   enum val-31;
   enum val-38;
   enum val-41;
   enum val-48;
   enum val-71;
   enum val-72;
   enum val-77;
   enum val-78;
   enum val-85;
   enum val-90;
   enum val-96;
   enum val-102;
   enum val-104;
   enum val-105;
   enum val-106;
   enum val-257;
   enum val-258;
   enum val-259;
   enum val-260;
   enum val-261;
  }
  mandatory false;
 }
 leaf AERIALCELLFLAG {
  type enumeration {
   enum val-0;
   enum val-1;
   enum val-2;
  }
  mandatory false;
 }
 leaf OLD_CELLID {
  type union {
   type int16 {
    range "-1..16383";
   }
  }
  mandatory false;
 }
 leaf CELLID {
  type union {
   type int16 {
    range "-1..16383";
   }
  }
  mandatory false;
 }
 leaf CELLNAME {
  type string {
   length "0..99";
  }
  mandatory false;
 }
 leaf CTRLMODE {
  type boolean;
  mandatory false;
 }
 leaf FREQUENCYBAND {
  type enumeration {
   enum val-0;
   enum val-1;
   enum val-2;
   enum val-3;
   enum val-5;
   enum val-7;
   enum val-8;
   enum val-12;
   enum val-13;
   enum val-14;
   enum val-18;
   enum val-20;
   enum val-24;
   enum val-25;
   enum val-26;
   enum val-28;
   enum val-30;
   enum val-31;
   enum val-34;
   enum val-38;
   enum val-39;
   enum val-40;
   enum val-41;
   enum val-46;
   enum val-48;
   enum val-50;
   enum val-51;
   enum val-53;
   enum val-54;
   enum val-65;
   enum val-66;
   enum val-70;
   enum val-71;
   enum val-72;
   enum val-74;
   enum val-75;
   enum val-77;
   enum val-78;
   enum val-79;
   enum val-85;
   enum val-90;
   enum val-91;
   enum val-92;
   enum val-93;
   enum val-94;
   enum val-96;
   enum val-100;
   enum val-101;
   enum val-102;
   enum val-104;
   enum val-105;
   enum val-106;
   enum val-109;
   enum val-257;
   enum val-258;
   enum val-259;
   enum val-260;
   enum val-261;
   enum val-262;
   enum val-263;
  }
  mandatory false;
 }
 leaf HIGHSPEEDFLAG {
  type boolean;
  mandatory false;
 }
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf MOBILITYFUNIND {
  type string;
  mandatory false;
 }
 leaf NRNETWORKINGOPTION {
  type enumeration {
   enum val-0;
   enum val-1;
   enum val-2;
   enum val-3;
  }
  mandatory false;
 }
 leaf PHYSICALCELLID {
  type uint16 {
   range "0..1007";
  }
  mandatory false;
 }
 leaf PLMNRESERVEDFLAG {
  type boolean;
  mandatory false;
 }
 leaf SSBDESCMETHOD {
  type boolean;
  mandatory false;
 }
 leaf SSBFREQPOS {
  type uint32 {
   range "0..3279165";
  }
  mandatory false;
 }
 leaf TAC {
  type union {
   type uint32 {
    range "0..4294967295";
   }
  }
  mandatory false;
 }
 leaf OLD_GNBID {
  type union {
   type int64 {
    range "-1..4294967295";
   }
  }
  mandatory false;
 }
 leaf GNBID {
  type union {
   type int64 {
    range "-1..4294967295";
   }
  }
  mandatory false;
 }
 }
 grouping NREXTERNALNCELLCAG-attributes {
 leaf CAGCELLID {
  type union {
   type uint16 {
    range "0..65535";
   }
  }
  mandatory false;
 }
 leaf OLD_CAGID {
  type union {
   type int64 {
    range "-1..4294967295";
   }
  }
  mandatory false;
 }
 leaf CAGID {
  type union {
   type int64 {
    range "-1..4294967295";
   }
  }
  mandatory false;
 }
 leaf OLD_CAGMCC {
  type string {
   length "3";
  }
  mandatory false;
 }
 leaf CAGMCC {
  type string {
   length "3";
  }
  mandatory false;
 }
 leaf OLD_CAGMNC {
  type string {
   length "2..3";
  }
  mandatory false;
 }
 leaf CAGMNC {
  type string {
   length "2..3";
  }
  mandatory false;
 }
 leaf CAGTAC {
  type uint32 {
   range "0..16777215";
  }
  mandatory false;
 }
 leaf CAGGNBID {
  type uint32 {
   range "0..4294967295";
  }
  mandatory false;
 }
 leaf OLD_CELLID {
  type union {
   type int16 {
    range "-1..16383";
   }
  }
  mandatory false;
 }
 leaf CELLID {
  type union {
   type int16 {
    range "-1..16383";
   }
  }
  mandatory false;
 }
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf OLD_GNBID {
  type union {
   type int64 {
    range "-1..4294967295";
   }
  }
  mandatory false;
 }
 leaf GNBID {
  type union {
   type int64 {
    range "-1..4294967295";
   }
  }
  mandatory false;
 }
 }
 grouping NREXTERNALNCELLPLMN-attributes {
 leaf OLD_CELLID {
  type union {
   type int16 {
    range "-1..16383";
   }
  }
  mandatory false;
 }
 leaf CELLID {
  type union {
   type int16 {
    range "-1..16383";
   }
  }
  mandatory false;
 }
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf MOBILITYFUNIND {
  type string;
  mandatory false;
 }
 leaf NRNETWORKINGOPTION {
  type enumeration {
   enum val-0;
   enum val-1;
   enum val-2;
   enum val-3;
  }
  mandatory false;
 }
 leaf PLMNRESERVEDFLAG {
  type boolean;
  mandatory false;
 }
 leaf OLD_SHAREDMCC {
  type string {
   length "3";
  }
  mandatory false;
 }
 leaf SHAREDMCC {
  type string {
   length "3";
  }
  mandatory false;
 }
 leaf OLD_SHAREDMNC {
  type string {
   length "2..3";
  }
  mandatory false;
 }
 leaf SHAREDMNC {
  type string {
   length "2..3";
  }
  mandatory false;
 }
 leaf SHAREDPLMNCELLID {
  type union {
   type uint16 {
    range "0..65535";
   }
  }
  mandatory false;
 }
 leaf SHAREDPLMNGNBID {
  type uint32 {
   range "0..4294967295";
  }
  mandatory false;
 }
 leaf TAC {
  type union {
   type uint32 {
    range "0..4294967295";
   }
  }
  mandatory false;
 }
 leaf OLD_GNBID {
  type union {
   type int64 {
    range "-1..4294967295";
   }
  }
  mandatory false;
 }
 leaf GNBID {
  type union {
   type int64 {
    range "-1..4294967295";
   }
  }
  mandatory false;
 }
 }
 grouping NRINTERRATHOPARAM-attributes {
 leaf DLRESOURCERATIO {
  type uint8 {
   range "1..100";
  }
  mandatory false;
 }
 leaf EPSFBMEASPROTECTTIMER {
  type uint8 {
   range "10..200";
  }
  mandatory false;
 }
 leaf EPSFBMODE {
  type boolean;
  mandatory false;
 }
 leaf EPSFBMULTIFREQB1RPTWAITTMR {
  type uint8 {
   range "0..200";
  }
  mandatory false;
 }
 leaf EPSFBPROTECTIONTIMER {
  type uint8 {
   range "1..100";
  }
  mandatory false;
 }
 leaf HOMODESWITCH {
  type string;
  mandatory false;
 }
 leaf INTERRATHOTRIGGEREVENTTYPE {
  type boolean;
  mandatory false;
 }
 leaf MOBILITYHOCONTROLSWITCH {
  type string;
  mandatory false;
 }
 leaf NRCELLID {
  type union {
   type int32 {
    range "-1..65534";
   }
  }
  mandatory false;
 }
 }
}
