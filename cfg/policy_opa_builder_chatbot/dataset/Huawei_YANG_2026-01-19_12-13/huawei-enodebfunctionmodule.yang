module huawei-enodebfunctionmodule {
 yang-version 1.1;
 namespace "urn:rdns:com:huawei:oammodel:huawei-enodebfunctionmodule";
 prefix enodebfunctionmodule;
 import huawei-ne {
 prefix ne;
 }
 import huawei-yang-types {
 prefix hwat;
 }
 import ietf-inet-types {
 prefix inet;
 }
 import ietf-yang-types {
 prefix yang;
 }
 import ietf-interfaces {
 prefix if;
 }
 import ietf-ip {
 prefix ip;
 }
 description
 "Auto-generated modular YANG for huawei-enodebfunctionmodule" ;
 revision "2026-01-19" {
 description "Auto-generated abstract group module (aggregated lists from relations.xml). Generated at 2026-01-19 12:13.";
 }
 augment "/ne:NE" {
 container eNodeBFunctionModule {
  description "Abstract group container injected between NE and its direct child.";
  container attributes {
    leaf neName {
     type string;
     mandatory false;
    }
    leaf productversion {
     type string;
     mandatory false;
    }
  }
 }
 }
 augment "/ne:NE/enodebfunctionmodule:eNodeBFunctionModule/ENODEBFUNCTION" {
  list ANR {
   max-elements 1;
   key "ACTIVEPCICONFLICTSWITCH";
   leaf ACTIVEPCICONFLICTSWITCH {
    type leafref {
     path "../attributes/ACTIVEPCICONFLICTSWITCH";
     require-instance true;
    }
   }
   container attributes {
    uses ANR-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ASPARAGROUP {
   max-elements 12;
   key "ASPARAGROUPID";
   leaf ASPARAGROUPID {
    type leafref {
     path "../attributes/ASPARAGROUPID";
     require-instance true;
    }
   }
   container attributes {
    uses ASPARAGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list BBPASSISTGROUP {
   max-elements 6;
   key "BBPASSISTGRPID";
   leaf BBPASSISTGRPID {
    type leafref {
     path "../attributes/BBPASSISTGRPID";
     require-instance true;
    }
   }
   container attributes {
    uses BBPASSISTGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list BBPCOLLABORATIONGRP {
   max-elements 3;
   key "BBCOGROUPID";
   leaf BBCOGROUPID {
    type leafref {
     path "../attributes/BBCOGROUPID";
     require-instance true;
    }
   }
   container attributes {
    uses BBPCOLLABORATIONGRP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list BCCHCFG {
   max-elements 1;
   key "LOCALCELLID";
   leaf LOCALCELLID {
    type leafref {
     path "../attributes/LOCALCELLID";
     require-instance true;
    }
   }
   container attributes {
    uses BCCHCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/SECTORSPLITGROUP" {
  list BEAMNUMADJALGO {
   max-elements 1;
   key "SECTORSPLITGROUPID";
   leaf SECTORSPLITGROUPID {
    type leafref {
     path "../attributes/SECTORSPLITGROUPID";
     require-instance true;
    }
   }
   container attributes {
    uses BEAMNUMADJALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list CAGROUP {
   max-elements 36;
   key "CAGROUPID";
   leaf CAGROUPID {
    type leafref {
     path "../attributes/CAGROUPID";
     require-instance true;
    }
   }
   container attributes {
    uses CAGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CAGROUP" {
  list CAGROUPCELL {
   max-elements 9;
   key "CAGROUPID";
   leaf CAGROUPID {
    type leafref {
     path "../attributes/CAGROUPID";
     require-instance true;
    }
   }
   container attributes {
    uses CAGROUPCELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CAGROUPSCELLCFG {
   max-elements 1152;
   key "LOCALCELLID";
   leaf LOCALCELLID {
    type leafref {
     path "../attributes/LOCALCELLID";
     require-instance true;
    }
   }
   container attributes {
    uses CAGROUPSCELLCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CAMGTCFG {
   max-elements 1;
   key "LOCALCELLID";
   leaf LOCALCELLID {
    type leafref {
     path "../attributes/LOCALCELLID";
     require-instance true;
    }
   }
   container attributes {
    uses CAMGTCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list CDMA20001XRTTEXTCELL {
   max-elements 1152;
   key "NID";
   leaf NID {
    type leafref {
     path "../attributes/NID";
     require-instance true;
    }
   }
   container attributes {
    uses CDMA20001XRTTEXTCELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CDMA20001XRTTNCELL {
   max-elements 32;
   key "LOCALCELLID";
   leaf LOCALCELLID {
    type leafref {
     path "../attributes/LOCALCELLID";
     require-instance true;
    }
   }
   container attributes {
    uses CDMA20001XRTTNCELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CDMA20001XRTTPREREG {
   max-elements 1;
   key "LOCALCELLID";
   leaf LOCALCELLID {
    type leafref {
     path "../attributes/LOCALCELLID";
     require-instance true;
    }
   }
   container attributes {
    uses CDMA20001XRTTPREREG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CDMA2000BANDCLASS {
   max-elements 16;
   key "LOCALCELLID";
   leaf LOCALCELLID {
    type leafref {
     path "../attributes/LOCALCELLID";
     require-instance true;
    }
   }
   container attributes {
    uses CDMA2000BANDCLASS-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL/CDMA2000BANDCLASS" {
  list CDMA2000BCSCELLOP {
   max-elements 6;
   key "LOCALCELLID BANDCLASS";
   leaf LOCALCELLID {
    type leafref {
     path "../attributes/LOCALCELLID";
     require-instance true;
    }
   }
   leaf BANDCLASS {
    type leafref {
     path "../attributes/BANDCLASS";
     require-instance true;
    }
   }
   container attributes {
    uses CDMA2000BCSCELLOP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list CDMA2000HRPDEXTCELL {
   max-elements 1152;
   key "CELLNAME";
   leaf CELLNAME {
    type leafref {
     path "../attributes/CELLNAME";
     require-instance true;
    }
   }
   container attributes {
    uses CDMA2000HRPDEXTCELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CDMA2000HRPDNCELL {
   max-elements 32;
   key "LOCALCELLID";
   leaf LOCALCELLID {
    type leafref {
     path "../attributes/LOCALCELLID";
     require-instance true;
    }
   }
   container attributes {
    uses CDMA2000HRPDNCELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CDMA2000HRPDPREREG {
   max-elements 1;
   key "LOCALCELLID";
   leaf LOCALCELLID {
    type leafref {
     path "../attributes/LOCALCELLID";
     require-instance true;
    }
   }
   container attributes {
    uses CDMA2000HRPDPREREG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CDMA2000HRPDREFCELL {
   max-elements 6;
   key "LOCALCELLID";
   leaf LOCALCELLID {
    type leafref {
     path "../attributes/LOCALCELLID";
     require-instance true;
    }
   }
   container attributes {
    uses CDMA2000HRPDREFCELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL/CDMA2000BANDCLASS" {
  list CDMA2000NFREQ {
   max-elements 16;
   key "LOCALCELLID BANDCLASS";
   leaf LOCALCELLID {
    type leafref {
     path "../attributes/LOCALCELLID";
     require-instance true;
    }
   }
   leaf BANDCLASS {
    type leafref {
     path "../attributes/BANDCLASS";
     require-instance true;
    }
   }
   container attributes {
    uses CDMA2000NFREQ-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list CELL {
   max-elements 256;
   key "CELLID";
   leaf CELLID {
    type leafref {
     path "../attributes/CELLID";
     require-instance true;
    }
   }
   container attributes {
    uses CELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLACBAR {
   max-elements 1;
   key "LOCALCELLID";
   leaf LOCALCELLID {
    type leafref {
     path "../attributes/LOCALCELLID";
     require-instance true;
    }
   }
   container attributes {
    uses CELLACBAR-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLACCESS {
   max-elements 1;
   key "LOCALCELLID";
   leaf LOCALCELLID {
    type leafref {
     path "../attributes/LOCALCELLID";
     require-instance true;
    }
   }
   container attributes {
    uses CELLACCESS-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLALGOEXTSWITCH {
   max-elements 1;
   key "LOCALCELLID";
   leaf LOCALCELLID {
    type leafref {
     path "../attributes/LOCALCELLID";
     require-instance true;
    }
   }
   container attributes {
    uses CELLALGOEXTSWITCH-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLALGOSWITCH {
   max-elements 1;
   key "LOCALCELLID";
   leaf LOCALCELLID {
    type leafref {
     path "../attributes/LOCALCELLID";
     require-instance true;
    }
   }
   container attributes {
    uses CELLALGOSWITCH-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLAUTOSHUTDOWN {
   max-elements 1;
   key "LOCALCELLID";
   leaf LOCALCELLID {
    type leafref {
     path "../attributes/LOCALCELLID";
     require-instance true;
    }
   }
   container attributes {
    uses CELLAUTOSHUTDOWN-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLAUXDUBIND {
   max-elements 6;
   key "LOCALCELLID";
   leaf LOCALCELLID {
    type leafref {
     path "../attributes/LOCALCELLID";
     require-instance true;
    }
   }
   container attributes {
    uses CELLAUXDUBIND-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLAUXENBBIND {
   max-elements 6;
   key "LOCALCELLID";
   leaf LOCALCELLID {
    type leafref {
     path "../attributes/LOCALCELLID";
     require-instance true;
    }
   }
   container attributes {
    uses CELLAUXENBBIND-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLBACKOFF {
   max-elements 1;
   key "LOCALCELLID";
   leaf LOCALCELLID {
    type leafref {
     path "../attributes/LOCALCELLID";
     require-instance true;
    }
   }
   container attributes {
    uses CELLBACKOFF-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLBF {
   max-elements 1;
   key "LOCALCELLID";
   leaf LOCALCELLID {
    type leafref {
     path "../attributes/LOCALCELLID";
     require-instance true;
    }
   }
   container attributes {
    uses CELLBF-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLBFMIMOPARACFG {
   max-elements 1;
   key "LOCALCELLID";
   leaf LOCALCELLID {
    type leafref {
     path "../attributes/LOCALCELLID";
     require-instance true;
    }
   }
   container attributes {
    uses CELLBFMIMOPARACFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLCECFG {
   max-elements 1;
   key "LOCALCELLID";
   leaf LOCALCELLID {
    type leafref {
     path "../attributes/LOCALCELLID";
     require-instance true;
    }
   }
   container attributes {
    uses CELLCECFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLCESCHCFG {
   max-elements 4;
   key "LOCALCELLID";
   leaf LOCALCELLID {
    type leafref {
     path "../attributes/LOCALCELLID";
     require-instance true;
    }
   }
   container attributes {
    uses CELLCESCHCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLCHPWRCFG {
   max-elements 1;
   key "LOCALCELLID";
   leaf LOCALCELLID {
    type leafref {
     path "../attributes/LOCALCELLID";
     require-instance true;
    }
   }
   container attributes {
    uses CELLCHPWRCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLCOUNTERPARAGROUP {
   max-elements 1;
   key "LOCALCELLID";
   leaf LOCALCELLID {
    type leafref {
     path "../attributes/LOCALCELLID";
     require-instance true;
    }
   }
   container attributes {
    uses CELLCOUNTERPARAGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLCQIADAPTIVECFG {
   max-elements 1;
   key "LOCALCELLID";
   leaf LOCALCELLID {
    type leafref {
     path "../attributes/LOCALCELLID";
     require-instance true;
    }
   }
   container attributes {
    uses CELLCQIADAPTIVECFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLCQIADJALGO {
   max-elements 1;
   key "LOCALCELLID";
   leaf LOCALCELLID {
    type leafref {
     path "../attributes/LOCALCELLID";
     require-instance true;
    }
   }
   container attributes {
    uses CELLCQIADJALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLCSIRSPARACFG {
   max-elements 1;
   key "LOCALCELLID";
   leaf LOCALCELLID {
    type leafref {
     path "../attributes/LOCALCELLID";
     require-instance true;
    }
   }
   container attributes {
    uses CELLCSIRSPARACFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLCSPCPARA {
   max-elements 1;
   key "LOCALCELLID";
   leaf LOCALCELLID {
    type leafref {
     path "../attributes/LOCALCELLID";
     require-instance true;
    }
   }
   container attributes {
    uses CELLCSPCPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLDACQCFG {
   max-elements 1;
   key "LOCALCELLID";
   leaf LOCALCELLID {
    type leafref {
     path "../attributes/LOCALCELLID";
     require-instance true;
    }
   }
   container attributes {
    uses CELLDACQCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLDLCOMPALGO {
   max-elements 1;
   key "LOCALCELLID";
   leaf LOCALCELLID {
    type leafref {
     path "../attributes/LOCALCELLID";
     require-instance true;
    }
   }
   container attributes {
    uses CELLDLCOMPALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLDLICIC {
   max-elements 1;
   key "LOCALCELLID";
   leaf LOCALCELLID {
    type leafref {
     path "../attributes/LOCALCELLID";
     require-instance true;
    }
   }
   container attributes {
    uses CELLDLICIC-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLDLPCPDCCH {
   max-elements 1;
   key "LOCALCELLID";
   leaf LOCALCELLID {
    type leafref {
     path "../attributes/LOCALCELLID";
     require-instance true;
    }
   }
   container attributes {
    uses CELLDLPCPDCCH-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLDLPCPDSCH {
   max-elements 1;
   key "LOCALCELLID";
   leaf LOCALCELLID {
    type leafref {
     path "../attributes/LOCALCELLID";
     require-instance true;
    }
   }
   container attributes {
    uses CELLDLPCPDSCH-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLDLPCPDSCHPA {
   max-elements 1;
   key "LOCALCELLID";
   leaf LOCALCELLID {
    type leafref {
     path "../attributes/LOCALCELLID";
     require-instance true;
    }
   }
   container attributes {
    uses CELLDLPCPDSCHPA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLDLPCPHICH {
   max-elements 1;
   key "LOCALCELLID";
   leaf LOCALCELLID {
    type leafref {
     path "../attributes/LOCALCELLID";
     require-instance true;
    }
   }
   container attributes {
    uses CELLDLPCPHICH-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLDLSCHALGO {
   max-elements 1;
   key "LOCALCELLID";
   leaf LOCALCELLID {
    type leafref {
     path "../attributes/LOCALCELLID";
     require-instance true;
    }
   }
   container attributes {
    uses CELLDLSCHALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLDLSCHEXTPARAM {
   max-elements 1;
   key "LOCALCELLID";
   leaf LOCALCELLID {
    type leafref {
     path "../attributes/LOCALCELLID";
     require-instance true;
    }
   }
   container attributes {
    uses CELLDLSCHEXTPARAM-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLDMRSCFG {
   max-elements 1;
   key "LOCALCELLID";
   leaf LOCALCELLID {
    type leafref {
     path "../attributes/LOCALCELLID";
     require-instance true;
    }
   }
   container attributes {
    uses CELLDMRSCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLDRXPARA {
   max-elements 1;
   key "LOCALCELLID";
   leaf LOCALCELLID {
    type leafref {
     path "../attributes/LOCALCELLID";
     require-instance true;
    }
   }
   container attributes {
    uses CELLDRXPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLDRXSPECIALPARA {
   max-elements 1;
   key "LOCALCELLID";
   leaf LOCALCELLID {
    type leafref {
     path "../attributes/LOCALCELLID";
     require-instance true;
    }
   }
   container attributes {
    uses CELLDRXSPECIALPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLDSS {
   max-elements 1;
   key "LOCALCELLID";
   leaf LOCALCELLID {
    type leafref {
     path "../attributes/LOCALCELLID";
     require-instance true;
    }
   }
   container attributes {
    uses CELLDSS-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLDYNACBARALGOPARA {
   max-elements 1;
   key "LOCALCELLID";
   leaf LOCALCELLID {
    type leafref {
     path "../attributes/LOCALCELLID";
     require-instance true;
    }
   }
   container attributes {
    uses CELLDYNACBARALGOPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLDYNPOWERSHARING {
   max-elements 1;
   key "LOCALCELLID";
   leaf LOCALCELLID {
    type leafref {
     path "../attributes/LOCALCELLID";
     require-instance true;
    }
   }
   container attributes {
    uses CELLDYNPOWERSHARING-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLEABALGOPARA {
   max-elements 1;
   key "LOCALCELLID";
   leaf LOCALCELLID {
    type leafref {
     path "../attributes/LOCALCELLID";
     require-instance true;
    }
   }
   container attributes {
    uses CELLEABALGOPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLEDTCONFIG {
   max-elements 1;
   key "LOCALCELLID";
   leaf LOCALCELLID {
    type leafref {
     path "../attributes/LOCALCELLID";
     require-instance true;
    }
   }
   container attributes {
    uses CELLEDTCONFIG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLEICIC {
   max-elements 1;
   key "LOCALCELLID";
   leaf LOCALCELLID {
    type leafref {
     path "../attributes/LOCALCELLID";
     require-instance true;
    }
   }
   container attributes {
    uses CELLEICIC-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLEMERGENCYAREA {
   max-elements 16;
   key "LOCALCELLID";
   leaf LOCALCELLID {
    type leafref {
     path "../attributes/LOCALCELLID";
     require-instance true;
    }
   }
   container attributes {
    uses CELLEMERGENCYAREA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLEMTCALGO {
   max-elements 1;
   key "LOCALCELLID";
   leaf LOCALCELLID {
    type leafref {
     path "../attributes/LOCALCELLID";
     require-instance true;
    }
   }
   container attributes {
    uses CELLEMTCALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLENHCOVERAGE {
   max-elements 1;
   key "LOCALCELLID";
   leaf LOCALCELLID {
    type leafref {
     path "../attributes/LOCALCELLID";
     require-instance true;
    }
   }
   container attributes {
    uses CELLENHCOVERAGE-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLHOPARACFG {
   max-elements 1;
   key "LOCALCELLID";
   leaf LOCALCELLID {
    type leafref {
     path "../attributes/LOCALCELLID";
     require-instance true;
    }
   }
   container attributes {
    uses CELLHOPARACFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list CELLIDPRDUPT {
   max-elements 1;
   key "ACTIONTIME";
   leaf ACTIONTIME {
    type leafref {
     path "../attributes/ACTIONTIME";
     require-instance true;
    }
   }
   container attributes {
    uses CELLIDPRDUPT-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLINTELAMCCONFIG {
   max-elements 1;
   key "LOCALCELLID";
   leaf LOCALCELLID {
    type leafref {
     path "../attributes/LOCALCELLID";
     require-instance true;
    }
   }
   container attributes {
    uses CELLINTELAMCCONFIG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLLAACOEXISTPARA {
   max-elements 1;
   key "LOCALCELLID";
   leaf LOCALCELLID {
    type leafref {
     path "../attributes/LOCALCELLID";
     require-instance true;
    }
   }
   container attributes {
    uses CELLLAACOEXISTPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLLAAFCSPARA {
   max-elements 2;
   key "LOCALCELLID";
   leaf LOCALCELLID {
    type leafref {
     path "../attributes/LOCALCELLID";
     require-instance true;
    }
   }
   container attributes {
    uses CELLLAAFCSPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLLCSCFG {
   max-elements 1;
   key "LOCALCELLID";
   leaf LOCALCELLID {
    type leafref {
     path "../attributes/LOCALCELLID";
     require-instance true;
    }
   }
   container attributes {
    uses CELLLCSCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLLOWPOWER {
   max-elements 1;
   key "LOCALCELLID";
   leaf LOCALCELLID {
    type leafref {
     path "../attributes/LOCALCELLID";
     require-instance true;
    }
   }
   container attributes {
    uses CELLLOWPOWER-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLLTEFLEXBW {
   max-elements 1;
   key "LOCALCELLID";
   leaf LOCALCELLID {
    type leafref {
     path "../attributes/LOCALCELLID";
     require-instance true;
    }
   }
   container attributes {
    uses CELLLTEFLEXBW-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLLTEFLEXBWITFCFG {
   max-elements 6;
   key "LOCALCELLID";
   leaf LOCALCELLID {
    type leafref {
     path "../attributes/LOCALCELLID";
     require-instance true;
    }
   }
   container attributes {
    uses CELLLTEFLEXBWITFCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLMBFCS {
   max-elements 1;
   key "LOCALCELLID";
   leaf LOCALCELLID {
    type leafref {
     path "../attributes/LOCALCELLID";
     require-instance true;
    }
   }
   container attributes {
    uses CELLMBFCS-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLMBMSCFG {
   max-elements 1;
   key "LOCALCELLID";
   leaf LOCALCELLID {
    type leafref {
     path "../attributes/LOCALCELLID";
     require-instance true;
    }
   }
   container attributes {
    uses CELLMBMSCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLMBSFNSFENHCONFIG {
   max-elements 1;
   key "LOCALCELLID";
   leaf LOCALCELLID {
    type leafref {
     path "../attributes/LOCALCELLID";
     require-instance true;
    }
   }
   container attributes {
    uses CELLMBSFNSFENHCONFIG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLMCPARA {
   max-elements 1;
   key "LOCALCELLID";
   leaf LOCALCELLID {
    type leafref {
     path "../attributes/LOCALCELLID";
     require-instance true;
    }
   }
   container attributes {
    uses CELLMCPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLMIMOPARACFG {
   max-elements 1;
   key "LOCALCELLID";
   leaf LOCALCELLID {
    type leafref {
     path "../attributes/LOCALCELLID";
     require-instance true;
    }
   }
   container attributes {
    uses CELLMIMOPARACFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLMLB {
   max-elements 1;
   key "LOCALCELLID";
   leaf LOCALCELLID {
    type leafref {
     path "../attributes/LOCALCELLID";
     require-instance true;
    }
   }
   container attributes {
    uses CELLMLB-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLMLBAUTOGROUP {
   max-elements 1;
   key "LOCALCELLID";
   leaf LOCALCELLID {
    type leafref {
     path "../attributes/LOCALCELLID";
     require-instance true;
    }
   }
   container attributes {
    uses CELLMLBAUTOGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLMLBHO {
   max-elements 1;
   key "LOCALCELLID";
   leaf LOCALCELLID {
    type leafref {
     path "../attributes/LOCALCELLID";
     require-instance true;
    }
   }
   container attributes {
    uses CELLMLBHO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLMLBUESEL {
   max-elements 1;
   key "LOCALCELLID";
   leaf LOCALCELLID {
    type leafref {
     path "../attributes/LOCALCELLID";
     require-instance true;
    }
   }
   container attributes {
    uses CELLMLBUESEL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLMMALGO {
   max-elements 1;
   key "LOCALCELLID";
   leaf LOCALCELLID {
    type leafref {
     path "../attributes/LOCALCELLID";
     require-instance true;
    }
   }
   container attributes {
    uses CELLMMALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLMRO {
   max-elements 1;
   key "LOCALCELLID";
   leaf LOCALCELLID {
    type leafref {
     path "../attributes/LOCALCELLID";
     require-instance true;
    }
   }
   container attributes {
    uses CELLMRO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLMULTICARRCFGGRP {
   max-elements 3840;
   key "LOCALCELLID";
   leaf LOCALCELLID {
    type leafref {
     path "../attributes/LOCALCELLID";
     require-instance true;
    }
   }
   container attributes {
    uses CELLMULTICARRCFGGRP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLMULTICARRUNISCH {
   max-elements 1;
   key "LOCALCELLID";
   leaf LOCALCELLID {
    type leafref {
     path "../attributes/LOCALCELLID";
     require-instance true;
    }
   }
   container attributes {
    uses CELLMULTICARRUNISCH-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLNPRSCFG {
   max-elements 2;
   key "LOCALCELLID";
   leaf LOCALCELLID {
    type leafref {
     path "../attributes/LOCALCELLID";
     require-instance true;
    }
   }
   container attributes {
    uses CELLNPRSCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLOP {
   max-elements 6;
   key "LOCALCELLID";
   leaf LOCALCELLID {
    type leafref {
     path "../attributes/LOCALCELLID";
     require-instance true;
    }
   }
   container attributes {
    uses CELLOP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLOPHOCFG {
   max-elements 6;
   key "LOCALCELLID";
   leaf LOCALCELLID {
    type leafref {
     path "../attributes/LOCALCELLID";
     require-instance true;
    }
   }
   container attributes {
    uses CELLOPHOCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLPCALGO {
   max-elements 1;
   key "LOCALCELLID";
   leaf LOCALCELLID {
    type leafref {
     path "../attributes/LOCALCELLID";
     require-instance true;
    }
   }
   container attributes {
    uses CELLPCALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLPDCCHALGO {
   max-elements 1;
   key "LOCALCELLID";
   leaf LOCALCELLID {
    type leafref {
     path "../attributes/LOCALCELLID";
     require-instance true;
    }
   }
   container attributes {
    uses CELLPDCCHALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLPRBGROUPPARAM {
   max-elements 1536;
   key "LOCALCELLID";
   leaf LOCALCELLID {
    type leafref {
     path "../attributes/LOCALCELLID";
     require-instance true;
    }
   }
   container attributes {
    uses CELLPRBGROUPPARAM-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLPRBVALMLB {
   max-elements 1;
   key "LOCALCELLID";
   leaf LOCALCELLID {
    type leafref {
     path "../attributes/LOCALCELLID";
     require-instance true;
    }
   }
   container attributes {
    uses CELLPRBVALMLB-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLPREALLOCGROUP {
   max-elements 10;
   key "LOCALCELLID";
   leaf LOCALCELLID {
    type leafref {
     path "../attributes/LOCALCELLID";
     require-instance true;
    }
   }
   container attributes {
    uses CELLPREALLOCGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLPRSCFG {
   max-elements 1;
   key "LOCALCELLID";
   leaf LOCALCELLID {
    type leafref {
     path "../attributes/LOCALCELLID";
     require-instance true;
    }
   }
   container attributes {
    uses CELLPRSCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLPUCCHALGO {
   max-elements 1;
   key "LOCALCELLID";
   leaf LOCALCELLID {
    type leafref {
     path "../attributes/LOCALCELLID";
     require-instance true;
    }
   }
   container attributes {
    uses CELLPUCCHALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLPWRSAVINGALGO {
   max-elements 1;
   key "LOCALCELLID";
   leaf LOCALCELLID {
    type leafref {
     path "../attributes/LOCALCELLID";
     require-instance true;
    }
   }
   container attributes {
    uses CELLPWRSAVINGALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLPWRSAVINGPOLICY {
   max-elements 16;
   key "LOCALCELLID";
   leaf LOCALCELLID {
    type leafref {
     path "../attributes/LOCALCELLID";
     require-instance true;
    }
   }
   container attributes {
    uses CELLPWRSAVINGPOLICY-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLQCIPARA {
   max-elements 75;
   key "LOCALCELLID";
   leaf LOCALCELLID {
    type leafref {
     path "../attributes/LOCALCELLID";
     require-instance true;
    }
   }
   container attributes {
    uses CELLQCIPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLQCIPARAEXTENSION {
   max-elements 75;
   key "LOCALCELLID";
   leaf LOCALCELLID {
    type leafref {
     path "../attributes/LOCALCELLID";
     require-instance true;
    }
   }
   container attributes {
    uses CELLQCIPARAEXTENSION-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLRACHALGO {
   max-elements 1;
   key "LOCALCELLID";
   leaf LOCALCELLID {
    type leafref {
     path "../attributes/LOCALCELLID";
     require-instance true;
    }
   }
   container attributes {
    uses CELLRACHALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLRACHCECFG {
   max-elements 3;
   key "LOCALCELLID";
   leaf LOCALCELLID {
    type leafref {
     path "../attributes/LOCALCELLID";
     require-instance true;
    }
   }
   container attributes {
    uses CELLRACHCECFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLRACTHD {
   max-elements 1;
   key "LOCALCELLID";
   leaf LOCALCELLID {
    type leafref {
     path "../attributes/LOCALCELLID";
     require-instance true;
    }
   }
   container attributes {
    uses CELLRACTHD-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLRBRESERVE {
   max-elements 100;
   key "LOCALCELLID";
   leaf LOCALCELLID {
    type leafref {
     path "../attributes/LOCALCELLID";
     require-instance true;
    }
   }
   container attributes {
    uses CELLRBRESERVE-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLRELAYALGOPARA {
   max-elements 1;
   key "LOCALCELLID";
   leaf LOCALCELLID {
    type leafref {
     path "../attributes/LOCALCELLID";
     require-instance true;
    }
   }
   container attributes {
    uses CELLRELAYALGOPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLRESEL {
   max-elements 1;
   key "LOCALCELLID";
   leaf LOCALCELLID {
    type leafref {
     path "../attributes/LOCALCELLID";
     require-instance true;
    }
   }
   container attributes {
    uses CELLRESEL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLRESELCDMA2000 {
   max-elements 1;
   key "LOCALCELLID";
   leaf LOCALCELLID {
    type leafref {
     path "../attributes/LOCALCELLID";
     require-instance true;
    }
   }
   container attributes {
    uses CELLRESELCDMA2000-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLRESELGERAN {
   max-elements 1;
   key "LOCALCELLID";
   leaf LOCALCELLID {
    type leafref {
     path "../attributes/LOCALCELLID";
     require-instance true;
    }
   }
   container attributes {
    uses CELLRESELGERAN-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLRESELTONR {
   max-elements 1;
   key "LOCALCELLID";
   leaf LOCALCELLID {
    type leafref {
     path "../attributes/LOCALCELLID";
     require-instance true;
    }
   }
   container attributes {
    uses CELLRESELTONR-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLRESELUTRAN {
   max-elements 1;
   key "LOCALCELLID";
   leaf LOCALCELLID {
    type leafref {
     path "../attributes/LOCALCELLID";
     require-instance true;
    }
   }
   container attributes {
    uses CELLRESELUTRAN-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLRFCHNDYNMUTING {
   max-elements 1;
   key "LOCALCELLID";
   leaf LOCALCELLID {
    type leafref {
     path "../attributes/LOCALCELLID";
     require-instance true;
    }
   }
   container attributes {
    uses CELLRFCHNDYNMUTING-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLRFSHUTDOWN {
   max-elements 1;
   key "LOCALCELLID";
   leaf LOCALCELLID {
    type leafref {
     path "../attributes/LOCALCELLID";
     require-instance true;
    }
   }
   container attributes {
    uses CELLRFSHUTDOWN-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLRICALGO {
   max-elements 1;
   key "LOCALCELLID";
   leaf LOCALCELLID {
    type leafref {
     path "../attributes/LOCALCELLID";
     require-instance true;
    }
   }
   container attributes {
    uses CELLRICALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLSEL {
   max-elements 1;
   key "LOCALCELLID";
   leaf LOCALCELLID {
    type leafref {
     path "../attributes/LOCALCELLID";
     require-instance true;
    }
   }
   container attributes {
    uses CELLSEL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLSERVICEDIFFCFG {
   max-elements 1;
   key "LOCALCELLID";
   leaf LOCALCELLID {
    type leafref {
     path "../attributes/LOCALCELLID";
     require-instance true;
    }
   }
   container attributes {
    uses CELLSERVICEDIFFCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLSHORTTTIALGO {
   max-elements 1;
   key "LOCALCELLID";
   leaf LOCALCELLID {
    type leafref {
     path "../attributes/LOCALCELLID";
     require-instance true;
    }
   }
   container attributes {
    uses CELLSHORTTTIALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLSHUTDOWN {
   max-elements 1;
   key "LOCALCELLID";
   leaf LOCALCELLID {
    type leafref {
     path "../attributes/LOCALCELLID";
     require-instance true;
    }
   }
   container attributes {
    uses CELLSHUTDOWN-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLSIDELINKV2XCFG {
   max-elements 1;
   key "LOCALCELLID";
   leaf LOCALCELLID {
    type leafref {
     path "../attributes/LOCALCELLID";
     require-instance true;
    }
   }
   container attributes {
    uses CELLSIDELINKV2XCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLSIMAP {
   max-elements 1;
   key "LOCALCELLID";
   leaf LOCALCELLID {
    type leafref {
     path "../attributes/LOCALCELLID";
     require-instance true;
    }
   }
   container attributes {
    uses CELLSIMAP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLSIMULOAD {
   max-elements 1;
   key "LOCALCELLID";
   leaf LOCALCELLID {
    type leafref {
     path "../attributes/LOCALCELLID";
     require-instance true;
    }
   }
   container attributes {
    uses CELLSIMULOAD-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLSLV2XCARRCFG {
   max-elements 2;
   key "LOCALCELLID";
   leaf LOCALCELLID {
    type leafref {
     path "../attributes/LOCALCELLID";
     require-instance true;
    }
   }
   container attributes {
    uses CELLSLV2XCARRCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLSMARTPWRLOCK {
   max-elements 1;
   key "LOCALCELLID";
   leaf LOCALCELLID {
    type leafref {
     path "../attributes/LOCALCELLID";
     require-instance true;
    }
   }
   container attributes {
    uses CELLSMARTPWRLOCK-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLSRLTE {
   max-elements 1;
   key "LOCALCELLID";
   leaf LOCALCELLID {
    type leafref {
     path "../attributes/LOCALCELLID";
     require-instance true;
    }
   }
   container attributes {
    uses CELLSRLTE-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLSRSADAPTIVECFG {
   max-elements 1;
   key "LOCALCELLID";
   leaf LOCALCELLID {
    type leafref {
     path "../attributes/LOCALCELLID";
     require-instance true;
    }
   }
   container attributes {
    uses CELLSRSADAPTIVECFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLTTIBUNDLINGALGO {
   max-elements 1;
   key "LOCALCELLID";
   leaf LOCALCELLID {
    type leafref {
     path "../attributes/LOCALCELLID";
     require-instance true;
    }
   }
   container attributes {
    uses CELLTTIBUNDLINGALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLTYPEEXT {
   max-elements 1;
   key "LOCALCELLID";
   leaf LOCALCELLID {
    type leafref {
     path "../attributes/LOCALCELLID";
     require-instance true;
    }
   }
   container attributes {
    uses CELLTYPEEXT-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLUCIONPUSCHPARA {
   max-elements 1;
   key "LOCALCELLID";
   leaf LOCALCELLID {
    type leafref {
     path "../attributes/LOCALCELLID";
     require-instance true;
    }
   }
   container attributes {
    uses CELLUCIONPUSCHPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLUEMEASCONTROLCFG {
   max-elements 1;
   key "LOCALCELLID";
   leaf LOCALCELLID {
    type leafref {
     path "../attributes/LOCALCELLID";
     require-instance true;
    }
   }
   container attributes {
    uses CELLUEMEASCONTROLCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLULCOMPALGO {
   max-elements 1;
   key "LOCALCELLID";
   leaf LOCALCELLID {
    type leafref {
     path "../attributes/LOCALCELLID";
     require-instance true;
    }
   }
   container attributes {
    uses CELLULCOMPALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLULICALGO {
   max-elements 1;
   key "LOCALCELLID";
   leaf LOCALCELLID {
    type leafref {
     path "../attributes/LOCALCELLID";
     require-instance true;
    }
   }
   container attributes {
    uses CELLULICALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLULICIC {
   max-elements 1;
   key "LOCALCELLID";
   leaf LOCALCELLID {
    type leafref {
     path "../attributes/LOCALCELLID";
     require-instance true;
    }
   }
   container attributes {
    uses CELLULICIC-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLULICICMCPARA {
   max-elements 1;
   key "LOCALCELLID";
   leaf LOCALCELLID {
    type leafref {
     path "../attributes/LOCALCELLID";
     require-instance true;
    }
   }
   container attributes {
    uses CELLULICICMCPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLULMIMOPARACFG {
   max-elements 1;
   key "LOCALCELLID";
   leaf LOCALCELLID {
    type leafref {
     path "../attributes/LOCALCELLID";
     require-instance true;
    }
   }
   container attributes {
    uses CELLULMIMOPARACFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLULPCCOMM {
   max-elements 1;
   key "LOCALCELLID";
   leaf LOCALCELLID {
    type leafref {
     path "../attributes/LOCALCELLID";
     require-instance true;
    }
   }
   container attributes {
    uses CELLULPCCOMM-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLULPCDEDIC {
   max-elements 1;
   key "LOCALCELLID";
   leaf LOCALCELLID {
    type leafref {
     path "../attributes/LOCALCELLID";
     require-instance true;
    }
   }
   container attributes {
    uses CELLULPCDEDIC-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLULSCHALGO {
   max-elements 1;
   key "LOCALCELLID";
   leaf LOCALCELLID {
    type leafref {
     path "../attributes/LOCALCELLID";
     require-instance true;
    }
   }
   container attributes {
    uses CELLULSCHALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLULSCHEXTPARAM {
   max-elements 1;
   key "LOCALCELLID";
   leaf LOCALCELLID {
    type leafref {
     path "../attributes/LOCALCELLID";
     require-instance true;
    }
   }
   container attributes {
    uses CELLULSCHEXTPARAM-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLULUNIFIEDOLC {
   max-elements 1;
   key "LOCALCELLID";
   leaf LOCALCELLID {
    type leafref {
     path "../attributes/LOCALCELLID";
     require-instance true;
    }
   }
   container attributes {
    uses CELLULUNIFIEDOLC-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLUSPARACFG {
   max-elements 1;
   key "LOCALCELLID";
   leaf LOCALCELLID {
    type leafref {
     path "../attributes/LOCALCELLID";
     require-instance true;
    }
   }
   container attributes {
    uses CELLUSPARACFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLVMS {
   max-elements 1;
   key "LOCALCELLID";
   leaf LOCALCELLID {
    type leafref {
     path "../attributes/LOCALCELLID";
     require-instance true;
    }
   }
   container attributes {
    uses CELLVMS-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLWTTXPARACFG {
   max-elements 1;
   key "LOCALCELLID";
   leaf LOCALCELLID {
    type leafref {
     path "../attributes/LOCALCELLID";
     require-instance true;
    }
   }
   container attributes {
    uses CELLWTTXPARACFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CELLWUSCONFIG {
   max-elements 1;
   key "LOCALCELLID";
   leaf LOCALCELLID {
    type leafref {
     path "../attributes/LOCALCELLID";
     require-instance true;
    }
   }
   container attributes {
    uses CELLWUSCONFIG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CEPUCCHCFG {
   max-elements 4;
   key "LOCALCELLID";
   leaf LOCALCELLID {
    type leafref {
     path "../attributes/LOCALCELLID";
     require-instance true;
    }
   }
   container attributes {
    uses CEPUCCHCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CERACHCFG {
   max-elements 4;
   key "LOCALCELLID";
   leaf LOCALCELLID {
    type leafref {
     path "../attributes/LOCALCELLID";
     require-instance true;
    }
   }
   container attributes {
    uses CERACHCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list CLKDETECT {
   max-elements 1;
   key "CLKASYNCDETECTSWITCH";
   leaf CLKASYNCDETECTSWITCH {
    type leafref {
     path "../attributes/CLKASYNCDETECTSWITCH";
     require-instance true;
    }
   }
   container attributes {
    uses CLKDETECT-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list CLUSTER {
   max-elements 740;
   key "CLUSTERID";
   leaf CLUSTERID {
    type leafref {
     path "../attributes/CLUSTERID";
     require-instance true;
    }
   }
   container attributes {
    uses CLUSTER-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CLUSTER" {
  list CLUSTERCELL {
   max-elements 36;
   key "CLUSTERID";
   leaf CLUSTERID {
    type leafref {
     path "../attributes/CLUSTERID";
     require-instance true;
    }
   }
   container attributes {
    uses CLUSTERCELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CLZEROBUFFERZONE {
   max-elements 1;
   key "LOCALCELLID";
   leaf LOCALCELLID {
    type leafref {
     path "../attributes/LOCALCELLID";
     require-instance true;
    }
   }
   container attributes {
    uses CLZEROBUFFERZONE-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list CNOPERATOR {
   max-elements 6;
   key "CNOPERATORID";
   leaf CNOPERATORID {
    type leafref {
     path "../attributes/CNOPERATORID";
     require-instance true;
    }
   }
   container attributes {
    uses CNOPERATOR-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CNOPERATOR" {
  list CNOPERATORHOCFG {
   max-elements 1;
   key "CNOPERATORID";
   leaf CNOPERATORID {
    type leafref {
     path "../attributes/CNOPERATORID";
     require-instance true;
    }
   }
   container attributes {
    uses CNOPERATORHOCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list CNOPERATORIPPATH {
   max-elements 320;
   key "IPPATHID";
   leaf IPPATHID {
    type leafref {
     path "../attributes/IPPATHID";
     require-instance true;
    }
   }
   container attributes {
    uses CNOPERATORIPPATH-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CNOPERATOR" {
  list CNOPERATORQCIPARA {
   max-elements 75;
   key "CNOPERATORID";
   leaf CNOPERATORID {
    type leafref {
     path "../attributes/CNOPERATORID";
     require-instance true;
    }
   }
   container attributes {
    uses CNOPERATORQCIPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CNOPERATOR" {
  list CNOPERATORSPIDCFG {
   max-elements 257;
   key "CNOPERATORID";
   leaf CNOPERATORID {
    type leafref {
     path "../attributes/CNOPERATORID";
     require-instance true;
    }
   }
   container attributes {
    uses CNOPERATORSPIDCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list CNOPERATORTA {
   max-elements 216;
   key "CNOPERATORID";
   leaf CNOPERATORID {
    type leafref {
     path "../attributes/CNOPERATORID";
     require-instance true;
    }
   }
   container attributes {
    uses CNOPERATORTA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list CNOPQCIEVENTPARAM {
   max-elements 120;
   key "CNOPERATORID";
   leaf CNOPERATORID {
    type leafref {
     path "../attributes/CNOPERATORID";
     require-instance true;
    }
   }
   container attributes {
    uses CNOPQCIEVENTPARAM-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list CNOPSHARINGGROUP {
   max-elements 6;
   key "CNOPSHARINGGROUPID";
   leaf CNOPSHARINGGROUPID {
    type leafref {
     path "../attributes/CNOPSHARINGGROUPID";
     require-instance true;
    }
   }
   container attributes {
    uses CNOPSHARINGGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CNOPERATOR" {
  list CNOPUSERATTRIBUTE {
   max-elements 90;
   key "CNOPERATORID";
   leaf CNOPERATORID {
    type leafref {
     path "../attributes/CNOPERATORID";
     require-instance true;
    }
   }
   container attributes {
    uses CNOPUSERATTRIBUTE-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CNOPERATOR" {
  list CNOPUSERQCIPARA {
   max-elements 96;
   key "CNOPERATORID";
   leaf CNOPERATORID {
    type leafref {
     path "../attributes/CNOPERATORID";
     require-instance true;
    }
   }
   container attributes {
    uses CNOPUSERQCIPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CONTIGINTRABANDCARR {
   max-elements 1;
   key "LOCALCELLID";
   leaf LOCALCELLID {
    type leafref {
     path "../attributes/LOCALCELLID";
     require-instance true;
    }
   }
   container attributes {
    uses CONTIGINTRABANDCARR-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list COPROCRES {
   max-elements 13;
   key "COPROCRESID";
   leaf COPROCRESID {
    type leafref {
     path "../attributes/COPROCRESID";
     require-instance true;
    }
   }
   container attributes {
    uses COPROCRES-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list COUNTERCHECKPARA {
   max-elements 1;
   key "COUNTERCHECKCOUNTNUM";
   leaf COUNTERCHECKCOUNTNUM {
    type leafref {
     path "../attributes/COUNTERCHECKCOUNTNUM";
     require-instance true;
    }
   }
   container attributes {
    uses COUNTERCHECKPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list CQIADAPTIVECFG {
   max-elements 1;
   key "PUCCHPERIODICCQIOPTSWITCH";
   leaf PUCCHPERIODICCQIOPTSWITCH {
    type leafref {
     path "../attributes/PUCCHPERIODICCQIOPTSWITCH";
     require-instance true;
    }
   }
   container attributes {
    uses CQIADAPTIVECFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CNOPERATOR" {
  list CSFALLBACKBLINDHOCFG {
   max-elements 1;
   key "CNOPERATORID";
   leaf CNOPERATORID {
    type leafref {
     path "../attributes/CNOPERATORID";
     require-instance true;
    }
   }
   container attributes {
    uses CSFALLBACKBLINDHOCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list CSFALLBACKHO {
   max-elements 1;
   key "LOCALCELLID";
   leaf LOCALCELLID {
    type leafref {
     path "../attributes/LOCALCELLID";
     require-instance true;
    }
   }
   container attributes {
    uses CSFALLBACKHO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list CSFALLBACKPOLICYCFG {
   max-elements 1;
   key "CSFBHOPOLICYCFG";
   leaf CSFBHOPOLICYCFG {
    type leafref {
     path "../attributes/CSFBHOPOLICYCFG";
     require-instance true;
    }
   }
   container attributes {
    uses CSFALLBACKPOLICYCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list CSPCALGOPARA {
   max-elements 1;
   key "CSPCALGOSWITCH";
   leaf CSPCALGOSWITCH {
    type leafref {
     path "../attributes/CSPCALGOSWITCH";
     require-instance true;
    }
   }
   container attributes {
    uses CSPCALGOPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list DDCELLGROUP {
   max-elements 128;
   key "DDBANDWIDTH";
   leaf DDBANDWIDTH {
    type leafref {
     path "../attributes/DDBANDWIDTH";
     require-instance true;
    }
   }
   container attributes {
    uses DDCELLGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CNOPERATOR" {
  list DEFAULTDCNCFG {
   max-elements 18;
   key "CNOPERATORID";
   leaf CNOPERATORID {
    type leafref {
     path "../attributes/CNOPERATORID";
     require-instance true;
    }
   }
   container attributes {
    uses DEFAULTDCNCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list DISTBASEDHO {
   max-elements 1;
   key "LOCALCELLID";
   leaf LOCALCELLID {
    type leafref {
     path "../attributes/LOCALCELLID";
     require-instance true;
    }
   }
   container attributes {
    uses DISTBASEDHO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list DMIMOALGO {
   max-elements 1;
   key "LOCALCELLID";
   leaf LOCALCELLID {
    type leafref {
     path "../attributes/LOCALCELLID";
     require-instance true;
    }
   }
   container attributes {
    uses DMIMOALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list DMIMOCLUSTER {
   max-elements 72;
   key "DMIMOCLUSTERID";
   leaf DMIMOCLUSTERID {
    type leafref {
     path "../attributes/DMIMOCLUSTERID";
     require-instance true;
    }
   }
   container attributes {
    uses DMIMOCLUSTER-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/DMIMOCLUSTER" {
  list DMIMOCLUSTERCELL {
   max-elements 1;
   key "DMIMOCLUSTERID";
   leaf DMIMOCLUSTERID {
    type leafref {
     path "../attributes/DMIMOCLUSTERID";
     require-instance true;
    }
   }
   container attributes {
    uses DMIMOCLUSTERCELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list DRX {
   max-elements 1;
   key "DRXFLEXCTRLSWITCH";
   leaf DRXFLEXCTRLSWITCH {
    type leafref {
     path "../attributes/DRXFLEXCTRLSWITCH";
     require-instance true;
    }
   }
   container attributes {
    uses DRX-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list DRXPARAGROUP {
   max-elements 50;
   key "LOCALCELLID";
   leaf LOCALCELLID {
    type leafref {
     path "../attributes/LOCALCELLID";
     require-instance true;
    }
   }
   container attributes {
    uses DRXPARAGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ECO {
   max-elements 1;
   key "ECOID";
   leaf ECOID {
    type leafref {
     path "../attributes/ECOID";
     require-instance true;
    }
   }
   container attributes {
    uses ECO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CNOPERATOR" {
  list EMC {
   max-elements 1;
   key "CNOPERATORID";
   leaf CNOPERATORID {
    type leafref {
     path "../attributes/CNOPERATORID";
     require-instance true;
    }
   }
   container attributes {
    uses EMC-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list EMTCCESCHCFG {
   max-elements 4;
   key "LOCALCELLID";
   leaf LOCALCELLID {
    type leafref {
     path "../attributes/LOCALCELLID";
     require-instance true;
    }
   }
   container attributes {
    uses EMTCCESCHCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list EMTCSIBCONFIG {
   max-elements 5;
   key "LOCALCELLID";
   leaf LOCALCELLID {
    type leafref {
     path "../attributes/LOCALCELLID";
     require-instance true;
    }
   }
   container attributes {
    uses EMTCSIBCONFIG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENBRSVDPARA {
   max-elements 1;
   key "RSVDPARA36";
   leaf RSVDPARA36 {
    type leafref {
     path "../attributes/RSVDPARA36";
     require-instance true;
    }
   }
   container attributes {
    uses ENBRSVDPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENDCBANDGAPFREECFG {
   max-elements 448;
   key "FREQUENCYBANDID";
   leaf FREQUENCYBANDID {
    type leafref {
     path "../attributes/FREQUENCYBANDID";
     require-instance true;
    }
   }
   container attributes {
    uses ENDCBANDGAPFREECFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENDCX2BLACKWHITELIST {
   max-elements 128;
   key "GNODEBID";
   leaf GNODEBID {
    type leafref {
     path "../attributes/GNODEBID";
     require-instance true;
    }
   }
   container attributes {
    uses ENDCX2BLACKWHITELIST-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENODEBALGOEXTSWITCH {
   max-elements 1;
   key "EXTENDEDQCIMAPPINGINDEX";
   leaf EXTENDEDQCIMAPPINGINDEX {
    type leafref {
     path "../attributes/EXTENDEDQCIMAPPINGINDEX";
     require-instance true;
    }
   }
   container attributes {
    uses ENODEBALGOEXTSWITCH-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENODEBALGOSWITCH {
   max-elements 1;
   key "ANRSWITCH";
   leaf ANRSWITCH {
    type leafref {
     path "../attributes/ANRSWITCH";
     require-instance true;
    }
   }
   container attributes {
    uses ENODEBALGOSWITCH-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENODEBALMCFG {
   max-elements 1;
   key "ALARMSWITCH";
   leaf ALARMSWITCH {
    type leafref {
     path "../attributes/ALARMSWITCH";
     require-instance true;
    }
   }
   container attributes {
    uses ENODEBALMCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENODEBAUTOPOWEROFF {
   max-elements 1;
   key "AUTOPOWEROFFSWITCH";
   leaf AUTOPOWEROFFSWITCH {
    type leafref {
     path "../attributes/AUTOPOWEROFFSWITCH";
     require-instance true;
    }
   }
   container attributes {
    uses ENODEBAUTOPOWEROFF-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENODEBCIPHERCAP {
   max-elements 1;
   key "FOURTHCIPHERALGO";
   leaf FOURTHCIPHERALGO {
    type leafref {
     path "../attributes/FOURTHCIPHERALGO";
     require-instance true;
    }
   }
   container attributes {
    uses ENODEBCIPHERCAP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENODEBCLUSTER {
   max-elements 60;
   key "ENODEBID";
   leaf ENODEBID {
    type leafref {
     path "../attributes/ENODEBID";
     require-instance true;
    }
   }
   container attributes {
    uses ENODEBCLUSTER-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENODEBCONNSTATETIMER {
   max-elements 1;
   key "AMRLCRXWINABNDETECTTIMETHD";
   leaf AMRLCRXWINABNDETECTTIMETHD {
    type leafref {
     path "../attributes/AMRLCRXWINABNDETECTTIMETHD";
     require-instance true;
    }
   }
   container attributes {
    uses ENODEBCONNSTATETIMER-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENODEBCOUNTERPARAGRP {
   max-elements 1;
   key "AMBRCOUNTERMEASPOLICY";
   leaf AMBRCOUNTERMEASPOLICY {
    type leafref {
     path "../attributes/AMBRCOUNTERMEASPOLICY";
     require-instance true;
    }
   }
   container attributes {
    uses ENODEBCOUNTERPARAGRP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENODEBFEATUREFREQCFG {
   max-elements 17;
   key "DLEARFCN";
   leaf DLEARFCN {
    type leafref {
     path "../attributes/DLEARFCN";
     require-instance true;
    }
   }
   container attributes {
    uses ENODEBFEATUREFREQCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENODEBFLOWCTRLPARA {
   max-elements 1;
   key "ADAPTUNSYNCTIMERLEN";
   leaf ADAPTUNSYNCTIMERLEN {
    type leafref {
     path "../attributes/ADAPTUNSYNCTIMERLEN";
     require-instance true;
    }
   }
   container attributes {
    uses ENODEBFLOWCTRLPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule" {
  list ENODEBFUNCTION {
   max-elements 1;
   key "ENODEBID";
   leaf ENODEBID {
    type leafref {
     path "../attributes/ENODEBID";
     require-instance true;
    }
   }
   container attributes {
    uses ENODEBFUNCTION-attributes;
    leaf modifier {
     type hwat:modifier_M;
     mandatory false;
    }
    leaf remark {
     type string;
     mandatory false;
    }
    leaf template {
     type string;
     mandatory false;
    }
   }
  }
 }
 augment "/ne:NE/enodebfunctionmodule:eNodeBFunctionModule/ENODEBFUNCTION" {
  list ENODEBIDBLACKLIST {
   max-elements 64;
   key "ENODEBID";
   leaf ENODEBID {
    type leafref {
     path "../attributes/ENODEBID";
     require-instance true;
    }
   }
   container attributes {
    uses ENODEBIDBLACKLIST-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENODEBINTEGRITYCAP {
   max-elements 1;
   key "NULLALGO";
   leaf NULLALGO {
    type leafref {
     path "../attributes/NULLALGO";
     require-instance true;
    }
   }
   container attributes {
    uses ENODEBINTEGRITYCAP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENODEBMLB {
   max-elements 1;
   key "CAUEMINDATAVOLRATIO";
   leaf CAUEMINDATAVOLRATIO {
    type leafref {
     path "../attributes/CAUEMINDATAVOLRATIO";
     require-instance true;
    }
   }
   container attributes {
    uses ENODEBMLB-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENODEBMPRUES {
   max-elements 1;
   key "DORMANCYALGOSWITCH";
   leaf DORMANCYALGOSWITCH {
    type leafref {
     path "../attributes/DORMANCYALGOSWITCH";
     require-instance true;
    }
   }
   container attributes {
    uses ENODEBMPRUES-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENODEBMTFLOWCONTROL {
   max-elements 1;
   key "BASEBANDOMFLOWCTRLTHLDCOEF";
   leaf BASEBANDOMFLOWCTRLTHLDCOEF {
    type leafref {
     path "../attributes/BASEBANDOMFLOWCTRLTHLDCOEF";
     require-instance true;
    }
   }
   container attributes {
    uses ENODEBMTFLOWCONTROL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENODEBNBPARA {
   max-elements 1;
   key "NBEXTENDEDPAGINGOPTSWITCH";
   leaf NBEXTENDEDPAGINGOPTSWITCH {
    type leafref {
     path "../attributes/NBEXTENDEDPAGINGOPTSWITCH";
     require-instance true;
    }
   }
   container attributes {
    uses ENODEBNBPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENODEBPATH {
   max-elements 320;
   key "IPPATHID";
   leaf IPPATHID {
    type leafref {
     path "../attributes/IPPATHID";
     require-instance true;
    }
   }
   container attributes {
    uses ENODEBPATH-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENODEBPWRSAVINGALGO {
   max-elements 1;
   key "ASUESCCADDTIMER";
   leaf ASUESCCADDTIMER {
    type leafref {
     path "../attributes/ASUESCCADDTIMER";
     require-instance true;
    }
   }
   container attributes {
    uses ENODEBPWRSAVINGALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENODEBRESMODEALGO {
   max-elements 1;
   key "BACKPLANEBWLACKPROTECTSW";
   leaf BACKPLANEBWLACKPROTECTSW {
    type leafref {
     path "../attributes/BACKPLANEBWLACKPROTECTSW";
     require-instance true;
    }
   }
   container attributes {
    uses ENODEBRESMODEALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENODEBRLALGOCONFIG {
   max-elements 25;
   key "RLCASETYPE";
   leaf RLCASETYPE {
    type leafref {
     path "../attributes/RLCASETYPE";
     require-instance true;
    }
   }
   container attributes {
    uses ENODEBRLALGOCONFIG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENODEBSHARINGMODE {
   max-elements 1;
   key "ENODEBSHARINGMODE";
   leaf ENODEBSHARINGMODE {
    type leafref {
     path "../attributes/ENODEBSHARINGMODE";
     require-instance true;
    }
   }
   container attributes {
    uses ENODEBSHARINGMODE-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENODEBSIGSECCONFIG {
   max-elements 1;
   key "EMTCSIGCTRLTHLD";
   leaf EMTCSIGCTRLTHLD {
    type leafref {
     path "../attributes/EMTCSIGCTRLTHLD";
     require-instance true;
    }
   }
   container attributes {
    uses ENODEBSIGSECCONFIG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENODEBSONDBCFG {
   max-elements 1;
   key "STARTTIME";
   leaf STARTTIME {
    type leafref {
     path "../attributes/STARTTIME";
     require-instance true;
    }
   }
   container attributes {
    uses ENODEBSONDBCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ENODEBUSPARACFG {
   max-elements 1;
   key "BIGPACKAGEIDENTIFY";
   leaf BIGPACKAGEIDENTIFY {
    type leafref {
     path "../attributes/BIGPACKAGEIDENTIFY";
     require-instance true;
    }
   }
   container attributes {
    uses ENODEBUSPARACFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list EUCELLALMCFG {
   max-elements 1;
   key "LOCALCELLID";
   leaf LOCALCELLID {
    type leafref {
     path "../attributes/LOCALCELLID";
     require-instance true;
    }
   }
   container attributes {
    uses EUCELLALMCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list EUCELLSECTOREQM {
   max-elements 12;
   key "LOCALCELLID";
   leaf LOCALCELLID {
    type leafref {
     path "../attributes/LOCALCELLID";
     require-instance true;
    }
   }
   container attributes {
    uses EUCELLSECTOREQM-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list EUCOSCHDLCOMPCFG {
   max-elements 1;
   key "CORDINFOEFFDELAY";
   leaf CORDINFOEFFDELAY {
    type leafref {
     path "../attributes/CORDINFOEFFDELAY";
     require-instance true;
    }
   }
   container attributes {
    uses EUCOSCHDLCOMPCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list EUCOSCHULICSCFG {
   max-elements 1;
   key "ULICSALGOSWITCH";
   leaf ULICSALGOSWITCH {
    type leafref {
     path "../attributes/ULICSALGOSWITCH";
     require-instance true;
    }
   }
   container attributes {
    uses EUCOSCHULICSCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list EUEPCINFO {
   max-elements 1;
   key "LOCALEPCID";
   leaf LOCALEPCID {
    type leafref {
     path "../attributes/LOCALEPCID";
     require-instance true;
    }
   }
   container attributes {
    uses EUEPCINFO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL/PRB" {
  list EUPRBSECTOREQM {
   max-elements 8;
   key "LOCALCELLID PRBID";
   leaf LOCALCELLID {
    type leafref {
     path "../attributes/LOCALCELLID";
     require-instance true;
    }
   }
   leaf PRBID {
    type leafref {
     path "../attributes/PRBID";
     require-instance true;
    }
   }
   container attributes {
    uses EUPRBSECTOREQM-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL/PRB" {
  list EUPRBSECTOREQMGROUP {
   max-elements 6;
   key "PRBID LOCALCELLID";
   leaf PRBID {
    type leafref {
     path "../attributes/PRBID";
     require-instance true;
    }
   }
   leaf LOCALCELLID {
    type leafref {
     path "../attributes/LOCALCELLID";
     require-instance true;
    }
   }
   container attributes {
    uses EUPRBSECTOREQMGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/EUSUBSCRIBER" {
  list EURRN {
   max-elements 1;
   key "LOCALSUBSCRIBERID";
   leaf LOCALSUBSCRIBERID {
    type leafref {
     path "../attributes/LOCALSUBSCRIBERID";
     require-instance true;
    }
   }
   container attributes {
    uses EURRN-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/EUSUBSCRIBER/EURRN" {
  list EURRNLANIP {
   max-elements 16;
   key "LOCALSUBSCRIBERID";
   leaf LOCALSUBSCRIBERID {
    type leafref {
     path "../attributes/LOCALSUBSCRIBERID";
     require-instance true;
    }
   }
   container attributes {
    uses EURRNLANIP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/EUSUBSCRIBER/EURRN" {
  list EURRNPORT {
   max-elements 2;
   key "LOCALSUBSCRIBERID";
   leaf LOCALSUBSCRIBERID {
    type leafref {
     path "../attributes/LOCALSUBSCRIBERID";
     require-instance true;
    }
   }
   container attributes {
    uses EURRNPORT-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/EUSUBSCRIBER" {
  list EURRNRT {
   max-elements 8;
   key "LOCALSUBSCRIBERID";
   leaf LOCALSUBSCRIBERID {
    type leafref {
     path "../attributes/LOCALSUBSCRIBERID";
     require-instance true;
    }
   }
   container attributes {
    uses EURRNRT-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list EUSECTOREQMGROUP {
   max-elements 8;
   key "LOCALCELLID";
   leaf LOCALCELLID {
    type leafref {
     path "../attributes/LOCALCELLID";
     require-instance true;
    }
   }
   container attributes {
    uses EUSECTOREQMGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list EUSUBSCRIBER {
   max-elements 600;
   key "RRNID";
   leaf RRNID {
    type leafref {
     path "../attributes/RRNID";
     require-instance true;
    }
   }
   container attributes {
    uses EUSUBSCRIBER-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list EUTRANBLKNCELL {
   max-elements 16;
   key "LOCALCELLID";
   leaf LOCALCELLID {
    type leafref {
     path "../attributes/LOCALCELLID";
     require-instance true;
    }
   }
   container attributes {
    uses EUTRANBLKNCELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list EUTRANEXTERNALCELL {
   max-elements 3456;
   key "CELLID";
   leaf CELLID {
    type leafref {
     path "../attributes/CELLID";
     require-instance true;
    }
   }
   container attributes {
    uses EUTRANEXTERNALCELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/EUTRANEXTERNALCELL" {
  list EUTRANEXTERNALCELLPLMN {
   max-elements 5;
   key "MCC MNC ENODEBID CELLID";
   leaf MCC {
    type leafref {
     path "../attributes/MCC";
     require-instance true;
    }
   }
   leaf MNC {
    type leafref {
     path "../attributes/MNC";
     require-instance true;
    }
   }
   leaf ENODEBID {
    type leafref {
     path "../attributes/ENODEBID";
     require-instance true;
    }
   }
   leaf CELLID {
    type leafref {
     path "../attributes/CELLID";
     require-instance true;
    }
   }
   container attributes {
    uses EUTRANEXTERNALCELLPLMN-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/EUTRANEXTERNALCELL" {
  list EUTRANEXTERNALCELL_MULTIBAND {
   max-elements 2;
   key "MCC MNC ENODEBID CELLID";
   leaf MCC {
    type leafref {
     path "../attributes/MCC";
     require-instance true;
    }
   }
   leaf MNC {
    type leafref {
     path "../attributes/MNC";
     require-instance true;
    }
   }
   leaf ENODEBID {
    type leafref {
     path "../attributes/ENODEBID";
     require-instance true;
    }
   }
   leaf CELLID {
    type leafref {
     path "../attributes/CELLID";
     require-instance true;
    }
   }
   container attributes {
    uses EUTRANEXTERNALCELL_MULTIBAND-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list EUTRANINTERFREQNCELL {
   max-elements 384;
   key "LOCALCELLID";
   leaf LOCALCELLID {
    type leafref {
     path "../attributes/LOCALCELLID";
     require-instance true;
    }
   }
   container attributes {
    uses EUTRANINTERFREQNCELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list EUTRANINTERNFREQ {
   max-elements 16;
   key "LOCALCELLID";
   leaf LOCALCELLID {
    type leafref {
     path "../attributes/LOCALCELLID";
     require-instance true;
    }
   }
   container attributes {
    uses EUTRANINTERNFREQ-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list EUTRANINTRAFREQNCELL {
   max-elements 384;
   key "LOCALCELLID";
   leaf LOCALCELLID {
    type leafref {
     path "../attributes/LOCALCELLID";
     require-instance true;
    }
   }
   container attributes {
    uses EUTRANINTRAFREQNCELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL/EUTRANINTERNFREQ" {
  list EUTRANNFREQRANSHARE {
   max-elements 6;
   key "LOCALCELLID DLEARFCN";
   leaf LOCALCELLID {
    type leafref {
     path "../attributes/LOCALCELLID";
     require-instance true;
    }
   }
   leaf DLEARFCN {
    type leafref {
     path "../attributes/DLEARFCN";
     require-instance true;
    }
   }
   container attributes {
    uses EUTRANNFREQRANSHARE-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL/EUTRANINTERNFREQ" {
  list EUTRANNFREQSCELLOP {
   max-elements 6;
   key "LOCALCELLID DLEARFCN";
   leaf LOCALCELLID {
    type leafref {
     path "../attributes/LOCALCELLID";
     require-instance true;
    }
   }
   leaf DLEARFCN {
    type leafref {
     path "../attributes/DLEARFCN";
     require-instance true;
    }
   }
   container attributes {
    uses EUTRANNFREQSCELLOP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list EUTRANSPEPCICELL {
   max-elements 16;
   key "STAPHYCELLID";
   leaf STAPHYCELLID {
    type leafref {
     path "../attributes/STAPHYCELLID";
     require-instance true;
    }
   }
   container attributes {
    uses EUTRANSPEPCICELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list EUULCOSCHCFG {
   max-elements 1;
   key "ULINTERENBCAMCSW";
   leaf ULINTERENBCAMCSW {
    type leafref {
     path "../attributes/ULINTERENBCAMCSW";
     require-instance true;
    }
   }
   container attributes {
    uses EUULCOSCHCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list EX2 {
   max-elements 7;
   key "EX2ID";
   leaf EX2ID {
    type leafref {
     path "../attributes/EX2ID";
     require-instance true;
    }
   }
   container attributes {
    uses EX2-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list FDDRESMODE {
   max-elements 1;
   key "BBCAPABILITYMODE";
   leaf BBCAPABILITYMODE {
    type leafref {
     path "../attributes/BBCAPABILITYMODE";
     require-instance true;
    }
   }
   container attributes {
    uses FDDRESMODE-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list FLEXCOUNTERPARAMGRP {
   max-elements 10;
   key "SPID";
   leaf SPID {
    type leafref {
     path "../attributes/SPID";
     require-instance true;
    }
   }
   container attributes {
    uses FLEXCOUNTERPARAMGRP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list FREQLAYERGROUP {
   max-elements 128;
   key "FREQLAYERGROUPID";
   leaf FREQLAYERGROUPID {
    type leafref {
     path "../attributes/FREQLAYERGROUPID";
     require-instance true;
    }
   }
   container attributes {
    uses FREQLAYERGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list GERANEXTERNALCELL {
   max-elements 1152;
   key "GERANCELLID";
   leaf GERANCELLID {
    type leafref {
     path "../attributes/GERANCELLID";
     require-instance true;
    }
   }
   container attributes {
    uses GERANEXTERNALCELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/GERANEXTERNALCELL" {
  list GERANEXTERNALCELLPLMN {
   max-elements 3;
   key "MCC MNC GERANCELLID LAC";
   leaf MCC {
    type leafref {
     path "../attributes/MCC";
     require-instance true;
    }
   }
   leaf MNC {
    type leafref {
     path "../attributes/MNC";
     require-instance true;
    }
   }
   leaf GERANCELLID {
    type leafref {
     path "../attributes/GERANCELLID";
     require-instance true;
    }
   }
   leaf LAC {
    type leafref {
     path "../attributes/LAC";
     require-instance true;
    }
   }
   container attributes {
    uses GERANEXTERNALCELLPLMN-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list GERANINTERFARFCN {
   max-elements 20;
   key "LOCALCELLID";
   leaf LOCALCELLID {
    type leafref {
     path "../attributes/LOCALCELLID";
     require-instance true;
    }
   }
   container attributes {
    uses GERANINTERFARFCN-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list GERANINTERFCFG {
   max-elements 1;
   key "LOCALCELLID";
   leaf LOCALCELLID {
    type leafref {
     path "../attributes/LOCALCELLID";
     require-instance true;
    }
   }
   container attributes {
    uses GERANINTERFCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list GERANNCELL {
   max-elements 128;
   key "LOCALCELLID";
   leaf LOCALCELLID {
    type leafref {
     path "../attributes/LOCALCELLID";
     require-instance true;
    }
   }
   container attributes {
    uses GERANNCELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list GERANNETWORKCAPCFG {
   max-elements 32;
   key "LAC";
   leaf LAC {
    type leafref {
     path "../attributes/LAC";
     require-instance true;
    }
   }
   container attributes {
    uses GERANNETWORKCAPCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL/GERANNFREQGROUP" {
  list GERANNFGROUPSCELLOP {
   max-elements 6;
   key "LOCALCELLID BCCHGROUPID";
   leaf LOCALCELLID {
    type leafref {
     path "../attributes/LOCALCELLID";
     require-instance true;
    }
   }
   leaf BCCHGROUPID {
    type leafref {
     path "../attributes/BCCHGROUPID";
     require-instance true;
    }
   }
   container attributes {
    uses GERANNFGROUPSCELLOP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list GERANNFREQGROUP {
   max-elements 16;
   key "LOCALCELLID";
   leaf LOCALCELLID {
    type leafref {
     path "../attributes/LOCALCELLID";
     require-instance true;
    }
   }
   container attributes {
    uses GERANNFREQGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL/GERANNFREQGROUP" {
  list GERANNFREQGROUPARFCN {
   max-elements 31;
   key "LOCALCELLID BCCHGROUPID";
   leaf LOCALCELLID {
    type leafref {
     path "../attributes/LOCALCELLID";
     require-instance true;
    }
   }
   leaf BCCHGROUPID {
    type leafref {
     path "../attributes/BCCHGROUPID";
     require-instance true;
    }
   }
   container attributes {
    uses GERANNFREQGROUPARFCN-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL/GERANNFREQGROUP" {
  list GERANRANSHARE {
   max-elements 4;
   key "LOCALCELLID BCCHGROUPID";
   leaf LOCALCELLID {
    type leafref {
     path "../attributes/LOCALCELLID";
     require-instance true;
    }
   }
   leaf BCCHGROUPID {
    type leafref {
     path "../attributes/BCCHGROUPID";
     require-instance true;
    }
   }
   container attributes {
    uses GERANRANSHARE-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list GLOBALPROCSWITCH {
   max-elements 1;
   key "CSFBFLOWOPTSWITCH";
   leaf CSFBFLOWOPTSWITCH {
    type leafref {
     path "../attributes/CSFBFLOWOPTSWITCH";
     require-instance true;
    }
   }
   container attributes {
    uses GLOBALPROCSWITCH-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list GNODEBBLACKLIST {
   max-elements 128;
   key "GNODEBID";
   leaf GNODEBID {
    type leafref {
     path "../attributes/GNODEBID";
     require-instance true;
    }
   }
   container attributes {
    uses GNODEBBLACKLIST-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list GSMINTERFARFCNCFG {
   max-elements 3600;
   key "GSMARFCNGROUPID";
   leaf GSMARFCNGROUPID {
    type leafref {
     path "../attributes/GSMARFCNGROUPID";
     require-instance true;
    }
   }
   container attributes {
    uses GSMINTERFARFCNCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list HENBTACRANGEGROUP {
   max-elements 10;
   key "HENBTACRAGID";
   leaf HENBTACRAGID {
    type leafref {
     path "../attributes/HENBTACRAGID";
     require-instance true;
    }
   }
   container attributes {
    uses HENBTACRANGEGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list HIGHSPDADAPTIONPARA {
   max-elements 1;
   key "LOCALCELLID";
   leaf LOCALCELLID {
    type leafref {
     path "../attributes/LOCALCELLID";
     require-instance true;
    }
   }
   container attributes {
    uses HIGHSPDADAPTIONPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list HOMEASCOMM {
   max-elements 1;
   key "GERANFILTERCOEFF";
   leaf GERANFILTERCOEFF {
    type leafref {
     path "../attributes/GERANFILTERCOEFF";
     require-instance true;
    }
   }
   container attributes {
    uses HOMEASCOMM-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list INCRCFG {
   max-elements 1;
   key "INCRCFGID";
   leaf INCRCFGID {
    type leafref {
     path "../attributes/INCRCFGID";
     require-instance true;
    }
   }
   container attributes {
    uses INCRCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list INTERFREQBLKCELL {
   max-elements 32;
   key "LOCALCELLID";
   leaf LOCALCELLID {
    type leafref {
     path "../attributes/LOCALCELLID";
     require-instance true;
    }
   }
   container attributes {
    uses INTERFREQBLKCELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list INTERFREQHOGROUP {
   max-elements 20;
   key "LOCALCELLID";
   leaf LOCALCELLID {
    type leafref {
     path "../attributes/LOCALCELLID";
     require-instance true;
    }
   }
   container attributes {
    uses INTERFREQHOGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CNOPERATOR" {
  list INTERPLMNHOLIST {
   max-elements 8;
   key "CNOPERATORID";
   leaf CNOPERATORID {
    type leafref {
     path "../attributes/CNOPERATORID";
     require-instance true;
    }
   }
   container attributes {
    uses INTERPLMNHOLIST-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list INTERRATCELLSHUTDOWN {
   max-elements 1;
   key "LOCALCELLID";
   leaf LOCALCELLID {
    type leafref {
     path "../attributes/LOCALCELLID";
     require-instance true;
    }
   }
   container attributes {
    uses INTERRATCELLSHUTDOWN-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list INTERRATHOCDMAHRPDGROUP {
   max-elements 10;
   key "LOCALCELLID";
   leaf LOCALCELLID {
    type leafref {
     path "../attributes/LOCALCELLID";
     require-instance true;
    }
   }
   container attributes {
    uses INTERRATHOCDMAHRPDGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list INTERRATHOCOMM {
   max-elements 1;
   key "CDMA20001XRTTFREQSELMODE";
   leaf CDMA20001XRTTFREQSELMODE {
    type leafref {
     path "../attributes/CDMA20001XRTTFREQSELMODE";
     require-instance true;
    }
   }
   container attributes {
    uses INTERRATHOCOMM-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list INTERRATHOCOMMGROUP {
   max-elements 20;
   key "LOCALCELLID";
   leaf LOCALCELLID {
    type leafref {
     path "../attributes/LOCALCELLID";
     require-instance true;
    }
   }
   container attributes {
    uses INTERRATHOCOMMGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list INTERRATHOGERANGROUP {
   max-elements 20;
   key "LOCALCELLID";
   leaf LOCALCELLID {
    type leafref {
     path "../attributes/LOCALCELLID";
     require-instance true;
    }
   }
   container attributes {
    uses INTERRATHOGERANGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list INTERRATHONRPARAMGRP {
   max-elements 10;
   key "LOCALCELLID";
   leaf LOCALCELLID {
    type leafref {
     path "../attributes/LOCALCELLID";
     require-instance true;
    }
   }
   container attributes {
    uses INTERRATHONRPARAMGRP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list INTERRATHOUTRANGROUP {
   max-elements 20;
   key "LOCALCELLID";
   leaf LOCALCELLID {
    type leafref {
     path "../attributes/LOCALCELLID";
     require-instance true;
    }
   }
   container attributes {
    uses INTERRATHOUTRANGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list INTERRATPOLICYCFGGROUP {
   max-elements 40;
   key "INTERRATPOLICYCFGGROUPID";
   leaf INTERRATPOLICYCFGGROUPID {
    type leafref {
     path "../attributes/INTERRATPOLICYCFGGROUPID";
     require-instance true;
    }
   }
   container attributes {
    uses INTERRATPOLICYCFGGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list INTERVENDORMLBALGO {
   max-elements 1;
   key "LOCALCELLID";
   leaf LOCALCELLID {
    type leafref {
     path "../attributes/LOCALCELLID";
     require-instance true;
    }
   }
   container attributes {
    uses INTERVENDORMLBALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list INTRAFREQBLKCELL {
   max-elements 32;
   key "LOCALCELLID";
   leaf LOCALCELLID {
    type leafref {
     path "../attributes/LOCALCELLID";
     require-instance true;
    }
   }
   container attributes {
    uses INTRAFREQBLKCELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list INTRAFREQHOGROUP {
   max-elements 20;
   key "LOCALCELLID";
   leaf LOCALCELLID {
    type leafref {
     path "../attributes/LOCALCELLID";
     require-instance true;
    }
   }
   container attributes {
    uses INTRAFREQHOGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list INTRARATHOCOMM {
   max-elements 1;
   key "A3INTERFREQHOA1A2TRIGQUAN";
   leaf A3INTERFREQHOA1A2TRIGQUAN {
    type leafref {
     path "../attributes/A3INTERFREQHOA1A2TRIGQUAN";
     require-instance true;
    }
   }
   container attributes {
    uses INTRARATHOCOMM-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list IOPSCFG {
   max-elements 1;
   key "ENTERIOPSTHD";
   leaf ENTERIOPSTHD {
    type leafref {
     path "../attributes/ENTERIOPSTHD";
     require-instance true;
    }
   }
   container attributes {
    uses IOPSCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list IPSERVICEQOS {
   max-elements 64;
   key "FIRQOSPOLICYID";
   leaf FIRQOSPOLICYID {
    type leafref {
     path "../attributes/FIRQOSPOLICYID";
     require-instance true;
    }
   }
   container attributes {
    uses IPSERVICEQOS-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list IRATNCELLCLASSMGT {
   max-elements 2;
   key "NCELLMEASNUMTHD";
   leaf NCELLMEASNUMTHD {
    type leafref {
     path "../attributes/NCELLMEASNUMTHD";
     require-instance true;
    }
   }
   container attributes {
    uses IRATNCELLCLASSMGT-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list LAAEXTERNALCELL {
   max-elements 144;
   key "CELLID";
   leaf CELLID {
    type leafref {
     path "../attributes/CELLID";
     require-instance true;
    }
   }
   container attributes {
    uses LAAEXTERNALCELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CNOPERATOR" {
  list LICENSESHARINGPOLICY {
   max-elements 1;
   key "CNOPERATORID";
   leaf CNOPERATORID {
    type leafref {
     path "../attributes/CNOPERATORID";
     require-instance true;
    }
   }
   container attributes {
    uses LICENSESHARINGPOLICY-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CNOPERATOR" {
  list LICRATIOSHAREPOLICY {
   max-elements 1;
   key "CNOPERATORID";
   leaf CNOPERATORID {
    type leafref {
     path "../attributes/CNOPERATORID";
     require-instance true;
    }
   }
   container attributes {
    uses LICRATIOSHAREPOLICY-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list LIOPTATOMRULE {
   max-elements 100;
   key "ATOMRULEID";
   leaf ATOMRULEID {
    type leafref {
     path "../attributes/ATOMRULEID";
     require-instance true;
    }
   }
   container attributes {
    uses LIOPTATOMRULE-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list LIOPTFEATURE {
   max-elements 20;
   key "IOPTFEATUREID";
   leaf IOPTFEATUREID {
    type leafref {
     path "../attributes/IOPTFEATUREID";
     require-instance true;
    }
   }
   container attributes {
    uses LIOPTFEATURE-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list LIOPTFUNCTION {
   max-elements 100;
   key "IOPTFEATUREID";
   leaf IOPTFEATUREID {
    type leafref {
     path "../attributes/IOPTFEATUREID";
     require-instance true;
    }
   }
   container attributes {
    uses LIOPTFUNCTION-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list LIOPTRULE {
   max-elements 200;
   key "RULEID";
   leaf RULEID {
    type leafref {
     path "../attributes/RULEID";
     require-instance true;
    }
   }
   container attributes {
    uses LIOPTRULE-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list LIOPTRULEMEMBER {
   max-elements 600;
   key "RULEID";
   leaf RULEID {
    type leafref {
     path "../attributes/RULEID";
     require-instance true;
    }
   }
   container attributes {
    uses LIOPTRULEMEMBER-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list LNRCARRIERSELECTION {
   max-elements 1;
   key "INTRAFREQMEASA3TIMETOTRIG";
   leaf INTRAFREQMEASA3TIMETOTRIG {
    type leafref {
     path "../attributes/INTRAFREQMEASA3TIMETOTRIG";
     require-instance true;
    }
   }
   container attributes {
    uses LNRCARRIERSELECTION-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list LNRFREQCOMB {
   max-elements 32;
   key "FREQCOMBID";
   leaf FREQCOMBID {
    type leafref {
     path "../attributes/FREQCOMBID";
     require-instance true;
    }
   }
   container attributes {
    uses LNRFREQCOMB-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list LNRFREQRELATIONSHIP {
   max-elements 128;
   key "RELATIONSHIPID";
   leaf RELATIONSHIPID {
    type leafref {
     path "../attributes/RELATIONSHIPID";
     require-instance true;
    }
   }
   container attributes {
    uses LNRFREQRELATIONSHIP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list LTENRSPCTSHRCELLGRP {
   max-elements 24;
   key "DSSFLEXREFARMGRPID";
   leaf DSSFLEXREFARMGRPID {
    type leafref {
     path "../attributes/DSSFLEXREFARMGRPID";
     require-instance true;
    }
   }
   container attributes {
    uses LTENRSPCTSHRCELLGRP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list LTESPSGRP {
   max-elements 64;
   key "LTESPSGRPID";
   leaf LTESPSGRPID {
    type leafref {
     path "../attributes/LTESPSGRPID";
     require-instance true;
    }
   }
   container attributes {
    uses LTESPSGRP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list LWAMGTCFG {
   max-elements 1;
   key "LOCALCELLID";
   leaf LOCALCELLID {
    type leafref {
     path "../attributes/LOCALCELLID";
     require-instance true;
    }
   }
   container attributes {
    uses LWAMGTCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list M1 {
   max-elements 2;
   key "M1ID";
   leaf M1ID {
    type leafref {
     path "../attributes/M1ID";
     require-instance true;
    }
   }
   container attributes {
    uses M1-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list M2 {
   max-elements 2;
   key "M2ID";
   leaf M2ID {
    type leafref {
     path "../attributes/M2ID";
     require-instance true;
    }
   }
   container attributes {
    uses M2-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list M3 {
   max-elements 6;
   key "M3ID";
   leaf M3ID {
    type leafref {
     path "../attributes/M3ID";
     require-instance true;
    }
   }
   container attributes {
    uses M3-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list MBMSPARA {
   max-elements 1;
   key "M2DISCONNPROTECTTIME";
   leaf M2DISCONNPROTECTTIME {
    type leafref {
     path "../attributes/M2DISCONNPROTECTTIME";
     require-instance true;
    }
   }
   container attributes {
    uses MBMSPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list MBSFNAREA {
   max-elements 3;
   key "MBSFNAREAID";
   leaf MBSFNAREAID {
    type leafref {
     path "../attributes/MBSFNAREAID";
     require-instance true;
    }
   }
   container attributes {
    uses MBSFNAREA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list MBSFNAREACELL {
   max-elements 256;
   key "CELLID";
   leaf CELLID {
    type leafref {
     path "../attributes/CELLID";
     require-instance true;
    }
   }
   container attributes {
    uses MBSFNAREACELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/MBSFNAREA" {
  list MBSFNSUBFRAME {
   max-elements 8;
   key "LOCALMCEID MBSFNAREAID";
   leaf LOCALMCEID {
    type leafref {
     path "../attributes/LOCALMCEID";
     require-instance true;
    }
   }
   leaf MBSFNAREAID {
    type leafref {
     path "../attributes/MBSFNAREAID";
     require-instance true;
    }
   }
   container attributes {
    uses MBSFNSUBFRAME-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/MBSFNAREA" {
  list MCCH {
   max-elements 1;
   key "LOCALMCEID MBSFNAREAID";
   leaf LOCALMCEID {
    type leafref {
     path "../attributes/LOCALMCEID";
     require-instance true;
    }
   }
   leaf MBSFNAREAID {
    type leafref {
     path "../attributes/MBSFNAREAID";
     require-instance true;
    }
   }
   container attributes {
    uses MCCH-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list MCE {
   max-elements 1;
   key "MCEID";
   leaf MCEID {
    type leafref {
     path "../attributes/MCEID";
     require-instance true;
    }
   }
   container attributes {
    uses MCE-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list MLBQCIGROUP {
   max-elements 10;
   key "MLBQCIGROUPID";
   leaf MLBQCIGROUPID {
    type leafref {
     path "../attributes/MLBQCIGROUPID";
     require-instance true;
    }
   }
   container attributes {
    uses MLBQCIGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list MMECAPINFO {
   max-elements 64;
   key "S1ID";
   leaf S1ID {
    type leafref {
     path "../attributes/S1ID";
     require-instance true;
    }
   }
   container attributes {
    uses MMECAPINFO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list MMEDOMAINNAME {
   max-elements 64;
   key "CNOPERATORID";
   leaf CNOPERATORID {
    type leafref {
     path "../attributes/CNOPERATORID";
     require-instance true;
    }
   }
   container attributes {
    uses MMEDOMAINNAME-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/S1INTERFACE" {
  list MMEFEATURECFG {
   max-elements 1;
   key "S1INTERFACEID";
   leaf S1INTERFACEID {
    type leafref {
     path "../attributes/S1INTERFACEID";
     require-instance true;
    }
   }
   container attributes {
    uses MMEFEATURECFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list MRO {
   max-elements 1;
   key "COVERABNORMALTHD";
   leaf COVERABNORMALTHD {
    type leafref {
     path "../attributes/COVERABNORMALTHD";
     require-instance true;
    }
   }
   container attributes {
    uses MRO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list MULTIBAND {
   max-elements 2;
   key "LOCALCELLID";
   leaf LOCALCELLID {
    type leafref {
     path "../attributes/LOCALCELLID";
     require-instance true;
    }
   }
   container attributes {
    uses MULTIBAND-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list MULTICARRUNIFIEDSCH {
   max-elements 1;
   key "BANDWIDTHHYSTERESIS";
   leaf BANDWIDTHHYSTERESIS {
    type leafref {
     path "../attributes/BANDWIDTHHYSTERESIS";
     require-instance true;
    }
   }
   container attributes {
    uses MULTICARRUNIFIEDSCH-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list NBCELLDYNPWRSHRPARA {
   max-elements 1;
   key "LOCALCELLID";
   leaf LOCALCELLID {
    type leafref {
     path "../attributes/LOCALCELLID";
     require-instance true;
    }
   }
   container attributes {
    uses NBCELLDYNPWRSHRPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list NBCELLMULTIPRBCONFIG {
   max-elements 1;
   key "LOCALCELLID";
   leaf LOCALCELLID {
    type leafref {
     path "../attributes/LOCALCELLID";
     require-instance true;
    }
   }
   container attributes {
    uses NBCELLMULTIPRBCONFIG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list NBPRBDYNAMICMGMT {
   max-elements 1;
   key "LOCALCELLID";
   leaf LOCALCELLID {
    type leafref {
     path "../attributes/LOCALCELLID";
     require-instance true;
    }
   }
   container attributes {
    uses NBPRBDYNAMICMGMT-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list NBRGNODEBPOLICY {
   max-elements 1024;
   key "GNODEBID";
   leaf GNODEBID {
    type leafref {
     path "../attributes/GNODEBID";
     require-instance true;
    }
   }
   container attributes {
    uses NBRGNODEBPOLICY-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CNOPERATOR" {
  list NBSHARINGPOLICY {
   max-elements 1;
   key "CNOPERATORID";
   leaf CNOPERATORID {
    type leafref {
     path "../attributes/CNOPERATORID";
     require-instance true;
    }
   }
   container attributes {
    uses NBSHARINGPOLICY-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list NCELLCLASSMGT {
   max-elements 1;
   key "CASCELLCFGTHD";
   leaf CASCELLCFGTHD {
    type leafref {
     path "../attributes/CASCELLCFGTHD";
     require-instance true;
    }
   }
   container attributes {
    uses NCELLCLASSMGT-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list NCELLDLRSRPMEASPARA {
   max-elements 1;
   key "LOCALCELLID";
   leaf LOCALCELLID {
    type leafref {
     path "../attributes/LOCALCELLID";
     require-instance true;
    }
   }
   container attributes {
    uses NCELLDLRSRPMEASPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list NCELLPARACFG {
   max-elements 4;
   key "LOCALCELLID";
   leaf LOCALCELLID {
    type leafref {
     path "../attributes/LOCALCELLID";
     require-instance true;
    }
   }
   container attributes {
    uses NCELLPARACFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list NCELLPLMNLIST {
   max-elements 32;
   key "GNBIDLENGTH";
   leaf GNBIDLENGTH {
    type leafref {
     path "../attributes/GNBIDLENGTH";
     require-instance true;
    }
   }
   container attributes {
    uses NCELLPLMNLIST-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list NCELLSRSMEASPARA {
   max-elements 1;
   key "LOCALCELLID";
   leaf LOCALCELLID {
    type leafref {
     path "../attributes/LOCALCELLID";
     require-instance true;
    }
   }
   container attributes {
    uses NCELLSRSMEASPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list NREXTERNALCELL {
   max-elements 2304;
   key "CELLID";
   leaf CELLID {
    type leafref {
     path "../attributes/CELLID";
     require-instance true;
    }
   }
   container attributes {
    uses NREXTERNALCELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/NREXTERNALCELL" {
  list NREXTERNALCELLPLMN {
   max-elements 11;
   key "GNODEBID CELLID MCC MNC";
   leaf GNODEBID {
    type leafref {
     path "../attributes/GNODEBID";
     require-instance true;
    }
   }
   leaf CELLID {
    type leafref {
     path "../attributes/CELLID";
     require-instance true;
    }
   }
   leaf MCC {
    type leafref {
     path "../attributes/MCC";
     require-instance true;
    }
   }
   leaf MNC {
    type leafref {
     path "../attributes/MNC";
     require-instance true;
    }
   }
   container attributes {
    uses NREXTERNALCELLPLMN-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list NRMFBIFREQ {
   max-elements 16;
   key "ADDITIONALFREQUENCYBAND";
   leaf ADDITIONALFREQUENCYBAND {
    type leafref {
     path "../attributes/ADDITIONALFREQUENCYBAND";
     require-instance true;
    }
   }
   container attributes {
    uses NRMFBIFREQ-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list NRNFREQ {
   max-elements 16;
   key "LOCALCELLID";
   leaf LOCALCELLID {
    type leafref {
     path "../attributes/LOCALCELLID";
     require-instance true;
    }
   }
   container attributes {
    uses NRNFREQ-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL/NRNFREQ" {
  list NRNFREQSCELLOP {
   max-elements 6;
   key "LOCALCELLID DLARFCN";
   leaf LOCALCELLID {
    type leafref {
     path "../attributes/LOCALCELLID";
     require-instance true;
    }
   }
   leaf DLARFCN {
    type leafref {
     path "../attributes/DLARFCN";
     require-instance true;
    }
   }
   container attributes {
    uses NRNFREQSCELLOP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list NRNRELATIONSHIP {
   max-elements 384;
   key "LOCALCELLID";
   leaf LOCALCELLID {
    type leafref {
     path "../attributes/LOCALCELLID";
     require-instance true;
    }
   }
   container attributes {
    uses NRNRELATIONSHIP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/PCCFREQCFG" {
  list NRSCGFREQCONFIG {
   max-elements 8;
   key "PCCDLEARFCN";
   leaf PCCDLEARFCN {
    type leafref {
     path "../attributes/PCCDLEARFCN";
     require-instance true;
    }
   }
   container attributes {
    uses NRSCGFREQCONFIG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list NRSCGFREQMGMT {
   max-elements 3;
   key "LOCALCELLID";
   leaf LOCALCELLID {
    type leafref {
     path "../attributes/LOCALCELLID";
     require-instance true;
    }
   }
   container attributes {
    uses NRSCGFREQMGMT-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list NRSCGFREQPRIGRP {
   max-elements 512;
   key "NRSCGFREQPRIORITYGROUPID";
   leaf NRSCGFREQPRIORITYGROUPID {
    type leafref {
     path "../attributes/NRSCGFREQPRIORITYGROUPID";
     require-instance true;
    }
   }
   container attributes {
    uses NRSCGFREQPRIGRP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list NSADCALGOPARAM {
   max-elements 1;
   key "ABNDLDATASPLITPENALTYPRD";
   leaf ABNDLDATASPLITPENALTYPRD {
    type leafref {
     path "../attributes/ABNDLDATASPLITPENALTYPRD";
     require-instance true;
    }
   }
   container attributes {
    uses NSADCALGOPARAM-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list NSADCMGMTCONFIG {
   max-elements 1;
   key "LOCALCELLID";
   leaf LOCALCELLID {
    type leafref {
     path "../attributes/LOCALCELLID";
     require-instance true;
    }
   }
   container attributes {
    uses NSADCMGMTCONFIG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list NSADCQCIPARAMGROUP {
   max-elements 10;
   key "LOCALCELLID";
   leaf LOCALCELLID {
    type leafref {
     path "../attributes/LOCALCELLID";
     require-instance true;
    }
   }
   container attributes {
    uses NSADCQCIPARAMGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list OPERATORBAND {
   max-elements 32;
   key "BANDID";
   leaf BANDID {
    type leafref {
     path "../attributes/BANDID";
     require-instance true;
    }
   }
   container attributes {
    uses OPERATORBAND-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list PARAAUTOOPTCFG {
   max-elements 1;
   key "ACHEFFECTIVETYPE";
   leaf ACHEFFECTIVETYPE {
    type leafref {
     path "../attributes/ACHEFFECTIVETYPE";
     require-instance true;
    }
   }
   container attributes {
    uses PARAAUTOOPTCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list PCCFREQCFG {
   max-elements 16;
   key "NSADCPCCA4RSRPTHLD";
   leaf NSADCPCCA4RSRPTHLD {
    type leafref {
     path "../attributes/NSADCPCCA4RSRPTHLD";
     require-instance true;
    }
   }
   container attributes {
    uses PCCFREQCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list PCCHCFG {
   max-elements 1;
   key "LOCALCELLID";
   leaf LOCALCELLID {
    type leafref {
     path "../attributes/LOCALCELLID";
     require-instance true;
    }
   }
   container attributes {
    uses PCCHCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list PDCPROHCPARA {
   max-elements 1;
   key "HIGHESTMODE";
   leaf HIGHESTMODE {
    type leafref {
     path "../attributes/HIGHESTMODE";
     require-instance true;
    }
   }
   container attributes {
    uses PDCPROHCPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list PDSCHCFG {
   max-elements 1;
   key "LOCALCELLID";
   leaf LOCALCELLID {
    type leafref {
     path "../attributes/LOCALCELLID";
     require-instance true;
    }
   }
   container attributes {
    uses PDSCHCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list PHICHCFG {
   max-elements 1;
   key "LOCALCELLID";
   leaf LOCALCELLID {
    type leafref {
     path "../attributes/LOCALCELLID";
     require-instance true;
    }
   }
   container attributes {
    uses PHICHCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/PIMFREQGROUP" {
  list PIMFREQCFG {
   max-elements 4;
   key "PIMFREQGROUPID";
   leaf PIMFREQGROUPID {
    type leafref {
     path "../attributes/PIMFREQGROUPID";
     require-instance true;
    }
   }
   container attributes {
    uses PIMFREQCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list PIMFREQGROUP {
   max-elements 6;
   key "PIMFREQGROUPID";
   leaf PIMFREQGROUPID {
    type leafref {
     path "../attributes/PIMFREQGROUPID";
     require-instance true;
    }
   }
   container attributes {
    uses PIMFREQGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list PIMINTERFSMARTAVOID {
   max-elements 1;
   key "LOCALCELLID";
   leaf LOCALCELLID {
    type leafref {
     path "../attributes/LOCALCELLID";
     require-instance true;
    }
   }
   container attributes {
    uses PIMINTERFSMARTAVOID-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/MBSFNAREA" {
  list PMCH {
   max-elements 15;
   key "LOCALMCEID MBSFNAREAID";
   leaf LOCALMCEID {
    type leafref {
     path "../attributes/LOCALMCEID";
     require-instance true;
    }
   }
   leaf MBSFNAREAID {
    type leafref {
     path "../attributes/MBSFNAREAID";
     require-instance true;
    }
   }
   container attributes {
    uses PMCH-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list PMCHALLOCPOLICY {
   max-elements 12;
   key "LOCALMCEID";
   leaf LOCALMCEID {
    type leafref {
     path "../attributes/LOCALMCEID";
     require-instance true;
    }
   }
   container attributes {
    uses PMCHALLOCPOLICY-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list PRB {
   max-elements 8;
   key "LOCALCELLID";
   leaf LOCALCELLID {
    type leafref {
     path "../attributes/LOCALCELLID";
     require-instance true;
    }
   }
   container attributes {
    uses PRB-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL/PRB" {
  list PRBDLGAPCONFIG {
   max-elements 1;
   key "LOCALCELLID PRBID";
   leaf LOCALCELLID {
    type leafref {
     path "../attributes/LOCALCELLID";
     require-instance true;
    }
   }
   leaf PRBID {
    type leafref {
     path "../attributes/PRBID";
     require-instance true;
    }
   }
   container attributes {
    uses PRBDLGAPCONFIG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL/PRB" {
  list PRBDLSCHCEALGO {
   max-elements 3;
   key "LOCALCELLID PRBID";
   leaf LOCALCELLID {
    type leafref {
     path "../attributes/LOCALCELLID";
     require-instance true;
    }
   }
   leaf PRBID {
    type leafref {
     path "../attributes/PRBID";
     require-instance true;
    }
   }
   container attributes {
    uses PRBDLSCHCEALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL/PRB" {
  list PRBPDCCHCECONFIG {
   max-elements 3;
   key "LOCALCELLID PRBID";
   leaf LOCALCELLID {
    type leafref {
     path "../attributes/LOCALCELLID";
     require-instance true;
    }
   }
   leaf PRBID {
    type leafref {
     path "../attributes/PRBID";
     require-instance true;
    }
   }
   container attributes {
    uses PRBPDCCHCECONFIG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL/PRB" {
  list PRBRACHCECONFIG {
   max-elements 3;
   key "LOCALCELLID PRBID";
   leaf LOCALCELLID {
    type leafref {
     path "../attributes/LOCALCELLID";
     require-instance true;
    }
   }
   leaf PRBID {
    type leafref {
     path "../attributes/PRBID";
     require-instance true;
    }
   }
   container attributes {
    uses PRBRACHCECONFIG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL/PRB" {
  list PRBSCHCONFIG {
   max-elements 1;
   key "LOCALCELLID PRBID";
   leaf LOCALCELLID {
    type leafref {
     path "../attributes/LOCALCELLID";
     require-instance true;
    }
   }
   leaf PRBID {
    type leafref {
     path "../attributes/PRBID";
     require-instance true;
    }
   }
   container attributes {
    uses PRBSCHCONFIG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL/PRB/EUPRBSECTOREQMGROUP" {
  list PRBSECTOREQMGRPITEM {
   max-elements 96;
   key "PRBID LOCALCELLID SECTOREQMGROUPID";
   leaf PRBID {
    type leafref {
     path "../attributes/PRBID";
     require-instance true;
    }
   }
   leaf LOCALCELLID {
    type leafref {
     path "../attributes/LOCALCELLID";
     require-instance true;
    }
   }
   leaf SECTOREQMGROUPID {
    type leafref {
     path "../attributes/SECTOREQMGROUPID";
     require-instance true;
    }
   }
   container attributes {
    uses PRBSECTOREQMGRPITEM-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL/PRB" {
  list PRBULSCHCEALGO {
   max-elements 3;
   key "LOCALCELLID PRBID";
   leaf LOCALCELLID {
    type leafref {
     path "../attributes/LOCALCELLID";
     require-instance true;
    }
   }
   leaf PRBID {
    type leafref {
     path "../attributes/PRBID";
     require-instance true;
    }
   }
   container attributes {
    uses PRBULSCHCEALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/PRIVATECABANDCOMB" {
  list PRIVATEBAND {
   max-elements 8;
   key "PRIVATECACOMBID";
   leaf PRIVATECACOMBID {
    type leafref {
     path "../attributes/PRIVATECACOMBID";
     require-instance true;
    }
   }
   container attributes {
    uses PRIVATEBAND-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list PRIVATECABANDCOMB {
   max-elements 64;
   key "BWCOMBSETID";
   leaf BWCOMBSETID {
    type leafref {
     path "../attributes/BWCOMBSETID";
     require-instance true;
    }
   }
   container attributes {
    uses PRIVATECABANDCOMB-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list PUCCHCFG {
   max-elements 1;
   key "LOCALCELLID";
   leaf LOCALCELLID {
    type leafref {
     path "../attributes/LOCALCELLID";
     require-instance true;
    }
   }
   container attributes {
    uses PUCCHCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list PUSCHCFG {
   max-elements 1;
   key "LOCALCELLID";
   leaf LOCALCELLID {
    type leafref {
     path "../attributes/LOCALCELLID";
     require-instance true;
    }
   }
   container attributes {
    uses PUSCHCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list PWRSAVINGTIMEPOLICY {
   max-elements 256;
   key "TIMEID";
   leaf TIMEID {
    type leafref {
     path "../attributes/TIMEID";
     require-instance true;
    }
   }
   container attributes {
    uses PWRSAVINGTIMEPOLICY-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list QCI5QICONFIG {
   max-elements 75;
   key "ASREFLECTIVEQOSSWITCH";
   leaf ASREFLECTIVEQOSSWITCH {
    type leafref {
     path "../attributes/ASREFLECTIVEQOSSWITCH";
     require-instance true;
    }
   }
   container attributes {
    uses QCI5QICONFIG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list QCIEUTRANRELATION {
   max-elements 160;
   key "LOCALCELLID";
   leaf LOCALCELLID {
    type leafref {
     path "../attributes/LOCALCELLID";
     require-instance true;
    }
   }
   container attributes {
    uses QCIEUTRANRELATION-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list QCIGERANRELATION {
   max-elements 320;
   key "LOCALCELLID";
   leaf LOCALCELLID {
    type leafref {
     path "../attributes/LOCALCELLID";
     require-instance true;
    }
   }
   container attributes {
    uses QCIGERANRELATION-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list QCIPARA {
   max-elements 75;
   key "DRXPARAGROUPID";
   leaf DRXPARAGROUPID {
    type leafref {
     path "../attributes/DRXPARAGROUPID";
     require-instance true;
    }
   }
   container attributes {
    uses QCIPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list QCIUETIMERCONFIG {
   max-elements 256;
   key "MAXNUMUESYNCOROUTOFSYNCIND";
   leaf MAXNUMUESYNCOROUTOFSYNCIND {
    type leafref {
     path "../attributes/MAXNUMUESYNCOROUTOFSYNCIND";
     require-instance true;
    }
   }
   container attributes {
    uses QCIUETIMERCONFIG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list QCIUTRANRELATION {
   max-elements 160;
   key "LOCALCELLID";
   leaf LOCALCELLID {
    type leafref {
     path "../attributes/LOCALCELLID";
     require-instance true;
    }
   }
   container attributes {
    uses QCIUTRANRELATION-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list QOSPOLICY {
   max-elements 128;
   key "QOSPOLICYID";
   leaf QOSPOLICYID {
    type leafref {
     path "../attributes/QOSPOLICYID";
     require-instance true;
    }
   }
   container attributes {
    uses QOSPOLICY-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list RACHCFG {
   max-elements 1;
   key "LOCALCELLID";
   leaf LOCALCELLID {
    type leafref {
     path "../attributes/LOCALCELLID";
     require-instance true;
    }
   }
   container attributes {
    uses RACHCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list RATFREQPRIORITYGROUP {
   max-elements 5120;
   key "RATFREQPRIORITYGROUPID";
   leaf RATFREQPRIORITYGROUPID {
    type leafref {
     path "../attributes/RATFREQPRIORITYGROUPID";
     require-instance true;
    }
   }
   container attributes {
    uses RATFREQPRIORITYGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list RELAYEXTENDEDQCI {
   max-elements 7;
   key "RLCPDCPPARAGROUPID";
   leaf RLCPDCPPARAGROUPID {
    type leafref {
     path "../attributes/RLCPDCPPARAGROUPID";
     require-instance true;
    }
   }
   container attributes {
    uses RELAYEXTENDEDQCI-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list RLCPDCPPARAGROUP {
   max-elements 241;
   key "RLCPDCPPARAGROUPID";
   leaf RLCPDCPPARAGROUPID {
    type leafref {
     path "../attributes/RLCPDCPPARAGROUPID";
     require-instance true;
    }
   }
   container attributes {
    uses RLCPDCPPARAGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list RLFTIMERCONSTGROUP {
   max-elements 10;
   key "LOCALCELLID";
   leaf LOCALCELLID {
    type leafref {
     path "../attributes/LOCALCELLID";
     require-instance true;
    }
   }
   container attributes {
    uses RLFTIMERCONSTGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list RRCCONNSTATETIMER {
   max-elements 1;
   key "BTRUNCINACTIVETIMER";
   leaf BTRUNCINACTIVETIMER {
    type leafref {
     path "../attributes/BTRUNCINACTIVETIMER";
     require-instance true;
    }
   }
   container attributes {
    uses RRCCONNSTATETIMER-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list RRUJOINTCALPARACFG {
   max-elements 1;
   key "LOCALCELLID";
   leaf LOCALCELLID {
    type leafref {
     path "../attributes/LOCALCELLID";
     require-instance true;
    }
   }
   container attributes {
    uses RRUJOINTCALPARACFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list S1 {
   max-elements 64;
   key "S1ID";
   leaf S1ID {
    type leafref {
     path "../attributes/S1ID";
     require-instance true;
    }
   }
   container attributes {
    uses S1-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list S1INTERFACE {
   max-elements 64;
   key "S1INTERFACEID";
   leaf S1INTERFACEID {
    type leafref {
     path "../attributes/S1INTERFACEID";
     require-instance true;
    }
   }
   container attributes {
    uses S1INTERFACE-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list S1REESTTIMER {
   max-elements 1;
   key "S1REESTMAXTIMER";
   leaf S1REESTMAXTIMER {
    type leafref {
     path "../attributes/S1REESTMAXTIMER";
     require-instance true;
    }
   }
   container attributes {
    uses S1REESTTIMER-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list SCAPPPARACFG {
   max-elements 302;
   key "APPDNSID";
   leaf APPDNSID {
    type leafref {
     path "../attributes/APPDNSID";
     require-instance true;
    }
   }
   container attributes {
    uses SCAPPPARACFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/PCCFREQCFG" {
  list SCCFREQCFG {
   max-elements 16;
   key "PCCDLEARFCN";
   leaf PCCDLEARFCN {
    type leafref {
     path "../attributes/PCCDLEARFCN";
     require-instance true;
    }
   }
   container attributes {
    uses SCCFREQCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list SCPOLICY {
   max-elements 1;
   key "IPADDRESSAGINGTIME";
   leaf IPADDRESSAGINGTIME {
    type leafref {
     path "../attributes/IPADDRESSAGINGTIME";
     require-instance true;
    }
   }
   container attributes {
    uses SCPOLICY-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list SCSERVICEQOS {
   max-elements 50;
   key "SCQOSID";
   leaf SCQOSID {
    type leafref {
     path "../attributes/SCQOSID";
     require-instance true;
    }
   }
   container attributes {
    uses SCSERVICEQOS-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CNOPSHARINGGROUP" {
  list SECONDARYOPIDTYPE {
   max-elements 5;
   key "CNOPSHARINGGROUPID";
   leaf CNOPSHARINGGROUPID {
    type leafref {
     path "../attributes/CNOPSHARINGGROUPID";
     require-instance true;
    }
   }
   container attributes {
    uses SECONDARYOPIDTYPE-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL/EUSECTOREQMGROUP" {
  list SECTOREQMREFTYPE {
   max-elements 96;
   key "LOCALCELLID SECTOREQMGROUPID";
   leaf LOCALCELLID {
    type leafref {
     path "../attributes/LOCALCELLID";
     require-instance true;
    }
   }
   leaf SECTOREQMGROUPID {
    type leafref {
     path "../attributes/SECTOREQMGROUPID";
     require-instance true;
    }
   }
   container attributes {
    uses SECTOREQMREFTYPE-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/SECTORSPLITGROUP" {
  list SECTORSPLITCELL {
   max-elements 256;
   key "SECTORSPLITGROUPID";
   leaf SECTORSPLITGROUPID {
    type leafref {
     path "../attributes/SECTORSPLITGROUPID";
     require-instance true;
    }
   }
   container attributes {
    uses SECTORSPLITCELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/SECTORSPLITGROUP/SECTORSPLITGROUPEXT" {
  list SECTORSPLITCELLEXT {
   max-elements 256;
   key "SECTORSPLITGROUPID SECTORSPLITBEAMNUM";
   leaf SECTORSPLITGROUPID {
    type leafref {
     path "../attributes/SECTORSPLITGROUPID";
     require-instance true;
    }
   }
   leaf SECTORSPLITBEAMNUM {
    type leafref {
     path "../attributes/SECTORSPLITBEAMNUM";
     require-instance true;
    }
   }
   container attributes {
    uses SECTORSPLITCELLEXT-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list SECTORSPLITGROUP {
   max-elements 128;
   key "SECTORSPLITGROUPID";
   leaf SECTORSPLITGROUPID {
    type leafref {
     path "../attributes/SECTORSPLITGROUPID";
     require-instance true;
    }
   }
   container attributes {
    uses SECTORSPLITGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/SECTORSPLITGROUP" {
  list SECTORSPLITGROUPEXT {
   max-elements 4;
   key "SECTORSPLITGROUPID";
   leaf SECTORSPLITGROUPID {
    type leafref {
     path "../attributes/SECTORSPLITGROUPID";
     require-instance true;
    }
   }
   container attributes {
    uses SECTORSPLITGROUPEXT-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list SERVERCONFIG {
   max-elements 50;
   key "SERVERINDEX";
   leaf SERVERINDEX {
    type leafref {
     path "../attributes/SERVERINDEX";
     require-instance true;
    }
   }
   container attributes {
    uses SERVERCONFIG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL/CELLMBMSCFG" {
  list SERVICEAREAIDREF {
   max-elements 6;
   key "LOCALCELLID";
   leaf LOCALCELLID {
    type leafref {
     path "../attributes/LOCALCELLID";
     require-instance true;
    }
   }
   container attributes {
    uses SERVICEAREAIDREF-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list SERVICEDIFFSETTING {
   max-elements 1;
   key "ENHSCELLBLINDCONFIGUETYPE";
   leaf ENHSCELLBLINDCONFIGUETYPE {
    type leafref {
     path "../attributes/ENHSCELLBLINDCONFIGUETYPE";
     require-instance true;
    }
   }
   container attributes {
    uses SERVICEDIFFSETTING-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list SERVICEIDENTIFYPARA {
   max-elements 1;
   key "ACCELERATIONSERVICEALGOSW";
   leaf ACCELERATIONSERVICEALGOSW {
    type leafref {
     path "../attributes/ACCELERATIONSERVICEALGOSW";
     require-instance true;
    }
   }
   container attributes {
    uses SERVICEIDENTIFYPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CNOPERATOR/SERVICEIFHOCFGGROUP" {
  list SERVICEIFDLEARFCNGRP {
   max-elements 16;
   key "SERVICEIFHOCFGGROUPID CNOPERATORID";
   leaf SERVICEIFHOCFGGROUPID {
    type leafref {
     path "../attributes/SERVICEIFHOCFGGROUPID";
     require-instance true;
    }
   }
   leaf CNOPERATORID {
    type leafref {
     path "../attributes/CNOPERATORID";
     require-instance true;
    }
   }
   container attributes {
    uses SERVICEIFDLEARFCNGRP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CNOPERATOR" {
  list SERVICEIFHOCFGGROUP {
   max-elements 10;
   key "CNOPERATORID";
   leaf CNOPERATORID {
    type leafref {
     path "../attributes/CNOPERATORID";
     require-instance true;
    }
   }
   container attributes {
    uses SERVICEIFHOCFGGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CNOPERATOR" {
  list SERVICEIRHOCFGGROUP {
   max-elements 10;
   key "CNOPERATORID";
   leaf CNOPERATORID {
    type leafref {
     path "../attributes/CNOPERATORID";
     require-instance true;
    }
   }
   container attributes {
    uses SERVICEIRHOCFGGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/MBSFNAREA/PMCH" {
  list SESSION {
   max-elements 28;
   key "LOCALMCEID MBSFNAREAID PMCHID";
   leaf LOCALMCEID {
    type leafref {
     path "../attributes/LOCALMCEID";
     require-instance true;
    }
   }
   leaf MBSFNAREAID {
    type leafref {
     path "../attributes/MBSFNAREAID";
     require-instance true;
    }
   }
   leaf PMCHID {
    type leafref {
     path "../attributes/PMCHID";
     require-instance true;
    }
   }
   container attributes {
    uses SESSION-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list SFNAUXRESBIND {
   max-elements 288;
   key "ENODEBID";
   leaf ENODEBID {
    type leafref {
     path "../attributes/ENODEBID";
     require-instance true;
    }
   }
   container attributes {
    uses SFNAUXRESBIND-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list SFNAUXRESGRPBIND {
   max-elements 256;
   key "ENODEBID";
   leaf ENODEBID {
    type leafref {
     path "../attributes/ENODEBID";
     require-instance true;
    }
   }
   container attributes {
    uses SFNAUXRESGRPBIND-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list SFNEDGERRURELATION {
   max-elements 2;
   key "LOCALCELLID";
   leaf LOCALCELLID {
    type leafref {
     path "../attributes/LOCALCELLID";
     require-instance true;
    }
   }
   container attributes {
    uses SFNEDGERRURELATION-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/SFNAUXRESGRPBIND" {
  list SFNSECTOREQMREFTYPE {
   max-elements 16;
   key "SECTOREQMGROUPID ENODEBID LOCALCELLID";
   leaf SECTOREQMGROUPID {
    type leafref {
     path "../attributes/SECTOREQMGROUPID";
     require-instance true;
    }
   }
   leaf ENODEBID {
    type leafref {
     path "../attributes/ENODEBID";
     require-instance true;
    }
   }
   leaf LOCALCELLID {
    type leafref {
     path "../attributes/LOCALCELLID";
     require-instance true;
    }
   }
   container attributes {
    uses SFNSECTOREQMREFTYPE-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list SIDELINKV2XCARRIER {
   max-elements 2;
   key "SIDELINKV2XCARRIERID";
   leaf SIDELINKV2XCARRIERID {
    type leafref {
     path "../attributes/SIDELINKV2XCARRIERID";
     require-instance true;
    }
   }
   container attributes {
    uses SIDELINKV2XCARRIER-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/SIDELINKV2XCARRIER" {
  list SIDELINKV2XPSSCHCFG {
   max-elements 2;
   key "SIDELINKV2XCARRIERID";
   leaf SIDELINKV2XCARRIERID {
    type leafref {
     path "../attributes/SIDELINKV2XCARRIERID";
     require-instance true;
    }
   }
   container attributes {
    uses SIDELINKV2XPSSCHCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/SIDELINKV2XCARRIER" {
  list SIDELINKV2XRESPLCFG {
   max-elements 3;
   key "SIDELINKV2XCARRIERID";
   leaf SIDELINKV2XCARRIERID {
    type leafref {
     path "../attributes/SIDELINKV2XCARRIERID";
     require-instance true;
    }
   }
   container attributes {
    uses SIDELINKV2XRESPLCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list SIMULOAD {
   max-elements 10;
   key "SIMULOADCFGINDEX";
   leaf SIMULOADCFGINDEX {
    type leafref {
     path "../attributes/SIMULOADCFGINDEX";
     require-instance true;
    }
   }
   container attributes {
    uses SIMULOAD-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL/CELLSIMULOAD" {
  list SIMULOADPMITEMPLATE {
   max-elements 16;
   key "LOCALCELLID";
   leaf LOCALCELLID {
    type leafref {
     path "../attributes/LOCALCELLID";
     require-instance true;
    }
   }
   container attributes {
    uses SIMULOADPMITEMPLATE-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/LTENRSPCTSHRCELLGRP" {
  list SPCTCLOUDAUXENODEB {
   max-elements 96;
   key "LTENRSPECTRUMSHRCELLGRPID";
   leaf LTENRSPECTRUMSHRCELLGRPID {
    type leafref {
     path "../attributes/LTENRSPECTRUMSHRCELLGRPID";
     require-instance true;
    }
   }
   container attributes {
    uses SPCTCLOUDAUXENODEB-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list SPECTRUMCLOUD {
   max-elements 1;
   key "LOCALCELLID";
   leaf LOCALCELLID {
    type leafref {
     path "../attributes/LOCALCELLID";
     require-instance true;
    }
   }
   container attributes {
    uses SPECTRUMCLOUD-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list SPIDCFG {
   max-elements 257;
   key "SPID";
   leaf SPID {
    type leafref {
     path "../attributes/SPID";
     require-instance true;
    }
   }
   container attributes {
    uses SPIDCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list SPIDGRPCFG {
   max-elements 72;
   key "ENDSPID";
   leaf ENDSPID {
    type leafref {
     path "../attributes/ENDSPID";
     require-instance true;
    }
   }
   container attributes {
    uses SPIDGRPCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list SPIDHOINPROHPLMNLIST {
   max-elements 200;
   key "SPID";
   leaf SPID {
    type leafref {
     path "../attributes/SPID";
     require-instance true;
    }
   }
   container attributes {
    uses SPIDHOINPROHPLMNLIST-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list SPIDHPLMNLIST {
   max-elements 256;
   key "ENDSPID";
   leaf ENDSPID {
    type leafref {
     path "../attributes/ENDSPID";
     require-instance true;
    }
   }
   container attributes {
    uses SPIDHPLMNLIST-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list SPIDPREALLOCPARAGRP {
   max-elements 10;
   key "PREALLOCATIONPARAGROUPID";
   leaf PREALLOCATIONPARAGROUPID {
    type leafref {
     path "../attributes/PREALLOCATIONPARAGROUPID";
     require-instance true;
    }
   }
   container attributes {
    uses SPIDPREALLOCPARAGRP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list SPIDQCIPARAM {
   max-elements 1028;
   key "SPID";
   leaf SPID {
    type leafref {
     path "../attributes/SPID";
     require-instance true;
    }
   }
   container attributes {
    uses SPIDQCIPARAM-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list SPLITCELLGROUPPARA {
   max-elements 128;
   key "SPLITCELLPARAGROUPID";
   leaf SPLITCELLPARAGROUPID {
    type leafref {
     path "../attributes/SPLITCELLPARAGROUPID";
     require-instance true;
    }
   }
   container attributes {
    uses SPLITCELLGROUPPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/SECTORSPLITGROUP" {
  list SPLITGRP3DEIRPTHLD {
   max-elements 28;
   key "SECTORSPLITGROUPID";
   leaf SECTORSPLITGROUPID {
    type leafref {
     path "../attributes/SECTORSPLITGROUPID";
     require-instance true;
    }
   }
   container attributes {
    uses SPLITGRP3DEIRPTHLD-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/SECTORSPLITGROUP" {
  list SPLITGRPSMARTPWRLOCK {
   max-elements 1;
   key "SECTORSPLITGROUPID";
   leaf SECTORSPLITGROUPID {
    type leafref {
     path "../attributes/SECTORSPLITGROUPID";
     require-instance true;
    }
   }
   container attributes {
    uses SPLITGRPSMARTPWRLOCK-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list SRBCFG {
   max-elements 1;
   key "HOCMDRRCRLSMSGRETXADPSW";
   leaf HOCMDRRCRLSMSGRETXADPSW {
    type leafref {
     path "../attributes/HOCMDRRCRLSMSGRETXADPSW";
     require-instance true;
    }
   }
   container attributes {
    uses SRBCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list SRBRLCPDCPCFG {
   max-elements 15;
   key "SRBID";
   leaf SRBID {
    type leafref {
     path "../attributes/SRBID";
     require-instance true;
    }
   }
   container attributes {
    uses SRBRLCPDCPCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list SRSCFG {
   max-elements 1;
   key "LOCALCELLID";
   leaf LOCALCELLID {
    type leafref {
     path "../attributes/LOCALCELLID";
     require-instance true;
    }
   }
   container attributes {
    uses SRSCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list SSRDCELLGROUP {
   max-elements 128;
   key "SSRDLOCALCELLID";
   leaf SSRDLOCALCELLID {
    type leafref {
     path "../attributes/SSRDLOCALCELLID";
     require-instance true;
    }
   }
   container attributes {
    uses SSRDCELLGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list SUPERCOMBCELL {
   max-elements 1;
   key "LOCALCELLID";
   leaf LOCALCELLID {
    type leafref {
     path "../attributes/LOCALCELLID";
     require-instance true;
    }
   }
   container attributes {
    uses SUPERCOMBCELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list SYMBOLPWRSAVING {
   max-elements 1;
   key "LOCALCELLID";
   leaf LOCALCELLID {
    type leafref {
     path "../attributes/LOCALCELLID";
     require-instance true;
    }
   }
   container attributes {
    uses SYMBOLPWRSAVING-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list TACOUNTERPARAMGRP {
   max-elements 16;
   key "TARANGEINDEX";
   leaf TARANGEINDEX {
    type leafref {
     path "../attributes/TARANGEINDEX";
     require-instance true;
    }
   }
   container attributes {
    uses TACOUNTERPARAMGRP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list TCEIPMAPPING {
   max-elements 256;
   key "TCEID";
   leaf TCEID {
    type leafref {
     path "../attributes/TCEID";
     require-instance true;
    }
   }
   container attributes {
    uses TCEIPMAPPING-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list TDDRESMODESWITCH {
   max-elements 1;
   key "BBRESEXCLUSIVESWITCH";
   leaf BBRESEXCLUSIVESWITCH {
    type leafref {
     path "../attributes/BBRESEXCLUSIVESWITCH";
     require-instance true;
    }
   }
   container attributes {
    uses TDDRESMODESWITCH-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list TIMEALIGNMENTTIMER {
   max-elements 1;
   key "LOCALCELLID";
   leaf LOCALCELLID {
    type leafref {
     path "../attributes/LOCALCELLID";
     require-instance true;
    }
   }
   container attributes {
    uses TIMEALIGNMENTTIMER-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list TM9DEDICATEDCARRIER {
   max-elements 16;
   key "CRSTRANSMISSIONSTRATEGY";
   leaf CRSTRANSMISSIONSTRATEGY {
    type leafref {
     path "../attributes/CRSTRANSMISSIONSTRATEGY";
     require-instance true;
    }
   }
   container attributes {
    uses TM9DEDICATEDCARRIER-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list TYPDRBBSR {
   max-elements 21;
   key "QCI";
   leaf QCI {
    type leafref {
     path "../attributes/QCI";
     require-instance true;
    }
   }
   container attributes {
    uses TYPDRBBSR-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list UECOMPAT {
   max-elements 128;
   key "INDEX";
   leaf INDEX {
    type leafref {
     path "../attributes/INDEX";
     require-instance true;
    }
   }
   container attributes {
    uses UECOMPAT-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list UECOOPERATIONPARA {
   max-elements 1;
   key "LOCALCELLID";
   leaf LOCALCELLID {
    type leafref {
     path "../attributes/LOCALCELLID";
     require-instance true;
    }
   }
   container attributes {
    uses UECOOPERATIONPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list UEDIFFCONFIG {
   max-elements 288;
   key "LOCALCELLID";
   leaf LOCALCELLID {
    type leafref {
     path "../attributes/LOCALCELLID";
     require-instance true;
    }
   }
   container attributes {
    uses UEDIFFCONFIG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list UEINFO {
   max-elements 64;
   key "UECAPINDEX";
   leaf UECAPINDEX {
    type leafref {
     path "../attributes/UECAPINDEX";
     require-instance true;
    }
   }
   container attributes {
    uses UEINFO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list UESPECDRXPARAGROUP {
   max-elements 252;
   key "LOCALCELLID";
   leaf LOCALCELLID {
    type leafref {
     path "../attributes/LOCALCELLID";
     require-instance true;
    }
   }
   container attributes {
    uses UESPECDRXPARAGROUP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list UETIMERCONFIG {
   max-elements 15;
   key "MAXNUMUESYNCOROUTOFSYNCIND";
   leaf MAXNUMUESYNCOROUTOFSYNCIND {
    type leafref {
     path "../attributes/MAXNUMUESYNCOROUTOFSYNCIND";
     require-instance true;
    }
   }
   container attributes {
    uses UETIMERCONFIG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list UETIMERCONST {
   max-elements 1;
   key "LOCALCELLID";
   leaf LOCALCELLID {
    type leafref {
     path "../attributes/LOCALCELLID";
     require-instance true;
    }
   }
   container attributes {
    uses UETIMERCONST-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list ULCSALGOPARA {
   max-elements 1;
   key "LOCALCELLID";
   leaf LOCALCELLID {
    type leafref {
     path "../attributes/LOCALCELLID";
     require-instance true;
    }
   }
   container attributes {
    uses ULCSALGOPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL/PRB" {
  list ULGUARDBANDCFG {
   max-elements 1;
   key "LOCALCELLID PRBID";
   leaf LOCALCELLID {
    type leafref {
     path "../attributes/LOCALCELLID";
     require-instance true;
    }
   }
   leaf PRBID {
    type leafref {
     path "../attributes/PRBID";
     require-instance true;
    }
   }
   container attributes {
    uses ULGUARDBANDCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list ULINTERFSUPPRESSCFG {
   max-elements 1;
   key "LOCALCELLID";
   leaf LOCALCELLID {
    type leafref {
     path "../attributes/LOCALCELLID";
     require-instance true;
    }
   }
   container attributes {
    uses ULINTERFSUPPRESSCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list ULSPECTRUMSHRCONFIG {
   max-elements 208;
   key "ULSPECTRUMSHARINGCONFIGID";
   leaf ULSPECTRUMSHARINGCONFIGID {
    type leafref {
     path "../attributes/ULSPECTRUMSHARINGCONFIGID";
     require-instance true;
    }
   }
   container attributes {
    uses ULSPECTRUMSHRCONFIG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list ULZEROBUFFERZONE {
   max-elements 1;
   key "LOCALCELLID";
   leaf LOCALCELLID {
    type leafref {
     path "../attributes/LOCALCELLID";
     require-instance true;
    }
   }
   container attributes {
    uses ULZEROBUFFERZONE-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list USERPRBGROUPPARAM {
   max-elements 1548;
   key "SPID";
   leaf SPID {
    type leafref {
     path "../attributes/SPID";
     require-instance true;
    }
   }
   container attributes {
    uses USERPRBGROUPPARAM-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list USERPRIORITY {
   max-elements 1;
   key "ARP10PRIORITY";
   leaf ARP10PRIORITY {
    type leafref {
     path "../attributes/ARP10PRIORITY";
     require-instance true;
    }
   }
   container attributes {
    uses USERPRIORITY-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list USERQCIPRIORITY {
   max-elements 4;
   key "BRONZEDLSCHPRIORITYFACTOR";
   leaf BRONZEDLSCHPRIORITYFACTOR {
    type leafref {
     path "../attributes/BRONZEDLSCHPRIORITYFACTOR";
     require-instance true;
    }
   }
   container attributes {
    uses USERQCIPRIORITY-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list USERVPFMPARA {
   max-elements 1;
   key "LOCALCELLID";
   leaf LOCALCELLID {
    type leafref {
     path "../attributes/LOCALCELLID";
     require-instance true;
    }
   }
   container attributes {
    uses USERVPFMPARA-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list UTRANBLKNCELL {
   max-elements 16;
   key "LOCALCELLID";
   leaf LOCALCELLID {
    type leafref {
     path "../attributes/LOCALCELLID";
     require-instance true;
    }
   }
   container attributes {
    uses UTRANBLKNCELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list UTRANEXTERNALCELL {
   max-elements 2304;
   key "RNCID";
   leaf RNCID {
    type leafref {
     path "../attributes/RNCID";
     require-instance true;
    }
   }
   container attributes {
    uses UTRANEXTERNALCELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/UTRANEXTERNALCELL" {
  list UTRANEXTERNALCELLPLMN {
   max-elements 3;
   key "MCC MNC RNCID CELLID";
   leaf MCC {
    type leafref {
     path "../attributes/MCC";
     require-instance true;
    }
   }
   leaf MNC {
    type leafref {
     path "../attributes/MNC";
     require-instance true;
    }
   }
   leaf RNCID {
    type leafref {
     path "../attributes/RNCID";
     require-instance true;
    }
   }
   leaf CELLID {
    type leafref {
     path "../attributes/CELLID";
     require-instance true;
    }
   }
   container attributes {
    uses UTRANEXTERNALCELLPLMN-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/UTRANEXTERNALCELL" {
  list UTRANEXTERNALCELL_MULTIBAND {
   max-elements 2;
   key "MCC MNC RNCID CELLID";
   leaf MCC {
    type leafref {
     path "../attributes/MCC";
     require-instance true;
    }
   }
   leaf MNC {
    type leafref {
     path "../attributes/MNC";
     require-instance true;
    }
   }
   leaf RNCID {
    type leafref {
     path "../attributes/RNCID";
     require-instance true;
    }
   }
   leaf CELLID {
    type leafref {
     path "../attributes/CELLID";
     require-instance true;
    }
   }
   container attributes {
    uses UTRANEXTERNALCELL_MULTIBAND-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list UTRANNCELL {
   max-elements 128;
   key "LOCALCELLID";
   leaf LOCALCELLID {
    type leafref {
     path "../attributes/LOCALCELLID";
     require-instance true;
    }
   }
   container attributes {
    uses UTRANNCELL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list UTRANNETWORKCAPCFG {
   max-elements 32;
   key "RNCID";
   leaf RNCID {
    type leafref {
     path "../attributes/RNCID";
     require-instance true;
    }
   }
   container attributes {
    uses UTRANNETWORKCAPCFG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list UTRANNFREQ {
   max-elements 16;
   key "LOCALCELLID";
   leaf LOCALCELLID {
    type leafref {
     path "../attributes/LOCALCELLID";
     require-instance true;
    }
   }
   container attributes {
    uses UTRANNFREQ-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL/UTRANNFREQ" {
  list UTRANNFREQSCELLOP {
   max-elements 6;
   key "LOCALCELLID UTRANDLARFCN";
   leaf LOCALCELLID {
    type leafref {
     path "../attributes/LOCALCELLID";
     require-instance true;
    }
   }
   leaf UTRANDLARFCN {
    type leafref {
     path "../attributes/UTRANDLARFCN";
     require-instance true;
    }
   }
   container attributes {
    uses UTRANNFREQSCELLOP-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL/UTRANNFREQ" {
  list UTRANRANSHARE {
   max-elements 4;
   key "LOCALCELLID UTRANDLARFCN";
   leaf LOCALCELLID {
    type leafref {
     path "../attributes/LOCALCELLID";
     require-instance true;
    }
   }
   leaf UTRANDLARFCN {
    type leafref {
     path "../attributes/UTRANDLARFCN";
     require-instance true;
    }
   }
   container attributes {
    uses UTRANRANSHARE-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list VOICEAMRCONTROL {
   max-elements 4;
   key "LOCALCELLID";
   leaf LOCALCELLID {
    type leafref {
     path "../attributes/LOCALCELLID";
     require-instance true;
    }
   }
   container attributes {
    uses VOICEAMRCONTROL-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list VOLTEALGOCONFIG {
   max-elements 1;
   key "LOCALCELLID";
   leaf LOCALCELLID {
    type leafref {
     path "../attributes/LOCALCELLID";
     require-instance true;
    }
   }
   container attributes {
    uses VOLTEALGOCONFIG-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list VQMALGO {
   max-elements 1;
   key "AMRLOWQUALRELPERIODNUM";
   leaf AMRLOWQUALRELPERIODNUM {
    type leafref {
     path "../attributes/AMRLOWQUALRELPERIODNUM";
     require-instance true;
    }
   }
   container attributes {
    uses VQMALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION/CELL" {
  list WTCPPROXYALGO {
   max-elements 1;
   key "LOCALCELLID";
   leaf LOCALCELLID {
    type leafref {
     path "../attributes/LOCALCELLID";
     require-instance true;
    }
   }
   container attributes {
    uses WTCPPROXYALGO-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list X2 {
   max-elements 12;
   key "X2ID";
   leaf X2ID {
    type leafref {
     path "../attributes/X2ID";
     require-instance true;
    }
   }
   container attributes {
    uses X2-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list X2AUTOSETUPOPERATOR {
   max-elements 10;
   key "MCC";
   leaf MCC {
    type leafref {
     path "../attributes/MCC";
     require-instance true;
    }
   }
   container attributes {
    uses X2AUTOSETUPOPERATOR-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list X2BLACKWHITELIST {
   max-elements 64;
   key "ENODEBID";
   leaf ENODEBID {
    type leafref {
     path "../attributes/ENODEBID";
     require-instance true;
    }
   }
   container attributes {
    uses X2BLACKWHITELIST-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list X2INTERFACE {
   max-elements 768;
   key "X2INTERFACEID";
   leaf X2INTERFACEID {
    type leafref {
     path "../attributes/X2INTERFACEID";
     require-instance true;
    }
   }
   container attributes {
    uses X2INTERFACE-attributes;
    leaf modifier {
     type hwat:modifier_AMD;
     mandatory false;
    }
    leaf remark {
     type string;
     mandatory false;
    }
    leaf template {
     type string;
     mandatory false;
    }
   }
  }
 }
 augment "/ne:NE/enodebfunctionmodule:eNodeBFunctionModule/ENODEBFUNCTION" {
  list XW {
   max-elements 1;
   key "XWID";
   leaf XWID {
    type leafref {
     path "../attributes/XWID";
     require-instance true;
    }
   }
   container attributes {
    uses XW-attributes;
    leaf modifier {
     type hwat:modifier_AMD;
     mandatory false;
    }
    leaf remark {
     type string;
     mandatory false;
    }
    leaf template {
     type string;
     mandatory false;
    }
   }
  }
 }
 augment "/if:interfaces/if:interface" {
  container attributes {
   uses CELLDLSCHALGO-attributes;
  }
 }
 augment "/if:interfaces/if:interface/ip:ipv4" {
  container eurrn-ipv4 {
   container attributes {
    uses EURRN-attributes;
   }
  }
 }
 augment "/if:interfaces/if:interface/ip:ipv4" {
  container eurrnlanip-ipv4 {
   container attributes {
    uses EURRNLANIP-attributes;
   }
  }
 }
 augment "/if:interfaces/if:interface/ip:ipv4" {
  container eurrnrt-ipv4 {
   container attributes {
    uses EURRNRT-attributes;
   }
  }
 }
 augment "/if:interfaces/if:interface/ip:ipv4" {
  container incrcfg-ipv4 {
   container attributes {
    uses INCRCFG-attributes;
   }
  }
 }
 augment "/if:interfaces/if:interface/ip:ipv6" {
  container incrcfg-ipv6 {
   container attributes {
    uses INCRCFG-attributes;
   }
  }
 }
 augment "/if:interfaces/if:interface/ip:ipv4" {
  container scappparacfg-ipv4 {
   container attributes {
    uses SCAPPPARACFG-attributes;
   }
  }
 }
 augment "/if:interfaces/if:interface/ip:ipv6" {
  container scappparacfg-ipv6 {
   container attributes {
    uses SCAPPPARACFG-attributes;
   }
  }
 }
 augment "/if:interfaces/if:interface/ip:ipv4" {
  container scserviceqos-ipv4 {
   container attributes {
    uses SCSERVICEQOS-attributes;
   }
  }
 }
 augment "/if:interfaces/if:interface/ip:ipv6" {
  container scserviceqos-ipv6 {
   container attributes {
    uses SCSERVICEQOS-attributes;
   }
  }
 }
 augment "/if:interfaces/if:interface/ip:ipv4" {
  container serverconfig-ipv4 {
   container attributes {
    uses SERVERCONFIG-attributes;
   }
  }
 }
 augment "/if:interfaces/if:interface/ip:ipv6" {
  container serverconfig-ipv6 {
   container attributes {
    uses SERVERCONFIG-attributes;
   }
  }
 }
 augment "/if:interfaces/if:interface/ip:ipv4" {
  container tceipmapping-ipv4 {
   container attributes {
    uses TCEIPMAPPING-attributes;
   }
  }
 }
 augment "/if:interfaces/if:interface/ip:ipv6" {
  container tceipmapping-ipv6 {
   container attributes {
    uses TCEIPMAPPING-attributes;
   }
  }
 }
 grouping ANR-attributes {
 leaf ACTIVEPCICONFLICTSWITCH {
  type boolean;
  mandatory false;
 }
 leaf ANRCONTROLLEDHOSTRATEGY {
  type boolean;
  mandatory false;
 }
 leaf ANROPTADVICERPTINTERVAL {
  type uint8 {
   range "0..168";
  }
  mandatory false;
 }
 leaf ANRROBUSTTHLD {
  type uint8 {
   range "0..10";
  }
  mandatory false;
 }
 leaf CGIREADSCGADDSCSRATETHLD {
  type uint8 {
   range "1..100";
  }
  mandatory false;
 }
 leaf CAUECHOSEMODE {
  type enumeration {
   enum val-0;
   enum val-1;
   enum val-2;
  }
  mandatory false;
 }
 leaf DELCELLTHD {
  type uint8 {
   range "0..100";
  }
  mandatory false;
 }
 leaf EUTRANNCELLDELPUNNUM {
  type uint16 {
   range "1..10000";
  }
  mandatory false;
 }
 leaf EVENTANRMODE {
  type boolean;
  mandatory false;
 }
 leaf EVENTANRWITHVOIPMODE {
  type inet:ip-address;
  mandatory false;
 }
 leaf FASTANRCHECKPERIOD {
  type uint16 {
   range "1..10080";
  }
  mandatory false;
 }
 leaf FASTANRINTERRATMEASUENUM {
  type uint8 {
   range "1..200";
  }
  mandatory false;
 }
 leaf FASTANRINTERRATUENUMTHD {
  type uint16 {
   range "1..10000";
  }
  mandatory false;
 }
 leaf FASTANRINTRARATMEASUENUM {
  type uint8 {
   range "1..200";
  }
  mandatory false;
 }
 leaf FASTANRINTRARATUENUMTHD {
  type uint16 {
   range "1..10000";
  }
  mandatory false;
 }
 leaf FASTANRMODE {
  type enumeration {
   enum val-0;
   enum val-1;
   enum val-2;
  }
  mandatory false;
 }
 leaf FASTANRMONITORSTATEPERIOD {
  type uint16 {
   range "0..65535";
  }
  mandatory false;
 }
 leaf FASTANRRPRTAMOUNT {
  type enumeration {
   enum val-0;
   enum val-1;
   enum val-2;
   enum val-3;
   enum val-4;
   enum val-5;
   enum val-6;
   enum val-7;
  }
  mandatory false;
 }
 leaf FASTANRRPRTINTERVAL {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf FASTANRRSCPTHD {
  type int8 {
   range "-120..-25";
  }
  mandatory false;
 }
 leaf FASTANRRSRPTHD {
  type int16 {
   range "-130..-70";
  }
  mandatory false;
 }
 leaf FASTANRRSSITHD {
  type int8 {
   range "-110..-48";
  }
  mandatory false;
 }
 leaf GERANEVENTANRCGITIMER {
  type uint8 {
   range "2..16";
  }
  mandatory false;
 }
 leaf GERANEVENTANRMODE {
  type boolean;
  mandatory false;
 }
 leaf GERANNCELLHOFORNRTDELTHD {
  type uint16 {
   range "0..10000";
  }
  mandatory false;
 }
 leaf HOSUCRATEFORCGIREAD {
  type uint8 {
   range "1..100";
  }
  mandatory false;
 }
 leaf NFREQMEASIDLESTATEPERIOD {
  type uint16 {
   range "15..10080";
  }
  mandatory false;
 }
 leaf NFREQMEASSTATPERIODNUM {
  type uint16 {
   range "1..10000";
  }
  mandatory false;
 }
 leaf NFREQMEASUENUM {
  type uint8 {
   range "5..200";
  }
  mandatory false;
 }
 leaf NCELLCATHDFORNRTDEL {
  type uint16 {
   range "0..1000";
  }
  mandatory false;
 }
 leaf NCELLDELPUNISHPERIOD {
  type uint16 {
   range "1..50400";
  }
  mandatory false;
 }
 leaf NCELLHOFORNRTDELTHD {
  type uint16 {
   range "0..10000";
  }
  mandatory false;
 }
 leaf NCELLHOSTATNUM {
  type uint16 {
   range "1..10000";
  }
  mandatory false;
 }
 leaf NOHONCELLRESTOREINTERVAL {
  type uint8 {
   range "0..180";
  }
  mandatory false;
 }
 leaf NOHOSETMODE {
  type boolean;
  mandatory false;
 }
 leaf NOHOSETTHD {
  type uint8 {
   range "0..100";
  }
  mandatory false;
 }
 leaf NOSCGADDNCELLRESTOREINT {
  type uint8 {
   range "0..180";
  }
  mandatory false;
 }
 leaf NOSCGADDTHLD {
  type uint8 {
   range "0..100";
  }
  mandatory false;
 }
 leaf NRFASTANRRSRPTHLD {
  type union {
   type int16 {
    range "-156..0";
   }
  }
  mandatory false;
 }
 leaf NRFR2CGIREADINGTIMER {
  type uint8 {
   range "2..32";
  }
  mandatory false;
 }
 leaf NRFREQMEASRPTNUMHIGHTHLD {
  type uint16 {
   range "1..640";
  }
  mandatory false;
 }
 leaf NRFREQMEASRPTNUMLOWTHLD {
  type uint16 {
   range "0..320";
  }
  mandatory false;
 }
 leaf NRNCELLSTATFORNRTDELTHLD {
  type uint16 {
   range "0..10000";
  }
  mandatory false;
 }
 leaf NRTDELMODE {
  type string;
  mandatory false;
 }
 leaf OPTMODE {
  type boolean;
  mandatory false;
 }
 leaf PERIODFORNCELLRANKING {
  type uint16 {
   range "10..50400";
  }
  mandatory false;
 }
 leaf SCGADDATTEMPTNUMTHLD {
  type uint16 {
   range "1..10000";
  }
  mandatory false;
 }
 leaf SMARTPREALLOCATIONMODE {
  type boolean;
  mandatory false;
 }
 leaf SPECSERVICECELLQUERYSW {
  type string;
  mandatory false;
 }
 leaf STANUMFORIRATNRTDEL {
  type uint16 {
   range "0..10000";
  }
  mandatory false;
 }
 leaf STAPERIODFORIRATNRTDEL {
  type uint16 {
   range "1..50400";
  }
  mandatory false;
 }
 leaf STARTTIME {
  type hwat:HH_MM_SS_Time;
  mandatory false;
 }
 leaf STATPERIODCOEFF {
  type uint8 {
   range "1..20";
  }
  mandatory false;
 }
 leaf STATPERIODFORNRNCELL {
  type uint16 {
   range "1..50400";
  }
  mandatory false;
 }
 leaf STATISTICNUMFORNRTDEL {
  type uint16 {
   range "1..10000";
  }
  mandatory false;
 }
 leaf STATISTICPERIOD {
  type uint16 {
   range "1..10080";
  }
  mandatory false;
 }
 leaf STATISTICPERIODFORNRTDEL {
  type uint16 {
   range "1..50400";
  }
  mandatory false;
 }
 leaf STOPTIME {
  type hwat:HH_MM_SS_Time;
  mandatory false;
 }
 leaf UTRANEVENTANRCGITIMER {
  type uint8 {
   range "2..16";
  }
  mandatory false;
 }
 leaf UTRANEVENTANRMODE {
  type boolean;
  mandatory false;
 }
 leaf UTRANNCELLDELPUNNUM {
  type uint16 {
   range "1..10000";
  }
  mandatory false;
 }
 leaf UTRANNCELLHOFORNRTDELTHD {
  type uint16 {
   range "0..10000";
  }
  mandatory false;
 }
 }
 grouping ASPARAGROUP-attributes {
 leaf ACCSERVICEUEINACTIVITYTMR {
  type union {
   type uint16 {
    range "0..65535";
   }
  }
  mandatory false;
 }
 leaf ACCSERVICEUEKEEPALIVETIMER {
  type uint16 {
   range "0..65535";
  }
  mandatory false;
 }
 leaf ACCELERATIONSERVICEOPTSW {
  type string;
  mandatory false;
 }
 leaf ACCESSTOASDURTHLD {
  type uint8 {
   range "0..20";
  }
  mandatory false;
 }
 leaf AGGREGATIONATTRIBUTE {
  type string;
  mandatory false;
 }
 leaf ASNACKCQIADJVALUE {
  type uint16 {
   range "0..330";
  }
  mandatory false;
 }
 leaf OLD_ASPARAGROUPID {
  type union {
   type int8 {
    range "-1..11";
   }
  }
  mandatory false;
 }
 leaf ASPARAGROUPID {
  type union {
   type int8 {
    range "-1..11";
   }
  }
  mandatory false;
 }
 leaf ASPREALLOCDURATION {
  type union {
   type uint16 {
    range "0..65535";
   }
  }
  mandatory false;
 }
 leaf ASPREALLOCMINPERIOD {
  type uint8 {
   range "1..80";
  }
  mandatory false;
 }
 leaf ASPREALLOCSIZE {
  type uint16 {
   range "45..1500";
  }
  mandatory false;
 }
 leaf ASRLCPDCPPARAGROUPID {
  type union {
   type uint8 {
    range "0..255";
   }
  }
  mandatory false;
 }
 leaf ASSCGADDINTERVAL {
  type union {
   type uint8 {
    range "0..50";
   }
  }
  mandatory false;
 }
 leaf ASSCHPRIFACTOR {
  type union {
   type uint16 {
    range "1..65535";
   }
  }
  mandatory false;
 }
 leaf ASUESERVICETYPE {
  type string;
  mandatory false;
 }
 leaf ASULSCHPRI {
  type enumeration {
   enum val-0;
   enum val-1;
   enum val-2;
  }
  mandatory false;
 }
 leaf DLGUARANTEEDRATE {
  type uint16 {
   range "0..12500";
  }
  mandatory false;
 }
 leaf GUARANTEEDUETYPE {
  type boolean;
  mandatory false;
 }
 leaf INTERFREQHOGROUPID {
  type union {
   type uint8 {
    range "0..255";
   }
  }
  mandatory false;
 }
 leaf INTRAFREQHOGROUPID {
  type union {
   type uint8 {
    range "0..255";
   }
  }
  mandatory false;
 }
 leaf MULTICARRCFGGROUPID {
  type union {
   type uint8 {
    range "0..255";
   }
  }
  mandatory false;
 }
 leaf NSADCINTERFREQHOGROUPID {
  type union {
   type uint8 {
    range "0..255";
   }
  }
  mandatory false;
 }
 leaf NSADCINTRAFREQHOGROUPID {
  type union {
   type uint8 {
    range "0..255";
   }
  }
  mandatory false;
 }
 leaf NSADCRATFREQPRIORITYGRPID {
  type union {
   type uint16 {
    range "0..65535";
   }
  }
  mandatory false;
 }
 leaf RATFREQPRIORITYGROUPID {
  type union {
   type uint16 {
    range "0..65535";
   }
  }
  mandatory false;
 }
 leaf SECONDASPARAGROUPID {
  type union {
   type uint8 {
    range "0..255";
   }
  }
  mandatory false;
 }
 leaf SERVAWAREPOLICY {
  type boolean;
  mandatory false;
 }
 leaf STUEGUARANTEEPOLICY {
  type enumeration {
   enum val-0;
   enum val-1;
   enum val-2;
  }
  mandatory false;
 }
 leaf STUEGUARANTEETYPE {
  type enumeration {
   enum val-0;
   enum val-1;
   enum val-2;
  }
  mandatory false;
 }
 leaf ULMINGBR {
  type uint16 {
   range "0..12500";
  }
  mandatory false;
 }
 leaf ULPREALLOCATIONPRI {
  type enumeration {
   enum val-0;
   enum val-1;
   enum val-2;
  }
  mandatory false;
 }
 }
 grouping BBPASSISTGROUP-attributes {
 leaf ASSISTCABINETNO {
  type uint8 {
   range "0..7";
  }
  mandatory false;
 }
 leaf ASSISTSLOTNO {
  type uint8 {
   range "0..5";
  }
  mandatory false;
 }
 leaf ASSISTSTARTTIME {
  type hwat:HH_MM_SS_Time;
  mandatory false;
 }
 leaf ASSISTSUBRACKNO {
  type uint8 {
   range "0..1";
  }
  mandatory false;
 }
 leaf OLD_BBPASSISTGRPID {
  type union {
   type int8 {
    range "-1..5";
   }
  }
  mandatory false;
 }
 leaf BBPASSISTGRPID {
  type union {
   type int8 {
    range "-1..5";
   }
  }
  mandatory false;
 }
 leaf CELLLOADSTATPERIOD {
  type uint16 {
   range "24..2160";
  }
  mandatory false;
 }
 leaf MASTERCABINETNO {
  type uint8 {
   range "0..7";
  }
  mandatory false;
 }
 leaf MASTERSLOTNO {
  type uint8 {
   range "0..5";
  }
  mandatory false;
 }
 leaf MASTERSUBRACKNO {
  type uint8 {
   range "0..1";
  }
  mandatory false;
 }
 }
 grouping BBPCOLLABORATIONGRP-attributes {
 leaf OLD_BBCOGROUPID {
  type union {
   type int8 {
    range "-1..2";
   }
  }
  mandatory false;
 }
 leaf BBCOGROUPID {
  type union {
   type int8 {
    range "-1..2";
   }
  }
  mandatory false;
 }
 leaf BLOCKSTATE {
  type enumeration {
   enum val-0;
   enum val-1;
   enum val-2;
  }
  mandatory false;
 }
 leaf COBASEBANDEQMID {
  type uint8 {
   range "0..23";
  }
  mandatory false;
 }
 leaf COLLABORATINGFEATURELIST {
  type string;
  mandatory false;
 }
 leaf INVENTORYBASEBANDEQMID {
  type uint8 {
   range "0..23";
  }
  mandatory false;
 }
 }
 grouping BCCHCFG-attributes {
 leaf LOCALCELLNAME {
  type string;
  mandatory false;
 }
 leaf LOCALCELLID {
  type union {
   type int16 {
    range "-1..255";
   }
  }
  mandatory false;
 }
 leaf MODIFYPERIODCOEFF {
  type enumeration {
   enum val-0;
   enum val-1;
   enum val-2;
   enum val-3;
  }
  mandatory false;
 }
 leaf MODIFYPERIODCOEFFFORNB {
  type enumeration {
   enum val-0;
   enum val-1;
   enum val-2;
   enum val-3;
  }
  mandatory false;
 }
 }
 grouping BEAMNUMADJALGO-attributes {
 leaf BEAMADJNUM {
  type boolean;
  mandatory false;
 }
 leaf BEAMADJTFCVOLVARRATETHLD {
  type uint8 {
   range "0..100";
  }
  mandatory false;
 }
 leaf BEAMADJUENUMVARRATETHLD {
  type uint8 {
   range "0..100";
  }
  mandatory false;
 }
 leaf BEAMNUMADJMODE {
  type enumeration {
   enum val-0;
   enum val-1;
   enum val-2;
   enum val-3;
   enum val-4;
   enum val-5;
  }
  mandatory false;
 }
 leaf BEAMNUMADJTABLE {
  type string {
   length "168";
  }
  mandatory false;
 }
 leaf BEAMNUMSWITCHSTARTTIME {
  type hwat:HH_MM_SS_Time;
  mandatory false;
 }
 leaf BEAMNUMSWITCHOVERSWITCH {
  type string;
  mandatory false;
 }
 leaf FOURBEAMDLPRBUSAGETHLD {
  type uint8 {
   range "0..100";
  }
  mandatory false;
 }
 leaf FOURBEAMLIGHTLOADTHLD {
  type uint8 {
   range "1..24";
  }
  mandatory false;
 }
 leaf FOURTOSINGLEBEAMSWITCHTHLD {
  type uint8 {
   range "1..15";
  }
  mandatory false;
 }
 leaf PROBEPRBUSAGEOFFSET {
  type int8 {
   range "-50..50";
  }
  mandatory false;
 }
 leaf REMAININGUENUM {
  type uint8 {
   range "0..100";
  }
  mandatory false;
 }
 leaf SECTORSPLITGROUPID {
  type union {
   type int16 {
    range "-1..255";
   }
  }
  mandatory false;
 }
 leaf SINGLEBEAMDLPRBUSAGETHLD {
  type uint8 {
   range "0..100";
  }
  mandatory false;
 }
 leaf SINGLEBEAMHEAVYLOADTHLD {
  type uint8 {
   range "1..24";
  }
  mandatory false;
 }
 leaf SINGLETOFOURBEAMSWITCHTHLD {
  type uint8 {
   range "1..15";
  }
  mandatory false;
 }
 leaf SNGLBEAMDLACTIVEUENUMTHLD {
  type uint8 {
   range "1..20";
  }
  mandatory false;
 }
 leaf TFCVOLANDTHPTGAINTHLD {
  type int8 {
   range "-100..100";
  }
  mandatory false;
 }
 leaf TRAFFICVARIATIONTHLD {
  type uint8 {
   range "0..100";
  }
  mandatory false;
 }
 leaf UENUMVARIATIONTHLD {
  type uint8 {
   range "0..100";
  }
  mandatory false;
 }
 }
 grouping CAGROUP-attributes {
 leaf OLD_CAGROUPID {
  type union {
   type int8 {
    range "-1..35";
   }
  }
  mandatory false;
 }
 leaf CAGROUPID {
  type union {
   type int8 {
    range "-1..35";
   }
  }
  mandatory false;
 }
 leaf CAGROUPTYPEIND {
  type enumeration {
   enum val-0;
   enum val-1;
   enum val-2;
  }
  mandatory false;
 }
 leaf CNOPERATORLIST {
  type string {
   length "6";
  }
  mandatory false;
 }
 }
 grouping CAGROUPCELL-attributes {
 leaf OLD_CAGROUPID {
  type union {
   type int8 {
    range "-1..35";
   }
  }
  mandatory false;
 }
 leaf CAGROUPID {
  type union {
   type int8 {
    range "-1..35";
   }
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf PCELLA4RSRPTHD {
  type int16 {
   range "-140..-43";
  }
  mandatory false;
 }
 leaf PCELLA4RSRQTHD {
  type int8 {
   range "-40..-6";
  }
  mandatory false;
 }
 leaf PREFERREDPCELLPRIORITY {
  type uint8 {
   range "0..7";
  }
  mandatory false;
 }
 leaf OLD_ENODEBID {
  type union {
   type int32 {
    range "-1..1048575";
   }
  }
  mandatory false;
 }
 leaf ENODEBID {
  type union {
   type int32 {
    range "-1..1048575";
   }
  }
  mandatory false;
 }
 }
 grouping CAGROUPSCELLCFG-attributes {
 leaf LOCALCELLNAME {
  type string;
  mandatory false;
 }
 leaf OLD_LOCALCELLID {
  type union {
   type int16 {
    range "-1..255";
   }
  }
  mandatory false;
 }
 leaf LOCALCELLID {
  type union {
   type int16 {
    range "-1..255";
   }
  }
  mandatory false;
 }
 leaf SCELLA2OFFSET {
  type int8 {
   range "-31..66";
  }
  mandatory false;
 }
 leaf SCELLA4OFFSET {
  type int8 {
   range "-35..62";
  }
  mandatory false;
 }
 leaf SCELLBLINDCFGFLAG {
  type boolean;
  mandatory false;
 }
 leaf OLD_SCELLLOCALCELLID {
  type union {
   type int16 {
    range "-1..255";
   }
  }
  mandatory false;
 }
 leaf SCELLLOCALCELLID {
  type union {
   type int16 {
    range "-1..255";
   }
  }
  mandatory false;
 }
 leaf SCELLPRIORITY {
  type uint8 {
   range "0..7";
  }
  mandatory false;
 }
 leaf OLD_SCELLENODEBID {
  type union {
   type int32 {
    range "-1..1048575";
   }
  }
  mandatory false;
 }
 leaf SCELLENODEBID {
  type union {
   type int32 {
    range "-1..1048575";
   }
  }
  mandatory false;
 }
 leaf SPIDGRPID {
  type union {
   type uint16 {
    range "0..65535";
   }
  }
  mandatory false;
 }
 }
 grouping CAMGTCFG-attributes {
 leaf LOCALCELLNAME {
  type string;
  mandatory false;
 }
 leaf ACTIVEBUFFERDELAYTHD {
  type uint16 {
   range "0..300";
  }
  mandatory false;
 }
 leaf ACTIVEBUFFERLENTHD {
  type uint16 {
   range "0..300";
  }
  mandatory false;
 }
 leaf ADDEDMEASCFG {
  type boolean;
  mandatory false;
 }
 leaf BLINDSCELLSAMPLENUM {
  type uint16 {
   range "1..65535";
  }
  mandatory false;
 }
 leaf CAA1TIMETOTRIGGER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf CAA2TIMETOTRIGGER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf CAA4TIMETOTRIGGER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf CAA6REPORTAMOUNT {
  type enumeration {
   enum val-0;
   enum val-1;
   enum val-2;
   enum val-3;
   enum val-4;
   enum val-5;
   enum val-6;
   enum val-7;
  }
  mandatory false;
 }
 leaf CAA6REPORTINTERVAL {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf CAA6TIMETOTRIGGER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf CAMIMOPRIORITYSTRATEGYSW {
  type enumeration {
   enum val-0;
   enum val-1;
   enum val-2;
  }
  mandatory false;
 }
 leaf CAPREALLOCATIONSCCUECOUNT {
  type uint8 {
   range "0..8";
  }
  mandatory false;
 }
 leaf CAROUTECONFIGPENALTYOFS {
  type uint16 {
   range "0..65535";
  }
  mandatory false;
 }
 leaf CAROUTECONFIGPENALTYWEIGHT {
  type uint8 {
   range "1..255";
  }
  mandatory false;
 }
 leaf CASCCFREQMEASOPTSW {
  type boolean;
  mandatory false;
 }
 leaf CATRAFFICDIRECTIONPREF {
  type enumeration {
   enum val-0;
   enum val-1;
   enum val-2;
  }
  mandatory false;
 }
 leaf CARRAGGRA2THDRSRP {
  type int16 {
   range "-140..-43";
  }
  mandatory false;
 }
 leaf CARRAGGRA4THDRSRP {
  type int16 {
   range "-140..-43";
  }
  mandatory false;
 }
 leaf CARRAGGRA6OFFSET {
  type int8 {
   range "-30..30";
  }
  mandatory false;
 }
 leaf CARRIERMGTSWITCH {
  type boolean;
  mandatory false;
 }
 leaf CELLCAALGOEXTSWITCH {
  type string;
  mandatory false;
 }
 leaf CELLCAALGOSWITCH {
  type string;
  mandatory false;
 }
 leaf CELLMAXPCCNUMBER {
  type uint16 {
   range "0..65535";
  }
  mandatory false;
 }
 leaf DEACTIVEBUFFERLENTHD {
  type uint8 {
   range "1..10";
  }
  mandatory false;
 }
 leaf DEACTIVETHROUGHPUTTHD {
  type uint16 {
   range "10..1000";
  }
  mandatory false;
 }
 leaf DISCLOUDBBCAMAXCCNUM {
  type enumeration {
   enum val-0;
   enum val-1;
   enum val-2;
   enum val-3;
   enum val-4;
  }
  mandatory false;
 }
 leaf ENHANCEDPCCANCHORA1THDRSRP {
  type int16 {
   range "-140..-43";
  }
  mandatory false;
 }
 leaf ENHANCEDSCCSELA1THLDRSRP {
  type union {
   type int16 {
    range "-140..-40";
   }
  }
  mandatory false;
 }
 leaf FTCA2CCANCHORPOLICY {
  type enumeration {
   enum val-0;
   enum val-1;
   enum val-2;
  }
  mandatory false;
 }
 leaf FTCAMULTICCANCHORPOLICY {
  type enumeration {
   enum val-0;
   enum val-1;
   enum val-2;
  }
  mandatory false;
 }
 leaf FTRELAXEDBHCADLMAXCCNUM {
  type enumeration {
   enum val-0;
   enum val-1;
   enum val-2;
   enum val-3;
   enum val-4;
   enum val-5;
  }
  mandatory false;
 }
 leaf FTRELAXEDBHCAULMAXCCNUM {
  type boolean;
  mandatory false;
 }
 leaf FASTSCELLSELAFTSCELLRMVSW {
  type boolean;
  mandatory false;
 }
 leaf FDDTDDCADLMAXCCNUM {
  type enumeration {
   enum val-0;
   enum val-1;
   enum val-2;
   enum val-3;
   enum val-4;
  }
  mandatory false;
 }
 leaf FDDTDDCAMAXFRAMEOFSDIFF {
  type union {
   type uint16 {
    range "0..65535";
   }
  }
  mandatory false;
 }
 leaf FDDTDDCAULMAXCCNUM {
  type boolean;
  mandatory false;
 }
 leaf FORBID2CCUERATIOTHLD {
  type uint8 {
   range "1..100";
  }
  mandatory false;
 }
 leaf FORBID3CCUERATIOTHLD {
  type uint8 {
   range "1..100";
  }
  mandatory false;
 }
 leaf FORBID4CCUERATIOTHLD {
  type uint8 {
   range "1..100";
  }
  mandatory false;
 }
 leaf FORBID5CCUERATIOTHLD {
  type uint8 {
   range "1..100";
  }
  mandatory false;
 }
 leaf HLUECNTTHLDFORSCELLCONFIG {
  type uint16 {
   range "0..65535";
  }
  mandatory false;
 }
 leaf HIGHLOADCELLTYPENOTASSCELL {
  type enumeration {
   enum val-0;
   enum val-1;
   enum val-2;
  }
  mandatory false;
 }
 leaf LARGEPKTUEDLTRAFFICTHLD {
  type union {
   type uint8 {
    range "0..20";
   }
  }
  mandatory false;
 }
 leaf LOCALCELLID {
  type union {
   type int16 {
    range "-1..255";
   }
  }
  mandatory false;
 }
 leaf MASSIVEMIMOGAINCOEFFICIENT {
  type uint8 {
   range "1..200";
  }
  mandatory false;
 }
 leaf MEASCYCLESCELL {
  type enumeration {
   enum val-0;
   enum val-1;
   enum val-2;
   enum val-3;
   enum val-4;
   enum val-5;
   enum val-6;
   enum val-7;
  }
  mandatory false;
 }
 leaf MINDLAVGTOBESCHEDULEDUENUM {
  type union {
   type uint8 {
    range "0..255";
   }
  }
  mandatory false;
 }
 leaf MINRSVROUTENUMBERFORLAA {
  type uint8 {
   range "0..48";
  }
  mandatory false;
 }
 leaf OPTMODE {
  type boolean;
  mandatory false;
 }
 leaf PCCUSERNUMBEROFFLOADTHD {
  type uint8 {
   range "0..100";
  }
  mandatory false;
 }
 leaf RELAXEDBHCAULMAXCCNUM {
  type boolean;
  mandatory false;
 }
 leaf RELAXEDBHSCCDEACTCQITHD {
  type uint8 {
   range "0..15";
  }
  mandatory false;
 }
 leaf RELAXEDBACKHAULCAMAXCCNUM {
  type enumeration {
   enum val-0;
   enum val-1;
   enum val-2;
   enum val-3;
   enum val-4;
   enum val-5;
  }
  mandatory false;
 }
 leaf RELAXEDBHSCCDLTARGETIBLER {
  type uint8 {
   range "0..99";
  }
  mandatory false;
 }
 leaf RSRPOFFSET {
  type uint8 {
   range "0..10";
  }
  mandatory false;
 }
 leaf SCELLAGINGTIME {
  type uint16 {
   range "1..65535";
  }
  mandatory false;
 }
 leaf SCCCFGINTERVAL {
  type uint8 {
   range "5..60";
  }
  mandatory false;
 }
 leaf SCCDEACTCQITHD {
  type uint8 {
   range "0..15";
  }
  mandatory false;
 }
 leaf SCCDETECTCQIDECREASESTEP {
  type uint8 {
   range "0..5";
  }
  mandatory false;
 }
 leaf SCCQUIETTIME {
  type uint8 {
   range "0..255";
  }
  mandatory false;
 }
 leaf SCCREACTIVATIONTIME {
  type uint8 {
   range "1..5";
  }
  mandatory false;
 }
 leaf SCELLDEACTRLCRETRANSNUMTHD {
  type uint8 {
   range "0..32";
  }
  mandatory false;
 }
 leaf SCELLHEAVYLOADUENUMTHLD {
  type uint16 {
   range "0..65535";
  }
  mandatory false;
 }
 leaf SCELLNOACTIVATIONUENUMTHLD {
  type uint16 {
   range "0..65535";
  }
  mandatory false;
 }
 leaf SLEEPPERIOD {
  type uint16 {
   range "0..65535";
  }
  mandatory false;
 }
 leaf SMARTCAPCCANCHORINGHYST {
  type uint8 {
   range "0..100";
  }
  mandatory false;
 }
 leaf SPECTRUMCOORDSINRTHLD {
  type int8 {
   range "-10..3";
  }
  mandatory false;
 }
 leaf SRSBASEDLOWEFFSINRTHLD {
  type union {
   type int16 {
    range "-50..255";
   }
  }
  mandatory false;
 }
 leaf STATPERIOD {
  type uint16 {
   range "1..65535";
  }
  mandatory false;
 }
 leaf TM9GAINCOEFFICIENT {
  type union {
   type uint8 {
    range "1..255";
   }
  }
  mandatory false;
 }
 leaf ULCAA1RSRPTHLD {
  type int16 {
   range "-140..-43";
  }
  mandatory false;
 }
 leaf ULCAA2RSRPTHLD {
  type int16 {
   range "-140..-43";
  }
  mandatory false;
 }
 leaf ULCAACTIVETIMETOTRIGGER {
  type uint16 {
   range "0..2000";
  }
  mandatory false;
 }
 leaf ULCAEXIT2CCSINRTHLD {
  type int8 {
   range "-10..100";
  }
  mandatory false;
 }
 leaf ULCALARGEPACKETDATAVOTHLD {
  type uint8 {
   range "0..255";
  }
  mandatory false;
 }
 leaf ULCAMAXPOWERDIFFTHLD {
  type uint8 {
   range "0..7";
  }
  mandatory false;
 }
 leaf ULHEAVYTRAFFICMLBTFCAOPTSW {
  type boolean;
  mandatory false;
 }
 leaf VOLTECAA2RSRPTHLD {
  type union {
   type int16 {
    range "-140..255";
   }
  }
  mandatory false;
 }
 }
 grouping CDMA20001XRTTEXTCELL-attributes {
 leaf BANDCLASS {
  type enumeration {
   enum val--1;
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
  }
  mandatory false;
 }
 leaf CDMA20001XRTTCELLID {
  type union {
   type int16 {
    range "-1..4095";
   }
  }
  mandatory false;
 }
 leaf CDMA20001XRTTSECTORID {
  type union {
   type int8 {
    range "-1..15";
   }
  }
  mandatory false;
 }
 leaf CELLNAME {
  type string {
   length "0..99";
  }
  mandatory false;
 }
 leaf CTRLMODE {
  type boolean;
  mandatory false;
 }
 leaf FREQUENCY {
  type union {
   type int16 {
    range "-1..2047";
   }
  }
  mandatory false;
 }
 leaf MCC {
  type string {
   length "3";
  }
  mandatory false;
 }
 leaf MNC {
  type string {
   length "2..3";
  }
  mandatory false;
 }
 leaf MSCID {
  type string {
   length "0..8";
  }
  mandatory false;
 }
 leaf NID {
  type union {
   type int32 {
    range "-1..65535";
   }
  }
  mandatory false;
 }
 leaf PNOFFSET {
  type uint16 {
   range "0..511";
  }
  mandatory false;
 }
 leaf SID {
  type union {
   type int16 {
    range "-1..32767";
   }
  }
  mandatory false;
 }
 }
 grouping CDMA20001XRTTNCELL-attributes {
 leaf ANRFLAG {
  type boolean;
  mandatory false;
 }
 leaf BANDCLASS {
  type enumeration {
   enum val--1;
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
  }
  mandatory false;
 }
 leaf CDMA20001XRTTCELLID {
  type union {
   type int16 {
    range "-1..4095";
   }
  }
  mandatory false;
 }
 leaf CDMA20001XRTTSECTORID {
  type union {
   type int8 {
    range "-1..15";
   }
  }
  mandatory false;
 }
 leaf CTRLMODE {
  type boolean;
  mandatory false;
 }
 leaf FREQUENCY {
  type union {
   type int16 {
    range "-1..2047";
   }
  }
  mandatory false;
 }
 leaf LOCALCELLID {
  type union {
   type int16 {
    range "-1..255";
   }
  }
  mandatory false;
 }
 leaf LOCALCELLNAME {
  type string {
   length "0..99";
  }
  mandatory false;
 }
 leaf NEIGHBOURCELLNAME {
  type string {
   length "0..99";
  }
  mandatory false;
 }
 leaf NID {
  type union {
   type int32 {
    range "-1..65535";
   }
  }
  mandatory false;
 }
 leaf NOHOFLAG {
  type boolean;
  mandatory false;
 }
 leaf NORMVFLAG {
  type boolean;
  mandatory false;
 }
 leaf SID {
  type union {
   type int16 {
    range "-1..32767";
   }
  }
  mandatory false;
 }
 }
 grouping CDMA20001XRTTPREREG-attributes {
 leaf LOCALCELLNAME {
  type string;
  mandatory false;
 }
 leaf CDMA20001XRTTCELLID {
  type uint16 {
   range "1..4095";
  }
  mandatory false;
 }
 leaf CDMA20001XRTTSECTORID {
  type uint8 {
   range "0..15";
  }
  mandatory false;
 }
 leaf LOCALCELLID {
  type union {
   type int16 {
    range "-1..255";
   }
  }
  mandatory false;
 }
 leaf MCC {
  type string {
   length "3";
  }
  mandatory false;
 }
 leaf MNC {
  type string {
   length "2..3";
  }
  mandatory false;
 }
 leaf MSCID {
  type string {
   length "0..8";
  }
  mandatory false;
 }
 leaf NID {
  type uint16 {
   range "0..65535";
  }
  mandatory false;
 }
 leaf SID {
  type uint16 {
   range "0..32767";
  }
  mandatory false;
 }
 }
 grouping CDMA2000BANDCLASS-attributes {
 leaf LOCALCELLNAME {
  type string;
  mandatory false;
 }
 leaf BANDCLASS {
  type enumeration {
   enum val--1;
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
  }
  mandatory false;
 }
 leaf CDMA2000HRPDCELLRESELIND {
  type boolean;
  mandatory false;
 }
 leaf CDMA2000HRPDCELLRESELPRI {
  type uint8 {
   range "0..7";
  }
  mandatory false;
 }
 leaf CDMA2000HRPDTHRESHXHIGH {
  type int8 {
   range "-63..0";
  }
  mandatory false;
 }
 leaf CDMA2000HRPDTHRESHXLOW {
  type int8 {
   range "-63..0";
  }
  mandatory false;
 }
 leaf LOCALCELLID {
  type union {
   type int16 {
    range "-1..255";
   }
  }
  mandatory false;
 }
 }
 grouping CDMA2000BCSCELLOP-attributes {
 leaf LOCALCELLNAME {
  type string;
  mandatory false;
 }
 leaf BANDCLASS {
  type enumeration {
   enum val--1;
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
  }
  mandatory false;
 }
 leaf CNOPERATORID {
  type union {
   type int8 {
    range "-1..5";
   }
  }
  mandatory false;
 }
 leaf HRPDCELLRESELDEDIPRI {
  type uint8 {
   range "0..7";
  }
  mandatory false;
 }
 leaf HRPDCELLRESELDEDIPRICFGIND {
  type boolean;
  mandatory false;
 }
 leaf LOCALCELLID {
  type union {
   type int16 {
    range "-1..255";
   }
  }
  mandatory false;
 }
 }
 grouping CDMA2000HRPDEXTCELL-attributes {
 leaf BANDCLASS {
  type enumeration {
   enum val--1;
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
  }
  mandatory false;
 }
 leaf CELLNAME {
  type string {
   length "0..99";
  }
  mandatory false;
 }
 leaf CTRLMODE {
  type boolean;
  mandatory false;
 }
 leaf FREQUENCY {
  type union {
   type int16 {
    range "-1..2047";
   }
  }
  mandatory false;
 }
 leaf MCC {
  type string {
   length "3";
  }
  mandatory false;
 }
 leaf MNC {
  type string {
   length "2..3";
  }
  mandatory false;
 }
 leaf PNOFFSET {
  type uint16 {
   range "0..511";
  }
  mandatory false;
 }
 leaf SECTORID104 {
  type string {
   length "3..28";
  }
  mandatory false;
 }
 leaf SECTORID24 {
  type string {
   length "3..8";
  }
  mandatory false;
 }
 }
 grouping CDMA2000HRPDNCELL-attributes {
 leaf ANRFLAG {
  type boolean;
  mandatory false;
 }
 leaf BANDCLASS {
  type enumeration {
   enum val--1;
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
  }
  mandatory false;
 }
 leaf CTRLMODE {
  type boolean;
  mandatory false;
 }
 leaf FREQUENCY {
  type union {
   type int16 {
    range "-1..2047";
   }
  }
  mandatory false;
 }
 leaf LOCALCELLID {
  type union {
   type int16 {
    range "-1..255";
   }
  }
  mandatory false;
 }
 leaf LOCALCELLNAME {
  type string {
   length "0..99";
  }
  mandatory false;
 }
 leaf NEIGHBOURCELLNAME {
  type string {
   length "0..99";
  }
  mandatory false;
 }
 leaf NOHOFLAG {
  type boolean;
  mandatory false;
 }
 leaf NORMVFLAG {
  type boolean;
  mandatory false;
 }
 leaf SECTORID104 {
  type string {
   length "3..28";
  }
  mandatory false;
 }
 leaf SECTORID24 {
  type string {
   length "3..8";
  }
  mandatory false;
 }
 }
 grouping CDMA2000HRPDPREREG-attributes {
 leaf LOCALCELLNAME {
  type string;
  mandatory false;
 }
 leaf LOCALCELLID {
  type union {
   type int16 {
    range "-1..255";
   }
  }
  mandatory false;
 }
 leaf MCPREREGPARACFGIND {
  type boolean;
  mandatory false;
 }
 leaf MCPREREGISTRATIONALLOWED {
  type boolean;
  mandatory false;
 }
 leaf MCC {
  type string {
   length "3";
  }
  mandatory false;
 }
 leaf MNC {
  type string {
   length "2..3";
  }
  mandatory false;
 }
 leaf PREREGISTRATIONZONEID {
  type uint8 {
   range "0..255";
  }
  mandatory false;
 }
 leaf SECONDARYPREREGZONEID0 {
  type uint8 {
   range "0..255";
  }
  mandatory false;
 }
 leaf SECONDARYPREREGZONEID0IND {
  type boolean;
  mandatory false;
 }
 leaf SECONDARYPREREGZONEID1 {
  type uint8 {
   range "0..255";
  }
  mandatory false;
 }
 leaf SECONDARYPREREGZONEID1IND {
  type boolean;
  mandatory false;
 }
 leaf SIB8PREREGISTRATIONALLOWED {
  type boolean;
  mandatory false;
 }
 }
 grouping CDMA2000HRPDREFCELL-attributes {
 leaf LOCALCELLNAME {
  type string;
  mandatory false;
 }
 leaf LOCALCELLID {
  type union {
   type int16 {
    range "-1..255";
   }
  }
  mandatory false;
 }
 leaf MCC {
  type string {
   length "3";
  }
  mandatory false;
 }
 leaf MNC {
  type string {
   length "2..3";
  }
  mandatory false;
 }
 leaf SECTORID104 {
  type string {
   length "3..28";
  }
  mandatory false;
 }
 leaf SECTORID24 {
  type string {
   length "3..8";
  }
  mandatory false;
 }
 leaf SELECTEDRATIO {
  type uint8 {
   range "0..50";
  }
  mandatory false;
 }
 }
 grouping CDMA2000NFREQ-attributes {
 leaf LOCALCELLNAME {
  type string;
  mandatory false;
 }
 leaf BANDCLASS {
  type enumeration {
   enum val--1;
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
  }
  mandatory false;
 }
 leaf FREQUENCY {
  type union {
   type int16 {
    range "-1..2047";
   }
  }
  mandatory false;
 }
 leaf FREQUENCYPRI {
  type uint8 {
   range "0..32";
  }
  mandatory false;
 }
 leaf LOCALCELLID {
  type union {
   type int16 {
    range "-1..255";
   }
  }
  mandatory false;
 }
 leaf OFFSETFREQ {
  type int8 {
   range "-15..15";
  }
  mandatory false;
 }
 leaf SEARCHWINDOWSIZE {
  type uint8 {
   range "0..15";
  }
  mandatory false;
 }
 leaf SEARCHWINDOWSIZECFGIND {
  type boolean;
  mandatory false;
 }
 }
 grouping CELL-attributes {
 leaf TEMPLATENAME {
  type string;
  mandatory false;
 }
 leaf ADDITIONALSPECTRUMEMISSION {
  type uint8 {
   range "1..32";
  }
  mandatory false;
 }
 leaf CPRICOMPRESSION {
  type enumeration {
   enum val-0;
   enum val-1;
   enum val-2;
   enum val-3;
   enum val-4;
   enum val-5;
   enum val-6;
   enum val-7;
  }
  mandatory false;
 }
 leaf CELLACTIVESTATE {
  type boolean;
  mandatory false;
 }
 leaf CELLADMINSTATE {
  type enumeration {
   enum val-0;
   enum val-1;
   enum val-2;
   enum val-3;
   enum val-4;
  }
  mandatory false;
 }
 leaf CELLID {
  type uint8 {
   range "0..255";
  }
  mandatory false;
 }
 leaf CELLMIDBLKTIMER {
  type uint16 {
   range "1..1440";
  }
  mandatory false;
 }
 leaf CELLNAME {
  type string {
   length "1..99";
  }
  mandatory false;
 }
 leaf CELLRADIUS {
  type union {
   type uint32 {
    range "1..656160";
   }
  }
  mandatory false;
 }
 leaf CELLRADIUSSTARTLOCATION {
  type union {
   type uint32 {
    range "0..328080";
   }
  }
  mandatory false;
 }
 leaf CELLSPECIFICOFFSET {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf CNOPSHARINGGROUPID {
  type union {
   type uint8 {
    range "0..255";
   }
  }
  mandatory false;
 }
 leaf COMPACTBWCTRLINTRFMODE {
  type enumeration {
   enum val-0;
   enum val-1;
   enum val-2;
   enum val-3;
   enum val-4;
   enum val-5;
  }
  mandatory false;
 }
 leaf COVERAGELEVELTYPE {
  type string;
  mandatory false;
 }
 leaf CPRIETHCOMPRESSIONRATIO {
  type enumeration {
   enum val-0;
   enum val-1;
   enum val-2;
   enum val-3;
  }
  mandatory false;
 }
 leaf CRSPORTMAP {
  type enumeration {
   enum val-0;
   enum val-1;
   enum val-2;
   enum val-3;
   enum val-4;
   enum val-5;
   enum val-6;
   enum val-13;
   enum val-14;
   enum val-15;
   enum val-16;
   enum val-17;
   enum val-18;
   enum val-19;
   enum val-20;
  }
  mandatory false;
 }
 leaf CRSPORTNUM {
  type enumeration {
   enum val-1;
   enum val-2;
   enum val-4;
  }
  mandatory false;
 }
 leaf CSGIND {
  type boolean;
  mandatory false;
 }
 leaf CUSTOMIZEDBANDWIDTHCFGIND {
  type enumeration {
   enum val-0;
   enum val-1;
   enum val-2;
  }
  mandatory false;
 }
 leaf CUSTOMIZEDDLBANDWIDTH {
  type union {
   type uint8 {
    range "12..200";
   }
  }
  mandatory false;
 }
 leaf CUSTOMIZEDULBANDWIDTH {
  type union {
   type uint8 {
    range "12..200";
   }
  }
  mandatory false;
 }
 leaf DLBANDWIDTH {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf DLCYCLICPREFIX {
  type boolean;
  mandatory false;
 }
 leaf DLEARFCN {
  type union {
   type uint32 {
    range "0..262143";
   }
  }
  mandatory false;
 }
 leaf DLPUNCTUREDRBNUM {
  type union {
   type uint8 {
    range "0..255";
   }
  }
  mandatory false;
 }
 leaf EUCELLSTANDBYMODE {
  type boolean;
  mandatory false;
 }
 leaf FDDTDDIND {
  type boolean;
  mandatory false;
 }
 leaf FREQBAND {
  type uint16 {
   range "1..256";
  }
  mandatory false;
 }
 leaf HIGHSPEEDFLAG {
  type enumeration {
   enum val-0;
   enum val-1;
   enum val-2;
  }
  mandatory false;
 }
 leaf HSCELLROOTSEQUENCEINDEX {
  type union {
   type uint16 {
    range "0..65535";
   }
  }
  mandatory false;
 }
 leaf INTRAFREQANRIND {
  type boolean;
  mandatory false;
 }
 leaf INTRAFREQRANSHARINGIND {
  type boolean;
  mandatory false;
 }
 leaf OLD_LOCALCELLID {
  type union {
   type int16 {
    range "-1..255";
   }
  }
  mandatory false;
 }
 leaf LOCALCELLID {
  type union {
   type int16 {
    range "-1..255";
   }
  }
  mandatory false;
 }
 leaf MULTICELLSHAREMODE {
  type boolean;
  mandatory false;
 }
 leaf MULTIRRUCELLFLAG {
  type boolean;
  mandatory false;
 }
 leaf MULTIRRUCELLMODE {
  type enumeration {
   enum val-0;
   enum val-1;
   enum val-2;
   enum val-3;
   enum val-5;
   enum val-6;
  }
  mandatory false;
 }
 leaf NBCELLFLAG {
  type boolean;
  mandatory false;
 }
 leaf PHYCELLID {
  type uint16 {
   range "0..503";
  }
  mandatory false;
 }
 leaf PREAMBLEFMT {
  type uint8 {
   range "0..4";
  }
  mandatory false;
 }
 leaf QOFFSETFREQ {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf ROOTSEQUENCEIDX {
  type uint16 {
   range "0..837";
  }
  mandatory false;
 }
 leaf SECTOREQMNUM {
  type uint8 {
   range "2..7";
  }
  mandatory false;
 }
 leaf SFNMASTERCELLLABEL {
  type string {
   length "0..100";
  }
  mandatory false;
 }
 leaf SPECIALSUBFRAMEPATTERNS {
  type enumeration {
   enum val-0;
   enum val-1;
   enum val-2;
   enum val-3;
   enum val-4;
   enum val-5;
   enum val-6;
   enum val-7;
   enum val-8;
   enum val-9;
   enum val-254;
  }
  mandatory false;
 }
 leaf SPECIFIEDCELLFLAG {
  type enumeration {
   enum val-0;
   enum val-1;
   enum val-2;
  }
  mandatory false;
 }
 leaf SSP6DWPTSMODE {
  type boolean;
  mandatory false;
 }
 leaf STANDBYCELLSFNRECOVETIME {
  type union {
   type uint8 {
    range "0..255";
   }
  }
  mandatory false;
 }
 leaf SUBFRAMEASSIGNMENT {
  type enumeration {
   enum val-0;
   enum val-1;
   enum val-2;
   enum val-3;
   enum val-4;
   enum val-5;
   enum val-6;
   enum val-254;
  }
  mandatory false;
 }
 leaf TXRXMODE {
  type enumeration {
   enum val-0;
   enum val-1;
   enum val-2;
   enum val-3;
   enum val-4;
   enum val-5;
   enum val-6;
   enum val-7;
   enum val-8;
   enum val-9;
  }
  mandatory false;
 }
 leaf UEPOWERMAX {
  type int8 {
   range "-30..36";
  }
  mandatory false;
 }
 leaf UEPOWERMAXCFGIND {
  type boolean;
  mandatory false;
 }
 leaf ULBANDWIDTH {
  type enumeration {
   enum val-0;
   enum val-1;
   enum val-2;
   enum val-3;
   enum val-4;
   enum val-5;
  }
  mandatory false;
 }
 leaf ULCYCLICPREFIX {
  type boolean;
  mandatory false;
 }
 leaf ULEARFCN {
  type union {
   type uint32 {
    range "18000..229575";
   }
  }
  mandatory false;
 }
 leaf ULEARFCNCFGIND {
  type boolean;
  mandatory false;
 }
 leaf ULPUNCTUREDRBNUMOFFSET {
  type int8 {
   range "-5..8";
  }
  mandatory false;
 }
 leaf USERLABEL {
  type string {
   length "0..256";
  }
  mandatory false;
 }
 leaf WORKMODE {
  type enumeration {
   enum val-0;
   enum val-1;
   enum val-2;
  }
  mandatory false;
 }
 }
 grouping CELLACBAR-attributes {
 leaf LOCALCELLNAME {
  type string;
  mandatory false;
 }
 leaf AC11BARFORSIG {
  type boolean;
  mandatory false;
 }
 leaf AC11BARFORCALL {
  type boolean;
  mandatory false;
 }
 leaf AC12BARFORSIG {
  type boolean;
  mandatory false;
 }
 leaf AC12BARFORCALL {
  type boolean;
  mandatory false;
 }
 leaf AC13BARFORSIG {
  type boolean;
  mandatory false;
 }
 leaf AC13BARFORCALL {
  type boolean;
  mandatory false;
 }
 leaf AC14BARFORSIG {
  type boolean;
  mandatory false;
 }
 leaf AC14BARFORCALL {
  type boolean;
  mandatory false;
 }
 leaf AC15BARFORSIG {
  type boolean;
  mandatory false;
 }
 leaf AC15BARFORCALL {
  type boolean;
  mandatory false;
 }
 leaf ACBARFACTORFORCSFB {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf ACBARFACTORFORMVIDEO {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf ACBARFACTORFORMVOICE {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf ACBARFORCSFBCFGIND {
  type boolean;
  mandatory false;
 }
 leaf ACBARFORMVIDEOCFGIND {
  type boolean;
  mandatory false;
 }
 leaf ACBARFORMVOICECFGIND {
  type boolean;
  mandatory false;
 }
 leaf ACBARTIMEFORCALL {
  type enumeration {
   enum val-0;
   enum val-1;
   enum val-2;
   enum val-3;
   enum val-4;
   enum val-5;
   enum val-6;
   enum val-7;
  }
  mandatory false;
 }
 leaf ACBARTIMEFORCSFB {
  type enumeration {
   enum val-0;
   enum val-1;
   enum val-2;
   enum val-3;
   enum val-4;
   enum val-5;
   enum val-6;
   enum val-7;
  }
  mandatory false;
 }
 leaf ACBARTIMEFORMVIDEO {
  type enumeration {
   enum val-0;
   enum val-1;
   enum val-2;
   enum val-3;
   enum val-4;
   enum val-5;
   enum val-6;
   enum val-7;
  }
  mandatory false;
 }
 leaf ACBARTIMEFORMVOICE {
  type enumeration {
   enum val-0;
   enum val-1;
   enum val-2;
   enum val-3;
   enum val-4;
   enum val-5;
   enum val-6;
   enum val-7;
  }
  mandatory false;
 }
 leaf ACBARTIMEFORSIG {
  type enumeration {
   enum val-0;
   enum val-1;
   enum val-2;
   enum val-3;
   enum val-4;
   enum val-5;
   enum val-6;
   enum val-7;
  }
  mandatory false;
 }
 leaf ACBARRINGFACTORFORCALL {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf ACBARRINGFACTORFORSIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf ACBARRINGFOREMERGENCY {
  type boolean;
  mandatory false;
 }
 leaf ACBARRINGFORMODATACFGIND {
  type boolean;
  mandatory false;
 }
 leaf ACBARRINGFORMOSIGCFGIND {
  type boolean;
  mandatory false;
 }
 leaf ACBARRINGINFOCFGIND {
  type enumeration {
   enum val-0;
   enum val-1;
   enum val-2;
  }
  mandatory false;
 }
 leaf LOCALCELLID {
  type union {
   type int16 {
    range "-1..255";
   }
  }
  mandatory false;
 }
 leaf SPECIALACBARFORCSFB {
  type string;
  mandatory false;
 }
 leaf SPECIALACBARFORMVIDEO {
  type string;
  mandatory false;
 }
 leaf SPECIALACBARFORMVOICE {
  type string;
  mandatory false;
 }
 leaf VOLTEPREFERCFGIND {
  type string;
  mandatory false;
 }
 }
 grouping CELLACCESS-attributes {
 leaf LOCALCELLNAME {
  type string;
  mandatory false;
 }
 leaf BROADCASTMODE {
  type enumeration {
   enum val-0;
   enum val-1;
   enum val-2;
  }
  mandatory false;
 }
 leaf CELLBARRED {
  type boolean;
  mandatory false;
 }
 leaf INTRAFREQRESEL {
  type boolean;
  mandatory false;
 }
 leaf LOCALCELLID {
  type union {
   type int16 {
    range "-1..255";
   }
  }
  mandatory false;
 }
 leaf REPTSYNCAVOIDIND {
  type boolean;
  mandatory false;
 }
 leaf REPTSYNCAVOIDTIME {
  type uint16 {
   range "1..1000";
  }
  mandatory false;
 }
 leaf ROUNDACTIONTIME {
  type hwat:yyyy_mm_dd_HH_MM_SS_Time;
  mandatory false;
 }
 leaf ROUNDPERIOD {
  type uint16 {
   range "1..720";
  }
  mandatory false;
 }
 }
 grouping CELLALGOEXTSWITCH-attributes {
 leaf LOCALCELLNAME {
  type string;
  mandatory false;
 }
 leaf ANROPTSWITCH {
  type string;
  mandatory false;
 }
 leaf ANTENNASELECTIONALGOSWITCH {
  type string;
  mandatory false;
 }
 leaf BEAMANTENNAEXTENSIONSWITCH {
  type string;
  mandatory false;
 }
 leaf CELLRLOPTSWITCH {
  type string;
  mandatory false;
 }
 leaf CELLRECOVERYTIME {
  type string;
  mandatory false;
 }
 leaf CODRSWITCH {
  type string;
  mandatory false;
 }
 leaf DLSCHENHSWITCH {
  type string;
  mandatory false;
 }
 leaf HEAVYLOADPRFMOPTSWITCH {
  type string;
  mandatory false;
 }
 leaf HOALLOWEDSWITCH {
  type string;
  mandatory false;
 }
 leaf LNRSMARTCARRIERSHUTDOWNSW {
  type boolean;
  mandatory false;
 }
 leaf LOCALCELLID {
  type union {
   type int16 {
    range "-1..255";
   }
  }
  mandatory false;
 }
 leaf LTEBWCOMPATIBILITYOPTSW {
  type string;
  mandatory false;
 }
 leaf LTEINBANDINTERFREQDEPLOYSW {
  type boolean;
  mandatory false;
 }
 leaf MEASOPTALGOEXTSW {
  type string;
  mandatory false;
 }
 leaf NCELLALGOSWITCH {
  type string;
  mandatory false;
 }
 leaf NBCELLALGOEXTSWITCH {
  type string;
  mandatory false;
 }
 leaf OPERATORFUNSWITCH {
  type string;
  mandatory false;
 }
 leaf RACHALGOEXTSWITCH {
  type string;
  mandatory false;
 }
 leaf SPEEDTESTSWITCH {
  type boolean;
  mandatory false;
 }
 leaf THPTBASELNRINTELCARRSHDNSW {
  type boolean;
  mandatory false;
 }
 leaf ULCOVERAGEENHANCEMENTSW {
  type boolean;
  mandatory false;
 }
 leaf ULSCHENHSWITCH {
  type string;
  mandatory false;
 }
 leaf WTTXALGOSWITCH {
  type string;
  mandatory false;
 }
 leaf WTTXMUMIMOSWITCH {
  type string;
  mandatory false;
 }
 }
 grouping CELLALGOSWITCH-attributes {
 leaf LOCALCELLNAME {
  type string;
  mandatory false;
 }
 leaf ACBARALGOSWITCH {
  type enumeration {
   enum val-0;
   enum val-1;
   enum val-2;
  }
  mandatory false;
 }
 leaf ACBARALGOFORDYNSWITCH {
  type string;
  mandatory false;
 }
 leaf AMRCALGOSWITCH {
  type string;
  mandatory false;
 }
 leaf ANRALGOSWITCH {
  type string;
  mandatory false;
 }
 leaf ANRFUNCTIONSWITCH {
  type string;
  mandatory false;
 }
 leaf ANTCALIBRATIONALGOSWITCH {
  type string;
  mandatory false;
 }
 leaf AQMALGOSWITCH {
  type string;
  mandatory false;
 }
 leaf ASALGOSWITCH {
  type boolean;
  mandatory false;
 }
 leaf ATTACHCELLSELFCFGSWITCH {
  type boolean;
  mandatory false;
 }
 leaf AVOIDINTERFSWITCH {
  type string;
  mandatory false;
 }
 leaf BACKOFFALGOSWITCH {
  type string;
  mandatory false;
 }
 leaf BFALGOSWITCH {
  type string;
  mandatory false;
 }
 leaf CAAUTOGROUPSWITCH {
  type string;
  mandatory false;
 }
 leaf CAMCSWITCH {
  type string;
  mandatory false;
 }
 leaf CEMODEHOSWITCH {
  type string;
  mandatory false;
 }
 leaf CELLDLCOVERENHANCESWITCH {
  type string;
  mandatory false;
 }
 leaf CELLPIMINTERMITIGSWITCH {
  type boolean;
  mandatory false;
 }
 leaf CELLRECOVERYSWITCH {
  type string;
  mandatory false;
 }
 leaf CELLSCHSTRATEGYSWITCH {
  type string;
  mandatory false;
 }
 leaf CMASSWITCH {
  type boolean;
  mandatory false;
 }
 leaf COORDINATIONALGOSWITCH {
  type string;
  mandatory false;
 }
 leaf COVBASEDINTERFREQHOMODE {
  type enumeration {
   enum val-0;
   enum val-1;
   enum val-2;
  }
  mandatory false;
 }
 leaf CQIADJALGOSWITCH {
  type string;
  mandatory false;
 }
 leaf CRESWITCH {
  type boolean;
  mandatory false;
 }
 leaf CRSICSWITCH {
  type boolean;
  mandatory false;
 }
 leaf DMIMOALGOSWITCH {
  type string;
  mandatory false;
 }
 leaf DACQENHANCEMENTSWITCH {
  type string;
  mandatory false;
 }
 leaf DACQSWITCH {
  type boolean;
  mandatory false;
 }
 leaf DEPRIORITISATIONDELIVERIND {
  type enumeration {
   enum val-0;
   enum val-1;
   enum val-2;
  }
  mandatory false;
 }
 leaf DETECTIONALGOSWITCH {
  type string;
  mandatory false;
 }
 leaf DISTBASEDHOSWITCH {
  type boolean;
  mandatory false;
 }
 leaf DL256QAMALGOSWITCH {
  type string;
  mandatory false;
 }
 leaf DLCOMPSWITCH {
  type string;
  mandatory false;
 }
 leaf DLPCALGOSWITCH {
  type string;
  mandatory false;
 }
 leaf DLSCHEXTSWITCH {
  type string;
  mandatory false;
 }
 leaf DLSCHSWITCH {
  type string;
  mandatory false;
 }
 leaf DTXDETECTIONALGOSWITCH {
  type string;
  mandatory false;
 }
 leaf DYNADJVOLTSWITCH {
  type string;
  mandatory false;
 }
 leaf DYNDRXSWITCH {
  type string;
  mandatory false;
 }
 leaf EICICSWITCH {
  type enumeration {
   enum val-0;
   enum val-1;
   enum val-2;
  }
  mandatory false;
 }
 leaf EMCSPSSCHSWITCH {
  type boolean;
  mandatory false;
 }
 leaf EMIMOSWITCH {
  type string;
  mandatory false;
 }
 leaf ENHCHNCALSWITCH {
  type string;
  mandatory false;
 }
 leaf ENHMIMOSWITCH {
  type string;
  mandatory false;
 }
 leaf ENHANCEDMLBALGOSWITCH {
  type string;
  mandatory false;
 }
 leaf FCSMODE {
  type enumeration {
   enum val-0;
   enum val-1;
   enum val-2;
  }
  mandatory false;
 }
 leaf FEICICSWITCH {
  type boolean;
  mandatory false;
 }
 leaf FREQLAYERSWITCH {
  type string;
  mandatory false;
 }
 leaf FREQPRIORITYHOSWITCH {
  type string;
  mandatory false;
 }
 leaf GLPWRSHARE {
  type boolean;
  mandatory false;
 }
 leaf HARQALGOSWITCH {
  type string;
  mandatory false;
 }
 leaf HIGHMOBITRIGIDLEMODESWITCH {
  type boolean;
  mandatory false;
 }
 leaf HIGHSPEEDINTERRATHOSWITCH {
  type string;
  mandatory false;
 }
 leaf HIGHSPEEDSCHOPTSWITCH {
  type string;
  mandatory false;
 }
 leaf HOALLOWEDSWITCH {
  type string;
  mandatory false;
 }
 leaf IDLEMODEEDRXSWITCH {
  type boolean;
  mandatory false;
 }
 leaf INTERFREQDIRECTHOSWITCH {
  type boolean;
  mandatory false;
 }
 leaf INTERFRANDSWITCH {
  type enumeration {
   enum val-0;
   enum val-1;
   enum val-2;
  }
  mandatory false;
 }
 leaf IRCSWITCH {
  type string;
  mandatory false;
 }
 leaf LBSSWITCH {
  type string;
  mandatory false;
 }
 leaf LOCALCELLID {
  type union {
   type int16 {
    range "-1..255";
   }
  }
  mandatory false;
 }
 leaf LOWSPEEDINTERFREQHOSWITCH {
  type boolean;
  mandatory false;
 }
 leaf LTEPTTQOSSWITCH {
  type boolean;
  mandatory false;
 }
 leaf LTEUTCBROADCASTSWITCH {
  type boolean;
  mandatory false;
 }
 leaf MFBIALGOSWITCH {
  type string;
  mandatory false;
 }
 leaf MPMUDETECTSWITCH {
  type string;
  mandatory false;
 }
 leaf MTCCONGCONTROLSWITCH {
  type string;
  mandatory false;
 }
 leaf MTCPOWERSAVSWITCH {
  type string;
  mandatory false;
 }
 leaf MCPTTSWITCH {
  type string;
  mandatory false;
 }
 leaf MEASOPTALGOSWITCH {
  type string;
  mandatory false;
 }
 leaf MIMOUEPAADAPTSW {
  type boolean;
  mandatory false;
 }
 leaf MLBALGOSWITCH {
  type string;
  mandatory false;
 }
 leaf MLBAUTOGROUPSWITCH {
  type string;
  mandatory false;
 }
 leaf MLBHOMODE {
  type string;
  mandatory false;
 }
 leaf MROSWITCH {
  type string;
  mandatory false;
 }
 leaf MTCSWITCH {
  type boolean;
  mandatory false;
 }
 leaf MUBFALGOSWITCH {
  type string;
  mandatory false;
 }
 leaf MULTICNCONNFREQPRISW {
  type boolean;
  mandatory false;
 }
 leaf MULTIFREQPRICONTROLSWITCH {
  type string;
  mandatory false;
 }
 leaf NCELLCLASSMGTSW {
  type string;
  mandatory false;
 }
 leaf NAICSSWITCH {
  type boolean;
  mandatory false;
 }
 leaf NBCELLALGOSWITCH {
  type string;
  mandatory false;
 }
 leaf NOSRSSCCBFALGOSWITCH {
  type string;
  mandatory false;
 }
 leaf NONSTANDARDBWALGOSW {
  type string;
  mandatory false;
 }
 leaf OPRESOURCEGROUPSHARESWITCH {
  type string;
  mandatory false;
 }
 leaf PUSCHMAXRBPUCCHADJSWITCH {
  type boolean;
  mandatory false;
 }
 leaf PCICONFLICTREPORTSWITCH {
  type inet:port-number;
  mandatory false;
 }
 leaf PRACHINTRFREJSWITCH {
  type boolean;
  mandatory false;
 }
 leaf PRACHJOINTRECEPTIONSWITCH {
  type boolean;
  mandatory false;
 }
 leaf PSICSWITCH {
  type string;
  mandatory false;
 }
 leaf PUCCHALGOSWITCH {
  type string;
  mandatory false;
 }
 leaf PUCCHIRCENHANCE {
  type boolean;
  mandatory false;
 }
 leaf PUSCHIRCALGOSWITCH {
  type string;
  mandatory false;
 }
 leaf PWRDERATSWITCH {
  type enumeration {
   enum val-0;
   enum val-1;
   enum val-2;
  }
  mandatory false;
 }
 leaf RACALGOSWITCH {
  type string;
  mandatory false;
 }
 leaf RACHALGOSWITCH {
  type string;
  mandatory false;
 }
 leaf RANSHAREMODESWITCH {
  type enumeration {
   enum val-0;
   enum val-1;
   enum val-2;
  }
  mandatory false;
 }
 leaf RELAYSWITCH {
  type string;
  mandatory false;
 }
 leaf REPEATERSWITCH {
  type string;
  mandatory false;
 }
 leaf RESELECPRIADAPTSWITCH {
  type boolean;
  mandatory false;
 }
 leaf ROHCSWITCH {
  type boolean;
  mandatory false;
 }
 leaf RRCREESTDATAFWDSWITCH {
  type boolean;
  mandatory false;
 }
 leaf RRUUEMAPSWITCH {
  type boolean;
  mandatory false;
 }
 leaf SASALGORITHMSWITCH {
  type string;
  mandatory false;
 }
 leaf SCVIDEOOPTSWITCH {
  type string;
  mandatory false;
 }
 leaf SERVICEDIFFSWITCH {
  type string;
  mandatory false;
 }
 leaf SFNALGOSWITCH {
  type string;
  mandatory false;
 }
 leaf SFNDLSCHSWITCH {
  type boolean;
  mandatory false;
 }
 leaf SFNLOADBASEDADPTSWITCH {
  type boolean;
  mandatory false;
 }
 leaf SFNULSCHSWITCH {
  type boolean;
  mandatory false;
 }
 leaf SFNUPLINKCOMPSWITCH {
  type string;
  mandatory false;
 }
 leaf SMALLBANDOPTSWITCH {
  type string;
  mandatory false;
 }
 leaf SPEPCIBASEDPOLICYSW {
  type string;
  mandatory false;
 }
 leaf SPECUSERALGOSWITCH {
  type string;
  mandatory false;
 }
 leaf SPIDSPECIFICHOSWITCH {
  type string;
  mandatory false;
 }
 leaf SRSALGOSWITCH {
  type string;
  mandatory false;
 }
 leaf SRSPUCCHENHANCEDSWITCH {
  type boolean;
  mandatory false;
 }
 leaf TRAFFICMLBSWITCH {
  type string;
  mandatory false;
 }
 leaf TURBORECEIVERSWITCH {
  type enumeration {
   enum val-0;
   enum val-1;
   enum val-2;
   enum val-3;
  }
  mandatory false;
 }
 leaf UEINACTIVETIMERQCI1SWITCH {
  type boolean;
  mandatory false;
 }
 leaf UDCALGOSWITCH {
  type string;
  mandatory false;
 }
 leaf ULAMRCMODE {
  type enumeration {
   enum val-0;
   enum val-1;
   enum val-3;
   enum val-5;
  }
  mandatory false;
 }
 leaf ULHIGHORDERCOMPSWITCH {
  type string;
  mandatory false;
 }
 leaf ULICSWITCH {
  type string;
  mandatory false;
 }
 leaf ULICSRBRATIO {
  type uint8 {
   range "1..100";
  }
  mandatory false;
 }
 leaf ULICSVOLTEPLTH {
  type uint8 {
   range "50..150";
  }
  mandatory false;
 }
 leaf ULJRANTNUMCOMBSW {
  type string;
  mandatory false;
 }
 leaf ULPCALGOSWITCH {
  type string;
  mandatory false;
 }
 leaf ULSCHEXTSWITCH {
  type string;
  mandatory false;
 }
 leaf ULSCHSWITCH {
  type string;
  mandatory false;
 }
 leaf ULSUMIMOALGOSWITCH {
  type string;
  mandatory false;
 }
 leaf UPLINKCOMPSWITCH {
  type string;
  mandatory false;
 }
 leaf UPLINKICSWITCH {
  type string;
  mandatory false;
 }
 leaf UUBASEDV2XALGOSWITCH {
  type string;
  mandatory false;
 }
 leaf VAMPHASESHIFTALGOSWITCH {
  type string;
  mandatory false;
 }
 leaf VMSSWITCH {
  type string;
  mandatory false;
 }
 leaf VOLTESWITCH {
  type string;
  mandatory false;
 }
 leaf VOIPFAILDECSELFRECSWITCH {
  type inet:ip-address;
  mandatory false;
 }
 leaf VOLTEREDIRECTSWITCH {
  type boolean;
  mandatory false;
 }
 }
 grouping CELLAUTOSHUTDOWN-attributes {
 leaf LOCALCELLNAME {
  type string;
  mandatory false;
 }
 leaf CELLAUTOSHUTDOWNSWITCH {
  type boolean;
  mandatory false;
 }
 leaf LOCALCELLID {
  type union {
   type int16 {
    range "-1..255";
   }
  }
  mandatory false;
 }
 leaf STARTTIME {
  type hwat:HH_MM_SS_Time;
  mandatory false;
 }
 leaf STOPTIME {
  type hwat:HH_MM_SS_Time;
  mandatory false;
 }
 }
 grouping CELLAUXDUBIND-attributes {
 leaf LOCALCELLNAME {
  type string;
  mandatory false;
 }
 leaf OLD_AUXILIARYENODEBDUID {
  type union {
   type int64 {
    range "-1..4294967295";
   }
  }
  mandatory false;
 }
 leaf AUXILIARYENODEBDUID {
  type union {
   type int64 {
    range "-1..4294967295";
   }
  }
  mandatory false;
 }
 leaf OLD_ENODEBID {
  type union {
   type int32 {
    range "-1..1048575";
   }
  }
  mandatory false;
 }
 leaf ENODEBID {
  type union {
   type int32 {
    range "-1..1048575";
   }
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 }
 grouping CELLAUXENBBIND-attributes {
 leaf LOCALCELLNAME {
  type string;
  mandatory false;
 }
 leaf OLD_ENODEBID {
  type union {
   type int32 {
    range "-1..1048575";
   }
  }
  mandatory false;
 }
 leaf ENODEBID {
  type union {
   type int32 {
    range "-1..1048575";
   }
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 }
 grouping CELLBACKOFF-attributes {
 leaf LOCALCELLNAME {
  type string;
  mandatory false;
 }
 leaf BACKOFFCAUSERHOSW {
  type boolean;
  mandatory false;
 }
 leaf BACKOFFMLBENHSW {
  type string;
  mandatory false;
 }
 leaf HOINREJECTPRBTHD {
  type uint8 {
   range "1..100";
  }
  mandatory false;
 }
 leaf HOINREJECTUENUMTHD {
  type uint16 {
   range "1..10000";
  }
  mandatory false;
 }
 leaf INTERFREQBACKOFFPRBTHD {
  type uint8 {
   range "1..100";
  }
  mandatory false;
 }
 leaf INTERFREQBACKOFFUENUMTHD {
  type uint16 {
   range "1..10000";
  }
  mandatory false;
 }
 leaf LOCALCELLID {
  type union {
   type int16 {
    range "-1..255";
   }
  }
  mandatory false;
 }
 leaf LOWEFFDLFACTORA {
  type uint16 {
   range "0..1000";
  }
  mandatory false;
 }
 leaf LOWEFFDLFACTORK {
  type uint8 {
   range "0..100";
  }
  mandatory false;
 }
 leaf LOWEFFDLMCSTHD {
  type uint8 {
   range "0..28";
  }
  mandatory false;
 }
 leaf LOWEFFULFACTORA {
  type uint16 {
   range "0..1000";
  }
  mandatory false;
 }
 leaf LOWEFFULFACTORK {
  type uint8 {
   range "0..100";
  }
  mandatory false;
 }
 leaf LOWEFFULMCSTHD {
  type uint8 {
   range "0..28";
  }
  mandatory false;
 }
 leaf LOWESTEFFDLMCSTHD {
  type uint8 {
   range "0..28";
  }
  mandatory false;
 }
 leaf LOWESTEFFULMCSTHD {
  type uint8 {
   range "0..28";
  }
  mandatory false;
 }
 leaf NRUEOFFLOADLOWEFFDLMCSTHD {
  type uint8 {
   range "0..28";
  }
  mandatory false;
 }
 leaf RBPRIMCSSELECTSTOPPRBTHD {
  type uint8 {
   range "1..100";
  }
  mandatory false;
 }
 leaf RBPRIMCSSELECTTRIGPRBTHD {
  type uint8 {
   range "1..100";
  }
  mandatory false;
 }
 leaf REJECTEDHOINCAUSE {
  type string;
  mandatory false;
 }
 leaf ULHEAVYTRAFFICJUDGEPERIOD {
  type uint8 {
   range "1..200";
  }
  mandatory false;
 }
 leaf ULHEAVYTRAFFICTTIPROPORTHD {
  type uint8 {
   range "1..100";
  }
  mandatory false;
 }
 leaf ULTRAFFICMLBUENUMTHD {
  type uint16 {
   range "1..10000";
  }
  mandatory false;
 }
 }
 grouping CELLBF-attributes {
 leaf LOCALCELLNAME {
  type string;
  mandatory false;
 }
 leaf ADAPTMUBFSTARTTHLD {
  type union {
   type uint8 {
    range "0..255";
   }
  }
  mandatory false;
 }
 leaf ANTSELUEMUBFPAIRMODE {
  type boolean;
  mandatory false;
 }
 leaf BFUEPOWERLIMITSWITCH {
  type boolean;
  mandatory false;
 }
 leaf BFWEIGHTOPTCHNQLTYTHLDOFS {
  type int16 {
   range "-200..50";
  }
  mandatory false;
 }
 leaf BFWEIGHTOPTDEGREEFACTOR {
  type uint8 {
   range "0..255";
  }
  mandatory false;
 }
 leaf BFWEIGHTOPTENH {
  type boolean;
  mandatory false;
 }
 leaf DUALSTREAMBFALGOSW {
  type string;
  mandatory false;
 }
 leaf HEAVYLOADSWITCHTOBFOPT {
  type union {
   type uint8 {
    range "0..255";
   }
  }
  mandatory false;
 }
 leaf HIGHORDERMUBFMAXLAYER {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf HIGHORDERMUBFPAIRRULE {
  type boolean;
  mandatory false;
 }
 leaf LOCALCELLID {
  type union {
   type int16 {
    range "-1..255";
   }
  }
  mandatory false;
 }
 leaf MASSIVEMIMOMUBFPAIRRULE {
  type boolean;
  mandatory false;
 }
 leaf MAXBFRANKPARA {
  type enumeration {
   enum val-0;
   enum val-1;
   enum val-2;
  }
  mandatory false;
 }
 leaf MOVINGUEMUBFSCHEME {
  type enumeration {
   enum val-0;
   enum val-1;
   enum val-2;
   enum val-3;
   enum val-4;
   enum val-5;
  }
  mandatory false;
 }
 leaf MUBFALGOOPTSWITCH {
  type string;
  mandatory false;
 }
 leaf MUBFPOWERNORMADPTFACTOR {
  type uint8 {
   range "0..10";
  }
  mandatory false;
 }
 leaf MULTILAYERCTRLSWITCH {
  type string;
  mandatory false;
 }
 leaf MULTILAYERTHDSWITCHTOTM7 {
  type uint16 {
   range "0..640";
  }
  mandatory false;
 }
 leaf NONANTSELUEMUBFPAIRMODE {
  type boolean;
  mandatory false;
 }
 leaf PDSCHSPLITBEAMCONFIGINDEX {
  type enumeration {
   enum val-0;
   enum val-1;
   enum val-2;
   enum val-3;
   enum val-4;
  }
  mandatory false;
 }
 leaf QUALUEPORTAVOIDMODE {
  type enumeration {
   enum val-0;
   enum val-1;
   enum val-2;
   enum val-3;
  }
  mandatory false;
 }
 leaf SPLITSDMAADAPTIONPERIOD {
  type enumeration {
   enum val-0;
   enum val-1;
   enum val-2;
   enum val-3;
   enum val-4;
  }
  mandatory false;
 }
 leaf SRSRSRPEXCTHLD {
  type enumeration {
   enum val-0;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
  }
  mandatory false;
 }
 leaf TM8PAIRINGOPTSWITCH {
  type boolean;
  mandatory false;
 }
 leaf TURBOBFWBBAVGUECOUNTTHLD {
  type uint16 {
   range "8..1200";
  }
  mandatory false;
 }
 leaf UEIDENTIFICATIONSWITCH {
  type string;
  mandatory false;
 }
 leaf WAITPAIRINGLAYERTHD {
  type uint16 {
   range "0..640";
  }
  mandatory false;
 }
 }
 grouping CELLBFMIMOPARACFG-attributes {
 leaf LOCALCELLNAME {
  type string;
  mandatory false;
 }
 leaf ANTBASEDBFMIMOALGOSELECT {
  type enumeration {
   enum val-0;
   enum val-1;
   enum val-2;
  }
  mandatory false;
 }
 leaf ASUEBFSINGLETODUALOFFSET {
  type int8 {
   range "-70..50";
  }
  mandatory false;
 }
 leaf ASUEDUALBFTOTM3RANK2OFFSET {
  type int8 {
   range "-70..50";
  }
  mandatory false;
 }
 leaf ASUETM3RANK2TODUALBFOFFSET {
  type int8 {
   range "-70..50";
  }
  mandatory false;
 }
 leaf BFMIMOADAPWITHTM4SWITCH {
  type boolean;
  mandatory false;
 }
 leaf BFMIMOADAPWITHOUTTM2 {
  type boolean;
  mandatory false;
 }
 leaf BFMIMOADAPTIVESWITCH {
  type enumeration {
   enum val-0;
   enum val-1;
   enum val-2;
  }
  mandatory false;
 }
 leaf BFMIMOALGOOPTSWITCH {
  type string;
  mandatory false;
 }
 leaf BFMIMOTHLDADAPTPERIOD {
  type uint8 {
   range "1..255";
  }
  mandatory false;
 }
 leaf BFSINGLETODUALTHDOFFSET {
  type int16 {
   range "-337..345";
  }
  mandatory false;
 }
 leaf BFTO2LAYERMUBFTHDOFFSET {
  type int16 {
   range "-500..500";
  }
  mandatory false;
 }
 leaf BFTO4LAYERMUBFTHDOFFSET {
  type int16 {
   range "-500..500";
  }
  mandatory false;
 }
 leaf CASCCADDTHLDOFFSET {
  type int8 {
   range "-120..120";
  }
  mandatory false;
 }
 leaf CASCCDELTHLDOFFSET {
  type int8 {
   range "-120..120";
  }
  mandatory false;
 }
 leaf CATM9RANK8HIGHSPCTEFFTHLD {
  type uint16 {
   range "0..400";
  }
  mandatory false;
 }
 leaf CATM9RANK8LOWSPCTEFFTHLD {
  type uint16 {
   range "0..400";
  }
  mandatory false;
 }
 leaf DUALBFTOTM3RANK2OFFSET {
  type int8 {
   range "-70..50";
  }
  mandatory false;
 }
 leaf FIXEDBFMIMOMODE {
  type enumeration {
   enum val-0;
   enum val-1;
   enum val-2;
   enum val-3;
   enum val-4;
   enum val-5;
   enum val-6;
  }
  mandatory false;
 }
 leaf HEAVYLOADAVGUECOUNTTHLD {
  type uint16 {
   range "0..65535";
  }
  mandatory false;
 }
 leaf HEAVYLOADDLPRBUSAGETHLD {
  type uint8 {
   range "0..100";
  }
  mandatory false;
 }
 leaf HEAVYLOADTARGETTRANSMODE {
  type boolean;
  mandatory false;
 }
 leaf HEAVYLOADTRANSMODEEVALPRD {
  type uint8 {
   range "1..30";
  }
  mandatory false;
 }
 leaf HIGHLOWSPEEDUETHDOFFSET {
  type uint8 {
   range "0..70";
  }
  mandatory false;
 }
 leaf HOBFTHDADJSWITCH {
  type boolean;
  mandatory false;
 }
 leaf INITIALBFMIMOTYPE {
  type boolean;
  mandatory false;
 }
 leaf LOCALCELLID {
  type union {
   type int16 {
    range "-1..255";
   }
  }
  mandatory false;
 }
 leaf MULTILAYERPAIRISOTHD {
  type uint16 {
   range "0..999";
  }
  mandatory false;
 }
 leaf OFFSETOFINSTAT {
  type int16 {
   range "-128..128";
  }
  mandatory false;
 }
 leaf OFFSETOFOUTSTAT {
  type int16 {
   range "-128..128";
  }
  mandatory false;
 }
 leaf SCCBFMIMOADAPTIVESWITCH {
  type boolean;
  mandatory false;
 }
 leaf TM3RANK2TODUALBFTHDOFFSET {
  type int8 {
   range "-70..50";
  }
  mandatory false;
 }
 leaf TM3ANDTM9THDOFFSET {
  type int8 {
   range "-30..50";
  }
  mandatory false;
 }
 leaf TM3DIRECTTODUALBFSWITCH {
  type boolean;
  mandatory false;
 }
 leaf TM3RANK2TOTM9RANK4OFFSET {
  type int8 {
   range "-120..120";
  }
  mandatory false;
 }
 leaf TM3TOTM9SWTGSEFFOFS256QAM {
  type int8 {
   range "-120..120";
  }
  mandatory false;
 }
 leaf TM9DL4LAYERMIMOENHSW {
  type string;
  mandatory false;
 }
 leaf TM9RANK4TOTM3RANK2OFFSET {
  type int8 {
   range "-120..120";
  }
  mandatory false;
 }
 leaf TM9TOTM3SWTGSEFFOFS256QAM {
  type int8 {
   range "-120..120";
  }
  mandatory false;
 }
 leaf TMACCELERATIONSWITCH {
  type enumeration {
   enum val-0;
   enum val-1;
   enum val-2;
  }
  mandatory false;
 }
 leaf UE4ROR8RBFMIMOADAPTOPTSW {
  type boolean;
  mandatory false;
 }
 leaf UEACCESSTMMODE {
  type boolean;
  mandatory false;
 }
 leaf VOLTEMIMOADAPTIVESWITCH {
  type boolean;
  mandatory false;
 }
 leaf WTTXUETM3TOTM9RANK4OFS {
  type union {
   type int8 {
    range "-120..127";
   }
  }
  mandatory false;
 }
 }
 grouping CELLCECFG-attributes {
 leaf LOCALCELLNAME {
  type string;
  mandatory false;
 }
 leaf COVERAGELEVEL {
  type enumeration {
   enum val-0;
   enum val-1;
   enum val-2;
   enum val-3;
  }
  mandatory false;
 }
 leaf LOCALCELLID {
  type union {
   type int16 {
    range "-1..255";
   }
  }
  mandatory false;
 }
 leaf RACHRSRPFSTTHD {
  type int16 {
   range "-141..-44";
  }
  mandatory false;
 }
 leaf RACHRSRPSNDTHD {
  type int16 {
   range "-141..-44";
  }
  mandatory false;
 }
 leaf RACHRSRPTRDTHD {
  type int16 {
   range "-141..-44";
  }
  mandatory false;
 }
 }
 grouping CELLCESCHCFG-attributes {
 leaf LOCALCELLNAME {
  type string;
  mandatory false;
 }
 leaf COVERAGELEVEL {
  type enumeration {
   enum val--1;
   enum val-0;
   enum val-1;
   enum val-2;
   enum val-3;
  }
  mandatory false;
 }
 leaf LOCALCELLID {
  type union {
   type int16 {
    range "-1..255";
   }
  }
  mandatory false;
 }
 leaf MPDCCHMAXNUMREPPAGING {
  type enumeration {
   enum val-0;
   enum val-1;
   enum val-2;
   enum val-3;
   enum val-4;
   enum val-5;
   enum val-6;
   enum val-7;
   enum val-8;
  }
  mandatory false;
 }
 leaf PAGINGGROUPNUM {
  type enumeration {
   enum val-0;
   enum val-1;
   enum val-2;
   enum val-3;
   enum val-4;
   enum val-5;
   enum val-6;
   enum val-7;
   enum val-8;
   enum val-9;
   enum val-10;
  }
  mandatory false;
 }
 leaf PDSCHMAXNUMREPMODEA {
  type enumeration {
   enum val-0;
   enum val-1;
   enum val-2;
  }
  mandatory false;
 }
 leaf PDSCHMAXNUMREPMODEB {
  type enumeration {
   enum val-0;
   enum val-1;
   enum val-2;
   enum val-3;
   enum val-4;
   enum val-5;
   enum val-6;
   enum val-7;
   enum val-8;
  }
  mandatory false;
 }
 leaf PUSCHMAXNUMREPMODEA {
  type enumeration {
   enum val-1;
   enum val-2;
   enum val-3;
  }
  mandatory false;
 }
 leaf PUSCHMAXNUMREPMODEB {
  type enumeration {
   enum val-0;
   enum val-1;
   enum val-2;
   enum val-3;
   enum val-4;
   enum val-5;
   enum val-6;
   enum val-7;
   enum val-8;
  }
  mandatory false;
 }
 leaf SIB1REPNUM {
  type enumeration {
   enum val-0;
   enum val-1;
   enum val-2;
  }
  mandatory false;
 }
 leaf SITRANSECR {
  type uint16 {
   range "17..1000";
  }
  mandatory false;
 }
 }
 grouping CELLCHPWRCFG-attributes {
 leaf LOCALCELLNAME {
  type string;
  mandatory false;
 }
 leaf ANTOUTPUTPWR {
  type uint8 {
   range "20..160";
  }
  mandatory false;
 }
 leaf DBCHPWR {
  type int16 {
   range "-3175..3175";
  }
  mandatory false;
 }
 leaf HORARPWRENHANCEDSWITCH {
  type boolean;
  mandatory false;
 }
 leaf LOCALCELLID {
  type union {
   type int16 {
    range "-1..255";
   }
  }
  mandatory false;
 }
 leaf OUTPUTPOWERRATE {
  type uint16 {
   range "0..1000";
  }
  mandatory false;
 }
 leaf PBCHPWR {
  type int16 {
   range "-3175..3175";
  }
  mandatory false;
 }
 leaf PCFICHPWR {
  type int16 {
   range "-3175..3175";
  }
  mandatory false;
 }
 leaf PCHPWR {
  type int16 {
   range "-3175..3175";
  }
  mandatory false;
 }
 leaf PDCCHPOWERINCREASEOFFSET {
  type uint8 {
   range "0..15";
  }
  mandatory false;
 }
 leaf PMCHPWROFFSET {
  type union {
   type uint8 {
    range "0..255";
   }
  }
  mandatory false;
 }
 leaf PRSPWR {
  type int16 {
   range "-3175..3175";
  }
  mandatory false;
 }
 leaf PWRASSISTANCESWITCH {
  type string;
  mandatory false;
 }
 leaf PWRCHECKSWITCH {
  type string;
  mandatory false;
 }
 leaf RARSPPWR {
  type int16 {
   range "-3175..3175";
  }
  mandatory false;
 }
 leaf SCHPWR {
  type int16 {
   range "-3175..3175";
  }
  mandatory false;
 }
 leaf TCCHPWROFFSET {
  type int16 {
   range "-3175..3175";
  }
  mandatory false;
 }
 leaf TPCCHPWROFFSET {
  type int16 {
   range "-3175..3175";
  }
  mandatory false;
 }
 leaf TTCHPWROFFSET {
  type int16 {
   range "-3175..3175";
  }
  mandatory false;
 }
 }
 grouping CELLCOUNTERPARAGROUP-attributes {
 leaf LOCALCELLNAME {
  type string;
  mandatory false;
 }
 leaf CELLCOUNTERALGOSWITCH {
  type string;
  mandatory false;
 }
 leaf CELLUSERNUMPDFTHD {
  type uint16 {
   range "0..10800";
  }
  mandatory false;
 }
 leaf CHROUTPUTMODESWITCH {
  type string;
  mandatory false;
 }
 leaf COVERAGEEDGEUSERULPLTHLD {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf DLPKTDELAYMEASPOLICY {
  type enumeration {
   enum val-0;
   enum val-1;
   enum val-2;
  }
  mandatory false;
 }
 leaf DLRMVLASTTTITIMETHLD {
  type uint32 {
   range "0..1000000";
  }
  mandatory false;
 }
 leaf DLRMVLASTTTITRAFFICTHLD {
  type uint32 {
   range "0..1000000";
  }
  mandatory false;
 }
 leaf DLRSRPDSTRCOUNTERTHLD0 {
  type int16 {
   range "-140..-43";
  }
  mandatory false;
 }
 leaf DLRSRPDSTRCOUNTERTHLD1 {
  type int16 {
   range "-140..-43";
  }
  mandatory false;
 }
 leaf DLRSRPDSTRCOUNTERTHLD2 {
  type int16 {
   range "-140..-43";
  }
  mandatory false;
 }
 leaf DLRSRPDSTRCOUNTERTHLD3 {
  type int16 {
   range "-140..-43";
  }
  mandatory false;
 }
 leaf DLTHRPPDFTHD0 {
  type uint32 {
   range "1..1000000";
  }
  mandatory false;
 }
 leaf DLTHRPPDFTHD1 {
  type uint32 {
   range "1..1000000";
  }
  mandatory false;
 }
 leaf DLTHRPPDFTHD2 {
  type uint32 {
   range "1..1000000";
  }
  mandatory false;
 }
 leaf DLTHRPPDFTHD3 {
  type uint32 {
   range "1..1000000";
  }
  mandatory false;
 }
 leaf DLTHRPPDFTHD4 {
  type uint32 {
   range "1..1000000";
  }
  mandatory false;
 }
 leaf DLTHRPPDFTHD5 {
  type uint32 {
   range "1..1000000";
  }
  mandatory false;
 }
 leaf DLTHRPPDFTHD6 {
  type uint32 {
   range "1..1000000";
  }
  mandatory false;
 }
 leaf DLTHRPPDFTHD7 {
  type uint32 {
   range "1..1000000";
  }
  mandatory false;
 }
 leaf DLTHRPPDFTHD8 {
  type uint32 {
   range "1..1000000";
  }
  mandatory false;
 }
 leaf DLTRAFFICVOLUMETHD {
  type uint16 {
   range "0..50000";
  }
  mandatory false;
 }
 leaf DLUSERXPUNSATITHD {
  type uint16 {
   range "0..50000";
  }
  mandatory false;
 }
 leaf DOWNLINKHIGHAMBRTHLD {
  type uint8 {
   range "0..255";
  }
  mandatory false;
 }
 leaf EDGEUSERA3OFFSET {
  type int8 {
   range "-30..30";
  }
  mandatory false;
 }
 leaf EDGEUSERSRSOFFSET {
  type int8 {
   range "-30..30";
  }
  mandatory false;
 }
 leaf EDGEUSERSERVRSRPTHD {
  type union {
   type int16 {
    range "-140..255";
   }
  }
  mandatory false;
 }
 leaf LOCALCELLID {
  type union {
   type int16 {
    range "-1..255";
   }
  }
  mandatory false;
 }
 leaf MTTTRAFFICRATIOTHLD {
  type uint8 {
   range "1..100";
  }
  mandatory false;
 }
 leaf QCI1CONTINUOUSPKTLOSSTHLD {
  type uint16 {
   range "3..1024";
  }
  mandatory false;
 }
 leaf QCILEVELTHPTMEASPOLICY {
  type enumeration {
   enum val-0;
   enum val-1;
   enum val-2;
  }
  mandatory false;
 }
 leaf THRPDFPOLICY {
  type enumeration {
   enum val-0;
   enum val-1;
   enum val-2;
  }
  mandatory false;
 }
 leaf UEABNORMALJUDGETHD {
  type uint8 {
   range "0..100";
  }
  mandatory false;
 }
 leaf ULIBLEROPTSWITCH {
  type boolean;
  mandatory false;
 }
 leaf ULINTRFSTATCONFIG {
  type uint8 {
   range "0..15";
  }
  mandatory false;
 }
 leaf ULRMVSMALLPKTTIMETHLD {
  type uint32 {
   range "0..1000000";
  }
  mandatory false;
 }
 leaf ULRMVSMALLPKTTRAFFICTHLD {
  type uint32 {
   range "0..1000000";
  }
  mandatory false;
 }
 leaf ULTHPTPDFPOLICY {
  type boolean;
  mandatory false;
 }
 leaf ULTHRPPDFTHD0 {
  type uint32 {
   range "1..1000000";
  }
  mandatory false;
 }
 leaf ULTHRPPDFTHD1 {
  type uint32 {
   range "1..1000000";
  }
  mandatory false;
 }
 leaf ULTHRPPDFTHD2 {
  type uint32 {
   range "1..1000000";
  }
  mandatory false;
 }
 leaf ULTHRPPDFTHD3 {
  type uint32 {
   range "1..1000000";
  }
  mandatory false;
 }
 leaf ULTHRPPDFTHD4 {
  type uint32 {
   range "1..1000000";
  }
  mandatory false;
 }
 leaf ULTHRPPDFTHD5 {
  type uint32 {
   range "1..1000000";
  }
  mandatory false;
 }
 leaf ULTHRPPDFTHD6 {
  type uint32 {
   range "1..1000000";
  }
  mandatory false;
 }
 leaf ULTHRPPDFTHD7 {
  type uint32 {
   range "1..1000000";
  }
  mandatory false;
 }
 leaf ULTHRPPDFTHD8 {
  type uint32 {
   range "1..1000000";
  }
  mandatory false;
 }
 }
 grouping CELLCQIADAPTIVECFG-attributes {
 leaf LOCALCELLNAME {
  type string;
  mandatory false;
 }
 leaf CELLCQIALGOSWITCH {
  type string;
  mandatory false;
 }
 leaf CQIPERIODADAPTIVE {
  type boolean;
  mandatory false;
 }
 leaf HOAPERIODICCQICFGSWITCH {
  type boolean;
  mandatory false;
 }
 leaf LOCALCELLID {
  type union {
   type int16 {
    range "-1..255";
   }
  }
  mandatory false;
 }
 leaf MINCQIPERIOD {
  type enumeration {
   enum val-0;
   enum val-1;
   enum val-2;
   enum val-3;
  }
  mandatory false;
 }
 leaf SCCCQIRPTENHANCEDSWITCH {
  type boolean;
  mandatory false;
 }
 leaf SIMULACKNACKANDCQISWITCH {
  type boolean;
  mandatory false;
 }
 leaf USERCQIPERIOD {
  type enumeration {
   enum val-2;
   enum val-5;
   enum val-10;
   enum val-20;
   enum val-40;
   enum val-80;
   enum val-160;
  }
  mandatory false;
 }
 }
 grouping CELLCQIADJALGO-attributes {
 leaf LOCALCELLNAME {
  type string;
  mandatory false;
 }
 leaf CELLCQIADJSCHCNTTHLD {
  type uint16 {
   range "0..1000";
  }
  mandatory false;
 }
 leaf CELLDELTACQISAMPSELTHD {
  type uint16 {
   range "0..400";
  }
  mandatory false;
 }
 leaf CQIADJAMOUNTVALIDDURTHLD {
  type uint8 {
   range "0..5";
  }
  mandatory false;
 }
 leaf CQIADJSTEP {
  type uint16 {
   range "0..1000";
  }
  mandatory false;
 }
 leaf CQIFILTERCOEFFORMCS {
  type uint16 {
   range "0..1024";
  }
  mandatory false;
 }
 leaf CQIOPTSWITCH {
  type string;
  mandatory false;
 }
 leaf DLVOLTECQIADJOPTSW {
  type string;
  mandatory false;
 }
 leaf DLVOLTECQIADJPRBUSAGETHLD {
  type uint8 {
   range "0..100";
  }
  mandatory false;
 }
 leaf IBLERTARGETOFFSET {
  type union {
   type uint8 {
    range "0..255";
   }
  }
  mandatory false;
 }
 leaf INITDELTACQI {
  type int8 {
   range "-10..26";
  }
  mandatory false;
 }
 leaf INITDLIBLERTARGET {
  type uint8 {
   range "0..100";
  }
  mandatory false;
 }
 leaf LOCALCELLID {
  type union {
   type int16 {
    range "-1..255";
   }
  }
  mandatory false;
 }
 leaf MUBFPACKETTHLD {
  type uint16 {
   range "0..65535";
  }
  mandatory false;
 }
 leaf VOLTENACKDELTACQI {
  type uint16 {
   range "0..330";
  }
  mandatory false;
 }
 leaf VOLTERPTCQIDIFFLIMIT {
  type uint8 {
   range "0..26";
  }
  mandatory false;
 }
 }
 grouping CELLCSIRSPARACFG-attributes {
 leaf LOCALCELLNAME {
  type string;
  mandatory false;
 }
 leaf CSIRSADAPTBEAMCOUNT {
  type enumeration {
   enum val-0;
   enum val-1;
   enum val-2;
   enum val-3;
   enum val-4;
   enum val-5;
   enum val-6;
   enum val-7;
   enum val-8;
   enum val-9;
   enum val-10;
  }
  mandatory false;
 }
 leaf CSIRSCONFIGUSERNUMTH {
  type uint16 {
   range "1..1200";
  }
  mandatory false;
 }
 leaf CSIRSCONFIGUSERRATIOTH {
  type uint8 {
   range "0..100";
  }
  mandatory false;
 }
 leaf CSIRSPERIOD {
  type enumeration {
   enum val-0;
   enum val-1;
   enum val-2;
   enum val-3;
   enum val-4;
  }
  mandatory false;
 }
 leaf CSIRSPORTNUM {
  type boolean;
  mandatory false;
 }
 leaf CSIRSSETJUDGEHYSTIMER {
  type uint16 {
   range "1..3600";
  }
  mandatory false;
 }
 leaf CSIRSSETJUDGETIMER {
  type uint16 {
   range "1..3600";
  }
  mandatory false;
 }
 leaf CSIRSSWITCH {
  type enumeration {
   enum val-0;
   enum val-1;
   enum val-2;
  }
  mandatory false;
 }
 leaf CSIRSUNCONFIGUSERNUMTH {
  type uint16 {
   range "1..1200";
  }
  mandatory false;
 }
 leaf CSIRSUNCONFIGUSERRATIOTH {
  type uint8 {
   range "0..100";
  }
  mandatory false;
 }
 leaf LOCALCELLID {
  type union {
   type int16 {
    range "-1..255";
   }
  }
  mandatory false;
 }
 }
 grouping CELLCSPCPARA-attributes {
 leaf LOCALCELLNAME {
  type string;
  mandatory false;
 }
 leaf CELLCSPCSWITCH {
  type boolean;
  mandatory false;
 }
 leaf CELLECSPCSWITCH {
  type boolean;
  mandatory false;
 }
 leaf CSPCCQIFILTERCOEFF {
  type uint8 {
   range "0..100";
  }
  mandatory false;
 }
 leaf CSPCRAPIDRPTSWITCH {
  type boolean;
  mandatory false;
 }
 leaf CSPCUESRSCFGRPTPERIOD {
  type uint8 {
   range "1..60";
  }
  mandatory false;
 }
 leaf INTRAENBCSPCSW {
  type boolean;
  mandatory false;
 }
 leaf LOCALCELLID {
  type union {
   type int16 {
    range "-1..255";
   }
  }
  mandatory false;
 }
 leaf ULRSRPRPTPERIOD {
  type uint8 {
   range "1..50";
  }
  mandatory false;
 }
 leaf ECSPCA3OFFSET {
  type int8 {
   range "-30..30";
  }
  mandatory false;
 }
 leaf ECSPCPCADJRANGE {
  type string;
  mandatory false;
 }
 leaf ECSPCPCADJUENUMTH {
  type uint8 {
   range "0..100";
  }
  mandatory false;
 }
 }
 grouping CELLDACQCFG-attributes {
 leaf LOCALCELLNAME {
  type string;
  mandatory false;
 }
 leaf AMBRLIMITSCHUSERNUM {
  type uint16 {
   range "0..1200";
  }
  mandatory false;
 }
 leaf AMBRPROTECTSCHUSERNUM {
  type uint16 {
   range "0..1200";
  }
  mandatory false;
 }
 leaf DACQCONGMONDUR {
  type uint16 {
   range "1..1800";
  }
  mandatory false;
 }
 leaf DACQEXECUTIONDURATION {
  type uint16 {
   range "0..1800";
  }
  mandatory false;
 }
 leaf DLAMBRLIMITFIRSTRANK {
  type uint32 {
   range "1..4294967295";
  }
  mandatory false;
 }
 leaf DLAMBRLIMITSECRANK {
  type uint32 {
   range "1..4294967295";
  }
  mandatory false;
 }
 leaf DLAMBRLIMITTHIRDRANK {
  type uint32 {
   range "1..4294967295";
  }
  mandatory false;
 }
 leaf DLPRBUSAGEFIRSTRANK {
  type uint8 {
   range "0..100";
  }
  mandatory false;
 }
 leaf DLPRBUSAGESECRANK {
  type uint8 {
   range "0..100";
  }
  mandatory false;
 }
 leaf DLPRBUSAGETHIRDRANK {
  type uint8 {
   range "0..100";
  }
  mandatory false;
 }
 leaf LOCALCELLID {
  type union {
   type int16 {
    range "-1..255";
   }
  }
  mandatory false;
 }
 leaf MBBUEEXPRATEPCTTARGETTHLD {
  type uint8 {
   range "0..100";
  }
  mandatory false;
 }
 leaf MBBUEEXPRATETARGETTHLD {
  type uint8 {
   range "1..20";
  }
  mandatory false;
 }
 leaf ULAMBRLIMITFIRSTRANK {
  type uint32 {
   range "1..4294967295";
  }
  mandatory false;
 }
 leaf ULAMBRLIMITSECRANK {
  type uint32 {
   range "1..4294967295";
  }
  mandatory false;
 }
 leaf ULAMBRLIMITTHIRDRANK {
  type uint32 {
   range "1..4294967295";
  }
  mandatory false;
 }
 leaf ULPRBUSAGEFIRSTRANK {
  type uint8 {
   range "0..100";
  }
  mandatory false;
 }
 leaf ULPRBUSAGESECRANK {
  type uint8 {
   range "0..100";
  }
  mandatory false;
 }
 leaf ULPRBUSAGETHIRDRANK {
  type uint8 {
   range "0..100";
  }
  mandatory false;
 }
 }
 grouping CELLDLCOMPALGO-attributes {
 leaf LOCALCELLNAME {
  type string;
  mandatory false;
 }
 leaf DLCOMPA3OFFSET {
  type int8 {
   range "-30..30";
  }
  mandatory false;
 }
 leaf DLCOMPREPORTINTERVAL {
  type enumeration {
   enum val-0;
   enum val-1;
   enum val-2;
   enum val-3;
   enum val-4;
   enum val-5;
   enum val-6;
   enum val-7;
   enum val-8;
   enum val-9;
   enum val-10;
   enum val-11;
   enum val-12;
   enum val-225;
  }
  mandatory false;
 }
 leaf DLCOMPSCHPRIFACTOR {
  type uint16 {
   range "1..1000";
  }
  mandatory false;
 }
 leaf DPSCOCELLUSERRATIOTHD {
  type uint8 {
   range "0..100";
  }
  mandatory false;
 }
 leaf DPSLOADDIFFTHD {
  type uint8 {
   range "0..50";
  }
  mandatory false;
 }
 leaf DPSSERVINGCELLDLPRBTHD {
  type uint8 {
   range "0..100";
  }
  mandatory false;
 }
 leaf HETNETDPSCOCELLRSRPTHD {
  type int8 {
   range "-30..30";
  }
  mandatory false;
 }
 leaf HOMNETDPSCOCELLRSRPTHD {
  type int8 {
   range "-30..30";
  }
  mandatory false;
 }
 leaf JTCOCELLDLPRBTHD {
  type uint8 {
   range "0..100";
  }
  mandatory false;
 }
 leaf JTCOCELLRSRPTHD {
  type int8 {
   range "-30..30";
  }
  mandatory false;
 }
 leaf JTSERVINGCELLDLPRBTHD {
  type uint8 {
   range "0..100";
  }
  mandatory false;
 }
 leaf LOCALCELLID {
  type union {
   type int16 {
    range "-1..255";
   }
  }
  mandatory false;
 }
 }
 grouping CELLDLICIC-attributes {
 leaf LOCALCELLNAME {
  type string;
  mandatory false;
 }
 leaf AICICPLUSA3OFFSET {
  type int8 {
   range "-30..30";
  }
  mandatory false;
 }
 leaf AICICPLUSPCADJRANGE {
  type string;
  mandatory false;
 }
 leaf BANDMODE {
  type enumeration {
   enum val-0;
   enum val-1;
   enum val-2;
   enum val-255;
  }
  mandatory false;
 }
 leaf DLICICNOISEUSERRSRPTHD {
  type uint8 {
   range "0..97";
  }
  mandatory false;
 }
 leaf DLICICUSERATTRGFACTORTHD {
  type int8 {
   range "-5..15";
  }
  mandatory false;
 }
 leaf LOCALCELLID {
  type union {
   type int16 {
    range "-1..255";
   }
  }
  mandatory false;
 }
 }
 grouping CELLDLPCPDCCH-attributes {
 leaf LOCALCELLNAME {
  type string;
  mandatory false;
 }
 leaf DEDIDCIPWROFFSET {
  type int16 {
   range "-150..150";
  }
  mandatory false;
 }
 leaf LOCALCELLID {
  type union {
   type int16 {
    range "-1..255";
   }
  }
  mandatory false;
 }
 leaf PAGINGDCIPWROFFSET {
  type union {
   type int16 {
    range "-30..255";
   }
  }
  mandatory false;
 }
 }
 grouping CELLDLPCPDSCH-attributes {
 leaf LOCALCELLNAME {
  type string;
  mandatory false;
 }
 leaf BFUSERADPTPWRA3OFFSET {
  type int8 {
   range "-30..30";
  }
  mandatory false;
 }
 leaf BFUSERADPTPWRA6OFFSET {
  type int8 {
   range "-30..30";
  }
  mandatory false;
 }
 leaf BFUSERPWRBOOSTPRD {
  type uint16 {
   range "5..3600";
  }
  mandatory false;
 }
 leaf CCUPA {
  type enumeration {
   enum val-0;
   enum val-1;
   enum val-2;
   enum val-3;
   enum val-4;
   enum val-5;
   enum val-6;
   enum val-7;
  }
  mandatory false;
 }
 leaf CELLEDGLOADEVALPRD {
  type uint16 {
   range "900..3600";
  }
  mandatory false;
 }
 leaf CEUPA {
  type enumeration {
   enum val-0;
   enum val-1;
   enum val-2;
   enum val-3;
   enum val-4;
   enum val-5;
   enum val-6;
   enum val-7;
  }
  mandatory false;
 }
 leaf EXCEEDNCELLEDGLOADTHDRATIO {
  type uint8 {
   range "1..100";
  }
  mandatory false;
 }
 leaf LOCALCELLID {
  type union {
   type int16 {
    range "-1..255";
   }
  }
  mandatory false;
 }
 leaf NEIGHCELLEDGLOADTHD {
  type uint8 {
   range "1..100";
  }
  mandatory false;
 }
 leaf REMAININGPWRUSESTRATEGY {
  type boolean;
  mandatory false;
 }
 }
 grouping CELLDLPCPDSCHPA-attributes {
 leaf LOCALCELLNAME {
  type string;
  mandatory false;
 }
 leaf CELLNPREOADJTHRESHOLD {
  type union {
   type uint8 {
    range "0..255";
   }
  }
  mandatory false;
 }
 leaf EPREOFFSETADJUSTMENTTHLD {
  type union {
   type uint8 {
    range "0..255";
   }
  }
  mandatory false;
 }
 leaf LOCALCELLID {
  type union {
   type int16 {
    range "-1..255";
   }
  }
  mandatory false;
 }
 leaf NOMPDSCHRSEPREOFFSET {
  type int8 {
   range "-1..6";
  }
  mandatory false;
 }
 leaf PAPCOFF {
  type enumeration {
   enum val-0;
   enum val-1;
   enum val-2;
   enum val-3;
   enum val-4;
   enum val-5;
   enum val-6;
   enum val-7;
  }
  mandatory false;
 }
 leaf TM9RANKCORRECTTHLD {
  type union {
   type uint8 {
    range "0..255";
   }
  }
  mandatory false;
 }
 leaf TM3TM4RANKCORRECTTHLD {
  type union {
   type uint8 {
    range "0..255";
   }
  }
  mandatory false;
 }
 leaf UENPREOADJOPTSWITCH {
  type string;
  mandatory false;
 }
 leaf UENPREOADJTHRESHOLD {
  type union {
   type int8 {
    range "-2..127";
   }
  }
  mandatory false;
 }
 leaf UENPREOADJUPPERLIMIT {
  type int8 {
   range "-1..6";
  }
  mandatory false;
 }
 leaf UENPREOADJUSTSWITCH {
  type string;
  mandatory false;
 }
 }
 grouping CELLDLPCPHICH-attributes {
 leaf LOCALCELLNAME {
  type string;
  mandatory false;
 }
 leaf LOCALCELLID {
  type union {
   type int16 {
    range "-1..255";
   }
  }
  mandatory false;
 }
 leaf PWROFFSET {
  type int16 {
   range "-150..150";
  }
  mandatory false;
 }
 }
 grouping CELLDLSCHALGO-attributes {
 leaf LOCALCELLNAME {
  type string;
  mandatory false;
 }
 leaf ADAPTPILOTOFFPRBTHLD {
  type uint8 {
   range "0..20";
  }
  mandatory false;
 }
 leaf AMBRCTRLTCYCLE {
  type enumeration {
   enum val-0;
   enum val-1;
   enum val-2;
   enum val-3;
   enum val-4;
  }
  mandatory false;
 }
 leaf APERIODICCSIREPORTMAXNUM {
  type uint16 {
   range "0..10000";
  }
  mandatory false;
 }
 leaf AVGPKTARRIVALINTVLTHLD {
  type uint16 {
   range "0..300";
  }
  mandatory false;
 }
 leaf BPUEODALIGNTHD {
  type uint8 {
   range "0..30";
  }
  mandatory false;
 }
 leaf BREATHINGPILOTALGOSWITCH {
  type string;
  mandatory false;
 }
 leaf CASCCDOPMEAS {
  type boolean;
  mandatory false;
 }
 leaf CASCHSTRATEGY {
  type boolean;
  mandatory false;
 }
 leaf CASCHWEIGHT {
  type uint8 {
   range "0..10";
  }
  mandatory false;
 }
 leaf CBTCDLSCHEDULINGMCSUPLIMIT {
  type uint8 {
   range "1..28";
  }
  mandatory false;
 }
 leaf CONGESTMAXVIDEORATE {
  type uint32 {
   range "0..4294967295";
  }
  mandatory false;
 }
 leaf CQIADJINITIALSTEP {
  type uint16 {
   range "0..1000";
  }
  mandatory false;
 }
 leaf CQIONLYOUTERLOOPSWITCH {
  type boolean;
  mandatory false;
 }
 leaf CRSCOMPENSATEPERIOD {
  type uint16 {
   range "0..1000";
  }
  mandatory false;
 }
 leaf CRSDYNMUTINGSYMBOLNUM {
  type uint8 {
   range "0..3";
  }
  mandatory false;
 }
 leaf CRSFULLBWPOSTODTTINUM {
  type uint16 {
   range "0..2560";
  }
  mandatory false;
 }
 leaf CRSFULLBWPREODTTINUM {
  type uint16 {
   range "0..2560";
  }
  mandatory false;
 }
 leaf CRSFULLBWPRESIBPAGINGTTINUM {
  type uint8 {
   range "0..3";
  }
  mandatory false;
 }
 leaf CSIRSSFSCHSTRSWITCH {
  type string;
  mandatory false;
 }
 leaf DATASPLITCCEUSAGEHIGHTHLD {
  type uint8 {
   range "0..100";
  }
  mandatory false;
 }
 leaf DATASPLITCCEUSAGELOWTHLD {
  type uint8 {
   range "0..100";
  }
  mandatory false;
 }
 leaf DATATHDINPDCCHPDSCHBAL {
  type uint32 {
   range "0..1000000";
  }
  mandatory false;
 }
 leaf DL256QAMCQITBLADPPERIOD {
  type uint16 {
   range "1..1000";
  }
  mandatory false;
 }
 leaf DL256QAMCQITBLCFGSTRATEGY {
  type enumeration {
   enum val-0;
   enum val-1;
   enum val-2;
  }
  mandatory false;
 }
 leaf DL2DFSSUSERDATAVOLTHLD {
  type uint16 {
   range "0..10000";
  }
  mandatory false;
 }
 leaf DLAFCMAXFREQ {
  type uint16 {
   range "0..1000";
  }
  mandatory false;
 }
 leaf DLCAUECAPALLOCSTRATEGY {
  type boolean;
  mandatory false;
 }
 leaf DLCAUSERSCHSWITCH {
  type string;
  mandatory false;
 }
 leaf DLCANDPAIRUECNTTHLD {
  type uint16 {
   range "0..300";
  }
  mandatory false;
 }
 leaf DLENHMUCELLAVGCQITHD {
  type uint8 {
   range "0..150";
  }
  mandatory false;
 }
 leaf DLENHMUONOFFTIMER {
  type uint32 {
   range "60..86400";
  }
  mandatory false;
 }
 leaf DLENHANCEDVOIPSCHSW {
  type inet:ip-address;
  mandatory false;
 }
 leaf DLEPFCAPACITYFACTOR {
  type enumeration {
   enum val-0;
   enum val-1;
   enum val-2;
   enum val-3;
   enum val-4;
   enum val-5;
  }
  mandatory false;
 }
 leaf DLFIRSTHARQTXTBSINCNUM {
  type uint8 {
   range "0..4";
  }
  mandatory false;
 }
 leaf DLFIRSTRETRANSRBRATIO {
  type uint8 {
   range "1..100";
  }
  mandatory false;
 }
 leaf DLHARQMAXTXNUM {
  type uint8 {
   range "1..6";
  }
  mandatory false;
 }
 leaf DLHIGHLOADSDMATHDOFFSET {
  type int8 {
   range "-25..25";
  }
  mandatory false;
 }
 leaf DLICICSCHMODE {
  type boolean;
  mandatory false;
 }
 leaf DLJOINTAMCALGOSW {
  type string;
  mandatory false;
 }
 leaf DLLOWLOADSDMATHDOFFSET {
  type int8 {
   range "-25..25";
  }
  mandatory false;
 }
 leaf DLMINEXPECTEDBITRATE {
  type union {
   type uint16 {
    range "0..65535";
   }
  }
  mandatory false;
 }
 leaf DLRANKDETECTSWITCH {
  type string;
  mandatory false;
 }
 leaf DLRANKOPTIMIZESWITCH {
  type boolean;
  mandatory false;
 }
 leaf DLSCHABNUETHD {
  type uint8 {
   range "6..120";
  }
  mandatory false;
 }
 leaf DLSCHPRIINCREASEUEPROP {
  type uint8 {
   range "0..100";
  }
  mandatory false;
 }
 leaf DLSPSINTERVAL {
  type enumeration {
   enum val-0;
   enum val-1;
   enum val-2;
  }
  mandatory false;
 }
 leaf DLSPSMCSDECREASEIBLERTHD {
  type uint8 {
   range "1..99";
  }
  mandatory false;
 }
 leaf DLUSERDATATHLD {
  type uint16 {
   range "0..10000";
  }
  mandatory false;
 }
 leaf DLSCHSTRATEGY {
  type enumeration {
   enum val-0;
   enum val-1;
   enum val-2;
   enum val-3;
  }
  mandatory false;
 }
 leaf EDGEBEAMTHLD {
  type uint8 {
   range "1..255";
  }
  mandatory false;
 }
 leaf EMIMOCELLRBRATIO {
  type uint8 {
   range "0..100";
  }
  mandatory false;
 }
 leaf EMIMOINDEPENDENTSCHTHD {
  type uint8 {
   range "0..40";
  }
  mandatory false;
 }
 leaf EMIMOJOINTINDEPTHDOFFSET {
  type uint8 {
   range "0..10";
  }
  mandatory false;
 }
 leaf EMIMOJOINTSCHTHD {
  type uint8 {
   range "0..40";
  }
  mandatory false;
 }
 leaf ENAPERIODICCQITRIGSTRATEGY {
  type boolean;
  mandatory false;
 }
 leaf ENBINTERFRANDMOD {
  type enumeration {
   enum val-0;
   enum val-1;
   enum val-2;
  }
  mandatory false;
 }
 leaf EPFENHANCEDSCHOPTSWITCH {
  type boolean;
  mandatory false;
 }
 leaf EPFSCHENHPRBUSAGETHLD {
  type uint8 {
   range "20..80";
  }
  mandatory false;
 }
 leaf ESTIMATEDDLMUGAINTHLD {
  type uint8 {
   range "0..100";
  }
  mandatory false;
 }
 leaf FDUEENHAPERCQITRIGPERIOD {
  type enumeration {
   enum val-0;
   enum val-1;
   enum val-2;
   enum val-3;
   enum val-4;
   enum val-5;
   enum val-6;
  }
  mandatory false;
 }
 leaf FSUEAPERCQITRIGPERIOD {
  type uint8 {
   range "1..100";
  }
  mandatory false;
 }
 leaf FSUESBCQIVALIDITYPERIOD {
  type uint8 {
   range "1..100";
  }
  mandatory false;
 }
 leaf FREEUSERDLRBUSEDRATIO {
  type uint8 {
   range "0..100";
  }
  mandatory false;
 }
 leaf FREQSELJUDGEPERIOD {
  type uint8 {
   range "1..10";
  }
  mandatory false;
 }
 leaf HIGHIBLERTARGETTBSIDXTHLD {
  type uint8 {
   range "0..33";
  }
  mandatory false;
 }
 leaf HOSTATICMCSTIMER {
  type uint8 {
   range "0..100";
  }
  mandatory false;
 }
 leaf IBLERPDCCHSINROFFSET {
  type uint8 {
   range "0..100";
  }
  mandatory false;
 }
 leaf INDEPENDENTBEAMPMITHLD {
  type union {
   type uint8 {
    range "0..255";
   }
  }
  mandatory false;
 }
 leaf INTERPOLERRUIDTHLD {
  type uint8 {
   range "0..100";
  }
  mandatory false;
 }
 leaf INTERFRANDPCIOFFSET {
  type uint8 {
   range "0..5";
  }
  mandatory false;
 }
 leaf INTRAPOLERRUIDPERIOD {
  type uint8 {
   range "0..30";
  }
  mandatory false;
 }
 leaf INTRAPOLERRUIDDURATION {
  type uint8 {
   range "0..168";
  }
  mandatory false;
 }
 leaf INTRFFILTERCOEFF {
  type uint8 {
   range "0..100";
  }
  mandatory false;
 }
 leaf LBTNIHIGHTHRESHOLD {
  type int16 {
   range "-1200..400";
  }
  mandatory false;
 }
 leaf LBTNILOWTHRESHOLD {
  type int16 {
   range "-1200..400";
  }
  mandatory false;
 }
 leaf LBTSWITCH {
  type boolean;
  mandatory false;
 }
 leaf LOCALCELLID {
  type union {
   type int16 {
    range "-1..255";
   }
  }
  mandatory false;
 }
 leaf LOWIBLERTARGETTBSIDXTHLD {
  type union {
   type uint8 {
    range "0..255";
   }
  }
  mandatory false;
 }
 leaf MAXMIMORANKPARA {
  type enumeration {
   enum val-0;
   enum val-1;
   enum val-2;
   enum val-3;
  }
  mandatory false;
 }
 leaf MBSFNSFCFG {
  type string;
  mandatory false;
 }
 leaf MCCSCQIPERIODTHLD {
  type enumeration {
   enum val-0;
   enum val-1;
   enum val-2;
   enum val-3;
  }
  mandatory false;
 }
 leaf MCCSPRBRATETHLD {
  type uint8 {
   range "0..100";
  }
  mandatory false;
 }
 leaf MCGHIGHLOADTHRESHOLD {
  type uint8 {
   range "0..100";
  }
  mandatory false;
 }
 leaf MIDUSERMCSTHRESHOLD {
  type uint8 {
   range "0..28";
  }
  mandatory false;
 }
 leaf MULTICARRIERCOSCHALGOSW {
  type string;
  mandatory false;
 }
 leaf NBDLHARQMAXTXCOUNT {
  type uint8 {
   range "1..8";
  }
  mandatory false;
 }
 leaf NGBRRUIDTHLD {
  type uint8 {
   range "0..100";
  }
  mandatory false;
 }
 leaf NOSCHSTOPACQITHD {
  type uint8 {
   range "2..40";
  }
  mandatory false;
 }
 leaf NONGBRRESOURCERATIO {
  type uint8 {
   range "0..50";
  }
  mandatory false;
 }
 leaf NONGBRSCHDELAYWEIGHT {
  type uint8 {
   range "0..10";
  }
  mandatory false;
 }
 leaf OVERLAPRSRPISOLATIONTHD {
  type uint8 {
   range "0..200";
  }
  mandatory false;
 }
 leaf PDSCHCODERATEUPPERLIMIT {
  type uint16 {
   range "930..1200";
  }
  mandatory false;
 }
 leaf PDSCHMAXCODERATE {
  type enumeration {
   enum val-0;
   enum val-1;
   enum val-2;
  }
  mandatory false;
 }
 leaf PILOTOFFDRXPARAGROUPID {
  type union {
   type uint8 {
    range "0..255";
   }
  }
  mandatory false;
 }
 leaf PILOTOFFRATEINCREASESW {
  type enumeration {
   enum val-0;
   enum val-1;
   enum val-2;
   enum val-3;
   enum val-4;
  }
  mandatory false;
 }
 leaf PILOTOFFSTRATEGY {
  type string;
  mandatory false;
 }
 leaf POSNEGFORATIOTHD {
  type uint8 {
   range "60..100";
  }
  mandatory false;
 }
 leaf POSTPOPROTECTIONTTINUM {
  type uint8 {
   range "0..4";
  }
  mandatory false;
 }
 leaf PRBENABLETHLDVIDEORESCTRL {
  type uint8 {
   range "0..100";
  }
  mandatory false;
 }
 leaf PREPOPROTECTIONTTINUM {
  type uint8 {
   range "0..8";
  }
  mandatory false;
 }
 leaf RBDAMAGENEARPOINTIBLERTH {
  type uint16 {
   range "0..1000";
  }
  mandatory false;
 }
 leaf RBPRIMCSSELECTRATIOTHD {
  type uint8 {
   range "0..100";
  }
  mandatory false;
 }
 leaf RBPRIMCSSELECTSTRATEGY {
  type enumeration {
   enum val-0;
   enum val-1;
   enum val-2;
   enum val-3;
  }
  mandatory false;
 }
 leaf RANKCHANGEATTEMPTMCSTHLD {
  type uint8 {
   range "3..28";
  }
  mandatory false;
 }
 leaf RANKDETECTSUCCESSCNTTHD {
  type uint8 {
   range "1..100";
  }
  mandatory false;
 }
 leaf RANKREVERSEDETECTCNTTHD {
  type uint16 {
   range "0..2000";
  }
  mandatory false;
 }
 leaf RARANDPAGINGCR {
  type uint16 {
   range "10..930";
  }
  mandatory false;
 }
 leaf RBPRIMCSREDUCEPWRRBGTHLD {
  type uint8 {
   range "1..25";
  }
  mandatory false;
 }
 leaf RBPRIMCSSELECTMAXDECTBSIDX {
  type union {
   type uint8 {
    range "1..255";
   }
  }
  mandatory false;
 }
 leaf RBGALLOCSTRATEGY {
  type enumeration {
   enum val-0;
   enum val-1;
   enum val-2;
   enum val-3;
  }
  mandatory false;
 }
 leaf RLCMACJOINTSCHSW {
  type yang:mac-address;
  mandatory false;
 }
 leaf RRCSPLITSCHDELAYTHLD {
  type union {
   type uint8 {
    range "0..40";
   }
  }
  mandatory false;
 }
 leaf SFNDLHIGHLOADTHD {
  type uint8 {
   range "0..100";
  }
  mandatory false;
 }
 leaf SFNDLLOADPERIOD {
  type uint16 {
   range "2..1800";
  }
  mandatory false;
 }
 leaf SFNDLLOWLOADTHD {
  type uint8 {
   range "0..100";
  }
  mandatory false;
 }
 leaf SRB1SCHENHANCEMENTSWITCH {
  type boolean;
  mandatory false;
 }
 leaf SRSRSRPFILTERCOEFFORDLAFC {
  type uint16 {
   range "0..1024";
  }
  mandatory false;
 }
 leaf STARTRANKDETECTCNTTHD {
  type uint16 {
   range "0..2000";
  }
  mandatory false;
 }
 leaf STARTRANKDETECTEFFTHD {
  type uint16 {
   range "0..741";
  }
  mandatory false;
 }
 leaf STEADYTARGETRATERATIO {
  type uint8 {
   range "1..100";
  }
  mandatory false;
 }
 leaf TXDDCI1ASWITCH {
  type boolean;
  mandatory false;
 }
 leaf UEATTJUDGEPERIOD {
  type enumeration {
   enum val-0;
   enum val-1;
   enum val-2;
   enum val-3;
  }
  mandatory false;
 }
 leaf UEATTJUDGERSRPHYST {
  type uint8 {
   range "0..20";
  }
  mandatory false;
 }
 leaf UENUMTHDINPDCCHPDSCHBAL {
  type uint16 {
   range "0..10000";
  }
  mandatory false;
 }
 leaf USERENABLETHLDVIDEORESCTRL {
  type uint16 {
   range "0..10000";
  }
  mandatory false;
 }
 leaf USERFOTHDFORDLAFC {
  type uint16 {
   range "200..500";
  }
  mandatory false;
 }
 leaf USERSPEEDDLSCHPRIWEIGHT {
  type uint8 {
   range "1..10";
  }
  mandatory false;
 }
 leaf VOICEDLSPSRESERVEDRBRATIO {
  type uint8 {
   range "30..100";
  }
  mandatory false;
 }
 leaf ZONEUSERNUMRATIOTHD {
  type uint8 {
   range "0..6";
  }
  mandatory false;
 }
 }
 grouping CELLDLSCHEXTPARAM-attributes {
 leaf LOCALCELLNAME {
  type string;
  mandatory false;
 }
 leaf AHRSWITCH {
  type string;
  mandatory false;
 }
 leaf APERIODICCQITRIGUETYPE {
  type enumeration {
   enum val-0;
   enum val-1;
   enum val-2;
   enum val-3;
  }
  mandatory false;
 }
 leaf DLCADATASPLITFACTOR {
  type uint8 {
   range "0..100";
  }
  mandatory false;
 }
 leaf DLENTER256QAMCQITBLTBSTHLD {
  type uint8 {
   range "4..33";
  }
  mandatory false;
 }
 leaf DLEXIT256QAMCQITBLTBSTHLD {
  type uint8 {
   range "4..33";
  }
  mandatory false;
 }
 leaf DLHARQRETRANSTBSINCREASE {
  type uint8 {
   range "0..6";
  }
  mandatory false;
 }
 leaf DLHEAVYLOADOPTPRBTHLD {
  type union {
   type uint8 {
    range "0..100";
   }
  }
  mandatory false;
 }
 leaf DLHEAVYLOADPRBUSAGETHLD {
  type union {
   type uint8 {
    range "0..255";
   }
  }
  mandatory false;
 }
 leaf DLLOADEVALPRBUSAGETHLD {
  type union {
   type uint8 {
    range "50..255";
   }
  }
  mandatory false;
 }
 leaf DLMAXAMBRTOKEN {
  type uint16 {
   range "0..1000";
  }
  mandatory false;
 }
 leaf DLMINAMBRTOKEN {
  type uint16 {
   range "0..1000";
  }
  mandatory false;
 }
 leaf DLPCCRSPWRINCREASEAMT {
  type uint8 {
   range "0..30";
  }
  mandatory false;
 }
 leaf DLPCCRSPWRINCREASEMCSTHLD {
  type uint8 {
   range "0..28";
  }
  mandatory false;
 }
 leaf DLPCCRSPWRREDUCEAMT {
  type enumeration {
   enum val-0;
   enum val-1;
   enum val-2;
   enum val-3;
   enum val-4;
   enum val-5;
  }
  mandatory false;
 }
 leaf DLPCPWRREDUCEREQPRBTHLD {
  type uint8 {
   range "0..100";
  }
  mandatory false;
 }
 leaf DLPCREQPWRREDUCEPRBDIFFTHD {
  type uint8 {
   range "0..5";
  }
  mandatory false;
 }
 leaf DLPCWEAKCOVUENUMTHD {
  type uint8 {
   range "0..255";
  }
  mandatory false;
 }
 leaf DLSCHEXTSWITCH {
  type string;
  mandatory false;
 }
 leaf DLSLOTAWARESCHPRBTHLD {
  type union {
   type uint8 {
    range "0..100";
   }
  }
  mandatory false;
 }
 leaf FASTMOVEUENCELLISAMOUNT {
  type uint8 {
   range "0..10";
  }
  mandatory false;
 }
 leaf LOCALCELLID {
  type union {
   type int16 {
    range "-1..255";
   }
  }
  mandatory false;
 }
 leaf PCCLOADTHLD {
  type union {
   type uint8 {
    range "10..255";
   }
  }
  mandatory false;
 }
 leaf PCCSCCLOADRATIOTHLD {
  type uint8 {
   range "10..250";
  }
  mandatory false;
 }
 leaf PRECISERBALLOCTBSINDEXDEC {
  type union {
   type uint8 {
    range "1..255";
   }
  }
  mandatory false;
 }
 leaf SCCSCHSTOPRESIDBLKERRTHLD {
  type uint8 {
   range "0..10";
  }
  mandatory false;
 }
 leaf TIMECHNCORRTHLD {
  type union {
   type uint8 {
    range "0..100";
   }
  }
  mandatory false;
 }
 }
 grouping CELLDMRSCFG-attributes {
 leaf LOCALCELLNAME {
  type string;
  mandatory false;
 }
 leaf LOCALCELLID {
  type union {
   type int16 {
    range "-1..255";
   }
  }
  mandatory false;
 }
 leaf SIXTONEBASESEQ {
  type uint8 {
   range "0..13";
  }
  mandatory false;
 }
 leaf SIXTONECYCLICSHIFT {
  type uint8 {
   range "0..3";
  }
  mandatory false;
 }
 leaf THREETONEBASESEQ {
  type uint8 {
   range "0..11";
  }
  mandatory false;
 }
 leaf THREETONECYCLICSHIFT {
  type uint8 {
   range "0..2";
  }
  mandatory false;
 }
 leaf TWELVETONEBASESEQ {
  type uint8 {
   range "0..29";
  }
  mandatory false;
 }
 }
 grouping CELLDRXPARA-attributes {
 leaf LOCALCELLNAME {
  type string;
  mandatory false;
 }
 leaf CADRXOPTSWITCH {
  type string;
  mandatory false;
 }
 leaf COVGSMMEASDRXCFGSWITCH {
  type boolean;
  mandatory false;
 }
 leaf CQIMASK {
  type boolean;
  mandatory false;
 }
 leaf DATAAMOUNTSTATTIMER {
  type uint16 {
   range "2..300";
  }
  mandatory false;
 }
 leaf DRXALGSWITCH {
  type boolean;
  mandatory false;
 }
 leaf DRXALGOEXTSWITCH {
  type string;
  mandatory false;
 }
 leaf DRXFORMEASSWITCH {
  type boolean;
  mandatory false;
 }
 leaf DRXINACTTIMERFORMEAS {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
  }
  mandatory false;
 }
 leaf DRXINACTIVITYTIMERUNSYNC {
  type enumeration {
   enum val-0;
   enum val-1;
   enum val-2;
   enum val-3;
   enum val-4;
   enum val-5;
   enum val-6;
  }
  mandatory false;
 }
 leaf DRXODPRESCHSWITCH {
  type boolean;
  mandatory false;
 }
 leaf DRXPOLICYMODE {
  type enumeration {
   enum val-0;
   enum val-1;
   enum val-2;
  }
  mandatory false;
 }
 leaf DRXRCVDTXPROSWITCH {
  type boolean;
  mandatory false;
 }
 leaf DRXRETXTIMERFORMEAS {
  type enumeration {
   enum val-0;
   enum val-1;
   enum val-2;
   enum val-3;
   enum val-4;
   enum val-5;
   enum val-6;
   enum val-7;
  }
  mandatory false;
 }
 leaf DRXSRDETECTOPTSWITCH {
  type boolean;
  mandatory false;
 }
 leaf DRXSTARTOFFSETOPTSWITCH {
  type boolean;
  mandatory false;
 }
 leaf DRXSTATEDURINGULHARQRETX {
  type boolean;
  mandatory false;
 }
 leaf DRXSTOPSRPENDINGSW {
  type boolean;
  mandatory false;
 }
 leaf DRXUESRSOPTSWITCH {
  type string;
  mandatory false;
 }
 leaf FDDENTERDRXTHD {
  type uint16 {
   range "0..1000";
  }
  mandatory false;
 }
 leaf FDDEXITDRXTHD {
  type uint16 {
   range "1..1000";
  }
  mandatory false;
 }
 leaf GAPDRXEXCLUSIVESWITCH {
  type boolean;
  mandatory false;
 }
 leaf LOCALCELLID {
  type union {
   type int16 {
    range "-1..255";
   }
  }
  mandatory false;
 }
 leaf LONGDRXCYCLEFORMEAS {
  type enumeration {
   enum val-6;
   enum val-7;
   enum val-8;
   enum val-9;
   enum val-10;
   enum val-11;
   enum val-12;
   enum val-13;
   enum val-14;
   enum val-15;
  }
  mandatory false;
 }
 leaf LONGDRXCYCLEUNSYNC {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf MEASDRXSPECSCHSWITCH {
  type boolean;
  mandatory false;
 }
 leaf NBDRXINACTIVITYTIMER {
  type enumeration {
   enum val-0;
   enum val-1;
   enum val-2;
   enum val-3;
   enum val-4;
   enum val-5;
   enum val-6;
   enum val-7;
  }
  mandatory false;
 }
 leaf NBDRXRETXTIMER {
  type enumeration {
   enum val-0;
   enum val-1;
   enum val-2;
   enum val-3;
   enum val-4;
   enum val-5;
   enum val-6;
   enum val-7;
   enum val-8;
  }
  mandatory false;
 }
 leaf NBDRXULRETXTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
  }
  mandatory false;
 }
 leaf NBINTERFREQMEASDRXACTTIMER {
  type union {
   type uint8 {
    range "1..255";
   }
  }
  mandatory false;
 }
 leaf NBLONGDRXCYCLE {
  type enumeration {
   enum val-0;
   enum val-1;
   enum val-2;
   enum val-3;
   enum val-4;
   enum val-5;
   enum val-6;
   enum val-7;
   enum val-8;
   enum val-9;
   enum val-10;
   enum val-11;
  }
  mandatory false;
 }
 leaf NBONDURATIONTIMER {
  type enumeration {
   enum val-0;
   enum val-1;
   enum val-2;
   enum val-3;
   enum val-4;
   enum val-5;
   enum val-6;
  }
  mandatory false;
 }
 leaf ONDURTIMERFORMEAS {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf ONDURATIONUNEXTENDSWITCH {
  type boolean;
  mandatory false;
 }
 leaf ONDURATIONTIMERUNSYNC {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf SHORTCYCLETIMERFORMEAS {
  type uint8 {
   range "1..16";
  }
  mandatory false;
 }
 leaf SHORTDRXCYCLEFORMEAS {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf SHORTDRXCYCLESWITCH {
  type boolean;
  mandatory false;
 }
 leaf SHORTDRXSWFORMEAS {
  type boolean;
  mandatory false;
 }
 leaf SINRTHLDFORVOLTEDRXCTRL {
  type union {
   type int8 {
    range "-100..35";
   }
  }
  mandatory false;
 }
 leaf TDDENTERDRXTHDDL {
  type uint16 {
   range "0..1999";
  }
  mandatory false;
 }
 leaf TDDENTERDRXTHDUL {
  type uint16 {
   range "0..1999";
  }
  mandatory false;
 }
 leaf TDDEXITDRXTHDDL {
  type uint16 {
   range "1..2000";
  }
  mandatory false;
 }
 leaf TDDEXITDRXTHDUL {
  type uint16 {
   range "1..2000";
  }
  mandatory false;
 }
 leaf TDDPOWERSAVEMEASSWITCH {
  type boolean;
  mandatory false;
 }
 leaf TDDPOWERSAVESTATTIMER {
  type uint16 {
   range "2..300";
  }
  mandatory false;
 }
 leaf TDDPOWERSAVINGENTERDRXTHD {
  type uint16 {
   range "0..1999";
  }
  mandatory false;
 }
 leaf TDDPOWERSAVINGEXITDRXTHD {
  type uint16 {
   range "1..2000";
  }
  mandatory false;
 }
 leaf VOCDRXENTRYFORBIDLOADTHLD {
  type uint8 {
   range "0..100";
  }
  mandatory false;
 }
 leaf VOLTEGAPDRXEXCLUSIVESWITCH {
  type boolean;
  mandatory false;
 }
 leaf VOLTEPLRTHLDFOREXITINGDRX {
  type uint8 {
   range "0..99";
  }
  mandatory false;
 }
 }
 grouping CELLDRXSPECIALPARA-attributes {
 leaf LOCALCELLNAME {
  type string;
  mandatory false;
 }
 leaf BFSPECIFICDRXPARASWITCH {
  type boolean;
  mandatory false;
 }
 leaf DRXINACTIVITYTIMERSPECIAL {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
  }
  mandatory false;
 }
 leaf DRXSHORTCYCLETIMERSPECIAL {
  type uint8 {
   range "1..16";
  }
  mandatory false;
 }
 leaf FDDANRDRXINACTIVITYTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
  }
  mandatory false;
 }
 leaf LOCALCELLID {
  type union {
   type int16 {
    range "-1..255";
   }
  }
  mandatory false;
 }
 leaf LONGDRXCYCLEFORINTERRATANR {
  type enumeration {
   enum val-6;
   enum val-7;
   enum val-8;
   enum val-9;
   enum val-10;
   enum val-11;
   enum val-12;
   enum val-13;
   enum val-14;
   enum val-15;
  }
  mandatory false;
 }
 leaf LONGDRXCYCLEFORINTRARATANR {
  type enumeration {
   enum val-6;
   enum val-7;
   enum val-8;
   enum val-9;
   enum val-10;
   enum val-11;
   enum val-12;
   enum val-13;
   enum val-14;
   enum val-15;
  }
  mandatory false;
 }
 leaf LONGDRXCYCLESPECIAL {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf ONDURATIONTIMERSPECIAL {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf SHORTDRXCYCLESPECIAL {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf SHORTDRXCYCLESWITCHSPECIAL {
  type boolean;
  mandatory false;
 }
 leaf TDDANRDRXINACTIVITYTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
  }
  mandatory false;
 }
 }
 grouping CELLDSS-attributes {
 leaf LOCALCELLNAME {
  type string;
  mandatory false;
 }
 leaf A3OFFSET {
  type int8 {
   range "-30..30";
  }
  mandatory false;
 }
 leaf A6OFFSET {
  type int8 {
   range "-30..30";
  }
  mandatory false;
 }
 leaf FARAREASINRTHD {
  type uint8 {
   range "0..15";
  }
  mandatory false;
 }
 leaf GSMINTERFINTHD {
  type uint8 {
   range "0..50";
  }
  mandatory false;
 }
 leaf HIGHFREQSHARERBNUM {
  type uint8 {
   range "0..20";
  }
  mandatory false;
 }
 leaf LOCALCELLID {
  type union {
   type int16 {
    range "-1..255";
   }
  }
  mandatory false;
 }
 leaf LOWFREQSHARERBNUM {
  type uint8 {
   range "0..20";
  }
  mandatory false;
 }
 leaf MIDDLEAREASINRTHD {
  type uint8 {
   range "0..15";
  }
  mandatory false;
 }
 leaf NEARAREASINRTHD {
  type uint8 {
   range "0..15";
  }
  mandatory false;
 }
 leaf NEARPTUSERRSRPTHD {
  type int8 {
   range "-120..-40";
  }
  mandatory false;
 }
 leaf REMUTESWITCH {
  type boolean;
  mandatory false;
 }
 leaf SINRTHDWITHOUTGSMINTERF {
  type uint8 {
   range "0..80";
  }
  mandatory false;
 }
 leaf SPECSHRPFMOPTSWITCH {
  type string;
  mandatory false;
 }
 leaf ULINTERFRESTRICTIONMODE {
  type enumeration {
   enum val-0;
   enum val-1;
   enum val-2;
   enum val-3;
  }
  mandatory false;
 }
 }
 grouping CELLDYNACBARALGOPARA-attributes {
 leaf LOCALCELLNAME {
  type string;
  mandatory false;
 }
 leaf DISASTERDURATION {
  type uint16 {
   range "1..10080";
  }
  mandatory false;
 }
 leaf DISASTERREFERENCEIND {
  type string;
  mandatory false;
 }
 leaf DYNACBARCANCELTHD {
  type uint8 {
   range "0..100";
  }
  mandatory false;
 }
 leaf DYNACBAROPTSW {
  type string;
  mandatory false;
 }
 leaf DYNACBARSTATPERIOD {
  type uint8 {
   range "6..60";
  }
  mandatory false;
 }
 leaf DYNACBARTRIGGERTHD {
  type uint8 {
   range "0..100";
  }
  mandatory false;
 }
 leaf LOCALCELLID {
  type union {
   type int16 {
    range "-1..255";
   }
  }
  mandatory false;
 }
 leaf MOCANCELCONDSATIPERIODS {
  type uint16 {
   range "1..1000";
  }
  mandatory false;
 }
 leaf MOFACTORADJSTEP {
  type uint8 {
   range "1..15";
  }
  mandatory false;
 }
 leaf MOFACTORINITIALVALUE {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf MOFACTORMINVALUEFORCALL {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf MOFACTORMINVALUEFORSIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf MOFACTORRETREATSTEP {
  type uint8 {
   range "0..15";
  }
  mandatory false;
 }
 leaf MOSIGNALTOMODATAFACTOROFS {
  type uint8 {
   range "0..15";
  }
  mandatory false;
 }
 leaf MOTRIGGERCONDSATIPERIODS {
  type uint16 {
   range "1..1000";
  }
  mandatory false;
 }
 leaf RRCREJECTCONGTRIGGERTHLD {
  type uint8 {
   range "0..100";
  }
  mandatory false;
 }
 leaf SSACCANCELCONDSATIPERIODS {
  type uint16 {
   range "1..1000";
  }
  mandatory false;
 }
 leaf SSACFACTORADJSTEP {
  type uint8 {
   range "1..15";
  }
  mandatory false;
 }
 leaf SSACFACTORRETREATSTEP {
  type uint8 {
   range "0..15";
  }
  mandatory false;
 }
 leaf SSACTRIGGERCONDSATIPERIODS {
  type uint16 {
   range "1..1000";
  }
  mandatory false;
 }
 leaf UENUMCONGCLEARTHLD {
  type uint16 {
   range "0..2000";
  }
  mandatory false;
 }
 leaf UENUMCONGTHLD {
  type uint16 {
   range "0..2000";
  }
  mandatory false;
 }
 }
 grouping CELLDYNPOWERSHARING-attributes {
 leaf LOCALCELLNAME {
  type string;
  mandatory false;
 }
 leaf DYNAMICPOWERSHARINGSWITCH {
  type string;
  mandatory false;
 }
 leaf INTERFERENCECONTROLSWITCH {
  type boolean;
  mandatory false;
 }
 leaf LOCALCELLID {
  type union {
   type int16 {
    range "-1..255";
   }
  }
  mandatory false;
 }
 leaf MAXPOWERSHARINGRATE {
  type uint8 {
   range "1..50";
  }
  mandatory false;
 }
 leaf MULTIBANDPWRADAPTSCHPRI {
  type uint8 {
   range "0..7";
  }
  mandatory false;
 }
 leaf POWERADJUSTMENTMODE {
  type boolean;
  mandatory false;
 }
 leaf POWERREDUCTIONAMOUNT {
  type uint8 {
   range "0..3";
  }
  mandatory false;
 }
 leaf PWRINSUFFTIMERATETHLD {
  type uint8 {
   range "0..100";
  }
  mandatory false;
 }
 leaf PWRREDUCTIONDLPRBUSAGETHLD {
  type uint8 {
   range "0..100";
  }
  mandatory false;
 }
 }
 grouping CELLEABALGOPARA-attributes {
 leaf LOCALCELLNAME {
  type string;
  mandatory false;
 }
 leaf ABFOREXCEPTIONDATA {
  type boolean;
  mandatory false;
 }
 leaf ABFORSPECIALAC {
  type string;
  mandatory false;
 }
 leaf ACCOUNTFORMANUALBARRING {
  type union {
   type uint8 {
    range "1..255";
   }
  }
  mandatory false;
 }
 leaf ABDETECTPRDFORCL {
  type uint8 {
   range "1..30";
  }
  mandatory false;
 }
 leaf ABFORCOVERAGELEVELSW {
  type enumeration {
   enum val-0;
   enum val-1;
   enum val-2;
   enum val-3;
  }
  mandatory false;
 }
 leaf EABCANCELCONDSATIPERIOD {
  type uint8 {
   range "1..9";
  }
  mandatory false;
 }
 leaf EABCANCELTHD {
  type uint8 {
   range "0..100";
  }
  mandatory false;
 }
 leaf EABCATEGORY {
  type enumeration {
   enum val-0;
   enum val-1;
   enum val-2;
  }
  mandatory false;
 }
 leaf EABSTATPERIOD {
  type uint8 {
   range "10..60";
  }
  mandatory false;
 }
 leaf EABTRIGGERTHD {
  type uint8 {
   range "0..100";
  }
  mandatory false;
 }
 leaf LOCALCELLID {
  type union {
   type int16 {
    range "-1..255";
   }
  }
  mandatory false;
 }
 }
 grouping CELLEDTCONFIG-attributes {
 leaf LOCALCELLNAME {
  type string;
  mandatory false;
 }
 leaf EDTALGOSWITCH {
  type string;
  mandatory false;
 }
 leaf EDTDLDATAWAITINGTIMER {
  type uint8 {
   range "1..200";
  }
  mandatory false;
 }
 leaf EDTEARLYCONTENTIONRESMODE {
  type enumeration {
   enum val-0;
   enum val-1;
   enum val-2;
  }
  mandatory false;
 }
 leaf EDTMTSCHTONENUM {
  type enumeration {
   enum val-0;
   enum val-1;
   enum val-2;
   enum val-3;
  }
  mandatory false;
 }
 leaf EDTSCHSTRATEGY {
  type enumeration {
   enum val-0;
   enum val-1;
   enum val-2;
  }
  mandatory false;
 }
 leaf LOCALCELLID {
  type union {
   type int16 {
    range "-1..255";
   }
  }
  mandatory false;
 }
 leaf NUMBEROFEDTTBSTYPE {
  type enumeration {
   enum val-0;
   enum val-1;
   enum val-2;
  }
  mandatory false;
 }
 }
 grouping CELLEICIC-attributes {
 leaf LOCALCELLNAME {
  type string;
  mandatory false;
 }
 leaf A3OFFSET {
  type int8 {
   range "-30..30";
  }
  mandatory false;
 }
 leaf ABSADJPERIOD {
  type uint16 {
   range "1..300";
  }
  mandatory false;
 }
 leaf ABSPATTERN {
  type enumeration {
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
  }
  mandatory false;
 }
 leaf ATTACHCELLADDTHD {
  type uint8 {
   range "0..100";
  }
  mandatory false;
 }
 leaf CREADJPERIOD {
  type uint16 {
   range "3..1440";
  }
  mandatory false;
 }
 leaf EICICADAPTIVESWITCH {
  type boolean;
  mandatory false;
 }
 leaf EICICCONFIGUSERRATIOTHD {
  type uint8 {
   range "0..100";
  }
  mandatory false;
 }
 leaf EICICMEASUREENABLE {
  type boolean;
  mandatory false;
 }
 leaf EICICUNCONFIGUSERRATIOTHD {
  type uint8 {
   range "0..100";
  }
  mandatory false;
 }
 leaf HSHANDINUSERTHD {
  type uint16 {
   range "0..1000";
  }
  mandatory false;
 }
 leaf HIGHCOORCCETHD {
  type uint8 {
   range "0..100";
  }
  mandatory false;
 }
 leaf HIGHCOORDTXTHD {
  type uint8 {
   range "0..100";
  }
  mandatory false;
 }
 leaf HIGHSPEEDENHANCEDOPTSWITCH {
  type string;
  mandatory false;
 }
 leaf LARGECREMICRONUMTHD {
  type uint8 {
   range "1..8";
  }
  mandatory false;
 }
 leaf LOCALCELLID {
  type union {
   type int16 {
    range "-1..255";
   }
  }
  mandatory false;
 }
 leaf NAICNCELLSTATPERIOD {
  type uint16 {
   range "1..10080";
  }
  mandatory false;
 }
 leaf SAMPLENUMTARGET {
  type uint32 {
   range "1..1000000";
  }
  mandatory false;
 }
 leaf STATPERIOD {
  type uint16 {
   range "1..43200";
  }
  mandatory false;
 }
 leaf WORKMODE {
  type boolean;
  mandatory false;
 }
 }
 grouping CELLEMERGENCYAREA-attributes {
 leaf LOCALCELLNAME {
  type string;
  mandatory false;
 }
 leaf OLD_EMERGENCYAREAID {
  type union {
   type int32 {
    range "-1..16777215";
   }
  }
  mandatory false;
 }
 leaf EMERGENCYAREAID {
  type union {
   type int32 {
    range "-1..16777215";
   }
  }
  mandatory false;
 }
 leaf OLD_LOCALCELLID {
  type union {
   type int16 {
    range "-1..255";
   }
  }
  mandatory false;
 }
 leaf LOCALCELLID {
  type union {
   type int16 {
    range "-1..255";
   }
  }
  mandatory false;
 }
 }
 grouping CELLEMTCALGO-attributes {
 leaf LOCALCELLNAME {
  type string;
  mandatory false;
 }
 leaf DLLTERSVNBCOUNT {
  type uint8 {
   range "2..13";
  }
  mandatory false;
 }
 leaf EMTCALGOEXTSWITCH {
  type string;
  mandatory false;
 }
 leaf EMTCALGOSWITCH {
  type string;
  mandatory false;
 }
 leaf EMTCAPERCQITRIGPRD {
  type enumeration {
   enum val-0;
   enum val-1;
   enum val-2;
   enum val-3;
   enum val-4;
   enum val-5;
   enum val-6;
  }
  mandatory false;
 }
 leaf EMTCDLFREQHOPPINGINTERVAL {
  type enumeration {
   enum val-0;
   enum val-1;
   enum val-2;
   enum val-3;
   enum val-4;
   enum val-5;
   enum val-6;
  }
  mandatory false;
 }
 leaf EMTCDLINVALIDSFCFG {
  type string;
  mandatory false;
 }
 leaf EMTCDLRBTARGETRATIO {
  type uint8 {
   range "1..100";
  }
  mandatory false;
 }
 leaf EMTCDLSCHSTRATEGY {
  type boolean;
  mandatory false;
 }
 leaf EMTCDYNHARQACKDELAYPARAM {
  type enumeration {
   enum val-0;
   enum val-1;
   enum val-2;
  }
  mandatory false;
 }
 leaf EMTCENHANCEDVOLTEALGOSW {
  type string;
  mandatory false;
 }
 leaf EMTCFREQHOPPINGSWITCH {
  type string;
  mandatory false;
 }
 leaf EMTCINITIALAGGLVLADJVALUE {
  type int8 {
   range "-5..25";
  }
  mandatory false;
 }
 leaf EMTCINITIALCQIADJVALUE {
  type int8 {
   range "-10..14";
  }
  mandatory false;
 }
 leaf EMTCNOSERVAPERCQITRIGPRD {
  type enumeration {
   enum val-0;
   enum val-1;
   enum val-2;
   enum val-3;
   enum val-4;
   enum val-5;
   enum val-6;
  }
  mandatory false;
 }
 leaf EMTCPDSCHPUSCHENHSWITCH {
  type boolean;
  mandatory false;
 }
 leaf EMTCRACHALGOSWITCH {
  type string;
  mandatory false;
 }
 leaf EMTCSRIREPUEMAXSRIUSAGE {
  type uint8 {
   range "0..100";
  }
  mandatory false;
 }
 leaf EMTCULFREQHOPPINGINTERVAL {
  type enumeration {
   enum val-0;
   enum val-1;
   enum val-2;
   enum val-3;
   enum val-4;
   enum val-5;
   enum val-6;
  }
  mandatory false;
 }
 leaf EMTCULRBTARGETRATIO {
  type uint8 {
   range "1..100";
  }
  mandatory false;
 }
 leaf EMTCVOLTESUPPORTSWITCH {
  type boolean;
  mandatory false;
 }
 leaf LOCALCELLID {
  type union {
   type int16 {
    range "-1..255";
   }
  }
  mandatory false;
 }
 leaf MPDCCHPDSCHFREQHOPPINGOFS {
  type uint8 {
   range "1..16";
  }
  mandatory false;
 }
 leaf MPDCCHPDSCHHOPPINGNBCNT {
  type boolean;
  mandatory false;
 }
 leaf PRACHFREQHOPPINGOFFSET {
  type uint8 {
   range "0..94";
  }
  mandatory false;
 }
 leaf PUSCHFREQHOPPINGOFFSET {
  type uint8 {
   range "1..16";
  }
  mandatory false;
 }
 leaf ULEMTCAVAILNBCOUNT {
  type uint8 {
   range "1..16";
  }
  mandatory false;
 }
 leaf ULLTERSVNBCOUNT {
  type uint8 {
   range "2..13";
  }
  mandatory false;
 }
 }
 grouping CELLENHCOVERAGE-attributes {
 leaf LOCALCELLNAME {
  type string;
  mandatory false;
 }
 leaf ENHCHCOVERAGESW {
  type string;
  mandatory false;
 }
 leaf LOCALCELLID {
  type union {
   type int16 {
    range "-1..255";
   }
  }
  mandatory false;
 }
 }
 grouping CELLHOPARACFG-attributes {
 leaf LOCALCELLNAME {
  type string;
  mandatory false;
 }
 leaf BLINDHOA1A2THDRSRP {
  type int16 {
   range "-140..-43";
  }
  mandatory false;
 }
 leaf BLINDHOA1A2THDRSRQ {
  type int8 {
   range "-40..-6";
  }
  mandatory false;
 }
 leaf BLINDREDIRA1A2THLDRSRPCEA {
  type int16 {
   range "-140..-43";
  }
  mandatory false;
 }
 leaf BLINDREDIRA1A2THLDRSRQCEA {
  type int8 {
   range "-40..-6";
  }
  mandatory false;
 }
 leaf CELLHOALGOSWITCH {
  type string;
  mandatory false;
 }
 leaf COVBASEDINTRARATMEASTIME {
  type uint8 {
   range "0..100";
  }
  mandatory false;
 }
 leaf CQIBASEDINTERFREQHOTHLD {
  type uint8 {
   range "0..6";
  }
  mandatory false;
 }
 leaf CSFBMRWAITINGTIMER {
  type uint16 {
   range "60..1000";
  }
  mandatory false;
 }
 leaf DEDICATEDGAPPATTERNTYPE {
  type enumeration {
   enum val-1;
   enum val-2;
  }
  mandatory false;
 }
 leaf ENGINEERINGTSTBLINDHOMODE {
  type boolean;
  mandatory false;
 }
 leaf EUTRANFILTERCOEFFRSRP {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf EUTRANFILTERCOEFFRSRQ {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf FLASHSRVCCSWITCH {
  type boolean;
  mandatory false;
 }
 leaf GAPPATTERNTYPE {
  type enumeration {
   enum val-1;
   enum val-2;
  }
  mandatory false;
 }
 leaf HSCELLHOINPROTECTTIMER {
  type uint16 {
   range "0..1200";
  }
  mandatory false;
 }
 leaf HSCELLSLEEPUSERNUM {
  type uint16 {
   range "0..500";
  }
  mandatory false;
 }
 leaf HIGHSPEEDTHRESHOLD {
  type uint16 {
   range "30..350";
  }
  mandatory false;
 }
 leaf HIGHSPEEDUEJUDGEMODE {
  type boolean;
  mandatory false;
 }
 leaf HOMODESWITCH {
  type string;
  mandatory false;
 }
 leaf HOMRDELAYTIMERQCI1 {
  type union {
   type uint16 {
    range "0..2000";
   }
  }
  mandatory false;
 }
 leaf HOUSEINACTIVETIMERSWITCH {
  type string;
  mandatory false;
 }
 leaf INTERRATMRDELAYTIMER {
  type uint16 {
   range "0..20000";
  }
  mandatory false;
 }
 leaf INTERRATUUHOFAILRETRYTIMES {
  type uint8 {
   range "0..50";
  }
  mandatory false;
 }
 leaf INTRAENBFREQPRIHODLPRBTHLD {
  type uint8 {
   range "1..100";
  }
  mandatory false;
 }
 leaf INTRAENBFREQPRIHOULPRBTHLD {
  type uint8 {
   range "1..100";
  }
  mandatory false;
 }
 leaf L2UCSFBMRPROMODE {
  type enumeration {
   enum val-0;
   enum val-1;
   enum val-2;
   enum val-3;
  }
  mandatory false;
 }
 leaf LOCALCELLID {
  type union {
   type int16 {
    range "-1..255";
   }
  }
  mandatory false;
 }
 leaf LOWSPEEDUSERSSELPROTIMER {
  type uint8 {
   range "0..60";
  }
  mandatory false;
 }
 leaf NRB1FASTHOTHLDOFFSET {
  type int8 {
   range "-30..30";
  }
  mandatory false;
 }
 leaf NRCOVPREDICTA1RSRPTHLD {
  type union {
   type int16 {
    range "-140..0";
   }
  }
  mandatory false;
 }
 leaf NRMRPROCESSMODE {
  type enumeration {
   enum val-0;
   enum val-1;
   enum val-2;
   enum val-3;
  }
  mandatory false;
 }
 leaf NRMRWAITINGTIMER {
  type uint8 {
   range "0..50";
  }
  mandatory false;
 }
 leaf NRRESOPTHOINPROTECTTMR {
  type uint8 {
   range "0..100";
  }
  mandatory false;
 }
 leaf QCI1PLRTHLDFORVOLTEQUALHO {
  type uint8 {
   range "1..100";
  }
  mandatory false;
 }
 leaf RINGINGMSGCHECKSW {
  type boolean;
  mandatory false;
 }
 leaf SERVBASEDNRB1RPTWAITINGTMR {
  type uint8 {
   range "1..15";
  }
  mandatory false;
 }
 leaf SERVBASEDNRMEASTIMER {
  type union {
   type uint8 {
    range "0..60";
   }
  }
  mandatory false;
 }
 leaf SPEEDEVALUATEDNUM {
  type uint8 {
   range "1..16";
  }
  mandatory false;
 }
 leaf SPEEDEVALUATEDNUMFORFASTUE {
  type uint8 {
   range "1..16";
  }
  mandatory false;
 }
 leaf SPEEDEVALUATEDPERIOD {
  type enumeration {
   enum val-0;
   enum val-1;
   enum val-2;
   enum val-3;
   enum val-4;
   enum val-5;
   enum val-6;
   enum val-7;
   enum val-8;
  }
  mandatory false;
 }
 leaf SRVCCHOOPTSWITCH {
  type string;
  mandatory false;
 }
 leaf SRVCCMRDELAYTIMER {
  type uint8 {
   range "0..20";
  }
  mandatory false;
 }
 leaf ULBADQUALENHHOSPCTEFFTHLD {
  type uint8 {
   range "1..255";
  }
  mandatory false;
 }
 leaf ULBADQUALHOIBLERTHD {
  type uint8 {
   range "0..100";
  }
  mandatory false;
 }
 leaf ULBADQUALHOMCSTHD {
  type uint8 {
   range "0..28";
  }
  mandatory false;
 }
 leaf ULPOORCOVERPATHLOSSTHD {
  type uint8 {
   range "70..145";
  }
  mandatory false;
 }
 leaf ULPOORCOVERSINRTHD {
  type int8 {
   range "-100..100";
  }
  mandatory false;
 }
 leaf VOLTEQUALITYHOALGOSWITCH {
  type string;
  mandatory false;
 }
 leaf VOLTEHONRDELAYTIMER {
  type uint8 {
   range "0..200";
  }
  mandatory false;
 }
 leaf VOLTEQUALIFHOQCI1PLRTHLD {
  type uint8 {
   range "1..100";
  }
  mandatory false;
 }
 leaf VOLTEQUALPKTLOSSPERIOD {
  type uint8 {
   range "1..10";
  }
  mandatory false;
 }
 leaf VOLTEQUALRECOVERYQCI1PLRTHLD {
  type uint8 {
   range "0..100";
  }
  mandatory false;
 }
 }
 grouping CELLIDPRDUPT-attributes {
 leaf ACTIONTIME {
  type hwat:yyyy_mm_dd_HH_MM_SS_Time;
  mandatory false;
 }
 leaf PERIOD {
  type uint16 {
   range "1..365";
  }
  mandatory false;
 }
 leaf PRDUPTSWITCH {
  type boolean;
  mandatory false;
 }
 }
 grouping CELLINTELAMCCONFIG-attributes {
 leaf LOCALCELLNAME {
  type string;
  mandatory false;
 }
 leaf DLDATACOLLECTIONINTERVAL {
  type boolean;
  mandatory false;
 }
 leaf DLMODELMINUPDATEPERIOD {
  type enumeration {
   enum val-0;
   enum val-1;
   enum val-2;
   enum val-3;
   enum val-4;
   enum val-5;
   enum val-6;
   enum val-7;
   enum val-8;
   enum val-9;
  }
  mandatory false;
 }
 leaf DLPREDERRORUPPERLIMIT {
  type uint8 {
   range "0..20";
  }
  mandatory false;
 }
 leaf INTELLIGENTAMCSWITCH {
  type string;
  mandatory false;
 }
 leaf LOCALCELLID {
  type union {
   type int16 {
    range "-1..255";
   }
  }
  mandatory false;
 }
 leaf ULFASTSINRPREDERRUPPERLMT {
  type uint8 {
   range "0..50";
  }
  mandatory false;
 }
 leaf ULFASTSINRPREDERROROFFSET {
  type uint8 {
   range "0..50";
  }
  mandatory false;
 }
 leaf ULIBLERPREDERRORUPPERLIMIT {
  type uint8 {
   range "0..20";
  }
  mandatory false;
 }
 leaf ULPREDERRORUPPERLIMIT {
  type uint8 {
   range "0..50";
  }
  mandatory false;
 }
 }
 grouping CELLLAACOEXISTPARA-attributes {
 leaf LOCALCELLNAME {
  type string;
  mandatory false;
 }
 leaf CCATHDOFFSET {
  type int8 {
   range "-20..20";
  }
  mandatory false;
 }
 leaf COEXISTMODE {
  type enumeration {
   enum val-0;
   enum val-1;
   enum val-2;
   enum val-3;
   enum val-4;
  }
  mandatory false;
 }
 leaf HIGHINTERFDURATIONTHD {
  type uint16 {
   range "60..3600";
  }
  mandatory false;
 }
 leaf HIGHINTERFDUTYTHD {
  type uint8 {
   range "1..100";
  }
  mandatory false;
 }
 leaf LBTPRIORITY {
  type union {
   type uint8 {
    range "1..16";
   }
  }
  mandatory false;
 }
 leaf LOCALCELLID {
  type union {
   type int16 {
    range "-1..255";
   }
  }
  mandatory false;
 }
 leaf LSBSWITCH {
  type boolean;
  mandatory false;
 }
 leaf TPCPOWERADJCQITHLD {
  type uint8 {
   range "10..15";
  }
  mandatory false;
 }
 }
 grouping CELLLAAFCSPARA-attributes {
 leaf LOCALCELLNAME {
  type string;
  mandatory false;
 }
 leaf CELLTPCMAXPOWER {
  type uint16 {
   range "20..1000";
  }
  mandatory false;
 }
 leaf CELLTPCPOWERADJRANGE {
  type uint8 {
   range "0..6";
  }
  mandatory false;
 }
 leaf DFSSWITCH {
  type string;
  mandatory false;
 }
 leaf DLTPCALGOSWITCH {
  type string;
  mandatory false;
 }
 leaf FCSINTERFTHD {
  type int8 {
   range "-100..0";
  }
  mandatory false;
 }
 leaf OLD_FCSSTARTFREQ {
  type union {
   type int16 {
    range "-1..5925";
   }
  }
  mandatory false;
 }
 leaf FCSSTARTFREQ {
  type union {
   type int16 {
    range "-1..5925";
   }
  }
  mandatory false;
 }
 leaf OLD_FCSSTOPFREQ {
  type union {
   type int16 {
    range "-1..5925";
   }
  }
  mandatory false;
 }
 leaf FCSSTOPFREQ {
  type union {
   type int16 {
    range "-1..5925";
   }
  }
  mandatory false;
 }
 leaf OLD_LOCALCELLID {
  type union {
   type int16 {
    range "-1..255";
   }
  }
  mandatory false;
 }
 leaf LOCALCELLID {
  type union {
   type int16 {
    range "-1..255";
   }
  }
  mandatory false;
 }
 }
 grouping CELLLCSCFG-attributes {
 leaf LOCALCELLNAME {
  type string;
  mandatory false;
 }
 leaf CELLLCSSWITCH {
  type string;
  mandatory false;
 }
 leaf LOCALCELLID {
  type union {
   type int16 {
    range "-1..255";
   }
  }
  mandatory false;
 }
 leaf NBECIDPOSITIONINGUECOUNT {
  type uint8 {
   range "0..12";
  }
  mandatory false;
 }
 }
 grouping CELLLOWPOWER-attributes {
 leaf LOCALCELLNAME {
  type string;
  mandatory false;
 }
 leaf BAKPWRSAVPOLICY {
  type enumeration {
   enum val-0;
   enum val-1;
   enum val-2;
   enum val-3;
   enum val-4;
   enum val-5;
   enum val-6;
   enum val-7;
   enum val-8;
   enum val-9;
   enum val-10;
  }
  mandatory false;
 }
 leaf CELLUSEDPWRRATIO {
  type uint8 {
   range "10..100";
  }
  mandatory false;
 }
 leaf CELLUSEDPWRREDUCESTARTPRI {
  type enumeration {
   enum val-0;
   enum val-1;
   enum val-2;
   enum val-3;
  }
  mandatory false;
 }
 leaf CELLUSEDPWRREDUCETIMELEN {
  type uint16 {
   range "0..1440";
  }
  mandatory false;
 }
 leaf ENTERTIMELEN {
  type uint16 {
   range "1..1440";
  }
  mandatory false;
 }
 leaf LOCALCELLID {
  type union {
   type int16 {
    range "-1..255";
   }
  }
  mandatory false;
 }
 leaf LOWPWRCONSUMEMODEEXTSW {
  type string;
  mandatory false;
 }
 leaf LOWPWRORDER {
  type boolean;
  mandatory false;
 }
 leaf LOWPWRSWITCH {
  type boolean;
  mandatory false;
 }
 leaf RFSHUTDOWNTIMELEN {
  type uint16 {
   range "0..1440";
  }
  mandatory false;
 }
 leaf RFSHUTDOWNSTARTPRI {
  type enumeration {
   enum val-0;
   enum val-1;
   enum val-2;
   enum val-3;
  }
  mandatory false;
 }
 leaf RSPWRADJOFFSET {
  type int8 {
   range "-10..0";
  }
  mandatory false;
 }
 leaf RSPWRREDUCESTARTPRI {
  type enumeration {
   enum val-0;
   enum val-1;
   enum val-2;
   enum val-3;
  }
  mandatory false;
 }
 leaf RSPWRREDUCETIMELEN {
  type uint16 {
   range "0..1440";
  }
  mandatory false;
 }
 leaf STARTTIME {
  type hwat:HH_MM_SS_Time;
  mandatory false;
 }
 leaf STOPTIME {
  type hwat:HH_MM_SS_Time;
  mandatory false;
 }
 }
 grouping CELLLTEFLEXBW-attributes {
 leaf LOCALCELLNAME {
  type string;
  mandatory false;
 }
 leaf DLCUSTENDPRBINDEX {
  type union {
   type uint8 {
    range "0..255";
   }
  }
  mandatory false;
 }
 leaf DLCUSTSTARTPRBINDEX {
  type union {
   type uint8 {
    range "0..255";
   }
  }
  mandatory false;
 }
 leaf LOCALCELLID {
  type union {
   type int16 {
    range "-1..255";
   }
  }
  mandatory false;
 }
 leaf LTEFLEXBWSWITCH {
  type string;
  mandatory false;
 }
 leaf ULCUSTENDPRBINDEX {
  type union {
   type uint8 {
    range "0..255";
   }
  }
  mandatory false;
 }
 leaf ULCUSTSTARTPRBINDEX {
  type union {
   type uint8 {
    range "0..255";
   }
  }
  mandatory false;
 }
 }
 grouping CELLLTEFLEXBWITFCFG-attributes {
 leaf LOCALCELLNAME {
  type string;
  mandatory false;
 }
 leaf OLD_GSMCARRIERFREQ {
  type enumeration {
   enum val--1;
   enum val-0;
   enum val-1;
   enum val-2;
   enum val-3;
  }
  mandatory false;
 }
 leaf GSMCARRIERFREQ {
  type enumeration {
   enum val--1;
   enum val-0;
   enum val-1;
   enum val-2;
   enum val-3;
  }
  mandatory false;
 }
 leaf OLD_HIGHITFGSMARFCN {
  type union {
   type int16 {
    range "-1..1023";
   }
  }
  mandatory false;
 }
 leaf HIGHITFGSMARFCN {
  type union {
   type int16 {
    range "-1..1023";
   }
  }
  mandatory false;
 }
 leaf OLD_LOCALCELLID {
  type union {
   type int16 {
    range "-1..255";
   }
  }
  mandatory false;
 }
 leaf LOCALCELLID {
  type union {
   type int16 {
    range "-1..255";
   }
  }
  mandatory false;
 }
 }
 grouping CELLMBFCS-attributes {
 leaf LOCALCELLNAME {
  type string;
  mandatory false;
 }
 leaf CELLSYNTHETICALRATEHOHYST {
  type uint8 {
   range "0..100";
  }
  mandatory false;
 }
 leaf CELLTRAFFICLOADTHD {
  type uint16 {
   range "0..1000";
  }
  mandatory false;
 }
 leaf INTERFREQMEASLOADRATIOTHD {
  type uint8 {
   range "0..100";
  }
  mandatory false;
 }
 leaf INTERFREQMEASMCSTHD {
  type uint8 {
   range "0..28";
  }
  mandatory false;
 }
 leaf INTERFREQMEASSERVICETHD {
  type uint16 {
   range "0..65535";
  }
  mandatory false;
 }
 leaf LOADDIFFRATIOTHLD {
  type int8 {
   range "-100..100";
  }
  mandatory false;
 }
 leaf LOCALCELLID {
  type union {
   type int16 {
    range "-1..255";
   }
  }
  mandatory false;
 }
 leaf MBOCSALGORITHMSWITCH {
  type string;
  mandatory false;
 }
 leaf MEASINFOUPDINTERVAL {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf UESPECTRALEFFHOHYST {
  type uint8 {
   range "0..100";
  }
  mandatory false;
 }
 }
 grouping CELLMBMSCFG-attributes {
 leaf LOCALCELLNAME {
  type string;
  mandatory false;
 }
 leaf LOCALCELLID {
  type union {
   type int16 {
    range "-1..255";
   }
  }
  mandatory false;
 }
 leaf MBMSSERVICESWITCH {
  type string;
  mandatory false;
 }
 leaf MBMSSWITCH {
  type string;
  mandatory false;
 }
 leaf MBSFNSYNCAREAID {
  type uint16 {
   range "0..65535";
  }
  mandatory false;
 }
 leaf NCELLMBMSCFGSWITCH {
  type string;
  mandatory false;
 }
 }
 grouping CELLMBSFNSFENHCONFIG-attributes {
 leaf LOCALCELLNAME {
  type string;
  mandatory false;
 }
 leaf FOURFRAMEALLOCATION {
  type uint32 {
   range "0..16777215";
  }
  mandatory false;
 }
 leaf LOCALCELLID {
  type union {
   type int16 {
    range "-1..255";
   }
  }
  mandatory false;
 }
 leaf ONEFRAMEALLOCATION {
  type uint8 {
   range "0..63";
  }
  mandatory false;
 }
 leaf RADIOFRAMEALLOCOFS {
  type uint8 {
   range "0..7";
  }
  mandatory false;
 }
 leaf RADIOFRAMEALLOCPRD {
  type enumeration {
   enum val-0;
   enum val-1;
   enum val-2;
   enum val-3;
   enum val-4;
   enum val-5;
  }
  mandatory false;
 }
 leaf SUBFRAMEALLOCATIONMODE {
  type enumeration {
   enum val-0;
   enum val-1;
   enum val-2;
  }
  mandatory false;
 }
 }
 grouping CELLMCPARA-attributes {
 leaf LOCALCELLNAME {
  type string;
  mandatory false;
 }
 leaf A3MCADAPTIVESWITCH {
  type string;
  mandatory false;
 }
 leaf A3OFFSET {
  type int8 {
   range "-30..30";
  }
  mandatory false;
 }
 leaf A6OFFSET {
  type int8 {
   range "-30..30";
  }
  mandatory false;
 }
 leaf AOADETECTTHD {
  type int16 {
   range "-10000..2000";
  }
  mandatory false;
 }
 leaf COVERAGEMEASINTERVAL {
  type uint8 {
   range "1..60";
  }
  mandatory false;
 }
 leaf COVERAGEMEASSTARTTIME {
  type hwat:HH_MM_SS_Time;
  mandatory false;
 }
 leaf COVERAGEMEASSTOPTIME {
  type hwat:HH_MM_SS_Time;
  mandatory false;
 }
 leaf COVERAGEMEASSW {
  type string;
  mandatory false;
 }
 leaf COVERAGEMEASTYPE {
  type boolean;
  mandatory false;
 }
 leaf COVERAGEMEASUREUENUM {
  type uint8 {
   range "1..10";
  }
  mandatory false;
 }
 leaf ECIDREPORTAMOUNT {
  type enumeration {
   enum val-0;
   enum val-1;
   enum val-2;
   enum val-3;
   enum val-4;
   enum val-5;
   enum val-6;
   enum val-7;
  }
  mandatory false;
 }
 leaf ECIDREPORTINTERVAL {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf HYSTERESIS {
  type uint8 {
   range "0..30";
  }
  mandatory false;
 }
 leaf INTERFREQMAXREPORTCELLS {
  type uint8 {
   range "1..8";
  }
  mandatory false;
 }
 leaf INTERFREQREPORTQUANTITY {
  type boolean;
  mandatory false;
 }
 leaf INTERFREQTRIGGERQUANTITY {
  type boolean;
  mandatory false;
 }
 leaf INTRAFREQMAXREPORTCELLS {
  type uint8 {
   range "1..8";
  }
  mandatory false;
 }
 leaf INTRAFREQREPORTQUANTITY {
  type boolean;
  mandatory false;
 }
 leaf INTRAFREQTRIGGERQUANTITY {
  type boolean;
  mandatory false;
 }
 leaf LOCALCELLID {
  type union {
   type int16 {
    range "-1..255";
   }
  }
  mandatory false;
 }
 leaf MAXREPORTCELLS {
  type uint8 {
   range "1..8";
  }
  mandatory false;
 }
 leaf REPORTAMOUNT {
  type enumeration {
   enum val-0;
   enum val-1;
   enum val-2;
   enum val-3;
   enum val-4;
   enum val-5;
   enum val-6;
   enum val-7;
  }
  mandatory false;
 }
 leaf REPORTINTERVAL {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf REPORTQUANTITY {
  type boolean;
  mandatory false;
 }
 leaf TIMETOTRIGGER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf TRIGGERQUANTITY {
  type boolean;
  mandatory false;
 }
 }
 grouping CELLMIMOPARACFG-attributes {
 leaf LOCALCELLNAME {
  type string;
  mandatory false;
 }
 leaf ADAPTIVELAYERINGSWITCH {
  type string;
  mandatory false;
 }
 leaf COVERAGESCENARIO {
  type enumeration {
   enum val-0;
   enum val-1;
   enum val-2;
  }
  mandatory false;
 }
 leaf DLTURBOPILOTCOMPATIDENTTIME {
  type uint8 {
   range "1..5";
  }
  mandatory false;
 }
 leaf DLTURBOPILOTCOMPATUEA3OFS {
  type uint8 {
   range "0..6";
  }
  mandatory false;
 }
 leaf DOPPLERSHIFTTHLDFORTM9 {
  type uint8 {
   range "10..120";
  }
  mandatory false;
 }
 leaf FIXEDMIMOMODE {
  type enumeration {
   enum val-0;
   enum val-1;
   enum val-2;
   enum val-3;
  }
  mandatory false;
 }
 leaf HIGHORDERMIMOPAIRINGSTRAT {
  type enumeration {
   enum val-0;
   enum val-1;
   enum val-2;
   enum val-3;
  }
  mandatory false;
 }
 leaf HIGHORDERMUPAIRINGMCSTHLD {
  type uint8 {
   range "0..33";
  }
  mandatory false;
 }
 leaf INITIALMIMOTYPE {
  type boolean;
  mandatory false;
 }
 leaf LOCALCELLID {
  type union {
   type int16 {
    range "-1..255";
   }
  }
  mandatory false;
 }
 leaf MCSINDEXTHLDFOR4PADAPTTM9 {
  type union {
   type uint8 {
    range "0..255";
   }
  }
  mandatory false;
 }
 leaf MCSINDEXTHLDFORADAPTTM9 {
  type union {
   type uint8 {
    range "0..255";
   }
  }
  mandatory false;
 }
 leaf MIMOADAPTIVESWITCH {
  type enumeration {
   enum val-0;
   enum val-1;
   enum val-2;
   enum val-3;
  }
  mandatory false;
 }
 leaf MIMOSWITCH {
  type string;
  mandatory false;
 }
 leaf MIMOTMADAPTDECISIONPERIOD {
  type uint16 {
   range "500..60000";
  }
  mandatory false;
 }
 leaf MIMOTMADAPTRANK1RATETHLD {
  type uint8 {
   range "0..20";
  }
  mandatory false;
 }
 leaf MIMOTMADAPTSPCTEFFHYST {
  type uint8 {
   range "0..200";
  }
  mandatory false;
 }
 leaf MUMIMOMAXPAIRLAYER {
  type enumeration {
   enum val-0;
   enum val-1;
   enum val-2;
   enum val-3;
   enum val-4;
   enum val-5;
   enum val-6;
   enum val-7;
  }
  mandatory false;
 }
 leaf MUMIMOPAIRINGSTRATEGY {
  type enumeration {
   enum val-0;
   enum val-1;
   enum val-2;
   enum val-3;
   enum val-4;
  }
  mandatory false;
 }
 leaf MUMIMOWEIGHTADJSTRATEGY {
  type boolean;
  mandatory false;
 }
 leaf MUPAIRINGGAINTHLDFORTM9 {
  type uint8 {
   range "0..100";
  }
  mandatory false;
 }
 leaf MUPAIRINGMCSTHLDFORTM9 {
  type uint8 {
   range "0..33";
  }
  mandatory false;
 }
 leaf PAIRINGPROBTHLDFORADAPTTM9 {
  type uint8 {
   range "0..100";
  }
  mandatory false;
 }
 leaf PRBRATIOTHLDFORTM9SUMIMO {
  type uint8 {
   range "0..100";
  }
  mandatory false;
 }
 leaf RANSHARINGSCHOPTSWITCH {
  type enumeration {
   enum val-0;
   enum val-1;
   enum val-2;
  }
  mandatory false;
 }
 leaf SRSMEASFILTERINGTHLD {
  type union {
   type int8 {
    range "-128..0";
   }
  }
  mandatory false;
 }
 leaf TM4SMARTBFCELLSPCTEFFTHLD {
  type uint16 {
   range "0..1000";
  }
  mandatory false;
 }
 leaf TM4SMARTBFTRANSTIMETHLD {
  type uint16 {
   range "0..1000";
  }
  mandatory false;
 }
 leaf TURBOPILOTPOWEROFFSET {
  type uint8 {
   range "0..30";
  }
  mandatory false;
 }
 }
 grouping CELLMLB-attributes {
 leaf LOCALCELLNAME {
  type string;
  mandatory false;
 }
 leaf CELLCAPACITYSCALEFACTOR {
  type uint8 {
   range "1..100";
  }
  mandatory false;
 }
 leaf CELLPUNISHPRDNUM {
  type uint8 {
   range "0..127";
  }
  mandatory false;
 }
 leaf DLDATAMLBMODE {
  type boolean;
  mandatory false;
 }
 leaf ENHANCEDMLBALGOEXTSWITCH {
  type string;
  mandatory false;
 }
 leaf EUTRANLOADJUDGESTRATEGY {
  type boolean;
  mandatory false;
 }
 leaf FREQPUNISHPRDNUM {
  type uint8 {
   range "0..127";
  }
  mandatory false;
 }
 leaf FREQSELECTSTRATEGY {
  type enumeration {
   enum val-0;
   enum val-1;
   enum val-2;
   enum val-3;
  }
  mandatory false;
 }
 leaf GUARANTEEDUEMLBUENUMOFS {
  type uint16 {
   range "1..10000";
  }
  mandatory false;
 }
 leaf GUARANTEEDUEMLBUENUMTHLD {
  type uint16 {
   range "1..10000";
  }
  mandatory false;
 }
 leaf HEAVYLOADBEAMUENUMTHLD {
  type uint16 {
   range "1..10000";
  }
  mandatory false;
 }
 leaf HOTSPOTUEMODE {
  type boolean;
  mandatory false;
 }
 leaf IDLEMLBUENUMDIFFTHD {
  type uint8 {
   range "0..100";
  }
  mandatory false;
 }
 leaf IDLEUESELFREQSCOPE {
  type enumeration {
   enum val-0;
   enum val-1;
   enum val-2;
  }
  mandatory false;
 }
 leaf INITVALIDPERIOD {
  type uint8 {
   range "1..30";
  }
  mandatory false;
 }
 leaf INTERFIDLEUENUMOFFLOADOFS {
  type uint16 {
   range "0..10000";
  }
  mandatory false;
 }
 leaf INTERFREQBEAMMLBUENUMTHLD {
  type uint16 {
   range "1..10000";
  }
  mandatory false;
 }
 leaf INTERFREQIDLEMLBMODE {
  type string;
  mandatory false;
 }
 leaf INTERFREQIDLEMLBUENUMTHD {
  type uint16 {
   range "1..10000";
  }
  mandatory false;
 }
 leaf INTERFREQLOADEVALPRD {
  type uint8 {
   range "5..30";
  }
  mandatory false;
 }
 leaf INTERFREQMLBRANSHAREMODE {
  type enumeration {
   enum val-0;
   enum val-1;
   enum val-2;
   enum val-3;
   enum val-4;
  }
  mandatory false;
 }
 leaf INTERFREQMLBTHD {
  type uint8 {
   range "1..100";
  }
  mandatory false;
 }
 leaf INTERFREQMLBUENUMTHD {
  type uint16 {
   range "1..10000";
  }
  mandatory false;
 }
 leaf INTERFREQMLBULTHD {
  type uint8 {
   range "1..100";
  }
  mandatory false;
 }
 leaf INTERFREQOFFLOADOFFSET {
  type uint8 {
   range "0..100";
  }
  mandatory false;
 }
 leaf INTERFREQUETRSFTYPE {
  type string;
  mandatory false;
 }
 leaf INTERFRQUENUMOFFLOADOFFSET {
  type uint16 {
   range "0..10000";
  }
  mandatory false;
 }
 leaf INTERRATIDLEMLBUENUMTHD {
  type uint16 {
   range "1..10000";
  }
  mandatory false;
 }
 leaf INTERRATLOADEVALPRD {
  type uint8 {
   range "5..30";
  }
  mandatory false;
 }
 leaf INTERRATMLBHOFAILPUNISH {
  type boolean;
  mandatory false;
 }
 leaf INTERRATMLBMAXUENUM {
  type uint8 {
   range "1..20";
  }
  mandatory false;
 }
 leaf INTERRATMLBTHD {
  type uint8 {
   range "1..100";
  }
  mandatory false;
 }
 leaf INTERRATMLBTRIGGERMODE {
  type enumeration {
   enum val-0;
   enum val-1;
   enum val-2;
  }
  mandatory false;
 }
 leaf INTERRATMLBUENUMMODETHD {
  type uint16 {
   range "1..10000";
  }
  mandatory false;
 }
 leaf INTERRATMLBUENUMOFFSET {
  type uint16 {
   range "0..10000";
  }
  mandatory false;
 }
 leaf INTERRATMLBUENUMTHD {
  type uint8 {
   range "1..100";
  }
  mandatory false;
 }
 leaf INTERRATMLBUESELPRBTHD {
  type uint8 {
   range "0..50";
  }
  mandatory false;
 }
 leaf INTERRATMLBUESELSTRATEGY {
  type boolean;
  mandatory false;
 }
 leaf INTERRATVOLTEOFFLDMAXUENUM {
  type uint8 {
   range "1..3";
  }
  mandatory false;
 }
 leaf L2USMARTOFFLOADOFFSET {
  type uint8 {
   range "1..100";
  }
  mandatory false;
 }
 leaf L2USMARTOFFLOADTHD {
  type uint32 {
   range "1..1000000";
  }
  mandatory false;
 }
 leaf LOADBALANCENCELLSCOPE {
  type boolean;
  mandatory false;
 }
 leaf LOADDIFFTHD {
  type uint8 {
   range "1..50";
  }
  mandatory false;
 }
 leaf LOADDIFFTHLDOFFSET {
  type uint8 {
   range "0..40";
  }
  mandatory false;
 }
 leaf LOADOFFSET {
  type uint8 {
   range "0..50";
  }
  mandatory false;
 }
 leaf LOADTRANSFERFACTOR {
  type uint16 {
   range "0..1000";
  }
  mandatory false;
 }
 leaf LOCALCELLID {
  type union {
   type int16 {
    range "-1..255";
   }
  }
  mandatory false;
 }
 leaf MAXSPECTRALEFFICIENCYVALUE {
  type uint16 {
   range "0..65535";
  }
  mandatory false;
 }
 leaf MBBDLAVGPERCEIVEDRATETHLD {
  type uint16 {
   range "0..65535";
  }
  mandatory false;
 }
 leaf MBBPERCEIVEDRATEOFFSET {
  type uint8 {
   range "1..100";
  }
  mandatory false;
 }
 leaf MBBULAVGPERCEIVEDRATETHLD {
  type uint16 {
   range "0..65535";
  }
  mandatory false;
 }
 leaf MINSPECTRALEFFICIENCYVALUE {
  type uint16 {
   range "0..65535";
  }
  mandatory false;
 }
 leaf MLBHOCELLSELECTSTRATEGY {
  type boolean;
  mandatory false;
 }
 leaf MLBIDLEUENUMADJFACTOR {
  type uint8 {
   range "0..50";
  }
  mandatory false;
 }
 leaf MLBMAXUENUM {
  type uint8 {
   range "1..80";
  }
  mandatory false;
 }
 leaf MLBMINUENUMOFFSET {
  type uint16 {
   range "0..10000";
  }
  mandatory false;
 }
 leaf MLBMINUENUMTHD {
  type uint16 {
   range "0..10000";
  }
  mandatory false;
 }
 leaf MLBSONLOGRECORDINTERVAL {
  type enumeration {
   enum val-0;
   enum val-1;
   enum val-2;
   enum val-3;
   enum val-4;
   enum val-5;
   enum val-6;
  }
  mandatory false;
 }
 leaf MLBTRIGJUDGEPERIOD {
  type uint8 {
   range "1..60";
  }
  mandatory false;
 }
 leaf MLBTRIGGERMODE {
  type enumeration {
   enum val-0;
   enum val-1;
   enum val-2;
  }
  mandatory false;
 }
 leaf MLBUENUMOFFSET {
  type uint16 {
   range "0..10000";
  }
  mandatory false;
 }
 leaf MLBUESELECTPRBTHD {
  type uint8 {
   range "0..100";
  }
  mandatory false;
 }
 leaf MLBUESELECTPUNISHTIMER {
  type uint16 {
   range "0..3600";
  }
  mandatory false;
 }
 leaf MMLOADSTEERINGADMTHLD {
  type union {
   type uint16 {
    range "1..65535";
   }
  }
  mandatory false;
 }
 leaf MMLOADSTEERINGLAYERTHLD {
  type uint16 {
   range "0..1600";
  }
  mandatory false;
 }
 leaf MMLOADSTEERINGUENUMTHLD {
  type uint16 {
   range "1..10000";
  }
  mandatory false;
 }
 leaf MUMIMOPRBSTATOPTSWITCH {
  type boolean;
  mandatory false;
 }
 leaf MULTIRRUMODE {
  type string;
  mandatory false;
 }
 leaf NCELLHOSUCCRATETHLD {
  type uint8 {
   range "80..100";
  }
  mandatory false;
 }
 leaf NCELLVENDORSELECTIONRANGE {
  type enumeration {
   enum val-0;
   enum val-1;
   enum val-2;
  }
  mandatory false;
 }
 leaf NBMLBUESELECTIONDLMCSTHLD {
  type union {
   type int16 {
    range "-9..255";
   }
  }
  mandatory false;
 }
 leaf NBMLBUESELECTIONRSRPTHLD {
  type union {
   type int16 {
    range "-141..0";
   }
  }
  mandatory false;
 }
 leaf PRBLOADCALCMETHOD {
  type enumeration {
   enum val-0;
   enum val-1;
   enum val-2;
  }
  mandatory false;
 }
 leaf PUNISHJUDGEPRDNUM {
  type uint8 {
   range "1..127";
  }
  mandatory false;
 }
 leaf SPECTRALEFFADJUSTMAXSTEP {
  type uint16 {
   range "0..65535";
  }
  mandatory false;
 }
 leaf UEDLPRBLOWTHDOFFSET {
  type int8 {
   range "-100..100";
  }
  mandatory false;
 }
 leaf UENUMDIFFOFFSETTRANSCA {
  type uint8 {
   range "0..100";
  }
  mandatory false;
 }
 leaf UENUMDIFFTHD {
  type uint8 {
   range "0..100";
  }
  mandatory false;
 }
 leaf UEULPRBHIGHTHDOFFSET {
  type int8 {
   range "-100..100";
  }
  mandatory false;
 }
 leaf UEULPRBLOWTHDOFFSET {
  type int8 {
   range "-100..100";
  }
  mandatory false;
 }
 leaf ULEXPERIENCEDIFFTHD {
  type uint8 {
   range "0..100";
  }
  mandatory false;
 }
 leaf ULEXPERIENCEEVALPRD {
  type uint8 {
   range "5..30";
  }
  mandatory false;
 }
 leaf ULEXPERIENCEMAXUENUM {
  type uint8 {
   range "1..40";
  }
  mandatory false;
 }
 leaf ULEXPERIENCEOFFLOADTHD {
  type uint32 {
   range "1..1000000";
  }
  mandatory false;
 }
 leaf ULEXPERIENCEOFFSET {
  type uint8 {
   range "1..100";
  }
  mandatory false;
 }
 leaf VIDEODLPRBTHD {
  type uint8 {
   range "0..100";
  }
  mandatory false;
 }
 leaf VIDEOLOADHIGHTHD {
  type uint8 {
   range "0..100";
  }
  mandatory false;
 }
 leaf VIDEOLOADLOWTHD {
  type uint8 {
   range "0..100";
  }
  mandatory false;
 }
 leaf WBBDLAVGPERCEIVEDRATETHLD {
  type uint16 {
   range "0..65535";
  }
  mandatory false;
 }
 leaf WBBPERCEIVEDRATEOFFSET {
  type uint8 {
   range "1..100";
  }
  mandatory false;
 }
 leaf WBBULAVGPERCEIVEDRATETHLD {
  type uint16 {
   range "0..65535";
  }
  mandatory false;
 }
 }
 grouping CELLMLBAUTOGROUP-attributes {
 leaf LOCALCELLNAME {
  type string;
  mandatory false;
 }
 leaf ADDEDMEASCFG {
  type boolean;
  mandatory false;
 }
 leaf LOCALCELLID {
  type union {
   type int16 {
    range "-1..255";
   }
  }
  mandatory false;
 }
 leaf MICROOVERLAPINDADDTHD {
  type uint8 {
   range "0..100";
  }
  mandatory false;
 }
 leaf MICROOVERLAPINDDELTHD {
  type uint8 {
   range "0..100";
  }
  mandatory false;
 }
 leaf OPTMODE {
  type boolean;
  mandatory false;
 }
 leaf OVERLAPINDADDTHD {
  type uint8 {
   range "0..100";
  }
  mandatory false;
 }
 leaf OVERLAPINDAUTOSAMPLENUM {
  type uint16 {
   range "1..65535";
  }
  mandatory false;
 }
 leaf OVERLAPINDDELTHD {
  type uint8 {
   range "0..100";
  }
  mandatory false;
 }
 leaf SLEEPPERIOD {
  type uint16 {
   range "0..65535";
  }
  mandatory false;
 }
 leaf STATPERIOD {
  type uint16 {
   range "1..65535";
  }
  mandatory false;
 }
 }
 grouping CELLMLBHO-attributes {
 leaf LOCALCELLNAME {
  type string;
  mandatory false;
 }
 leaf IDLEUESELFREQSTRATEGY {
  type boolean;
  mandatory false;
 }
 leaf INTERFREQMLBHOINA1THDRSRP {
  type int16 {
   range "-140..-43";
  }
  mandatory false;
 }
 leaf INTERFREQMLBHOINA1THDRSRQ {
  type int8 {
   range "-40..-6";
  }
  mandatory false;
 }
 leaf INTERFREQMLBHOINA2THDRSRP {
  type int16 {
   range "-140..-43";
  }
  mandatory false;
 }
 leaf INTERFREQMLBHOINA2THDRSRQ {
  type int8 {
   range "-40..-6";
  }
  mandatory false;
 }
 leaf INTERRATMLBSTRATEGY {
  type string;
  mandatory false;
 }
 leaf LOCALCELLID {
  type union {
   type int16 {
    range "-1..255";
   }
  }
  mandatory false;
 }
 leaf MLBHOINPROTECTMODE {
  type string;
  mandatory false;
 }
 leaf MLBHOINPROTECTTIMER {
  type uint16 {
   range "0..3600";
  }
  mandatory false;
 }
 leaf MLBMATCHOTHERFEATUREMODE {
  type string;
  mandatory false;
 }
 }
 grouping CELLMLBUESEL-attributes {
 leaf LOCALCELLNAME {
  type string;
  mandatory false;
 }
 leaf INTERFREQMLBUEARPTHD {
  type uint8 {
   range "1..15";
  }
  mandatory false;
 }
 leaf INTERFREQMLBUEDLMCSTHD {
  type uint8 {
   range "0..28";
  }
  mandatory false;
 }
 leaf LOCALCELLID {
  type union {
   type int16 {
    range "-1..255";
   }
  }
  mandatory false;
 }
 leaf MMLOADSTEERINGUEPRBTHLD {
  type uint8 {
   range "0..100";
  }
  mandatory false;
 }
 leaf NSADCUESELECTIONSTRATEGY {
  type enumeration {
   enum val-0;
   enum val-1;
   enum val-2;
  }
  mandatory false;
 }
 leaf UESELECTARPPRIO {
  type uint8 {
   range "0..255";
  }
  mandatory false;
 }
 leaf UESELECTDLMCSPRIO {
  type uint8 {
   range "0..255";
  }
  mandatory false;
 }
 leaf UESELECTPRBPRIO {
  type uint8 {
   range "0..255";
  }
  mandatory false;
 }
 leaf UESELECTQCIPRIO {
  type uint8 {
   range "0..255";
  }
  mandatory false;
 }
 leaf ULEXPSERVSTEERUESELMCSTHLD {
  type uint8 {
   range "0..28";
  }
  mandatory false;
 }
 }
 grouping CELLMMALGO-attributes {
 leaf LOCALCELLNAME {
  type string;
  mandatory false;
 }
 leaf ASPLITSDMASRSLMTUEPROPTHLD {
  type uint8 {
   range "0..100";
  }
  mandatory false;
 }
 leaf ASPLITSDMATM9UEPROPTHLD {
  type uint8 {
   range "0..100";
  }
  mandatory false;
 }
 leaf ABNUEPKTDELAYTHLD {
  type uint16 {
   range "0..65535";
  }
  mandatory false;
 }
 leaf ACTIVEUENUMTHLD {
  type uint8 {
   range "0..255";
  }
  mandatory false;
 }
 leaf ASTM8RANK2PAIRINGOPTTHLD {
  type uint16 {
   range "0..65535";
  }
  mandatory false;
 }
 leaf BEAMGAINLIMITSWITCH {
  type boolean;
  mandatory false;
 }
 leaf BEAMSHUTDOWNSWITCH {
  type string;
  mandatory false;
 }
 leaf BFGAINTHLDSATURATEDUEIDENT {
  type uint8 {
   range "9..24";
  }
  mandatory false;
 }
 leaf BFWEIGHTTYPE {
  type boolean;
  mandatory false;
 }
 leaf DLMAXLAYERALLOWDELPERTTI {
  type uint8 {
   range "0..4";
  }
  mandatory false;
 }
 leaf DLSUBFPRBUSAGERESTRTHLD {
  type uint8 {
   range "0..100";
  }
  mandatory false;
 }
 leaf GUARANTEEUEMCSTHLD {
  type uint8 {
   range "0..28";
  }
  mandatory false;
 }
 leaf LARGEPKTTHLDUPPERLIMIT {
  type uint8 {
   range "0..255";
  }
  mandatory false;
 }
 leaf LOCALCELLID {
  type union {
   type int16 {
    range "-1..255";
   }
  }
  mandatory false;
 }
 leaf LOWSRSSINRUEPAIRLAYERTHLD {
  type uint8 {
   range "0..8";
  }
  mandatory false;
 }
 leaf MMALGOOPTSWITCH {
  type string;
  mandatory false;
 }
 leaf MASSIVEMIMOINITDELTACQI {
  type int8 {
   range "-10..10";
  }
  mandatory false;
 }
 leaf MMPARAMINTELSELECTDLUXTHLD {
  type uint16 {
   range "512..10240";
  }
  mandatory false;
 }
 leaf MMPARAMINTELSELECTSW {
  type string;
  mandatory false;
 }
 leaf MMPARAMINTELSELECTULUXTHLD {
  type uint16 {
   range "256..5120";
  }
  mandatory false;
 }
 leaf MMVMIMOOUTERLOOPINITIALOFS {
  type int8 {
   range "-50..0";
  }
  mandatory false;
 }
 leaf MUBFSINRTHLDOFSBEFSRSBAL {
  type int8 {
   range "-12..38";
  }
  mandatory false;
 }
 leaf MUBFTBSFORECASTPAIRLYRTHLD {
  type uint8 {
   range "0..64";
  }
  mandatory false;
 }
 leaf OUTLOOPTHLDSTRTDUEIDENT {
  type union {
   type int8 {
    range "-20..127";
   }
  }
  mandatory false;
 }
 leaf PRECISEMUBFOPTSWITCH {
  type string;
  mandatory false;
 }
 leaf SCCSPLSDMAISOTHLDOFS {
  type uint8 {
   range "0..20";
  }
  mandatory false;
 }
 leaf SPLITSDMABEAMRSRPISLTNTHLD {
  type uint8 {
   range "1..31";
  }
  mandatory false;
 }
 leaf SPLITSDMACORRTHLD {
  type uint8 {
   range "0..100";
  }
  mandatory false;
 }
 leaf SPLITSDMAUEIDENSRSSINRTHLD {
  type int8 {
   range "-50..50";
  }
  mandatory false;
 }
 }
 grouping CELLMRO-attributes {
 leaf LOCALCELLNAME {
  type string;
  mandatory false;
 }
 leaf A3INTERFREQA2RSRPLOWLIMIT {
  type int16 {
   range "-140..-43";
  }
  mandatory false;
 }
 leaf A3INTERFREQA2RSRPUPLIMIT {
  type int16 {
   range "-140..-43";
  }
  mandatory false;
 }
 leaf CIOADJLIMITCFGIND {
  type boolean;
  mandatory false;
 }
 leaf CIOADJLOWERLIMIT {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf CIOADJUPPERLIMIT {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf INTERFREQA2RSRPLOWLIMIT {
  type int16 {
   range "-140..-43";
  }
  mandatory false;
 }
 leaf INTERFREQA2RSRPUPLIMIT {
  type int16 {
   range "-140..-43";
  }
  mandatory false;
 }
 leaf INTERFREQMROADJPARASEL {
  type string;
  mandatory false;
 }
 leaf LOCALCELLID {
  type union {
   type int16 {
    range "-1..255";
   }
  }
  mandatory false;
 }
 }
 grouping CELLMULTICARRCFGGRP-attributes {
 leaf LOCALCELLNAME {
  type string;
  mandatory false;
 }
 leaf AGGREGATIONATTRIBUTE {
  type string;
  mandatory false;
 }
 leaf ASB1RSRPTHLDOFFSET {
  type int8 {
   range "-100..100";
  }
  mandatory false;
 }
 leaf OLD_CNOPERATORID {
  type union {
   type int8 {
    range "-1..5";
   }
  }
  mandatory false;
 }
 leaf CNOPERATORID {
  type union {
   type int8 {
    range "-1..5";
   }
  }
  mandatory false;
 }
 leaf OLD_DLARFCN {
  type union {
   type int32 {
    range "-1..3279165";
   }
  }
  mandatory false;
 }
 leaf DLARFCN {
  type union {
   type int32 {
    range "-1..3279165";
   }
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf LTEPREFERREDPCCPRIORITY {
  type union {
   type uint8 {
    range "0..255";
   }
  }
  mandatory false;
 }
 leaf LTESCCA2RSRPTHLDOFFSET {
  type int8 {
   range "-100..100";
  }
  mandatory false;
 }
 leaf LTESCCA4RSRPTHLDOFFSET {
  type int8 {
   range "-100..100";
  }
  mandatory false;
 }
 leaf LTESCCULBWEXPCOMPENSCOEFF {
  type uint8 {
   range "0..100";
  }
  mandatory false;
 }
 leaf OLD_MULTICARRCFGGROUPID {
  type union {
   type int8 {
    range "-1..15";
   }
  }
  mandatory false;
 }
 leaf MULTICARRCFGGROUPID {
  type union {
   type int8 {
    range "-1..15";
   }
  }
  mandatory false;
 }
 leaf NRSCGPRIORITYOFFSET {
  type int8 {
   range "-8..8";
  }
  mandatory false;
 }
 leaf NRSCGULEXPERIENCECOEF {
  type uint8 {
   range "0..100";
  }
  mandatory false;
 }
 leaf NSADCB1RSRPTHLDOFFSET {
  type int8 {
   range "-100..100";
  }
  mandatory false;
 }
 leaf NSAPCCANCHORINGPRIORITY {
  type union {
   type uint8 {
    range "0..255";
   }
  }
  mandatory false;
 }
 leaf OLD_RATTYPE {
  type enumeration {
   enum val--1;
   enum val-0;
   enum val-1;
  }
  mandatory false;
 }
 leaf RATTYPE {
  type enumeration {
   enum val--1;
   enum val-0;
   enum val-1;
  }
  mandatory false;
 }
 }
 grouping CELLMULTICARRUNISCH-attributes {
 leaf LOCALCELLNAME {
  type string;
  mandatory false;
 }
 leaf ACTIVEUENUMTHLD {
  type uint8 {
   range "0..255";
  }
  mandatory false;
 }
 leaf ADAPTCOVA4RSRPTHLD {
  type union {
   type int16 {
    range "-140..0";
   }
  }
  mandatory false;
 }
 leaf ADAPTCOVA4RSRPTHLDOFS {
  type int8 {
   range "-15..0";
  }
  mandatory false;
 }
 leaf ADAPTCOVLOWFREQA4RSRPTHLD {
  type union {
   type int16 {
    range "-140..0";
   }
  }
  mandatory false;
 }
 leaf ADAPTCOVLOWFREQRSRPTHLD {
  type union {
   type int16 {
    range "-140..0";
   }
  }
  mandatory false;
 }
 leaf ADAPTCOVLOWFREQRSRPTHLDOFS {
  type int8 {
   range "-15..0";
  }
  mandatory false;
 }
 leaf ADAPTCOVPUSCHSINRTHLD {
  type int8 {
   range "-30..10";
  }
  mandatory false;
 }
 leaf ADAPTCOVRSRPTHLD {
  type union {
   type int16 {
    range "-140..0";
   }
  }
  mandatory false;
 }
 leaf ADAPTCOVRSRPTHLDOFFSET {
  type uint8 {
   range "2..97";
  }
  mandatory false;
 }
 leaf CELLMULTICARRUNIFIEDSCHSW {
  type string;
  mandatory false;
 }
 leaf DLCCEALLOCFAILRATETHLD {
  type uint8 {
   range "10..100";
  }
  mandatory false;
 }
 leaf DLTRAFFICVOLUMETHLD {
  type uint32 {
   range "0..20000000";
  }
  mandatory false;
 }
 leaf FASTMOVINGUESCCCFGINTERVAL {
  type uint8 {
   range "5..60";
  }
  mandatory false;
 }
 leaf FLEXACTVDLPRBTHLD {
  type uint8 {
   range "85..100";
  }
  mandatory false;
 }
 leaf FLEXACTVULPRBTHLD {
  type uint8 {
   range "25..50";
  }
  mandatory false;
 }
 leaf HIGHLOADDLSCHPRIOPTTHLD {
  type uint8 {
   range "0..100";
  }
  mandatory false;
 }
 leaf LNRMULTICARRUNIFIEDSCHSW {
  type string;
  mandatory false;
 }
 leaf LOCALCELLID {
  type union {
   type int16 {
    range "-1..255";
   }
  }
  mandatory false;
 }
 leaf LOWFREQEXTENDMINA2THLD {
  type int16 {
   range "-140..-43";
  }
  mandatory false;
 }
 leaf MCSDIFFTHLD {
  type uint8 {
   range "0..15";
  }
  mandatory false;
 }
 leaf MOBILADAPTCOVDLSPCTEFFTHLD {
  type uint8 {
   range "1..255";
  }
  mandatory false;
 }
 leaf MOBILADAPTCOVULSPCTEFFTHLD {
  type uint8 {
   range "1..255";
  }
  mandatory false;
 }
 leaf NONCACONNUESCSA1RSRPTHLD {
  type union {
   type int16 {
    range "-140..0";
   }
  }
  mandatory false;
 }
 leaf NONDTXSINRINCREASESTEP {
  type uint8 {
   range "0..10";
  }
  mandatory false;
 }
 leaf OVLPUECARRCAPBADJFACTOR {
  type uint8 {
   range "0..100";
  }
  mandatory false;
 }
 leaf SCCADAPTCOVRSRPTHLD {
  type int16 {
   range "-140..-43";
  }
  mandatory false;
 }
 leaf SCELLCAPBSCALEFACTOR {
  type uint8 {
   range "1..10";
  }
  mandatory false;
 }
 leaf SCELLDEACTVWAITINGTIMER {
  type uint8 {
   range "0..200";
  }
  mandatory false;
 }
 leaf TRAFFICMODEEXITPERIODNUM {
  type uint8 {
   range "1..100";
  }
  mandatory false;
 }
 leaf ULCCEALLOCFAILRATETHLD {
  type uint8 {
   range "10..100";
  }
  mandatory false;
 }
 leaf ULTRAFFICVOLUMETHLD {
  type uint32 {
   range "0..20000000";
  }
  mandatory false;
 }
 leaf VGMDLBUILDULTRAFFICTHLD {
  type uint32 {
   range "0..20000000";
  }
  mandatory false;
 }
 }
 grouping CELLNPRSCFG-attributes {
 leaf LOCALCELLNAME {
  type string;
  mandatory false;
 }
 leaf CONSECNPRSSUBFRAMECOUNT {
  type enumeration {
   enum val-0;
   enum val-1;
   enum val-2;
   enum val-3;
   enum val-4;
   enum val-5;
   enum val-6;
   enum val-7;
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf NPRSMUTINGCONFIGURATION {
  type uint16 {
   range "0..65535";
  }
  mandatory false;
 }
 leaf OLD_NPRSPARAGROUPID {
  type union {
   type int8 {
    range "-1..15";
   }
  }
  mandatory false;
 }
 leaf NPRSPARAGROUPID {
  type union {
   type int8 {
    range "-1..15";
   }
  }
  mandatory false;
 }
 leaf NPRSPERIOD {
  type enumeration {
   enum val-0;
   enum val-1;
   enum val-2;
   enum val-3;
  }
  mandatory false;
 }
 leaf NPRSSTARTSUBFRAMEOFFSET {
  type enumeration {
   enum val-0;
   enum val-1;
   enum val-2;
   enum val-3;
   enum val-4;
   enum val-5;
   enum val-6;
   enum val-7;
  }
  mandatory false;
 }
 leaf NPRSSUBFRAMEBITMAP10 {
  type uint16 {
   range "0..1023";
  }
  mandatory false;
 }
 leaf NPRSSUBFRAMEBITMAP30 {
  type uint32 {
   range "0..1073741823";
  }
  mandatory false;
 }
 leaf NPRSSUBFRAMECONFIGMODE {
  type enumeration {
   enum val-0;
   enum val-1;
   enum val-2;
  }
  mandatory false;
 }
 leaf NUMBEROFNPRSMUTINGBITS {
  type enumeration {
   enum val-0;
   enum val-1;
   enum val-2;
   enum val-3;
  }
  mandatory false;
 }
 }
 grouping CELLOP-attributes {
 leaf LOCALCELLNAME {
  type string;
  mandatory false;
 }
 leaf CELLRESERVEDFOROP {
  type enumeration {
   enum val-0;
   enum val-1;
   enum val-2;
  }
  mandatory false;
 }
 leaf LOCALCELLID {
  type union {
   type int16 {
    range "-1..255";
   }
  }
  mandatory false;
 }
 leaf MMEC1 {
  type uint8 {
   range "0..255";
  }
  mandatory false;
 }
 leaf MMEC2 {
  type uint8 {
   range "0..255";
  }
  mandatory false;
 }
 leaf MMEC3 {
  type uint8 {
   range "0..255";
  }
  mandatory false;
 }
 leaf MMEC4 {
  type uint8 {
   range "0..255";
  }
  mandatory false;
 }
 leaf MMECFGNUM {
  type enumeration {
   enum val-0;
   enum val-1;
   enum val-2;
   enum val-3;
   enum val-4;
  }
  mandatory false;
 }
 leaf MMEGI1 {
  type uint16 {
   range "0..65535";
  }
  mandatory false;
 }
 leaf MMEGI2 {
  type uint16 {
   range "0..65535";
  }
  mandatory false;
 }
 leaf MMEGI3 {
  type uint16 {
   range "0..65535";
  }
  mandatory false;
 }
 leaf MMEGI4 {
  type uint16 {
   range "0..65535";
  }
  mandatory false;
 }
 leaf NSADCB1RSRPTHLDOFFSET {
  type int8 {
   range "-20..20";
  }
  mandatory false;
 }
 leaf NSADCRATFREQPRIORITYGRPID {
  type union {
   type uint16 {
    range "0..65535";
   }
  }
  mandatory false;
 }
 leaf OPDLRBUSEDRATIO {
  type uint8 {
   range "1..100";
  }
  mandatory false;
 }
 leaf OPGTEEPAGINGCAPACITYRATIO {
  type uint8 {
   range "0..100";
  }
  mandatory false;
 }
 leaf OPLEVELMLBTHLDADJVALUE {
  type int8 {
   range "-50..50";
  }
  mandatory false;
 }
 leaf OPLIGHTSHARINGRBUSEDRATIO {
  type uint8 {
   range "1..100";
  }
  mandatory false;
 }
 leaf OPMAXAVAILABLERBRATIO {
  type uint8 {
   range "1..100";
  }
  mandatory false;
 }
 leaf OPNONGBRRESOURCERATIO {
  type uint8 {
   range "0..50";
  }
  mandatory false;
 }
 leaf OPPTTDLRBHIGHTHD {
  type uint8 {
   range "1..100";
  }
  mandatory false;
 }
 leaf OPPTTDLRBLOWTHD {
  type uint8 {
   range "1..100";
  }
  mandatory false;
 }
 leaf OPPTTULRBHIGHTHD {
  type uint8 {
   range "1..100";
  }
  mandatory false;
 }
 leaf OPPTTULRBLOWTHD {
  type uint8 {
   range "1..100";
  }
  mandatory false;
 }
 leaf OPRESOURCEGROUPINDEX {
  type union {
   type uint8 {
    range "0..255";
   }
  }
  mandatory false;
 }
 leaf OPUENUMRATIO {
  type uint8 {
   range "1..100";
  }
  mandatory false;
 }
 leaf OPULRBUSEDRATIO {
  type uint8 {
   range "1..100";
  }
  mandatory false;
 }
 leaf OPERATORCONFIGSWITCH {
  type string;
  mandatory false;
 }
 leaf OPERATORFUNSWITCH {
  type string;
  mandatory false;
 }
 leaf OPERATORPLMNROUNDPERIOD {
  type uint16 {
   range "1..720";
  }
  mandatory false;
 }
 leaf RATFREQPRIORITYGROUPID {
  type union {
   type uint16 {
    range "0..65535";
   }
  }
  mandatory false;
 }
 leaf RBSHARINGRATIOWITHOTHEROP {
  type union {
   type uint8 {
    range "0..255";
   }
  }
  mandatory false;
 }
 leaf TRACKINGAREAID {
  type union {
   type int32 {
    range "-1..65535";
   }
  }
  mandatory false;
 }
 leaf ULAMRCMODE {
  type enumeration {
   enum val-0;
   enum val-1;
   enum val-2;
   enum val-4;
   enum val-5;
  }
  mandatory false;
 }
 leaf ULVOICEALIVECONTDUR {
  type uint16 {
   range "1..3600";
  }
  mandatory false;
 }
 leaf ULVOICEALIVEINTERVAL {
  type uint8 {
   range "3..30";
  }
  mandatory false;
 }
 leaf ULVOICEJITTERELIMINATETIME {
  type uint8 {
   range "0..10";
  }
  mandatory false;
 }
 leaf USERLABEL {
  type string {
   length "0..256";
  }
  mandatory false;
 }
 }
 grouping CELLOPHOCFG-attributes {
 leaf LOCALCELLNAME {
  type string;
  mandatory false;
 }
 leaf CNOPERATORID {
  type union {
   type int8 {
    range "-1..5";
   }
  }
  mandatory false;
 }
 leaf FDDIFHOA2THDRSRPOFFSET {
  type union {
   type int8 {
    range "-100..20";
   }
  }
  mandatory false;
 }
 leaf FIRSTRATPRI {
  type enumeration {
   enum val-1;
   enum val-2;
   enum val-3;
  }
  mandatory false;
 }
 leaf HIGHMOBIUEHOFORBIDSW {
  type string;
  mandatory false;
 }
 leaf HOMODESWITCH {
  type string;
  mandatory false;
 }
 leaf IDLECSFBHIGHESTPRI {
  type enumeration {
   enum val-0;
   enum val-1;
   enum val-2;
  }
  mandatory false;
 }
 leaf IDLECSFBLOWESTPRI {
  type enumeration {
   enum val-0;
   enum val-1;
   enum val-2;
   enum val-3;
  }
  mandatory false;
 }
 leaf IDLECSFBSECONDPRI {
  type enumeration {
   enum val-0;
   enum val-1;
   enum val-2;
   enum val-3;
  }
  mandatory false;
 }
 leaf INTERRATHIGHESTPRI {
  type enumeration {
   enum val-0;
   enum val-1;
   enum val-2;
  }
  mandatory false;
 }
 leaf INTERRATLOWESTPRI {
  type enumeration {
   enum val-0;
   enum val-1;
   enum val-2;
   enum val-3;
  }
  mandatory false;
 }
 leaf INTERRATSECONDPRI {
  type enumeration {
   enum val-0;
   enum val-1;
   enum val-2;
   enum val-3;
  }
  mandatory false;
 }
 leaf LOCALCELLID {
  type union {
   type int16 {
    range "-1..255";
   }
  }
  mandatory false;
 }
 leaf SERVINGFREQRESELPRIORITY {
  type union {
   type uint8 {
    range "0..255";
   }
  }
  mandatory false;
 }
 leaf TDDIFHOA2THDRSRPOFFSET {
  type union {
   type int8 {
    range "-100..20";
   }
  }
  mandatory false;
 }
 }
 grouping CELLPCALGO-attributes {
 leaf LOCALCELLNAME {
  type string;
  mandatory false;
 }
 leaf CELLSRSPCSINRTARGETMIN {
  type union {
   type int8 {
    range "-8..127";
   }
  }
  mandatory false;
 }
 leaf CLOSELOOPOPTPUSCHTYPE {
  type enumeration {
   enum val-0;
   enum val-1;
   enum val-2;
   enum val-3;
  }
  mandatory false;
 }
 leaf DMSRSPCSINROFFSET {
  type uint8 {
   range "0..10";
  }
  mandatory false;
 }
 leaf DTDATAUECELLCENTERSINROFS {
  type uint8 {
   range "0..20";
  }
  mandatory false;
 }
 leaf INTRFUESRSPCSINRTARGET {
  type int8 {
   range "-8..10";
  }
  mandatory false;
 }
 leaf IOTCTRLEUPLTHRESHOLD {
  type uint8 {
   range "70..140";
  }
  mandatory false;
 }
 leaf IOTCTRLINCORRECTSWITCH {
  type boolean;
  mandatory false;
 }
 leaf IOTCTRLNITHRESHOLD {
  type int8 {
   range "-118..-100";
  }
  mandatory false;
 }
 leaf IOTNEARPOINTOPTSWITCH {
  type boolean;
  mandatory false;
 }
 leaf IOTNEARPOINTPLTHRESHOLD {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
  }
  mandatory false;
 }
 leaf LOCALCELLID {
  type union {
   type int16 {
    range "-1..255";
   }
  }
  mandatory false;
 }
 leaf MMCELLCENTSINRTHLDADJVALUE {
  type uint8 {
   range "0..50";
  }
  mandatory false;
 }
 leaf NBRPUSCHSINRHIGHTHLDOFFSET {
  type int8 {
   range "-12..0";
  }
  mandatory false;
 }
 leaf NEARPOINTUEPUSCHTYPE {
  type enumeration {
   enum val-0;
   enum val-1;
   enum val-2;
  }
  mandatory false;
 }
 leaf PUSCHOPTIBLERTHRESHOLD {
  type uint8 {
   range "0..11";
  }
  mandatory false;
 }
 leaf PUSCHPSDCTRLTARGET {
  type enumeration {
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-20;
   enum val-25;
   enum val-32;
   enum val-40;
   enum val-50;
   enum val-64;
   enum val-80;
   enum val-100;
  }
  mandatory false;
 }
 leaf PUSCHPSDCTRLTARGETFORUS {
  type enumeration {
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
  }
  mandatory false;
 }
 leaf PCALGOOPTSWITCH {
  type string;
  mandatory false;
 }
 leaf PUCCHCLOSELOOPPCTYPE {
  type boolean;
  mandatory false;
 }
 leaf PUCCHPCPERIOD {
  type uint8 {
   range "1..10";
  }
  mandatory false;
 }
 leaf PUCCHPCTARGETSINROFFSET {
  type uint8 {
   range "0..15";
  }
  mandatory false;
 }
 leaf PUSCHINTRFRSRPHIGHTHLD {
  type int8 {
   range "-126..24";
  }
  mandatory false;
 }
 leaf PUSCHIOTCTRLA3OFFSET {
  type int8 {
   range "-30..30";
  }
  mandatory false;
 }
 leaf PUSCHRSRPHIGHTHD {
  type int8 {
   range "-126..24";
  }
  mandatory false;
 }
 leaf PUSCHRSRPHIGHTHDOFFSETVOIP {
  type union {
   type uint8 {
    range "0..255";
   }
  }
  mandatory false;
 }
 leaf PWRCHECKINGFUNCTIONSW {
  type boolean;
  mandatory false;
 }
 leaf SRSPCRSRPTARGET {
  type int16 {
   range "-140..-43";
  }
  mandatory false;
 }
 leaf SRSPCRSRPTARGETFORULSF {
  type int16 {
   range "-140..-43";
  }
  mandatory false;
 }
 leaf SRSPCSINRTARGET {
  type int8 {
   range "-50..50";
  }
  mandatory false;
 }
 leaf SRSPCSINRTARGETFORULSF {
  type int8 {
   range "-50..50";
  }
  mandatory false;
 }
 leaf SRSPCSTRATEGY {
  type enumeration {
   enum val-0;
   enum val-1;
   enum val-2;
  }
  mandatory false;
 }
 leaf VOLTESINRHIGHTHDOFFSET {
  type int8 {
   range "-100..0";
  }
  mandatory false;
 }
 leaf VOICEPUCCHRSRPHIGHTHLDOFS {
  type uint8 {
   range "0..30";
  }
  mandatory false;
 }
 leaf VOLTEPUSCHPOWEROFFSET {
  type uint8 {
   range "0..21";
  }
  mandatory false;
 }
 }
 grouping CELLPDCCHALGO-attributes {
 leaf LOCALCELLNAME {
  type string;
  mandatory false;
 }
 leaf ABNUEPDCCHOPTCCEUSAGETHLD {
  type uint8 {
   range "0..100";
  }
  mandatory false;
 }
 leaf ABNUEPDCCHOPTCQITHLD {
  type uint8 {
   range "0..255";
  }
  mandatory false;
 }
 leaf AGGLVLSELSTRAGEFORDUALCW {
  type enumeration {
   enum val-1;
   enum val-2;
  }
  mandatory false;
 }
 leaf CCETHDDISABLEFLOWCTRL {
  type uint8 {
   range "0..100";
  }
  mandatory false;
 }
 leaf CCETHDENABLEFLOWCTRL {
  type uint8 {
   range "0..100";
  }
  mandatory false;
 }
 leaf CAPACITYBFOPT {
  type boolean;
  mandatory false;
 }
 leaf CCEALLOCOPTDLFAILTHLD {
  type uint8 {
   range "0..100";
  }
  mandatory false;
 }
 leaf CCEALLOCOPTULFAILTHLD {
  type union {
   type uint8 {
    range "0..100";
   }
  }
  mandatory false;
 }
 leaf CCEINITIALRATIOOPTTRIGTHLD {
  type union {
   type uint8 {
    range "0..80";
   }
  }
  mandatory false;
 }
 leaf CCEMAXINITIALRATIO {
  type enumeration {
   enum val-0;
   enum val-1;
   enum val-2;
   enum val-3;
   enum val-4;
   enum val-5;
   enum val-6;
   enum val-7;
   enum val-8;
   enum val-9;
   enum val-10;
  }
  mandatory false;
 }
 leaf CCERATIOADJSWITCH {
  type enumeration {
   enum val-0;
   enum val-1;
   enum val-2;
  }
  mandatory false;
 }
 leaf CCETHDTODISABLEEPDCCH {
  type uint8 {
   range "0..100";
  }
  mandatory false;
 }
 leaf CCETHDTOENABLEEPDCCH {
  type uint8 {
   range "0..100";
  }
  mandatory false;
 }
 leaf CCEUSERATIO {
  type uint8 {
   range "1..100";
  }
  mandatory false;
 }
 leaf CFIADJCCETHLD {
  type enumeration {
   enum val-0;
   enum val-1;
   enum val-2;
   enum val-3;
   enum val-4;
   enum val-5;
   enum val-6;
  }
  mandatory false;
 }
 leaf COMSIGCONGREGLV {
  type enumeration {
   enum val-2;
   enum val-3;
  }
  mandatory false;
 }
 leaf DPDVIRTUALLOADSWITCH {
  type boolean;
  mandatory false;
 }
 leaf DPDVIRTUALLOADTYPE {
  type enumeration {
   enum val-0;
   enum val-1;
   enum val-2;
  }
  mandatory false;
 }
 leaf ECCETHDTODISABLEEPDCCH {
  type uint8 {
   range "0..100";
  }
  mandatory false;
 }
 leaf ENHCFIADAPTOPTTRIGTHLD {
  type uint8 {
   range "10..80";
  }
  mandatory false;
 }
 leaf EPDCCHALGOSWITCH {
  type string;
  mandatory false;
 }
 leaf EPDCCHSFCFG {
  type boolean;
  mandatory false;
 }
 leaf HLNETACCSIGAGGLVLSELENHSW {
  type boolean;
  mandatory false;
 }
 leaf HLNETACCSIGATTEMPT {
  type string;
  mandatory false;
 }
 leaf HARQACKFDBKMODEOPTTHLD {
  type uint8 {
   range "60..100";
  }
  mandatory false;
 }
 leaf HYSFORCFIBASEDPRESCH {
  type uint8 {
   range "0..1";
  }
  mandatory false;
 }
 leaf INITPDCCHSYMNUM {
  type uint8 {
   range "1..4";
  }
  mandatory false;
 }
 leaf LOCALCELLID {
  type union {
   type int16 {
    range "-1..255";
   }
  }
  mandatory false;
 }
 leaf NACKDTXRATIOTHD {
  type uint8 {
   range "0..100";
  }
  mandatory false;
 }
 leaf PDCCHAGGLVLADAPTSTRAGE {
  type enumeration {
   enum val-1;
   enum val-2;
  }
  mandatory false;
 }
 leaf PDCCHPWRUPPERLIMITOPTSW {
  type boolean;
  mandatory false;
 }
 leaf PDCCHADJALGOSWITCH {
  type string;
  mandatory false;
 }
 leaf PDCCHAGGLVLCLADJUSTSWITCH {
  type boolean;
  mandatory false;
 }
 leaf PDCCHBDRYPWRINCRUPPERLMT {
  type union {
   type uint8 {
    range "0..255";
   }
  }
  mandatory false;
 }
 leaf PDCCHBFGAINOFFSET {
  type union {
   type int8 {
    range "-127..10";
   }
  }
  mandatory false;
 }
 leaf PDCCHBLERTARGET {
  type uint16 {
   range "0..1000";
  }
  mandatory false;
 }
 leaf PDCCHCAPACITYIMPROVESWITCH {
  type boolean;
  mandatory false;
 }
 leaf PDCCHDLAGGLVLSLCEHNSWITCH {
  type boolean;
  mandatory false;
 }
 leaf PDCCHINITIALCCEADJUSTVALUE {
  type int8 {
   range "-10..5";
  }
  mandatory false;
 }
 leaf PDCCHMAXCODERATE {
  type uint8 {
   range "75..120";
  }
  mandatory false;
 }
 leaf PDCCHOPTIMIZATIONSWITCH {
  type string;
  mandatory false;
 }
 leaf PDCCHOUTLOOPADJBASESTEP {
  type uint8 {
   range "0..10";
  }
  mandatory false;
 }
 leaf PDCCHOUTLOOPADJLOWERLIMIT {
  type int8 {
   range "-20..0";
  }
  mandatory false;
 }
 leaf PDCCHOUTERLOOPADJLOWERLMT {
  type int8 {
   range "-20..0";
  }
  mandatory false;
 }
 leaf PDCCHPOWERBOOSTUPPERLIMIT {
  type enumeration {
   enum val-0;
   enum val-1;
   enum val-2;
  }
  mandatory false;
 }
 leaf PDCCHPOWERCHECKOPTSWITCH {
  type enumeration {
   enum val-0;
   enum val-1;
   enum val-2;
  }
  mandatory false;
 }
 leaf PDCCHPOWERCHECKSWITCH {
  type boolean;
  mandatory false;
 }
 leaf PDCCHPOWERENHANCEDSWITCH {
  type enumeration {
   enum val-0;
   enum val-1;
   enum val-2;
   enum val-3;
  }
  mandatory false;
 }
 leaf PDCCHPWRCTRLUSERNUMTHD {
  type union {
   type uint16 {
    range "0..65535";
   }
  }
  mandatory false;
 }
 leaf PDCCHSDMAWEIGHTTYPE {
  type enumeration {
   enum val-0;
   enum val-1;
   enum val-2;
   enum val-3;
   enum val-4;
  }
  mandatory false;
 }
 leaf PDCCHSINROFFSET {
  type int8 {
   range "-10..10";
  }
  mandatory false;
 }
 leaf PDCCHSPAREPOWERALLOCSTRAGE {
  type enumeration {
   enum val-0;
   enum val-1;
   enum val-2;
  }
  mandatory false;
 }
 leaf PDCCHSPECUEPWRINCREASE {
  type enumeration {
   enum val-0;
   enum val-1;
   enum val-2;
   enum val-3;
  }
  mandatory false;
 }
 leaf PDCCHSYMNUMSWITCH {
  type enumeration {
   enum val-0;
   enum val-1;
   enum val-2;
   enum val-3;
  }
  mandatory false;
 }
 leaf PDCCHSYMREDUCERATIO {
  type enumeration {
   enum val-0;
   enum val-1;
   enum val-2;
   enum val-3;
   enum val-4;
   enum val-5;
   enum val-6;
   enum val-7;
   enum val-8;
   enum val-9;
  }
  mandatory false;
 }
 leaf RBTHDTODISABLEEPDCCH {
  type uint8 {
   range "0..100";
  }
  mandatory false;
 }
 leaf RBTHDTOENABLEEPDCCH {
  type uint8 {
   range "0..100";
  }
  mandatory false;
 }
 leaf SFNPDCCHDCSTHD {
  type uint8 {
   range "0..100";
  }
  mandatory false;
 }
 leaf SFNPDCCHSDMATHD {
  type uint8 {
   range "0..100";
  }
  mandatory false;
 }
 leaf SPLITBEAMPDCCHSDMASW {
  type string;
  mandatory false;
 }
 leaf SPLITBEAMPDCCHSDMATHD {
  type uint8 {
   range "0..100";
  }
  mandatory false;
 }
 leaf SPLITBEAMPDCCHSDMATHLDOFS {
  type enumeration {
   enum val-0;
   enum val-1;
   enum val-2;
   enum val-3;
  }
  mandatory false;
 }
 leaf ULDLPDCCHSYMNUM {
  type enumeration {
   enum val-1;
   enum val-2;
   enum val-3;
  }
  mandatory false;
 }
 leaf UEMAXAGGLEVEL {
  type enumeration {
   enum val-0;
   enum val-1;
   enum val-2;
  }
  mandatory false;
 }
 leaf ULCCEALLOCOPTTHLD {
  type union {
   type uint8 {
    range "0..99";
   }
  }
  mandatory false;
 }
 leaf ULDLECCEINITIALRATIOADJSW {
  type boolean;
  mandatory false;
 }
 leaf ULPDCCHALLOCIMPROVESWITCH {
  type string;
  mandatory false;
 }
 leaf VIRTUALLOADPRO {
  type uint8 {
   range "0..100";
  }
  mandatory false;
 }
 leaf VOICEPDCCHOTLPADJLOWERLMT {
  type union {
   type int16 {
    range "-20..255";
   }
  }
  mandatory false;
 }
 leaf VOLTEPDCCHOPTSWITCH {
  type string;
  mandatory false;
 }
 leaf VOLTEPDCCHSINROFFSET {
  type uint8 {
   range "0..150";
  }
  mandatory false;
 }
 }
 grouping CELLPRBGROUPPARAM-attributes {
 leaf LOCALCELLNAME {
  type string;
  mandatory false;
 }
 leaf OLD_CELLPRBGROUPID {
  type union {
   type int8 {
    range "-1..35";
   }
  }
  mandatory false;
 }
 leaf CELLPRBGROUPID {
  type union {
   type int8 {
    range "-1..35";
   }
  }
  mandatory false;
 }
 leaf COMMONPRFMSTATGROUPID {
  type union {
   type uint8 {
    range "0..255";
   }
  }
  mandatory false;
 }
 leaf DLPRBRESERVEDRATIO {
  type uint8 {
   range "1..100";
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf PERFORMANCESTATGROUPID {
  type union {
   type uint8 {
    range "0..255";
   }
  }
  mandatory false;
 }
 leaf TRACKINGAREAID {
  type uint16 {
   range "0..65535";
  }
  mandatory false;
 }
 leaf ULPRBRESERVEDRATIO {
  type uint8 {
   range "1..100";
  }
  mandatory false;
 }
 leaf USERPRBGROUPID {
  type uint8 {
   range "0..215";
  }
  mandatory false;
 }
 }
 grouping CELLPRBVALMLB-attributes {
 leaf LOCALCELLNAME {
  type string;
  mandatory false;
 }
 leaf LOCALCELLID {
  type union {
   type int16 {
    range "-1..255";
   }
  }
  mandatory false;
 }
 leaf MLBUESELECTPRBVALTHD {
  type uint8 {
   range "0..50";
  }
  mandatory false;
 }
 leaf PRBVALFILTERFACTOR {
  type uint8 {
   range "1..100";
  }
  mandatory false;
 }
 leaf PRBVALMLBADMITTHD {
  type uint8 {
   range "1..100";
  }
  mandatory false;
 }
 leaf PRBVALMLBTRIGTHD {
  type uint8 {
   range "1..100";
  }
  mandatory false;
 }
 }
 grouping CELLPREALLOCGROUP-attributes {
 leaf LOCALCELLNAME {
  type string;
  mandatory false;
 }
 leaf OLD_LOCALCELLID {
  type union {
   type int16 {
    range "-1..255";
   }
  }
  mandatory false;
 }
 leaf LOCALCELLID {
  type union {
   type int16 {
    range "-1..255";
   }
  }
  mandatory false;
 }
 leaf PREALLOCATIONMINPERIOD {
  type uint8 {
   range "1..40";
  }
  mandatory false;
 }
 leaf OLD_PREALLOCATIONPARAGROUPID {
  type union {
   type int8 {
    range "-1..9";
   }
  }
  mandatory false;
 }
 leaf PREALLOCATIONPARAGROUPID {
  type union {
   type int8 {
    range "-1..9";
   }
  }
  mandatory false;
 }
 leaf PREALLOCATIONSIZE {
  type uint16 {
   range "45..1500";
  }
  mandatory false;
 }
 leaf PREALLOCATIONSWITCH {
  type boolean;
  mandatory false;
 }
 leaf SMARTPREALLOCATIONDURATION {
  type uint16 {
   range "0..2000";
  }
  mandatory false;
 }
 leaf SMARTPREALLOCATIONSWITCH {
  type boolean;
  mandatory false;
 }
 }
 grouping CELLPRSCFG-attributes {
 leaf LOCALCELLNAME {
  type string;
  mandatory false;
 }
 leaf LOCALCELLID {
  type union {
   type int16 {
    range "-1..255";
   }
  }
  mandatory false;
 }
 leaf NUMBEROFDLFRAMESFORPRS {
  type enumeration {
   enum val-0;
   enum val-1;
   enum val-2;
   enum val-3;
  }
  mandatory false;
 }
 leaf NUMOFPRSMUTINGBIT {
  type enumeration {
   enum val-0;
   enum val-1;
   enum val-2;
   enum val-3;
  }
  mandatory false;
 }
 leaf PRSBANDWIDTH {
  type enumeration {
   enum val-0;
   enum val-1;
   enum val-2;
   enum val-3;
   enum val-4;
   enum val-5;
  }
  mandatory false;
 }
 leaf PRSCONFIGURATIONINDEX {
  type uint16 {
   range "0..2399";
  }
  mandatory false;
 }
 leaf PRSMUTINGCONFIGURATION {
  type uint16 {
   range "0..65535";
  }
  mandatory false;
 }
 }
 grouping CELLPUCCHALGO-attributes {
 leaf LOCALCELLNAME {
  type string;
  mandatory false;
 }
 leaf LOCALCELLID {
  type union {
   type int16 {
    range "-1..255";
   }
  }
  mandatory false;
 }
 leaf SRIALGOSWITCH {
  type string;
  mandatory false;
 }
 leaf SRILOWLOADTHD {
  type uint8 {
   range "0..50";
  }
  mandatory false;
 }
 leaf SRIRECFGIND {
  type boolean;
  mandatory false;
 }
 }
 grouping CELLPWRSAVINGALGO-attributes {
 leaf LOCALCELLNAME {
  type string;
  mandatory false;
 }
 leaf AVAILABLEREMAININGRBRATIO {
  type uint8 {
   range "0..100";
  }
  mandatory false;
 }
 leaf CARRIERDYNSHUTDOWNPH2SW {
  type enumeration {
   enum val-0;
   enum val-1;
   enum val-2;
   enum val-3;
  }
  mandatory false;
 }
 leaf DORMANCYCELLTYPE {
  type boolean;
  mandatory false;
 }
 leaf INTELPCCRSPWRRDAMT {
  type enumeration {
   enum val-0;
   enum val-1;
   enum val-2;
   enum val-3;
   enum val-4;
   enum val-5;
   enum val-6;
   enum val-7;
   enum val-8;
   enum val-9;
   enum val-10;
   enum val-11;
  }
  mandatory false;
 }
 leaf INTELPCSTARTTIME {
  type hwat:HH_MM_SS_Time;
  mandatory false;
 }
 leaf INTELPCSTOPTIME {
  type hwat:HH_MM_SS_Time;
  mandatory false;
 }
 leaf INTELPCWEAKCOVRSRPTHLD {
  type int16 {
   range "-140..-43";
  }
  mandatory false;
 }
 leaf INTELPCWEAKCOVUSERNUMTHLD {
  type uint8 {
   range "0..255";
  }
  mandatory false;
 }
 leaf INTERFREQHOENHA2THLDOFS {
  type uint8 {
   range "0..60";
  }
  mandatory false;
 }
 leaf INTERFREQHOENHA3MEASPRD {
  type union {
   type uint8 {
    range "0..60";
   }
  }
  mandatory false;
 }
 leaf INTERFREQHOENHPROTECTTHLD {
  type int16 {
   range "-140..-43";
  }
  mandatory false;
 }
 leaf LOCALCELLID {
  type union {
   type int16 {
    range "-1..255";
   }
  }
  mandatory false;
 }
 leaf PWRRCYDLHILDTTINUMTHLD {
  type uint8 {
   range "0..20";
  }
  mandatory false;
 }
 leaf PWRRCYDLPRBTHLD {
  type uint8 {
   range "0..100";
  }
  mandatory false;
 }
 leaf PWRRDDLHILDTTINUMTHLD {
  type uint8 {
   range "0..20";
  }
  mandatory false;
 }
 leaf PWRRDDLPRBTHLD {
  type uint8 {
   range "0..100";
  }
  mandatory false;
 }
 leaf PWRSAVINGALGOSWITCH {
  type string;
  mandatory false;
 }
 }
 grouping CELLPWRSAVINGPOLICY-attributes {
 leaf LOCALCELLNAME {
  type string;
  mandatory false;
 }
 leaf DLPRBOFFSET {
  type uint8 {
   range "0..100";
  }
  mandatory false;
 }
 leaf DLPRBTHLD {
  type uint8 {
   range "0..100";
  }
  mandatory false;
 }
 leaf EXITJUDGEPERIOD {
  type uint8 {
   range "1..120";
  }
  mandatory false;
 }
 leaf FORCIBLETRIGGERUENUMTHLD {
  type uint8 {
   range "0..10";
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf PENALTYTIME {
  type uint16 {
   range "0..360";
  }
  mandatory false;
 }
 leaf OLD_POLICYINDEX {
  type union {
   type int8 {
    range "-1..15";
   }
  }
  mandatory false;
 }
 leaf POLICYINDEX {
  type union {
   type int8 {
    range "-1..15";
   }
  }
  mandatory false;
 }
 leaf POWERADJUSTMENTLEVEL {
  type enumeration {
   enum val-1;
   enum val-2;
   enum val-3;
   enum val-4;
  }
  mandatory false;
 }
 leaf POWERSAVINGTYPE {
  type enumeration {
   enum val-0;
   enum val-1;
   enum val-2;
   enum val-3;
   enum val-4;
   enum val-5;
  }
  mandatory false;
 }
 leaf PROTECTDLPRBOFFSET {
  type uint8 {
   range "0..100";
  }
  mandatory false;
 }
 leaf PROTECTDLPRBTHLD {
  type uint8 {
   range "0..100";
  }
  mandatory false;
 }
 leaf PROTECTULPRBOFFSET {
  type uint8 {
   range "0..100";
  }
  mandatory false;
 }
 leaf PROTECTULPRBTHLD {
  type uint8 {
   range "0..100";
  }
  mandatory false;
 }
 leaf STARTTIME {
  type hwat:HH_MM_SS_Time;
  mandatory false;
 }
 leaf STOPTIME {
  type hwat:HH_MM_SS_Time;
  mandatory false;
 }
 leaf TRIGGERJUDGEPERIOD {
  type uint8 {
   range "1..10";
  }
  mandatory false;
 }
 leaf UENUMOFFSET {
  type uint16 {
   range "0..5000";
  }
  mandatory false;
 }
 leaf UENUMTHLD {
  type uint16 {
   range "0..5000";
  }
  mandatory false;
 }
 leaf ULPRBOFFSET {
  type uint8 {
   range "0..100";
  }
  mandatory false;
 }
 leaf ULPRBTHLD {
  type uint8 {
   range "0..100";
  }
  mandatory false;
 }
 }
 grouping CELLQCIPARA-attributes {
 leaf LOCALCELLNAME {
  type string;
  mandatory false;
 }
 leaf CEUULPATHLOSSTHLD {
  type enumeration {
   enum val-0;
   enum val-1;
   enum val-2;
   enum val-3;
   enum val-4;
   enum val-5;
   enum val-6;
   enum val-7;
   enum val-8;
   enum val-9;
  }
  mandatory false;
 }
 leaf CONGESTIONTHRESHOLD {
  type uint8 {
   range "0..99";
  }
  mandatory false;
 }
 leaf DECREASEINNACKCQIADJ {
  type uint16 {
   range "0..330";
  }
  mandatory false;
 }
 leaf DLAMBRLIMITFACTOR {
  type uint16 {
   range "10..1000";
  }
  mandatory false;
 }
 leaf DRXPARAGROUPID {
  type uint8 {
   range "0..49";
  }
  mandatory false;
 }
 leaf EMTCMODEACL0DRXPARAGROUPID {
  type union {
   type uint8 {
    range "0..255";
   }
  }
  mandatory false;
 }
 leaf EMTCMODEADRXPARAGROUPID {
  type union {
   type uint8 {
    range "0..255";
   }
  }
  mandatory false;
 }
 leaf EMTCMODEBCL2DRXPARAGROUPID {
  type union {
   type uint8 {
    range "0..255";
   }
  }
  mandatory false;
 }
 leaf EMTCMODEBDRXPARAGROUPID {
  type union {
   type uint8 {
    range "0..255";
   }
  }
  mandatory false;
 }
 leaf EMTCSRIPERIOD {
  type enumeration {
   enum val-0;
   enum val-1;
   enum val-2;
   enum val-3;
   enum val-4;
  }
  mandatory false;
 }
 leaf HANDOVERADMISSIONTHRESHOLD {
  type uint8 {
   range "10..99";
  }
  mandatory false;
 }
 leaf INITDLTARGETIBLER {
  type uint8 {
   range "0..99";
  }
  mandatory false;
 }
 leaf INTERFREQHOGROUPID {
  type uint8 {
   range "0..19";
  }
  mandatory false;
 }
 leaf INTERRATHOCDMAHRPDGROUPID {
  type uint8 {
   range "0..9";
  }
  mandatory false;
 }
 leaf INTERRATHOCOMMGROUPID {
  type uint8 {
   range "0..19";
  }
  mandatory false;
 }
 leaf INTERRATHOGERANGROUPID {
  type uint8 {
   range "0..19";
  }
  mandatory false;
 }
 leaf INTERRATHOUTRANGROUPID {
  type uint8 {
   range "0..19";
  }
  mandatory false;
 }
 leaf INTRAFREQHOGROUPID {
  type uint8 {
   range "0..19";
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf LOWDELAYCEUPREALLOCOPTTHLD {
  type int8 {
   range "-51..100";
  }
  mandatory false;
 }
 leaf LOWDELAYUESRSCHMINDATAVOL {
  type uint16 {
   range "0..65535";
  }
  mandatory false;
 }
 leaf LOWLATENCYFLAG {
  type boolean;
  mandatory false;
 }
 leaf MAXQUEUEDURATION {
  type uint8 {
   range "0..5";
  }
  mandatory false;
 }
 leaf MAXIMUMNUMBEROFCARRIERS {
  type uint8 {
   range "1..8";
  }
  mandatory false;
 }
 leaf MLBQCIGROUPID {
  type union {
   type uint8 {
    range "0..255";
   }
  }
  mandatory false;
 }
 leaf NRHOPARAMGROUPID {
  type uint8 {
   range "0..9";
  }
  mandatory false;
 }
 leaf NRSCGFREQPRIORITYGROUPID {
  type union {
   type uint16 {
    range "0..65535";
   }
  }
  mandatory false;
 }
 leaf NSADCDEFAULTBEARERMODE {
  type enumeration {
   enum val-0;
   enum val-1;
   enum val-2;
   enum val-3;
  }
  mandatory false;
 }
 leaf NSADCDRXPARAGROUPID {
  type union {
   type uint8 {
    range "0..255";
   }
  }
  mandatory false;
 }
 leaf NSADCGERANHOGROUPID {
  type uint8 {
   range "0..19";
  }
  mandatory false;
 }
 leaf NSADCINTERFREQHOGROUPID {
  type union {
   type uint8 {
    range "0..255";
   }
  }
  mandatory false;
 }
 leaf NSADCINTERRATHOCOMMGROUPID {
  type uint8 {
   range "0..19";
  }
  mandatory false;
 }
 leaf NSADCINTRAFREQHOGROUPID {
  type uint8 {
   range "0..19";
  }
  mandatory false;
 }
 leaf NSADCOPTSWITCH {
  type string;
  mandatory false;
 }
 leaf NSADCQCIPARAMGROUPID {
  type uint8 {
   range "0..9";
  }
  mandatory false;
 }
 leaf NSADCRATFREQPRIORITYGRPID {
  type union {
   type uint16 {
    range "0..65535";
   }
  }
  mandatory false;
 }
 leaf NSADCUTRANHOGROUPID {
  type uint8 {
   range "0..19";
  }
  mandatory false;
 }
 leaf PREALLOCATIONPARAGROUPID {
  type union {
   type uint8 {
    range "0..255";
   }
  }
  mandatory false;
 }
 leaf OLD_QCI {
  type union {
   type int16 {
    range "-1..254";
   }
  }
  mandatory false;
 }
 leaf QCI {
  type union {
   type int16 {
    range "-1..254";
   }
  }
  mandatory false;
 }
 leaf QCIALGOSWITCH {
  type string;
  mandatory false;
 }
 leaf QCIAMBRLIMITFLAG {
  type enumeration {
   enum val-0;
   enum val-1;
   enum val-2;
  }
  mandatory false;
 }
 leaf QCIEUTRANFREQRELATIONID {
  type uint8 {
   range "0..9";
  }
  mandatory false;
 }
 leaf QCIGERANFREQRELATIONID {
  type uint8 {
   range "0..9";
  }
  mandatory false;
 }
 leaf QCIPDCCHSINROFFSET {
  type uint8 {
   range "0..150";
  }
  mandatory false;
 }
 leaf QCIPRIORITYFORDRX {
  type uint8 {
   range "1..254";
  }
  mandatory false;
 }
 leaf QCIPRIORITYFORHO {
  type uint8 {
   range "1..254";
  }
  mandatory false;
 }
 leaf QCISINRTHLDFORTRIGTTIBB {
  type int8 {
   range "-5..10";
  }
  mandatory false;
 }
 leaf QCIUTRANFREQRELATIONID {
  type uint8 {
   range "0..9";
  }
  mandatory false;
 }
 leaf RATFREQPRIORITYGROUPID {
  type union {
   type uint16 {
    range "0..65535";
   }
  }
  mandatory false;
 }
 leaf RLFTIMERCONSTCFGIND {
  type boolean;
  mandatory false;
 }
 leaf RLFTIMERCONSTGROUPID {
  type uint8 {
   range "0..9";
  }
  mandatory false;
 }
 leaf SERVRESELTRGDLEARFCN {
  type union {
   type uint32 {
    range "0..4294967295";
   }
  }
  mandatory false;
 }
 leaf SERVICEFLAG {
  type boolean;
  mandatory false;
 }
 leaf SINRADJUSTTARGETIBLER {
  type uint8 {
   range "0..99";
  }
  mandatory false;
 }
 leaf SRIPERIOD {
  type enumeration {
   enum val-0;
   enum val-1;
   enum val-2;
   enum val-3;
   enum val-4;
  }
  mandatory false;
 }
 leaf TRAFFICRELDELAY {
  type uint16 {
   range "0..65000";
  }
  mandatory false;
 }
 leaf ULAMBRLIMITFACTOR {
  type uint16 {
   range "10..1000";
  }
  mandatory false;
 }
 leaf ULHARQMAXTXNUM {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf USUECONTROLRATE {
  type uint16 {
   range "1..65535";
  }
  mandatory false;
 }
 }
 grouping CELLQCIPARAEXTENSION-attributes {
 leaf LOCALCELLNAME {
  type string;
  mandatory false;
 }
 leaf DLMINGBR {
  type enumeration {
   enum val-0;
   enum val-8000;
   enum val-16000;
   enum val-32000;
   enum val-64000;
   enum val-128000;
   enum val-256000;
   enum val-512000;
   enum val-1024000;
   enum val-2048000;
   enum val-4096000;
   enum val-8192000;
   enum val-12288000;
   enum val-16384000;
   enum val-20480000;
  }
  mandatory false;
 }
 leaf DLSCHPRIORITYWEIGHTFACTOR {
  type uint16 {
   range "1..1000";
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf OLD_QCI {
  type union {
   type int16 {
    range "-1..254";
   }
  }
  mandatory false;
 }
 leaf QCI {
  type union {
   type int16 {
    range "-1..254";
   }
  }
  mandatory false;
 }
 leaf ULBESTEFFORTGBR {
  type uint16 {
   range "0..65535";
  }
  mandatory false;
 }
 leaf ULMINGBR {
  type enumeration {
   enum val-0;
   enum val-8000;
   enum val-16000;
   enum val-32000;
   enum val-64000;
   enum val-128000;
   enum val-256000;
   enum val-512000;
   enum val-1024000;
   enum val-2048000;
   enum val-4096000;
   enum val-8192000;
   enum val-12288000;
   enum val-16384000;
   enum val-20480000;
  }
  mandatory false;
 }
 leaf ULSCHPRIORITYWEIGHTFACTOR {
  type uint16 {
   range "1..1000";
  }
  mandatory false;
 }
 }
 grouping CELLRACHALGO-attributes {
 leaf LOCALCELLNAME {
  type string;
  mandatory false;
 }
 leaf LOCALCELLID {
  type union {
   type int16 {
    range "-1..255";
   }
  }
  mandatory false;
 }
 leaf PRACHFALSEALARMDETRADTHD {
  type union {
   type uint32 {
    range "0..328080";
   }
  }
  mandatory false;
 }
 leaf PRACHINTERFHYSTERESIS {
  type uint8 {
   range "5..35";
  }
  mandatory false;
 }
 leaf PRACHINTERFPERIOD {
  type uint16 {
   range "10..600";
  }
  mandatory false;
 }
 leaf PRACHINTERFTHRESHOLD {
  type int8 {
   range "-115..-80";
  }
  mandatory false;
 }
 leaf RACHTHDBOOSTRATIO {
  type int16 {
   range "-100..1000";
  }
  mandatory false;
 }
 }
 grouping CELLRACHCECFG-attributes {
 leaf LOCALCELLNAME {
  type string;
  mandatory false;
 }
 leaf CONTENTIONRESOLUTIONTIMER {
  type enumeration {
   enum val-0;
   enum val-1;
   enum val-2;
   enum val-3;
   enum val-4;
   enum val-5;
   enum val-6;
   enum val-7;
  }
  mandatory false;
 }
 leaf COVERAGELEVEL {
  type enumeration {
   enum val--1;
   enum val-0;
   enum val-1;
   enum val-2;
  }
  mandatory false;
 }
 leaf EDTCONTENTIONRESTIMER {
  type enumeration {
   enum val-0;
   enum val-1;
   enum val-2;
   enum val-3;
   enum val-4;
   enum val-5;
   enum val-6;
   enum val-7;
  }
  mandatory false;
 }
 leaf LOCALCELLID {
  type union {
   type int16 {
    range "-1..255";
   }
  }
  mandatory false;
 }
 leaf MAXNUMPREAMBLEATTEMPT {
  type enumeration {
   enum val-0;
   enum val-1;
   enum val-2;
   enum val-3;
   enum val-4;
   enum val-5;
   enum val-6;
  }
  mandatory false;
 }
 leaf RARESPONSEWINDOWSIZE {
  type enumeration {
   enum val-0;
   enum val-1;
   enum val-2;
   enum val-3;
   enum val-4;
   enum val-5;
   enum val-6;
   enum val-7;
  }
  mandatory false;
 }
 }
 grouping CELLRACTHD-attributes {
 leaf LOCALCELLNAME {
  type string;
  mandatory false;
 }
 leaf ACRESERVEDUSERNUMBER {
  type uint8 {
   range "0..30";
  }
  mandatory false;
 }
 leaf ACUSERNUMBER {
  type uint16 {
   range "0..65535";
  }
  mandatory false;
 }
 leaf ADMISSIONCONTROLPOLICY {
  type string;
  mandatory false;
 }
 leaf CCEALFAILHIGHTHD {
  type uint8 {
   range "0..100";
  }
  mandatory false;
 }
 leaf CCETHDFORVOLTELOADAMRC {
  type uint8 {
   range "0..100";
  }
  mandatory false;
 }
 leaf CCEUSAGETHD {
  type union {
   type uint8 {
    range "0..100";
   }
  }
  mandatory false;
 }
 leaf CELLCAPACITYMODE {
  type enumeration {
   enum val-0;
   enum val-1;
   enum val-2;
  }
  mandatory false;
 }
 leaf CONGBEARRELPERIOD {
  type uint8 {
   range "1..15";
  }
  mandatory false;
 }
 leaf CONGRELOFFSET {
  type uint8 {
   range "0..50";
  }
  mandatory false;
 }
 leaf CONGESTIONBEARERRELCOUNT {
  type uint8 {
   range "1..15";
  }
  mandatory false;
 }
 leaf COPPERSERVICEARPTHLD {
  type uint8 {
   range "1..15";
  }
  mandatory false;
 }
 leaf CQIFARTHD {
  type uint8 {
   range "0..32";
  }
  mandatory false;
 }
 leaf DLEXPERIENCETHD {
  type uint32 {
   range "1..1000000";
  }
  mandatory false;
 }
 leaf EMTCADMISSIONCONTROLUECNT {
  type uint16 {
   range "0..65535";
  }
  mandatory false;
 }
 leaf GOLDSERVICEARPTHD {
  type uint8 {
   range "1..15";
  }
  mandatory false;
 }
 leaf HORESERVEDUENUMBER {
  type uint16 {
   range "0..500";
  }
  mandatory false;
 }
 leaf LOADHOADMITOFFSET {
  type uint8 {
   range "0..90";
  }
  mandatory false;
 }
 leaf LOCALCELLID {
  type union {
   type int16 {
    range "-1..255";
   }
  }
  mandatory false;
 }
 leaf MOSIGARPOVERRIDE {
  type uint8 {
   range "0..15";
  }
  mandatory false;
 }
 leaf NEWCOPPERSERVICEOFFSET {
  type uint8 {
   range "0..90";
  }
  mandatory false;
 }
 leaf NEWGOLDSERVICEOFFSET {
  type uint8 {
   range "0..90";
  }
  mandatory false;
 }
 leaf NEWIRONSERVICEOFFSET {
  type uint8 {
   range "0..90";
  }
  mandatory false;
 }
 leaf NEWSILVERSERVICEOFFSET {
  type uint8 {
   range "0..90";
  }
  mandatory false;
 }
 leaf NSAARPOVERRIDE {
  type uint8 {
   range "0..30";
  }
  mandatory false;
 }
 leaf PRERESNEEDTUNINGFACTOR {
  type uint8 {
   range "1..100";
  }
  mandatory false;
 }
 leaf PREEMPTABLEBEARERNUM {
  type uint8 {
   range "10..100";
  }
  mandatory false;
 }
 leaf RBCONGHIGHTHD {
  type uint8 {
   range "0..100";
  }
  mandatory false;
 }
 leaf SILVERSERVICEARPTHD {
  type uint8 {
   range "1..15";
  }
  mandatory false;
 }
 leaf ULEXPERIENCETHD {
  type uint32 {
   range "1..1000000";
  }
  mandatory false;
 }
 leaf ULRBHIGHTHD {
  type uint8 {
   range "10..100";
  }
  mandatory false;
 }
 leaf ULRBLOWTHD {
  type uint8 {
   range "10..100";
  }
  mandatory false;
 }
 leaf ULRBTHDFORVOLTELOADAMRC {
  type uint8 {
   range "0..100";
  }
  mandatory false;
 }
 leaf VOIPOVERADMITOFFSET {
  type uint8 {
   range "0..100";
  }
  mandatory false;
 }
 leaf VOLTEARPOVERRIDE {
  type uint8 {
   range "0..15";
  }
  mandatory false;
 }
 leaf VOLTEPREFADMISSIONTIMER {
  type uint8 {
   range "1..10";
  }
  mandatory false;
 }
 leaf VOLTERESERVEDNUMBER {
  type uint8 {
   range "0..100";
  }
  mandatory false;
 }
 }
 grouping CELLRBRESERVE-attributes {
 leaf LOCALCELLNAME {
  type string;
  mandatory false;
 }
 leaf OLD_INDEX {
  type union {
   type int8 {
    range "-1..99";
   }
  }
  mandatory false;
 }
 leaf INDEX {
  type union {
   type int8 {
    range "-1..99";
   }
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf RBRSVENDINDEX {
  type uint8 {
   range "0..99";
  }
  mandatory false;
 }
 leaf RBRSVMODE {
  type enumeration {
   enum val-0;
   enum val-1;
   enum val-2;
   enum val-3;
   enum val-4;
   enum val-5;
   enum val-6;
   enum val-7;
   enum val-8;
  }
  mandatory false;
 }
 leaf RBRSVSTARTINDEX {
  type uint8 {
   range "0..99";
  }
  mandatory false;
 }
 leaf RBRSVTYPE {
  type boolean;
  mandatory false;
 }
 }
 grouping CELLRELAYALGOPARA-attributes {
 leaf LOCALCELLNAME {
  type string;
  mandatory false;
 }
 leaf DLENHANCEDRELAYSCHSW {
  type string;
  mandatory false;
 }
 leaf DLRELAYSUBFRAMERATIO {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
  }
  mandatory false;
 }
 leaf DLSINRADJTARGETIBLER {
  type uint8 {
   range "1..99";
  }
  mandatory false;
 }
 leaf INBANDRELAYCONCNT {
  type enumeration {
   enum val-0;
   enum val-1;
   enum val-2;
   enum val-3;
   enum val-4;
  }
  mandatory false;
 }
 leaf LOCALCELLID {
  type union {
   type int16 {
    range "-1..255";
   }
  }
  mandatory false;
 }
 leaf RRNPREALLOCATIONMINPERIOD {
  type uint8 {
   range "1..40";
  }
  mandatory false;
 }
 leaf RRNPREALLOCATIONSIZE {
  type uint16 {
   range "45..1500";
  }
  mandatory false;
 }
 leaf ULENHANCEDRELAYSCHSW {
  type string;
  mandatory false;
 }
 leaf ULRELAYSUBFRAMERATIO {
  type enumeration {
   enum val-0;
   enum val-1;
   enum val-2;
   enum val-3;
   enum val-4;
   enum val-5;
   enum val-6;
   enum val-7;
   enum val-8;
   enum val-9;
  }
  mandatory false;
 }
 leaf ULSINRADJTARGETIBLER {
  type uint8 {
   range "1..99";
  }
  mandatory false;
 }
 }
 grouping CELLRESEL-attributes {
 leaf LOCALCELLNAME {
  type string;
  mandatory false;
 }
 leaf AGGREGATIONATTRIBUTE {
  type string;
  mandatory false;
 }
 leaf CELLRESELPRIORITY {
  type uint8 {
   range "0..7";
  }
  mandatory false;
 }
 leaf EMTCCELLRESELPRIORITY {
  type uint8 {
   range "0..7";
  }
  mandatory false;
 }
 leaf EMTCRESELRELAXMONMEASTHLD {
  type enumeration {
   enum val-0;
   enum val-1;
   enum val-2;
   enum val-3;
   enum val-4;
  }
  mandatory false;
 }
 leaf LOCALCELLID {
  type union {
   type int16 {
    range "-1..255";
   }
  }
  mandatory false;
 }
 leaf MEASBANDWIDTH {
  type enumeration {
   enum val-0;
   enum val-1;
   enum val-2;
   enum val-3;
   enum val-4;
   enum val-5;
  }
  mandatory false;
 }
 leaf MEASBANDWIDTHCFGIND {
  type boolean;
  mandatory false;
 }
 leaf NCELLCHANGEHIGH {
  type uint8 {
   range "1..16";
  }
  mandatory false;
 }
 leaf NCELLCHANGEMEDIUM {
  type uint8 {
   range "1..16";
  }
  mandatory false;
 }
 leaf NBCONNMODERELAXMONITORTHLD {
  type enumeration {
   enum val-0;
   enum val-1;
   enum val-2;
   enum val-3;
   enum val-4;
  }
  mandatory false;
 }
 leaf NBRESELRELAXEDMONMEASTHLD {
  type enumeration {
   enum val-0;
   enum val-1;
   enum val-2;
   enum val-3;
   enum val-4;
  }
  mandatory false;
 }
 leaf NEIGHCELLCONFIG {
  type enumeration {
   enum val-0;
   enum val-1;
   enum val-2;
   enum val-3;
  }
  mandatory false;
 }
 leaf PMAX {
  type int8 {
   range "-30..33";
  }
  mandatory false;
 }
 leaf PMAXCFGIND {
  type boolean;
  mandatory false;
 }
 leaf PRESENCEANTENNAPORT1 {
  type boolean;
  mandatory false;
 }
 leaf PWROFFSETFORRESELTOINTRANB {
  type enumeration {
   enum val-0;
   enum val-1;
   enum val-2;
   enum val-3;
   enum val-4;
   enum val-5;
   enum val-255;
  }
  mandatory false;
 }
 leaf QHYSTSFHIGH {
  type enumeration {
   enum val-0;
   enum val-1;
   enum val-2;
   enum val-3;
  }
  mandatory false;
 }
 leaf QHYSTSFMEDIUM {
  type enumeration {
   enum val-0;
   enum val-1;
   enum val-2;
   enum val-3;
  }
  mandatory false;
 }
 leaf QQUALMIN {
  type int8 {
   range "-34..-3";
  }
  mandatory false;
 }
 leaf QQUALMINCFGIND {
  type boolean;
  mandatory false;
 }
 leaf QQUALMINFORCEMODEA {
  type union {
   type int8 {
    range "-34..0";
   }
  }
  mandatory false;
 }
 leaf QQUALMINFORCEMODEB {
  type union {
   type int8 {
    range "-34..0";
   }
  }
  mandatory false;
 }
 leaf QRXLEVMIN {
  type int8 {
   range "-78..-22";
  }
  mandatory false;
 }
 leaf QRXLEVMINFORCEMODEA {
  type int8 {
   range "-70..-22";
  }
  mandatory false;
 }
 leaf QRXLEVMINFORCEMODEB {
  type int8 {
   range "-78..-22";
  }
  mandatory false;
 }
 leaf QHYST {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf SINTRASEARCH {
  type uint8 {
   range "0..63";
  }
  mandatory false;
 }
 leaf SINTRASEARCHCFGIND {
  type boolean;
  mandatory false;
 }
 leaf SINTRASEARCHQ {
  type uint8 {
   range "0..31";
  }
  mandatory false;
 }
 leaf SMEASINTERFORNBCONN {
  type union {
   type int16 {
    range "-156..0";
   }
  }
  mandatory false;
 }
 leaf SMEASINTRAFORNBCONN {
  type union {
   type int16 {
    range "-156..0";
   }
  }
  mandatory false;
 }
 leaf SNONINTRASEARCH {
  type uint8 {
   range "0..31";
  }
  mandatory false;
 }
 leaf SNONINTRASEARCHCFGIND {
  type boolean;
  mandatory false;
 }
 leaf SNONINTRASEARCHQ {
  type uint8 {
   range "0..31";
  }
  mandatory false;
 }
 leaf SPEEDDEPRESELCFGIND {
  type boolean;
  mandatory false;
 }
 leaf SPEEDSTATESFCFGIND {
  type boolean;
  mandatory false;
 }
 leaf TEVALUATION {
  type enumeration {
   enum val-0;
   enum val-1;
   enum val-2;
   enum val-3;
   enum val-4;
  }
  mandatory false;
 }
 leaf THYSTNORMAL {
  type enumeration {
   enum val-0;
   enum val-1;
   enum val-2;
   enum val-3;
   enum val-4;
  }
  mandatory false;
 }
 leaf TRESELEUTRAN {
  type uint8 {
   range "0..7";
  }
  mandatory false;
 }
 leaf TRESELEUTRANCE {
  type uint8 {
   range "0..15";
  }
  mandatory false;
 }
 leaf TRESELEUTRANSFHIGH {
  type enumeration {
   enum val-0;
   enum val-1;
   enum val-2;
   enum val-3;
  }
  mandatory false;
 }
 leaf TRESELEUTRANSFMEDIUM {
  type enumeration {
   enum val-0;
   enum val-1;
   enum val-2;
   enum val-3;
  }
  mandatory false;
 }
 leaf TRESELFORNB {
  type enumeration {
   enum val-0;
   enum val-1;
   enum val-2;
   enum val-3;
   enum val-4;
   enum val-5;
   enum val-6;
   enum val-7;
  }
  mandatory false;
 }
 leaf TRESELINTERFREQFORNB {
  type enumeration {
   enum val-0;
   enum val-3;
   enum val-6;
   enum val-9;
   enum val-12;
   enum val-15;
   enum val-18;
   enum val-21;
  }
  mandatory false;
 }
 leaf THRSHSERVLOW {
  type uint8 {
   range "0..31";
  }
  mandatory false;
 }
 leaf THRSHSERVLOWQ {
  type uint8 {
   range "0..31";
  }
  mandatory false;
 }
 leaf THRSHSERVLOWQCFGIND {
  type boolean;
  mandatory false;
 }
 }
 grouping CELLRESELCDMA2000-attributes {
 leaf LOCALCELLNAME {
  type string;
  mandatory false;
 }
 leaf CDMAEUTRASYN {
  type boolean;
  mandatory false;
 }
 leaf HRPDCELLRESELECTPARAMCFGIND {
  type boolean;
  mandatory false;
 }
 leaf HRPDPARACFGIND {
  type boolean;
  mandatory false;
 }
 leaf LOCALCELLID {
  type union {
   type int16 {
    range "-1..255";
   }
  }
  mandatory false;
 }
 leaf SEARCHWNDSIZE {
  type uint8 {
   range "0..15";
  }
  mandatory false;
 }
 leaf SEARCHWNDSIZECFGIND {
  type boolean;
  mandatory false;
 }
 leaf SPEEDSTATESFCFGIND {
  type boolean;
  mandatory false;
 }
 leaf SUPPORTDUALRXCSFB {
  type boolean;
  mandatory false;
 }
 leaf SUPPORTDUALRXCSFBCFGIND {
  type boolean;
  mandatory false;
 }
 leaf SYSTIMECFGIND {
  type boolean;
  mandatory false;
 }
 leaf TRESELCDMAHRPDSFHIGH {
  type enumeration {
   enum val-0;
   enum val-1;
   enum val-2;
   enum val-3;
  }
  mandatory false;
 }
 leaf TRESELCDMAHRPDSFMEDIUM {
  type enumeration {
   enum val-0;
   enum val-1;
   enum val-2;
   enum val-3;
  }
  mandatory false;
 }
 leaf TRESELECTIONHRPD {
  type uint8 {
   range "0..7";
  }
  mandatory false;
 }
 }
 grouping CELLRESELGERAN-attributes {
 leaf LOCALCELLNAME {
  type string;
  mandatory false;
 }
 leaf LOCALCELLID {
  type union {
   type int16 {
    range "-1..255";
   }
  }
  mandatory false;
 }
 leaf SPEEDSTATESFCFGIND {
  type boolean;
  mandatory false;
 }
 leaf TRESELGERAN {
  type uint8 {
   range "0..7";
  }
  mandatory false;
 }
 leaf TRESELGERANSFHIGH {
  type enumeration {
   enum val-0;
   enum val-1;
   enum val-2;
   enum val-3;
  }
  mandatory false;
 }
 leaf TRESELGERANSFMEDIUM {
  type enumeration {
   enum val-0;
   enum val-1;
   enum val-2;
   enum val-3;
  }
  mandatory false;
 }
 }
 grouping CELLRESELTONR-attributes {
 leaf LOCALCELLNAME {
  type string;
  mandatory false;
 }
 leaf LOCALCELLID {
  type union {
   type int16 {
    range "-1..255";
   }
  }
  mandatory false;
 }
 leaf NRCELLRESELECTIONTIMER {
  type uint8 {
   range "0..7";
  }
  mandatory false;
 }
 }
 grouping CELLRESELUTRAN-attributes {
 leaf LOCALCELLNAME {
  type string;
  mandatory false;
 }
 leaf LOCALCELLID {
  type union {
   type int16 {
    range "-1..255";
   }
  }
  mandatory false;
 }
 leaf SPEEDSTATESFCFGIND {
  type boolean;
  mandatory false;
 }
 leaf TRESELUTRAN {
  type uint8 {
   range "0..7";
  }
  mandatory false;
 }
 leaf TRESELUTRANSFHIGH {
  type enumeration {
   enum val-0;
   enum val-1;
   enum val-2;
   enum val-3;
  }
  mandatory false;
 }
 leaf TRESELUTRANSFMEDIUM {
  type enumeration {
   enum val-0;
   enum val-1;
   enum val-2;
   enum val-3;
  }
  mandatory false;
 }
 }
 grouping CELLRFCHNDYNMUTING-attributes {
 leaf LOCALCELLNAME {
  type string;
  mandatory false;
 }
 leaf COMB8TRFDYNMUTEMODE {
  type enumeration {
   enum val-0;
   enum val-1;
   enum val-2;
   enum val-3;
  }
  mandatory false;
 }
 leaf FLEXPWRALLOCDLPRBTHLD {
  type uint8 {
   range "0..70";
  }
  mandatory false;
 }
 leaf FLEXPWRALLOCEXITDLPRBTHLD {
  type uint8 {
   range "30..100";
  }
  mandatory false;
 }
 leaf LOCALCELLID {
  type union {
   type int16 {
    range "-1..255";
   }
  }
  mandatory false;
 }
 leaf LOWPWRRFDYNMUTINGDLPRBTHLD {
  type uint8 {
   range "0..100";
  }
  mandatory false;
 }
 leaf LOWPWRRFDYNMUTINGDLPWRTHLD {
  type uint8 {
   range "0..20";
  }
  mandatory false;
 }
 leaf LOWPWRRFDYNMUTINGSTARTTIME {
  type hwat:HH_MM_SS_Time;
  mandatory false;
 }
 leaf LOWPWRRFDYNMUTINGSTOPTIME {
  type hwat:HH_MM_SS_Time;
  mandatory false;
 }
 leaf RFCHNDYNMUTINGALGOSWITCH {
  type string;
  mandatory false;
 }
 leaf RFDYNMUTEOPTNOAPPSTPTIME {
  type hwat:HH_MM_SS_Time;
  mandatory false;
 }
 leaf RFDYNMUTEOPTNOAPPSTRTIME {
  type hwat:HH_MM_SS_Time;
  mandatory false;
 }
 leaf RFMUTEDLHIGHLOADTTINUMTHLD {
  type uint8 {
   range "0..20";
  }
  mandatory false;
 }
 leaf RFMUTEDLPRBTHLD {
  type uint8 {
   range "0..100";
  }
  mandatory false;
 }
 leaf RFMUTENRDLHIGHLOADTTITHLD {
  type uint8 {
   range "0..20";
  }
  mandatory false;
 }
 leaf RFRCYDLHIGHLOADTTINUMTHLD {
  type uint8 {
   range "0..20";
  }
  mandatory false;
 }
 leaf RFRCYDLPRBTHLD {
  type uint8 {
   range "0..100";
  }
  mandatory false;
 }
 leaf RFRCYNRDLHIGHLOADTTITHLD {
  type uint8 {
   range "0..20";
  }
  mandatory false;
 }
 leaf STARTTIME {
  type hwat:HH_MM_SS_Time;
  mandatory false;
 }
 leaf STOPTIME {
  type hwat:HH_MM_SS_Time;
  mandatory false;
 }
 }
 grouping CELLRFSHUTDOWN-attributes {
 leaf LOCALCELLNAME {
  type string;
  mandatory false;
 }
 leaf CELLAVGDLTHPTOFFSET {
  type uint8 {
   range "0..100";
  }
  mandatory false;
 }
 leaf CELLAVGDLTHPTTHLD {
  type union {
   type uint8 {
    range "0..255";
   }
  }
  mandatory false;
 }
 leaf DLPRBOFFSET {
  type uint8 {
   range "0..100";
  }
  mandatory false;
 }
 leaf DLPRBTHD {
  type uint8 {
   range "0..100";
  }
  mandatory false;
 }
 leaf LOCALCELLID {
  type union {
   type int16 {
    range "-1..255";
   }
  }
  mandatory false;
 }
 leaf MULTIRATJOINTCHNSHUTDOWNSW {
  type boolean;
  mandatory false;
 }
 leaf PENALTYDURATION {
  type uint8 {
   range "1..60";
  }
  mandatory false;
 }
 leaf RFCHNSHUTDOWNPWRCHECKSW {
  type string;
  mandatory false;
 }
 leaf RFSHUTDOWNALGOSWITCH {
  type string;
  mandatory false;
 }
 leaf RFSHUTDOWNEVALMODE {
  type boolean;
  mandatory false;
 }
 leaf RFSHUTDOWNJUDGINGPOLICY {
  type boolean;
  mandatory false;
 }
 leaf RFSHUTDOWNSWITCH {
  type enumeration {
   enum val-0;
   enum val-1;
   enum val-2;
  }
  mandatory false;
 }
 leaf RSPWRADJOFFSET {
  type uint8 {
   range "0..7";
  }
  mandatory false;
 }
 leaf STARTTIME {
  type hwat:HH_MM_SS_Time;
  mandatory false;
 }
 leaf STOPTIME {
  type hwat:HH_MM_SS_Time;
  mandatory false;
 }
 leaf TIMEPOLICYID {
  type uint16 {
   range "0..256";
  }
  mandatory false;
 }
 leaf UENUMTHD {
  type uint8 {
   range "0..60";
  }
  mandatory false;
 }
 leaf UEAVGDLTHPTOFFSET {
  type uint8 {
   range "0..100";
  }
  mandatory false;
 }
 leaf UEAVGDLTHPTTHLD {
  type union {
   type uint8 {
    range "0..255";
   }
  }
  mandatory false;
 }
 leaf ULINTERFERENCEOFFSET {
  type uint8 {
   range "0..20";
  }
  mandatory false;
 }
 leaf ULINTERFERENCETHLD {
  type int8 {
   range "-125..-40";
  }
  mandatory false;
 }
 leaf ULPRBOFFSET {
  type uint8 {
   range "0..100";
  }
  mandatory false;
 }
 leaf ULPRBTHD {
  type uint8 {
   range "0..100";
  }
  mandatory false;
 }
 }
 grouping CELLRICALGO-attributes {
 leaf LOCALCELLNAME {
  type string;
  mandatory false;
 }
 leaf ATMOSDUCTRMTINTERFTHLDBYRB {
  type union {
   type int16 {
    range "-120..32767";
   }
  }
  mandatory false;
 }
 leaf ATMOSDUCTULAVGINTRFPWRTHLD {
  type int16 {
   range "-150..-50";
  }
  mandatory false;
 }
 leaf ATMOSDUCTULPWRDIFFTHLD {
  type int8 {
   range "-30..30";
  }
  mandatory false;
 }
 leaf DUCTDLSUBFRMSHUTOFFINFTHLD {
  type int16 {
   range "-150..30";
  }
  mandatory false;
 }
 leaf DUCTDLSUBFRMSHUTOFFOPTSW {
  type string;
  mandatory false;
 }
 leaf DUCTDLSUBFRMSHUTOFFSWITCH {
  type boolean;
  mandatory false;
 }
 leaf DUCTDLSFSHUTDNDETNENDTIME {
  type hwat:HH_MM_SS_Time;
  mandatory false;
 }
 leaf DUCTDLSFSHUTDNDETNSTRTTIME {
  type hwat:HH_MM_SS_Time;
  mandatory false;
 }
 leaf DUCTINFDETPERIODCOUNT {
  type uint8 {
   range "1..20";
  }
  mandatory false;
 }
 leaf DUCTINFPWRDIFFINTHLD {
  type int8 {
   range "-30..50";
  }
  mandatory false;
 }
 leaf DUCTINFPWRDIFFOUTTHLD {
  type int8 {
   range "-30..50";
  }
  mandatory false;
 }
 leaf DUCTSUBFRMSHUTOFFDEPTH {
  type boolean;
  mandatory false;
 }
 leaf DUCTINGREMOTEINFTHD {
  type int8 {
   range "-120..-50";
  }
  mandatory false;
 }
 leaf FREQUENCYOFFSET {
  type int8 {
   range "-100..100";
  }
  mandatory false;
 }
 leaf INFAVOIDDETPERIODNUM {
  type uint8 {
   range "1..10";
  }
  mandatory false;
 }
 leaf INFAVOIDRECDETPERIODNUM {
  type uint8 {
   range "1..10";
  }
  mandatory false;
 }
 leaf LOCALCELLID {
  type union {
   type int16 {
    range "-1..255";
   }
  }
  mandatory false;
 }
 leaf MUTEULSYM {
  type boolean;
  mandatory false;
 }
 leaf MUTEUPPTSSYMNUM {
  type uint8 {
   range "0..2";
  }
  mandatory false;
 }
 leaf REMOTEINFADPAVOIDSWITCH {
  type boolean;
  mandatory false;
 }
 leaf RICALGOSWITCH {
  type boolean;
  mandatory false;
 }
 leaf ULINTERFERENCEDURATION {
  type uint8 {
   range "1..180";
  }
  mandatory false;
 }
 leaf ULINTERFERENCESYMBMAXDIFF {
  type uint8 {
   range "0..99";
  }
  mandatory false;
 }
 leaf ULINTERFERENCETHD {
  type int16 {
   range "-140..-43";
  }
  mandatory false;
 }
 }
 grouping CELLSEL-attributes {
 leaf LOCALCELLNAME {
  type string;
  mandatory false;
 }
 leaf LOCALCELLID {
  type union {
   type int16 {
    range "-1..255";
   }
  }
  mandatory false;
 }
 leaf PWROFFSETFORSELECTIONTONB {
  type enumeration {
   enum val-0;
   enum val-1;
   enum val-2;
   enum val-3;
   enum val-4;
   enum val-5;
   enum val-255;
  }
  mandatory false;
 }
 leaf QQUALMIN {
  type union {
   type int8 {
    range "-34..0";
   }
  }
  mandatory false;
 }
 leaf QQUALMINCE {
  type union {
   type int8 {
    range "-34..0";
   }
  }
  mandatory false;
 }
 leaf QQUALMINFORCEMODEB {
  type union {
   type int8 {
    range "-34..0";
   }
  }
  mandatory false;
 }
 leaf QQUALMINOFFSET {
  type uint8 {
   range "1..8";
  }
  mandatory false;
 }
 leaf QQUALMINOFFSETCFGIND {
  type boolean;
  mandatory false;
 }
 leaf QRXLEVMIN {
  type int8 {
   range "-78..-22";
  }
  mandatory false;
 }
 leaf QRXLEVMINCE {
  type int8 {
   range "-70..-22";
  }
  mandatory false;
 }
 leaf QRXLEVMINFORCEMODEB {
  type int8 {
   range "-78..-22";
  }
  mandatory false;
 }
 leaf QRXLEVMINOFFSET {
  type uint8 {
   range "0..8";
  }
  mandatory false;
 }
 }
 grouping CELLSERVICEDIFFCFG-attributes {
 leaf LOCALCELLNAME {
  type string;
  mandatory false;
 }
 leaf ASDLCQITABLEADAPTTBSTHLD {
  type uint8 {
   range "4..33";
  }
  mandatory false;
 }
 leaf ASULMCSTABLEADAPTSINRTHLD {
  type int16 {
   range "-100..300";
  }
  mandatory false;
 }
 leaf CELLCONSTATEPRBTHD {
  type uint8 {
   range "1..100";
  }
  mandatory false;
 }
 leaf CELLCONSTATEUENUMTHD {
  type uint16 {
   range "1..10000";
  }
  mandatory false;
 }
 leaf CELLOVERLOADSTATEPRBTHD {
  type uint8 {
   range "1..100";
  }
  mandatory false;
 }
 leaf CELLOVERLOADSTATEUENUMTHD {
  type uint16 {
   range "1..10000";
  }
  mandatory false;
 }
 leaf CHNCARRALLOCTIMETOTRIG {
  type uint16 {
   range "0..600";
  }
  mandatory false;
 }
 leaf DLLARGEPACKETSCHPRIFACTOR {
  type uint16 {
   range "1..1000";
  }
  mandatory false;
 }
 leaf DLLARGEPACKETUEOPTTHLD {
  type uint32 {
   range "0..1000000";
  }
  mandatory false;
 }
 leaf DLLRGPKTOPTTOTALTIMEUPRLMT {
  type uint8 {
   range "0..20";
  }
  mandatory false;
 }
 leaf EXITULLARGEPACKETCNTTHD {
  type uint8 {
   range "1..200";
  }
  mandatory false;
 }
 leaf FOUESPDLVLIDENTINTVL {
  type uint8 {
   range "0..60";
  }
  mandatory false;
 }
 leaf FOUESPDLVLIDENTLOWERTHLD {
  type uint8 {
   range "1..100";
  }
  mandatory false;
 }
 leaf FOUESPDLVLIDENTMIDTHLDOFS {
  type uint8 {
   range "1..50";
  }
  mandatory false;
 }
 leaf FOUESPDLVLIDENTUPPRTHLDOFS {
  type uint8 {
   range "1..50";
  }
  mandatory false;
 }
 leaf HIGHPRISRSCHCNTTHLD {
  type uint16 {
   range "0..1000";
  }
  mandatory false;
 }
 leaf INTRFCOBDLSCHMAXEFFTIME {
  type uint16 {
   range "0..3600";
  }
  mandatory false;
 }
 leaf INTRFCOULRBRSVMAXEFFTIME {
  type uint16 {
   range "0..3600";
  }
  mandatory false;
 }
 leaf JUDGEULLARGEPACKETCNTTHD {
  type uint8 {
   range "1..200";
  }
  mandatory false;
 }
 leaf LOCALCELLID {
  type union {
   type int16 {
    range "-1..255";
   }
  }
  mandatory false;
 }
 leaf LOWLATENCYUEULMCSUPPERLMT {
  type union {
   type uint8 {
    range "0..255";
   }
  }
  mandatory false;
 }
 leaf MAXEXTHEADERTRANSNUM {
  type uint8 {
   range "0..100";
  }
  mandatory false;
 }
 leaf QUEUESERVICEWEIGHT0 {
  type uint8 {
   range "0..100";
  }
  mandatory false;
 }
 leaf QUEUESERVICEWEIGHT1 {
  type uint8 {
   range "0..100";
  }
  mandatory false;
 }
 leaf QUEUESERVICEWEIGHT2 {
  type uint8 {
   range "0..100";
  }
  mandatory false;
 }
 leaf QUEUESERVICEWEIGHT3 {
  type uint8 {
   range "0..100";
  }
  mandatory false;
 }
 leaf QUEUESERVICEWEIGHT4 {
  type uint8 {
   range "0..100";
  }
  mandatory false;
 }
 leaf QUEUESERVICEWEIGHT5 {
  type uint8 {
   range "0..100";
  }
  mandatory false;
 }
 leaf QUEUESERVICEWEIGHT6 {
  type uint8 {
   range "0..100";
  }
  mandatory false;
 }
 leaf SECONDPRISRSCHCNTTHLD {
  type uint16 {
   range "0..1000";
  }
  mandatory false;
 }
 leaf SERVICEDIFFSWITCH {
  type string;
  mandatory false;
 }
 leaf ULLARGEPACKETDATAVOTHD {
  type uint8 {
   range "0..255";
  }
  mandatory false;
 }
 leaf ULLARGEPACKETSCHPRIFACTOR {
  type uint16 {
   range "1..1000";
  }
  mandatory false;
 }
 }
 grouping CELLSHORTTTIALGO-attributes {
 leaf LOCALCELLNAME {
  type string;
  mandatory false;
 }
 leaf BETAOFSSUBSLOTACKINDEX1 {
  type uint8 {
   range "0..15";
  }
  mandatory false;
 }
 leaf BETAOFSSUBSLOTACKINDEX2 {
  type uint8 {
   range "0..15";
  }
  mandatory false;
 }
 leaf BETAOFSSUBSLOTCQIINDEX {
  type uint8 {
   range "0..15";
  }
  mandatory false;
 }
 leaf BETAOFSSUBSLOTRIINDEX1 {
  type uint8 {
   range "0..15";
  }
  mandatory false;
 }
 leaf BETAOFSSUBSLOTRIINDEX2 {
  type uint8 {
   range "0..15";
  }
  mandatory false;
 }
 leaf DLSRBGCNTRESERVEDFORSTTI {
  type uint8 {
   range "1..8";
  }
  mandatory false;
 }
 leaf LOCALCELLID {
  type union {
   type int16 {
    range "-1..255";
   }
  }
  mandatory false;
 }
 leaf NTTISTTIRBADJSTRATEGY {
  type boolean;
  mandatory false;
 }
 leaf PDCCHCCECNTRESERVEDFORSTTI {
  type uint8 {
   range "0..32";
  }
  mandatory false;
 }
 leaf SPDCCHRBCNT {
  type enumeration {
   enum val-0;
   enum val-1;
   enum val-2;
   enum val-3;
  }
  mandatory false;
 }
 leaf SPUCCHFORMAT1AND1ADELTAF {
  type enumeration {
   enum val-0;
   enum val-1;
   enum val-2;
   enum val-3;
   enum val-4;
   enum val-5;
   enum val-6;
   enum val-7;
  }
  mandatory false;
 }
 leaf SPUCCHFORMAT1BDELTAF {
  type enumeration {
   enum val-0;
   enum val-1;
   enum val-2;
   enum val-3;
   enum val-4;
   enum val-5;
   enum val-6;
   enum val-7;
  }
  mandatory false;
 }
 leaf SPUCCHRBCNT {
  type uint8 {
   range "1..10";
  }
  mandatory false;
 }
 leaf STTIALGOSWITCH {
  type string;
  mandatory false;
 }
 leaf STTIDLHARQMAXTXCNT {
  type enumeration {
   enum val-0;
   enum val-1;
   enum val-2;
   enum val-3;
   enum val-4;
   enum val-5;
   enum val-6;
   enum val-7;
   enum val-8;
   enum val-9;
   enum val-10;
   enum val-11;
   enum val-12;
   enum val-13;
  }
  mandatory false;
 }
 leaf STTIENTRYDCCHQUALITYHYST {
  type int8 {
   range "-20..20";
  }
  mandatory false;
 }
 leaf STTIENTRYDLRBUSAGETHLD {
  type uint8 {
   range "5..100";
  }
  mandatory false;
 }
 leaf STTIENTRYULRBUSAGETHLD {
  type uint8 {
   range "5..100";
  }
  mandatory false;
 }
 leaf STTIENTRYULSINRTHLD {
  type int8 {
   range "-5..20";
  }
  mandatory false;
 }
 leaf STTIPREALLOCATIONDURATION {
  type uint16 {
   range "1..1500";
  }
  mandatory false;
 }
 leaf STTIPREALLOCATIONMINPERIOD {
  type uint8 {
   range "1..60";
  }
  mandatory false;
 }
 leaf STTIPREALLOCATIONSIZE {
  type uint16 {
   range "15..1500";
  }
  mandatory false;
 }
 leaf STTISRIPERIOD {
  type enumeration {
   enum val-0;
   enum val-1;
   enum val-2;
   enum val-3;
   enum val-4;
   enum val-5;
   enum val-6;
   enum val-7;
   enum val-8;
  }
  mandatory false;
 }
 leaf STTIULHARQMAXTXCNT {
  type enumeration {
   enum val-0;
   enum val-1;
   enum val-2;
   enum val-3;
   enum val-4;
   enum val-5;
   enum val-6;
   enum val-7;
   enum val-8;
   enum val-9;
   enum val-10;
   enum val-11;
   enum val-12;
   enum val-13;
  }
  mandatory false;
 }
 leaf ULSRBGCNTRESERVEDFORSTTI {
  type uint8 {
   range "1..24";
  }
  mandatory false;
 }
 }
 grouping CELLSHUTDOWN-attributes {
 leaf LOCALCELLNAME {
  type string;
  mandatory false;
 }
 leaf CARRDYNSHUTDNCRSMUTINGNUM {
  type uint8 {
   range "0..3";
  }
  mandatory false;
 }
 leaf CARRDYNSHUTDNMINDURATION {
  type uint8 {
   range "0..60";
  }
  mandatory false;
 }
 leaf CARRSHUTDOWNEXITJUDGEPRD {
  type uint8 {
   range "1..12";
  }
  mandatory false;
 }
 leaf CARRSHUTDOWNTRIGJUDGEPRD {
  type uint8 {
   range "1..10";
  }
  mandatory false;
 }
 leaf CARRIERDYNSHUTDOWNPRBOFS {
  type uint8 {
   range "1..100";
  }
  mandatory false;
 }
 leaf CARRIERSHUTDOWNCELLTYPE {
  type boolean;
  mandatory false;
 }
 leaf CARRIERSHUTDOWNENHANCEDSW {
  type string;
  mandatory false;
 }
 leaf CELLAVGDLTHPTOFFSET {
  type uint8 {
   range "0..100";
  }
  mandatory false;
 }
 leaf CELLAVGDLTHPTTHLD {
  type union {
   type uint8 {
    range "0..255";
   }
  }
  mandatory false;
 }
 leaf CELLSHUTDOWNSWITCH {
  type enumeration {
   enum val-0;
   enum val-1;
   enum val-2;
   enum val-3;
   enum val-4;
   enum val-5;
  }
  mandatory false;
 }
 leaf DLPRBOFFSET {
  type uint8 {
   range "0..100";
  }
  mandatory false;
 }
 leaf DLPRBTHD {
  type uint8 {
   range "0..100";
  }
  mandatory false;
 }
 leaf FASTEXITEVALUATIONPERIOD {
  type uint8 {
   range "0..4";
  }
  mandatory false;
 }
 leaf FORCESHUTDOWNUENUMTHD {
  type uint8 {
   range "0..10";
  }
  mandatory false;
 }
 leaf INTERBBUCARRIERSHUTDOWNSW {
  type boolean;
  mandatory false;
 }
 leaf LOCALCELLID {
  type union {
   type int16 {
    range "-1..255";
   }
  }
  mandatory false;
 }
 leaf NSAUENUMOFFSET {
  type uint8 {
   range "1..100";
  }
  mandatory false;
 }
 leaf NSAUENUMTHLD {
  type uint8 {
   range "1..100";
  }
  mandatory false;
 }
 leaf PUNISHTIME {
  type uint16 {
   range "0..360";
  }
  mandatory false;
 }
 leaf STARTTIME {
  type hwat:HH_MM_SS_Time;
  mandatory false;
 }
 leaf STOPTIME {
  type hwat:HH_MM_SS_Time;
  mandatory false;
 }
 leaf TIMEPOLICYID {
  type uint16 {
   range "0..256";
  }
  mandatory false;
 }
 leaf UENUMTHD {
  type uint8 {
   range "1..100";
  }
  mandatory false;
 }
 leaf UEAVGDLTHPTOFFSET {
  type uint8 {
   range "0..100";
  }
  mandatory false;
 }
 leaf UEAVGDLTHPTTHLD {
  type union {
   type uint8 {
    range "0..255";
   }
  }
  mandatory false;
 }
 leaf ULPRBOFFSET {
  type uint8 {
   range "0..100";
  }
  mandatory false;
 }
 leaf ULPRBTHD {
  type uint8 {
   range "0..100";
  }
  mandatory false;
 }
 }
 grouping CELLSIDELINKV2XCFG-attributes {
 leaf LOCALCELLNAME {
  type string;
  mandatory false;
 }
 leaf LOCALCELLID {
  type union {
   type int16 {
    range "-1..255";
   }
  }
  mandatory false;
 }
 leaf SIDELINKV2XCFGSWITCH {
  type string;
  mandatory false;
 }
 }
 grouping CELLSIMAP-attributes {
 leaf LOCALCELLNAME {
  type string;
  mandatory false;
 }
 leaf DEDINETWORKSIB20PERIOD {
  type enumeration {
   enum val-0;
   enum val-1;
   enum val-2;
   enum val-3;
   enum val-4;
   enum val-5;
   enum val-6;
   enum val-7;
  }
  mandatory false;
 }
 leaf ETWSPNDURATION {
  type uint16 {
   range "1..300";
  }
  mandatory false;
 }
 leaf ETWSPNOVERLAPPOLICY {
  type boolean;
  mandatory false;
 }
 leaf ETWSSNOVERLAPPOLICY {
  type boolean;
  mandatory false;
 }
 leaf HIGHPRECISIONTIMESERVINGSW {
  type boolean;
  mandatory false;
 }
 leaf LOCALCELLID {
  type union {
   type int16 {
    range "-1..255";
   }
  }
  mandatory false;
 }
 leaf MIBREPETITIONCTRLOPTSWITCH {
  type boolean;
  mandatory false;
 }
 leaf NBSIB14HOLDINGTIME {
  type union {
   type uint8 {
    range "0..255";
   }
  }
  mandatory false;
 }
 leaf NBSIB14PERIOD {
  type enumeration {
   enum val-0;
   enum val-1;
   enum val-2;
   enum val-3;
   enum val-4;
   enum val-5;
   enum val-6;
  }
  mandatory false;
 }
 leaf NBSIB16PERIOD {
  type enumeration {
   enum val-0;
   enum val-1;
   enum val-2;
   enum val-3;
   enum val-4;
   enum val-5;
   enum val-6;
  }
  mandatory false;
 }
 leaf NBSIB1REPETITIONNUM {
  type enumeration {
   enum val-0;
   enum val-1;
   enum val-2;
  }
  mandatory false;
 }
 leaf NBSIB22PERIOD {
  type enumeration {
   enum val-0;
   enum val-1;
   enum val-2;
   enum val-3;
   enum val-4;
   enum val-5;
   enum val-6;
  }
  mandatory false;
 }
 leaf NBSIB2PERIOD {
  type enumeration {
   enum val-0;
   enum val-1;
   enum val-2;
   enum val-3;
   enum val-4;
   enum val-5;
   enum val-6;
  }
  mandatory false;
 }
 leaf NBSIB3PERIOD {
  type enumeration {
   enum val-0;
   enum val-1;
   enum val-2;
   enum val-3;
   enum val-4;
   enum val-5;
   enum val-6;
  }
  mandatory false;
 }
 leaf NBSIB4PERIOD {
  type enumeration {
   enum val-0;
   enum val-1;
   enum val-2;
   enum val-3;
   enum val-4;
   enum val-5;
   enum val-6;
  }
  mandatory false;
 }
 leaf NBSIB5PERIOD {
  type enumeration {
   enum val-0;
   enum val-1;
   enum val-2;
   enum val-3;
   enum val-4;
   enum val-5;
   enum val-6;
  }
  mandatory false;
 }
 leaf SIMAPSWITCH {
  type boolean;
  mandatory false;
 }
 leaf SISCHRESRATIO {
  type union {
   type uint8 {
    range "0..100";
   }
  }
  mandatory false;
 }
 leaf SISWITCH {
  type string;
  mandatory false;
 }
 leaf SITRANSECR {
  type uint16 {
   range "27..1000";
  }
  mandatory false;
 }
 leaf SIB10PERIOD {
  type enumeration {
   enum val-0;
   enum val-1;
   enum val-2;
   enum val-3;
   enum val-4;
   enum val-5;
   enum val-6;
  }
  mandatory false;
 }
 leaf SIB11PERIOD {
  type enumeration {
   enum val-0;
   enum val-1;
   enum val-2;
   enum val-3;
   enum val-4;
   enum val-5;
   enum val-6;
  }
  mandatory false;
 }
 leaf SIB12PERIOD {
  type enumeration {
   enum val-0;
   enum val-1;
   enum val-2;
   enum val-3;
   enum val-4;
   enum val-5;
   enum val-6;
  }
  mandatory false;
 }
 leaf SIB13PERIOD {
  type enumeration {
   enum val-0;
   enum val-1;
   enum val-2;
   enum val-3;
   enum val-4;
   enum val-5;
   enum val-6;
  }
  mandatory false;
 }
 leaf SIB14PERIOD {
  type enumeration {
   enum val-0;
   enum val-1;
   enum val-2;
   enum val-3;
   enum val-4;
   enum val-5;
   enum val-6;
  }
  mandatory false;
 }
 leaf SIB15PERIOD {
  type enumeration {
   enum val-0;
   enum val-1;
   enum val-2;
   enum val-3;
   enum val-4;
   enum val-5;
   enum val-6;
  }
  mandatory false;
 }
 leaf SIB16PERIOD {
  type enumeration {
   enum val-0;
   enum val-1;
   enum val-2;
   enum val-3;
   enum val-4;
   enum val-5;
   enum val-6;
  }
  mandatory false;
 }
 leaf SIB24PERIOD {
  type enumeration {
   enum val-0;
   enum val-1;
   enum val-2;
   enum val-3;
   enum val-4;
   enum val-5;
   enum val-6;
  }
  mandatory false;
 }
 leaf SIB25PERIOD {
  type enumeration {
   enum val-0;
   enum val-1;
   enum val-2;
   enum val-3;
   enum val-4;
   enum val-5;
   enum val-6;
   enum val-7;
  }
  mandatory false;
 }
 leaf SIB2PERIOD {
  type enumeration {
   enum val-0;
   enum val-1;
   enum val-2;
   enum val-3;
   enum val-4;
   enum val-5;
   enum val-6;
  }
  mandatory false;
 }
 leaf SIB32PERIOD {
  type enumeration {
   enum val-0;
   enum val-1;
   enum val-2;
   enum val-3;
   enum val-4;
   enum val-5;
   enum val-6;
  }
  mandatory false;
 }
 leaf SIB3PERIOD {
  type enumeration {
   enum val-0;
   enum val-1;
   enum val-2;
   enum val-3;
   enum val-4;
   enum val-5;
   enum val-6;
  }
  mandatory false;
 }
 leaf SIB4PERIOD {
  type enumeration {
   enum val-0;
   enum val-1;
   enum val-2;
   enum val-3;
   enum val-4;
   enum val-5;
   enum val-6;
  }
  mandatory false;
 }
 leaf SIB5PERIOD {
  type enumeration {
   enum val-0;
   enum val-1;
   enum val-2;
   enum val-3;
   enum val-4;
   enum val-5;
   enum val-6;
  }
  mandatory false;
 }
 leaf SIB6PERIOD {
  type enumeration {
   enum val-0;
   enum val-1;
   enum val-2;
   enum val-3;
   enum val-4;
   enum val-5;
   enum val-6;
  }
  mandatory false;
 }
 leaf SIB7PERIOD {
  type enumeration {
   enum val-0;
   enum val-1;
   enum val-2;
   enum val-3;
   enum val-4;
   enum val-5;
   enum val-6;
  }
  mandatory false;
 }
 leaf SIB8PERIOD {
  type enumeration {
   enum val-0;
   enum val-1;
   enum val-2;
   enum val-3;
   enum val-4;
   enum val-5;
   enum val-6;
  }
  mandatory false;
 }
 leaf SIBTRANSCTRLSWITCH {
  type boolean;
  mandatory false;
 }
 leaf SIBUPDOPTSWITCH {
  type string;
  mandatory false;
 }
 leaf SIDELINKV2XSIB21PERIOD {
  type enumeration {
   enum val-0;
   enum val-1;
   enum val-2;
   enum val-3;
   enum val-4;
   enum val-5;
   enum val-6;
  }
  mandatory false;
 }
 }
 grouping CELLSIMULOAD-attributes {
 leaf LOCALCELLNAME {
  type string;
  mandatory false;
 }
 leaf AUTORMVTIME {
  type uint32 {
   range "0..70560";
  }
  mandatory false;
 }
 leaf LOCALCELLID {
  type union {
   type int16 {
    range "-1..255";
   }
  }
  mandatory false;
 }
 leaf SIMLOADCFGINDEX {
  type uint8 {
   range "0..9";
  }
  mandatory false;
 }
 leaf SIMULOADADJVOLTTIME {
  type uint16 {
   range "0..4320";
  }
  mandatory false;
 }
 leaf SIMULOADMODE {
  type enumeration {
   enum val-0;
   enum val-1;
   enum val-2;
  }
  mandatory false;
 }
 leaf SIMULOADPERIOD {
  type enumeration {
   enum val-5;
   enum val-10;
   enum val-20;
   enum val-40;
   enum val-80;
   enum val-160;
  }
  mandatory false;
 }
 leaf SIMULOADPERIODOFFSET {
  type uint8 {
   range "0..159";
  }
  mandatory false;
 }
 leaf SIMULOADRBNUMBER {
  type uint8 {
   range "1..20";
  }
  mandatory false;
 }
 leaf SIMULOADSTARTRBINDEX {
  type uint8 {
   range "0..99";
  }
  mandatory false;
 }
 leaf SIMULOADTRANSMODE {
  type enumeration {
   enum val-0;
   enum val-1;
   enum val-3;
   enum val-6;
   enum val-7;
   enum val-8;
  }
  mandatory false;
 }
 }
 grouping CELLSLV2XCARRCFG-attributes {
 leaf LOCALCELLNAME {
  type string;
  mandatory false;
 }
 leaf LOCALCELLID {
  type union {
   type int16 {
    range "-1..255";
   }
  }
  mandatory false;
 }
 leaf SIDELINKV2XCARRIERID {
  type union {
   type int8 {
    range "-1..1";
   }
  }
  mandatory false;
 }
 }
 grouping CELLSMARTPWRLOCK-attributes {
 leaf LOCALCELLNAME {
  type string;
  mandatory false;
 }
 leaf AVERAGEPOWERMEASPERIOD {
  type uint32 {
   range "1..86400";
  }
  mandatory false;
 }
 leaf LOCALCELLID {
  type union {
   type int16 {
    range "-1..255";
   }
  }
  mandatory false;
 }
 leaf LTESPSGRPID {
  type uint16 {
   range "0..65535";
  }
  mandatory false;
 }
 leaf MAXANTAMPLIFYFACTOR {
  type union {
   type uint16 {
    range "0..1000";
   }
  }
  mandatory false;
 }
 leaf POWERCONTROLTHRESHOLD {
  type uint16 {
   range "0..65500";
  }
  mandatory false;
 }
 leaf PWRDENSITYREFLEVEL {
  type union {
   type uint32 {
    range "0..1000000";
   }
  }
  mandatory false;
 }
 leaf PWRINSUFFICIENCYTIMETHLD {
  type uint8 {
   range "1..60";
  }
  mandatory false;
 }
 leaf PWRRESTOREFORBIDTIMER {
  type uint8 {
   range "1..96";
  }
  mandatory false;
 }
 leaf PWRROLLBACKFACTOR {
  type uint8 {
   range "0..30";
  }
  mandatory false;
 }
 leaf RBUSAGEOFFSET {
  type uint8 {
   range "0..100";
  }
  mandatory false;
 }
 leaf SMARTPOWERLOCKMODE {
  type boolean;
  mandatory false;
 }
 leaf SMARTPWRLOCKALGOSWITCH {
  type string;
  mandatory false;
 }
 }
 grouping CELLSRLTE-attributes {
 leaf LOCALCELLNAME {
  type string;
  mandatory false;
 }
 leaf LOCALCELLID {
  type union {
   type int16 {
    range "-1..255";
   }
  }
  mandatory false;
 }
 leaf SRLTEDISCARDALGOSWITCH {
  type boolean;
  mandatory false;
 }
 leaf SRLTEDTXTHRD {
  type uint8 {
   range "1..15";
  }
  mandatory false;
 }
 leaf SRLTESUSPENDTIME {
  type uint8 {
   range "1..120";
  }
  mandatory false;
 }
 leaf SRLTESWITCH {
  type boolean;
  mandatory false;
 }
 }
 grouping CELLSRSADAPTIVECFG-attributes {
 leaf LOCALCELLNAME {
  type string;
  mandatory false;
 }
 leaf LOCALCELLID {
  type union {
   type int16 {
    range "-1..255";
   }
  }
  mandatory false;
 }
 leaf SRSPERIODADAPTIVE {
  type boolean;
  mandatory false;
 }
 leaf USERSRSPERIOD {
  type enumeration {
   enum val-1;
   enum val-2;
   enum val-3;
   enum val-4;
   enum val-5;
   enum val-6;
   enum val-7;
  }
  mandatory false;
 }
 }
 grouping CELLTTIBUNDLINGALGO-attributes {
 leaf LOCALCELLNAME {
  type string;
  mandatory false;
 }
 leaf LOCALCELLID {
  type union {
   type int16 {
    range "-1..255";
   }
  }
  mandatory false;
 }
 leaf R12TTIBHARQMAXTXNUM {
  type enumeration {
   enum val-0;
   enum val-1;
   enum val-2;
   enum val-3;
   enum val-4;
   enum val-5;
   enum val-6;
  }
  mandatory false;
 }
 leaf R12TTIBUNDLINGSWITCH {
  type boolean;
  mandatory false;
 }
 leaf SINRTHDTOTRIGR12TTIB {
  type int8 {
   range "-10..20";
  }
  mandatory false;
 }
 leaf SINRTHDTOTRIGTTIB {
  type union {
   type int16 {
    range "-5..255";
   }
  }
  mandatory false;
 }
 leaf SINRTHDTOTRIGVIDEOTTIB {
  type int8 {
   range "-5..10";
  }
  mandatory false;
 }
 leaf TTIBUNDLINGALGOSW {
  type string;
  mandatory false;
 }
 }
 grouping CELLTYPEEXT-attributes {
 leaf LOCALCELLNAME {
  type string;
  mandatory false;
 }
 leaf DRSCELLFLAG {
  type boolean;
  mandatory false;
 }
 leaf LOCALCELLID {
  type union {
   type int16 {
    range "-1..255";
   }
  }
  mandatory false;
 }
 leaf WIRELESSFHCELLFLAG {
  type boolean;
  mandatory false;
 }
 }
 grouping CELLUCIONPUSCHPARA-attributes {
 leaf LOCALCELLNAME {
  type string;
  mandatory false;
 }
 leaf DELTAOFFSETACKINDEX {
  type uint8 {
   range "0..15";
  }
  mandatory false;
 }
 leaf DELTAOFFSETACKINDEXFORTTIB {
  type uint8 {
   range "0..15";
  }
  mandatory false;
 }
 leaf DELTAOFFSETCQIINDEX {
  type uint8 {
   range "0..15";
  }
  mandatory false;
 }
 leaf DELTAOFFSETRIINDEX {
  type uint8 {
   range "0..15";
  }
  mandatory false;
 }
 leaf LOCALCELLID {
  type union {
   type int16 {
    range "-1..255";
   }
  }
  mandatory false;
 }
 }
 grouping CELLUEMEASCONTROLCFG-attributes {
 leaf LOCALCELLNAME {
  type string;
  mandatory false;
 }
 leaf FASTUEPRSTB1MAXMEASOBJNUM {
  type uint8 {
   range "0..15";
  }
  mandatory false;
 }
 leaf INTERFREQPERIODICMRCTRLSW {
  type string;
  mandatory false;
 }
 leaf LOCALCELLID {
  type union {
   type int16 {
    range "-1..255";
   }
  }
  mandatory false;
 }
 leaf MAXEUTRANFDDMEASFREQNUM {
  type uint8 {
   range "1..16";
  }
  mandatory false;
 }
 leaf MAXEUTRANTDDMEASFREQNUM {
  type uint8 {
   range "1..16";
  }
  mandatory false;
 }
 leaf MAXGERANMEASFREQNUM {
  type uint8 {
   range "1..64";
  }
  mandatory false;
 }
 leaf MAXNONINTRAMEASOBJNUM {
  type uint8 {
   range "1..32";
  }
  mandatory false;
 }
 leaf MAXNRMEASFREQNUM {
  type uint8 {
   range "1..16";
  }
  mandatory false;
 }
 leaf MAXPRDCINTERFMEASFREQNUM {
  type uint8 {
   range "0..8";
  }
  mandatory false;
 }
 leaf MAXUETDDMEASFREQNUM {
  type uint8 {
   range "1..32";
  }
  mandatory false;
 }
 leaf MAXUTRANFDDMEASFREQNUM {
  type uint8 {
   range "1..16";
  }
  mandatory false;
 }
 leaf MAXUTRANTDDMEASFREQNUM {
  type uint8 {
   range "1..16";
  }
  mandatory false;
 }
 leaf MEASOPTALGOSWITCH {
  type string;
  mandatory false;
 }
 leaf NSADCMAXINTERFMEASOBJNUM {
  type uint8 {
   range "2..32";
  }
  mandatory false;
 }
 leaf NSAMAXLTEINTERFMEASOBJNUM {
  type uint8 {
   range "1..32";
  }
  mandatory false;
 }
 }
 grouping CELLULCOMPALGO-attributes {
 leaf LOCALCELLNAME {
  type string;
  mandatory false;
 }
 leaf LOCALCELLID {
  type union {
   type int16 {
    range "-1..255";
   }
  }
  mandatory false;
 }
 leaf SFNULCOMPTHD {
  type int8 {
   range "-15..15";
  }
  mandatory false;
 }
 leaf ULCOMPA3OFFSET {
  type int8 {
   range "-30..30";
  }
  mandatory false;
 }
 leaf ULCOMPA3OFFSETFORRELAXEDBH {
  type int8 {
   range "-30..30";
  }
  mandatory false;
 }
 leaf ULCOMPALGOSWITCH {
  type string;
  mandatory false;
 }
 leaf ULCOMPULRSRPOFFSET {
  type int8 {
   range "-50..30";
  }
  mandatory false;
 }
 }
 grouping CELLULICALGO-attributes {
 leaf LOCALCELLNAME {
  type string;
  mandatory false;
 }
 leaf LOCALCELLID {
  type union {
   type int16 {
    range "-1..255";
   }
  }
  mandatory false;
 }
 leaf SRSADAPTISDEGREETHLD {
  type uint8 {
   range "0..10";
  }
  mandatory false;
 }
 leaf SRSICSWITCH {
  type string;
  mandatory false;
 }
 leaf SRSSICESWITCH {
  type string;
  mandatory false;
 }
 leaf ULICA3OFFSET {
  type int8 {
   range "-30..30";
  }
  mandatory false;
 }
 }
 grouping CELLULICIC-attributes {
 leaf LOCALCELLNAME {
  type string;
  mandatory false;
 }
 leaf BANDMODE {
  type enumeration {
   enum val-1;
   enum val-2;
   enum val-3;
   enum val-255;
  }
  mandatory false;
 }
 leaf LOCALCELLID {
  type union {
   type int16 {
    range "-1..255";
   }
  }
  mandatory false;
 }
 }
 grouping CELLULICICMCPARA-attributes {
 leaf LOCALCELLNAME {
  type string;
  mandatory false;
 }
 leaf A3OFFSET {
  type int8 {
   range "-30..30";
  }
  mandatory false;
 }
 leaf LOCALCELLID {
  type union {
   type int16 {
    range "-1..255";
   }
  }
  mandatory false;
 }
 }
 grouping CELLULMIMOPARACFG-attributes {
 leaf LOCALCELLNAME {
  type string;
  mandatory false;
 }
 leaf LOCALCELLID {
  type union {
   type int16 {
    range "-1..255";
   }
  }
  mandatory false;
 }
 leaf ULSUMIMORANKPARA {
  type enumeration {
   enum val-0;
   enum val-1;
   enum val-2;
  }
  mandatory false;
 }
 }
 grouping CELLULPCCOMM-attributes {
 leaf LOCALCELLNAME {
  type string;
  mandatory false;
 }
 leaf DELTAFPUCCHFORMAT1 {
  type enumeration {
   enum val-0;
   enum val-1;
   enum val-2;
  }
  mandatory false;
 }
 leaf DELTAFPUCCHFORMAT1B {
  type enumeration {
   enum val-0;
   enum val-1;
   enum val-2;
  }
  mandatory false;
 }
 leaf DELTAFPUCCHFORMAT1BCS {
  type enumeration {
   enum val-0;
   enum val-1;
   enum val-255;
  }
  mandatory false;
 }
 leaf DELTAFPUCCHFORMAT2 {
  type enumeration {
   enum val-0;
   enum val-1;
   enum val-2;
   enum val-3;
  }
  mandatory false;
 }
 leaf DELTAFPUCCHFORMAT2A {
  type enumeration {
   enum val-0;
   enum val-1;
   enum val-2;
  }
  mandatory false;
 }
 leaf DELTAFPUCCHFORMAT2B {
  type enumeration {
   enum val-0;
   enum val-1;
   enum val-2;
  }
  mandatory false;
 }
 leaf DELTAFPUCCHFORMAT3 {
  type enumeration {
   enum val-0;
   enum val-1;
   enum val-2;
   enum val-3;
   enum val-4;
   enum val-5;
   enum val-6;
   enum val-7;
   enum val-255;
  }
  mandatory false;
 }
 leaf DELTAMSG2 {
  type enumeration {
   enum val-0;
   enum val-1;
   enum val-2;
   enum val-3;
   enum val-4;
   enum val-5;
   enum val-6;
   enum val-7;
  }
  mandatory false;
 }
 leaf DELTAPREAMBLEMSG3 {
  type int8 {
   range "-1..6";
  }
  mandatory false;
 }
 leaf LOCALCELLID {
  type union {
   type int16 {
    range "-1..255";
   }
  }
  mandatory false;
 }
 leaf P0NOMINALPUCCH {
  type int8 {
   range "-127..-96";
  }
  mandatory false;
 }
 leaf P0NOMINALPUSCH {
  type int8 {
   range "-126..24";
  }
  mandatory false;
 }
 leaf PASSLOSSCOEFF {
  type enumeration {
   enum val-0;
   enum val-1;
   enum val-2;
   enum val-3;
   enum val-4;
   enum val-5;
   enum val-6;
   enum val-7;
  }
  mandatory false;
 }
 }
 grouping CELLULPCDEDIC-attributes {
 leaf LOCALCELLNAME {
  type string;
  mandatory false;
 }
 leaf DELTAMCSENABLED {
  type boolean;
  mandatory false;
 }
 leaf FILTERRSRP {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf LOCALCELLID {
  type union {
   type int16 {
    range "-1..255";
   }
  }
  mandatory false;
 }
 leaf PSRSOFFSETDELTAMCSDISABLE {
  type union {
   type int8 {
    range "-105..120";
   }
  }
  mandatory false;
 }
 leaf PSRSOFFSETDELTAMCSENABLE {
  type union {
   type int8 {
    range "-30..120";
   }
  }
  mandatory false;
 }
 leaf PATHLOSSREFERENCELINK {
  type boolean;
  mandatory false;
 }
 }
 grouping CELLULSCHALGO-attributes {
 leaf LOCALCELLNAME {
  type string;
  mandatory false;
 }
 leaf ABNORMALUESCHCNTTHLD {
  type uint16 {
   range "0..1000";
  }
  mandatory false;
 }
 leaf ADAPTHARQSWITCH {
  type enumeration {
   enum val-0;
   enum val-1;
   enum val-2;
  }
  mandatory false;
 }
 leaf AMRCDECREASINGPERIOD {
  type uint8 {
   range "1..10";
  }
  mandatory false;
 }
 leaf APERIODICCSIULTXMODE {
  type boolean;
  mandatory false;
 }
 leaf BUNDLEDPTTVOICEPACKETNUM {
  type uint8 {
   range "1..10";
  }
  mandatory false;
 }
 leaf DATATHDINPDCCHPUSCHBAL {
  type uint32 {
   range "0..1000000";
  }
  mandatory false;
 }
 leaf DOPALGOSWITCH {
  type string;
  mandatory false;
 }
 leaf DOPMEASLEVEL {
  type boolean;
  mandatory false;
 }
 leaf ENHANCEDVMIMOSWITCH {
  type boolean;
  mandatory false;
 }
 leaf ESTIMATEDTCPACKPACKETCOUNT {
  type uint8 {
   range "0..20";
  }
  mandatory false;
 }
 leaf FREEUSERULRBUSEDRATIO {
  type uint8 {
   range "0..100";
  }
  mandatory false;
 }
 leaf HEADOVERHEADFORULSCH {
  type enumeration {
   enum val-0;
   enum val-1;
   enum val-2;
   enum val-3;
   enum val-4;
   enum val-5;
   enum val-6;
  }
  mandatory false;
 }
 leaf HIGHLOADULSCHOPTSWITCH {
  type boolean;
  mandatory false;
 }
 leaf HIGHLOADULSCHOPTTHLD {
  type uint8 {
   range "60..100";
  }
  mandatory false;
 }
 leaf HIGHPRISRSCHDELAYTHLD {
  type union {
   type uint8 {
    range "0..255";
   }
  }
  mandatory false;
 }
 leaf HIGHSPEEDSDMAISOLATIONTHLD {
  type uint8 {
   range "0..20";
  }
  mandatory false;
 }
 leaf HTTPGETULSCHBYTE {
  type uint16 {
   range "0..1500";
  }
  mandatory false;
 }
 leaf HYSTTOEXITTTIBUNDLING {
  type uint8 {
   range "3..20";
  }
  mandatory false;
 }
 leaf INITULSINRADJUST {
  type int8 {
   range "-100..100";
  }
  mandatory false;
 }
 leaf INTVLOFULSPSWITHSKIPPING {
  type enumeration {
   enum val-0;
   enum val-1;
   enum val-5;
  }
  mandatory false;
 }
 leaf LOCALCELLID {
  type union {
   type int16 {
    range "-1..255";
   }
  }
  mandatory false;
 }
 leaf LOWPRISRSCHDELAYTHLD {
  type uint8 {
   range "0..150";
  }
  mandatory false;
 }
 leaf MAXLAYERHOVMIMO {
  type enumeration {
   enum val-0;
   enum val-1;
   enum val-2;
  }
  mandatory false;
 }
 leaf MAXLAYERMMVMIMO {
  type enumeration {
   enum val-2;
   enum val-4;
   enum val-6;
   enum val-8;
  }
  mandatory false;
 }
 leaf MAXPREALLOCATEDHTTPGETCNT {
  type uint8 {
   range "1..3";
  }
  mandatory false;
 }
 leaf MAXULSCHRBNUM {
  type uint8 {
   range "1..255";
  }
  mandatory false;
 }
 leaf NBULHARQMAXTXCOUNT {
  type uint8 {
   range "1..8";
  }
  mandatory false;
 }
 leaf NBULSUBCARRIERSPACINGTYPE {
  type enumeration {
   enum val-0;
   enum val-1;
   enum val-2;
  }
  mandatory false;
 }
 leaf NOULSCHTTINUMAFFTERGAP {
  type uint8 {
   range "0..4";
  }
  mandatory false;
 }
 leaf PRACHSINRTHLDFORCOVENH {
  type int8 {
   range "-20..0";
  }
  mandatory false;
 }
 leaf PREALLOCMINPERIODFORSPARSE {
  type enumeration {
   enum val-0;
   enum val-1;
   enum val-2;
   enum val-3;
   enum val-4;
   enum val-5;
  }
  mandatory false;
 }
 leaf PREALLOCATIONBANDWIDTHRATIO {
  type uint8 {
   range "0..100";
  }
  mandatory false;
 }
 leaf PREALLOCATIONMINPERIOD {
  type uint8 {
   range "1..40";
  }
  mandatory false;
 }
 leaf PREALLOCATIONSIZE {
  type uint16 {
   range "45..1500";
  }
  mandatory false;
 }
 leaf PREALLOSYSTEMBWCOEFF {
  type uint8 {
   range "0..10";
  }
  mandatory false;
 }
 leaf PREALLOCATIONSIZEFORSPARSE {
  type enumeration {
   enum val-0;
   enum val-1;
   enum val-2;
   enum val-3;
   enum val-4;
   enum val-5;
   enum val-6;
  }
  mandatory false;
 }
 leaf PREALLOCATIONUSERCNTTHLD {
  type uint16 {
   range "1..1250";
  }
  mandatory false;
 }
 leaf PUSCHDTXSCHSTRATEGY {
  type enumeration {
   enum val-0;
   enum val-1;
   enum val-2;
  }
  mandatory false;
 }
 leaf PUSCHSINRTHLDFORCOVENH {
  type int8 {
   range "-15..10";
  }
  mandatory false;
 }
 leaf RATECTRLCMRPROCESSSTRATEGY {
  type boolean;
  mandatory false;
 }
 leaf RATECTRLRSPDECISIONTHLD {
  type enumeration {
   enum val-0;
   enum val-1;
   enum val-2;
   enum val-3;
   enum val-4;
   enum val-5;
   enum val-6;
   enum val-7;
  }
  mandatory false;
 }
 leaf SFNULLOADPERIOD {
  type uint16 {
   range "2..1800";
  }
  mandatory false;
 }
 leaf SFNULPAIRRSRPTHD {
  type uint8 {
   range "0..100";
  }
  mandatory false;
 }
 leaf SINRADJUSTTARGETIBLER {
  type uint8 {
   range "1..99";
  }
  mandatory false;
 }
 leaf SINRTHDFORVOLTERATECTRL {
  type union {
   type int8 {
    range "-100..35";
   }
  }
  mandatory false;
 }
 leaf SMARTPREALLOCDURAFORSPARSE {
  type uint16 {
   range "0..2000";
  }
  mandatory false;
 }
 leaf SMARTPREALLOCATIONDURATION {
  type uint16 {
   range "0..2000";
  }
  mandatory false;
 }
 leaf SMARTPREALLODURATIONCOEFF {
  type uint8 {
   range "0..10";
  }
  mandatory false;
 }
 leaf SPADOMAINPREFVMIMOSTRTTHLD {
  type union {
   type uint8 {
    range "0..255";
   }
  }
  mandatory false;
 }
 leaf SPECIFICPKTSIZETHD {
  type uint32 {
   range "0..100000";
  }
  mandatory false;
 }
 leaf SPLUEPREALLOCDATAVOLUME {
  type uint16 {
   range "45..1500";
  }
  mandatory false;
 }
 leaf SPLUEPREALLOCMININTERVAL {
  type uint8 {
   range "1..40";
  }
  mandatory false;
 }
 leaf SPLUESMARTPREALLOCDURATION {
  type uint16 {
   range "0..2000";
  }
  mandatory false;
 }
 leaf SPSRELTHD {
  type uint8 {
   range "2..3";
  }
  mandatory false;
 }
 leaf SRMASKSWITCH {
  type boolean;
  mandatory false;
 }
 leaf SRIFALSEDETTHDSWITCH {
  type boolean;
  mandatory false;
 }
 leaf STATISTICNUMTHDFORTTIBEXIT {
  type enumeration {
   enum val-0;
   enum val-1;
   enum val-2;
   enum val-3;
  }
  mandatory false;
 }
 leaf STATISTICNUMTHDFORTTIBTRIG {
  type enumeration {
   enum val-0;
   enum val-1;
   enum val-2;
   enum val-3;
  }
  mandatory false;
 }
 leaf TARRRUSELRSRPOFFSETTHD {
  type uint8 {
   range "0..40";
  }
  mandatory false;
 }
 leaf TBSFORULSPSWITHSKIPPING {
  type uint16 {
   range "45..1000";
  }
  mandatory false;
 }
 leaf TTIBJUDGTIMESTHLDFORCOVENH {
  type uint8 {
   range "0..20";
  }
  mandatory false;
 }
 leaf TTIBSINRTHLDFORCOVENH {
  type int8 {
   range "-15..10";
  }
  mandatory false;
 }
 leaf TTIBUNDLINGHARQMAXTXNUM {
  type enumeration {
   enum val-0;
   enum val-1;
   enum val-2;
   enum val-3;
   enum val-4;
   enum val-5;
   enum val-6;
  }
  mandatory false;
 }
 leaf TTIBUNDLINGRETXSTRATEGY {
  type string;
  mandatory false;
 }
 leaf TTIBUNDLINGRLCMAXSEGNUM {
  type uint8 {
   range "0..7";
  }
  mandatory false;
 }
 leaf TTIBUNDLINGTRIGGERSTRATEGY {
  type boolean;
  mandatory false;
 }
 leaf UENUMTHDINPDCCHPUSCHBAL {
  type uint16 {
   range "0..10000";
  }
  mandatory false;
 }
 leaf ULASSISTANCESWITCH {
  type string;
  mandatory false;
 }
 leaf ULCAMCDLRSRPOFFSET {
  type int8 {
   range "-30..30";
  }
  mandatory false;
 }
 leaf ULCOMPENSCHPERIODINSILENCE {
  type enumeration {
   enum val-0;
   enum val-1;
   enum val-2;
   enum val-3;
   enum val-4;
   enum val-5;
   enum val-6;
   enum val-7;
  }
  mandatory false;
 }
 leaf ULCOMPENSCHPERIODINSPURT {
  type enumeration {
   enum val-0;
   enum val-1;
   enum val-2;
   enum val-3;
   enum val-4;
   enum val-5;
   enum val-6;
   enum val-7;
  }
  mandatory false;
 }
 leaf ULDELAYSCHSTRATEGY {
  type enumeration {
   enum val-0;
   enum val-1;
   enum val-2;
   enum val-3;
  }
  mandatory false;
 }
 leaf ULENHENCEDVOIPSCHSW {
  type inet:ip-address;
  mandatory false;
 }
 leaf ULEPFCAPACITYFACTOR {
  type enumeration {
   enum val-0;
   enum val-1;
   enum val-2;
   enum val-3;
   enum val-4;
   enum val-5;
  }
  mandatory false;
 }
 leaf ULEXTVOLTESCHSW {
  type string;
  mandatory false;
 }
 leaf ULHARQMAXTXNUM {
  type uint8 {
   range "1..8";
  }
  mandatory false;
 }
 leaf ULHEAVYLOADOPTSCHSWITCH {
  type boolean;
  mandatory false;
 }
 leaf ULHOPPINGTYPE {
  type enumeration {
   enum val-0;
   enum val-1;
   enum val-2;
   enum val-3;
  }
  mandatory false;
 }
 leaf ULIBLERADAPTBIGTRAFFICSW {
  type boolean;
  mandatory false;
 }
 leaf ULICSA3OFFSET {
  type int8 {
   range "-30..30";
  }
  mandatory false;
 }
 leaf ULINBASEDFSSSINRTHLD {
  type int16 {
   range "-500..500";
  }
  mandatory false;
 }
 leaf ULINTERFRANDOMMODE {
  type boolean;
  mandatory false;
 }
 leaf ULMAXCISCHOPTPRBUSAGETHLD {
  type uint8 {
   range "50..100";
  }
  mandatory false;
 }
 leaf ULMCSLOWTHRESHOLD {
  type enumeration {
   enum val-0;
   enum val-1;
   enum val-2;
   enum val-3;
  }
  mandatory false;
 }
 leaf ULMINEXPECTEDBITRATE {
  type uint16 {
   range "0..1024";
  }
  mandatory false;
 }
 leaf ULPTTRLCMAXSEGNUM {
  type uint16 {
   range "0..300";
  }
  mandatory false;
 }
 leaf ULPTTTTIBRLCMAXSEGNUM {
  type uint8 {
   range "0..70";
  }
  mandatory false;
 }
 leaf ULRATEGUARANTEERESRATIO {
  type uint8 {
   range "0..100";
  }
  mandatory false;
 }
 leaf ULRBALLOCATIONSTRATEGY {
  type boolean;
  mandatory false;
 }
 leaf ULSCHABNUETHD {
  type uint8 {
   range "6..120";
  }
  mandatory false;
 }
 leaf ULSCHOPTSWITCH {
  type string;
  mandatory false;
 }
 leaf ULSINRADJUSTSTEP {
  type uint16 {
   range "0..1000";
  }
  mandatory false;
 }
 leaf ULSINRFILTERCOEF {
  type uint16 {
   range "0..1024";
  }
  mandatory false;
 }
 leaf ULSPSINTERVAL {
  type enumeration {
   enum val-0;
   enum val-1;
   enum val-2;
  }
  mandatory false;
 }
 leaf ULSRSCHDATAVOLADPTOPTUPTHD {
  type uint16 {
   range "0..20000";
  }
  mandatory false;
 }
 leaf ULSRSCHDATELEN {
  type uint16 {
   range "16..15000";
  }
  mandatory false;
 }
 leaf ULSRSCHDATELENFORVOLTE {
  type uint16 {
   range "0..15000";
  }
  mandatory false;
 }
 leaf ULSRSFREQSELSCHRBRATETHLD {
  type uint8 {
   range "0..30";
  }
  mandatory false;
 }
 leaf ULSRSFREQSELSCHSINRTHLD {
  type union {
   type int16 {
    range "-10..255";
   }
  }
  mandatory false;
 }
 leaf ULTARGETIBLERADAPTTYPE {
  type string;
  mandatory false;
 }
 leaf ULVOLTERETRANSSCHSTRATEGY {
  type string;
  mandatory false;
 }
 leaf ULVOIPRLCMAXSEGNUM {
  type uint8 {
   range "0..30";
  }
  mandatory false;
 }
 leaf ULVOIPRSVRBNUM {
  type enumeration {
   enum val-0;
   enum val-1;
   enum val-2;
   enum val-3;
   enum val-4;
   enum val-5;
   enum val-6;
   enum val-7;
   enum val-8;
   enum val-9;
   enum val-10;
   enum val-11;
   enum val-12;
   enum val-13;
  }
  mandatory false;
 }
 leaf ULVOIPRSVRBSTART {
  type uint8 {
   range "0..98";
  }
  mandatory false;
 }
 leaf ULVOLTEDELTASINRFORNACK {
  type uint16 {
   range "0..300";
  }
  mandatory false;
 }
 leaf ULSCHSTRATEGY {
  type enumeration {
   enum val-0;
   enum val-1;
   enum val-2;
   enum val-3;
  }
  mandatory false;
 }
 leaf USERSPEEDULSCHPRIWEIGHT {
  type uint8 {
   range "1..10";
  }
  mandatory false;
 }
 leaf VMIMOEGDERESRATIO {
  type uint8 {
   range "0..50";
  }
  mandatory false;
 }
 leaf VMIMOMLPAIRINGCORRTHLD {
  type uint16 {
   range "111..999";
  }
  mandatory false;
 }
 leaf VMIMOOPTALGOSWITCH {
  type string;
  mandatory false;
 }
 leaf VMIMOPAIRINGSTRATEGY {
  type enumeration {
   enum val-0;
   enum val-1;
   enum val-2;
  }
  mandatory false;
 }
 leaf VMIMOULPRBTHLD {
  type uint8 {
   range "0..100";
  }
  mandatory false;
 }
 leaf VOICEULSPSRESERVEDRBRATIO {
  type uint8 {
   range "30..100";
  }
  mandatory false;
 }
 leaf VOLTECALLSETUPSCHENHTIMER {
  type uint16 {
   range "0..6000";
  }
  mandatory false;
 }
 }
 grouping CELLULSCHEXTPARAM-attributes {
 leaf LOCALCELLNAME {
  type string;
  mandatory false;
 }
 leaf LOCALCELLID {
  type union {
   type int16 {
    range "-1..255";
   }
  }
  mandatory false;
 }
 leaf UL256QAMSINRAVGUPPERTHLD {
  type uint16 {
   range "1861..3000";
  }
  mandatory false;
 }
 leaf ULMAXSINROFFSET {
  type uint8 {
   range "0..10";
  }
  mandatory false;
 }
 leaf ULSATURATIONSCHA3OFFSET {
  type int8 {
   range "-30..30";
  }
  mandatory false;
 }
 leaf ULSATURATIONSCHRBEXTRATIO {
  type uint8 {
   range "0..200";
  }
  mandatory false;
 }
 leaf ULSATURATIONSCHSWITCH {
  type boolean;
  mandatory false;
 }
 leaf ULSCHEXTADAPTSWITCH {
  type string;
  mandatory false;
 }
 leaf ULSINRAVGLOWERTHLD {
  type uint16 {
   range "1..1000";
  }
  mandatory false;
 }
 leaf ULSINRAVGMIDDLETHLD {
  type uint16 {
   range "1001..1860";
  }
  mandatory false;
 }
 leaf ULSINRAVGUPPERTHLD {
  type uint16 {
   range "1861..3000";
  }
  mandatory false;
 }
 leaf ULSINRDIFFLOWERTHLD {
  type uint16 {
   range "1..1000";
  }
  mandatory false;
 }
 leaf ULSINRDIFFUPPERTHLD {
  type uint16 {
   range "1..1000";
  }
  mandatory false;
 }
 }
 grouping CELLULUNIFIEDOLC-attributes {
 leaf LOCALCELLNAME {
  type string;
  mandatory false;
 }
 leaf LOCALCELLID {
  type union {
   type int16 {
    range "-1..255";
   }
  }
  mandatory false;
 }
 leaf RRCREJECTRATEHIGHTHD {
  type uint8 {
   range "0..200";
  }
  mandatory false;
 }
 leaf RRCREJECTRATELOWTHD {
  type uint8 {
   range "0..200";
  }
  mandatory false;
 }
 leaf RRCREQNUMHIGHTHD {
  type uint16 {
   range "1..20000";
  }
  mandatory false;
 }
 leaf RRCREQNUMLOWTHD {
  type uint16 {
   range "1..20000";
  }
  mandatory false;
 }
 leaf UENUMHIGHTHD {
  type uint16 {
   range "1..1200";
  }
  mandatory false;
 }
 leaf UENUMLOWTHD {
  type uint16 {
   range "1..1200";
  }
  mandatory false;
 }
 }
 grouping CELLUSPARACFG-attributes {
 leaf LOCALCELLNAME {
  type string;
  mandatory false;
 }
 leaf CRSSHUTDOWNRSRPOFFSET {
  type int8 {
   range "-30..30";
  }
  mandatory false;
 }
 leaf CRSSHUTDOWNSTRATEGY {
  type enumeration {
   enum val-0;
   enum val-1;
   enum val-2;
  }
  mandatory false;
 }
 leaf DLCCESCHPRIORITYPENALTYLVL {
  type enumeration {
   enum val-0;
   enum val-1;
   enum val-2;
   enum val-3;
  }
  mandatory false;
 }
 leaf LARGEPACKETDLDATATHLD {
  type uint16 {
   range "0..300";
  }
  mandatory false;
 }
 leaf LNRUSDETECTTIMER {
  type uint16 {
   range "1..21600";
  }
  mandatory false;
 }
 leaf LNRUSNEIGHBORINTRFCTRL {
  type uint8 {
   range "0..80";
  }
  mandatory false;
 }
 leaf LOCALCELLID {
  type union {
   type int16 {
    range "-1..255";
   }
  }
  mandatory false;
 }
 leaf MMPOWERRATIO {
  type uint8 {
   range "0..10";
  }
  mandatory false;
 }
 leaf NSIDLERATFREQPRIGROUPID {
  type uint8 {
   range "0..255";
  }
  mandatory false;
 }
 leaf NSMAXNUMALLOWSCHPERTTI {
  type uint8 {
   range "0..255";
  }
  mandatory false;
 }
 leaf NSNOTALLOWSCHSUBFRAME {
  type string;
  mandatory false;
 }
 leaf NSNUMTHDFORUSHO {
  type uint16 {
   range "0..10000";
  }
  mandatory false;
 }
 leaf NSRATFREQPRIGROUPID {
  type uint8 {
   range "0..255";
  }
  mandatory false;
 }
 leaf NSRBRESTRICTRATIO {
  type uint8 {
   range "0..100";
  }
  mandatory false;
 }
 leaf NSRBSCHRESTRICTIONSTRATEGY {
  type enumeration {
   enum val-0;
   enum val-1;
   enum val-2;
  }
  mandatory false;
 }
 leaf NSUENRDELAYTIMER {
  type uint8 {
   range "0..60";
  }
  mandatory false;
 }
 leaf RESTRICTEDNSDLRBCOUNT {
  type uint8 {
   range "4..100";
  }
  mandatory false;
 }
 leaf RESTRICTEDNSULRBCOUNT {
  type uint8 {
   range "4..100";
  }
  mandatory false;
 }
 leaf SCHGUARANTEEUSNUM {
  type uint8 {
   range "1..255";
  }
  mandatory false;
 }
 leaf SFCTRLPRBTHD {
  type enumeration {
   enum val-0;
   enum val-1;
   enum val-2;
   enum val-3;
  }
  mandatory false;
 }
 leaf UEMOBILIDENTIFYSTRATEGY {
  type enumeration {
   enum val-0;
   enum val-1;
   enum val-2;
   enum val-3;
  }
  mandatory false;
 }
 leaf ULCCESCHPRIORITYPENALTYLVL {
  type enumeration {
   enum val-0;
   enum val-1;
   enum val-2;
   enum val-3;
  }
  mandatory false;
 }
 leaf ULSCHOPTCOUNT {
  type uint8 {
   range "0..3";
  }
  mandatory false;
 }
 leaf ULUSDATARATFREQPRIGROUPID {
  type uint8 {
   range "0..255";
  }
  mandatory false;
 }
 leaf ULUSVOIPIBLERTARGET {
  type uint8 {
   range "0..100";
  }
  mandatory false;
 }
 leaf ULUSVOIPRSVENDRB {
  type uint8 {
   range "0..99";
  }
  mandatory false;
 }
 leaf ULUSVOIPRSVSTARTRB {
  type uint8 {
   range "0..99";
  }
  mandatory false;
 }
 leaf USA3HOA1THDOFFSET {
  type int8 {
   range "-20..20";
  }
  mandatory false;
 }
 leaf USA3HOA2THDOFFSET {
  type int8 {
   range "-20..20";
  }
  mandatory false;
 }
 leaf USA4A5HOA1THDOFFSET {
  type int8 {
   range "-20..20";
  }
  mandatory false;
 }
 leaf USA4A5HOA2THDOFFSET {
  type int8 {
   range "-20..20";
  }
  mandatory false;
 }
 leaf USALGOEXSWITCH {
  type string;
  mandatory false;
 }
 leaf USALGOSWITCH {
  type string;
  mandatory false;
 }
 leaf USCELLSCHOPTSWITCH {
  type string;
  mandatory false;
 }
 leaf USDATAPDCCHSINROFFSET {
  type uint8 {
   range "0..30";
  }
  mandatory false;
 }
 leaf USDATAPREALLOCMINPERIOD {
  type uint8 {
   range "1..40";
  }
  mandatory false;
 }
 leaf USDATAPREALLOCSIZE {
  type uint16 {
   range "45..1500";
  }
  mandatory false;
 }
 leaf USDATARATFREQPRIGROUPID {
  type uint8 {
   range "0..255";
  }
  mandatory false;
 }
 leaf USDATASMARTPREALLOCDURA {
  type uint16 {
   range "0..60000";
  }
  mandatory false;
 }
 leaf USDETECTTIMER {
  type uint16 {
   range "1..21600";
  }
  mandatory false;
 }
 leaf USDLMINGBR {
  type uint16 {
   range "0..12500";
  }
  mandatory false;
 }
 leaf USDLPRIORITYRATIO {
  type uint16 {
   range "0..1000";
  }
  mandatory false;
 }
 leaf USGAPMEASUREMENTPERIOD {
  type uint16 {
   range "3..3600";
  }
  mandatory false;
 }
 leaf USGUARANTEEDURTIMER {
  type uint16 {
   range "1..360";
  }
  mandatory false;
 }
 leaf USNCELLRESTRICTSTRATEGY {
  type boolean;
  mandatory false;
 }
 leaf USNBINTERFCTRL {
  type uint8 {
   range "0..80";
  }
  mandatory false;
 }
 leaf USNBULRBRESTRICTRAT {
  type uint8 {
   range "0..100";
  }
  mandatory false;
 }
 leaf USNBULSINRHIGHTHDOFFSET {
  type int8 {
   range "-12..0";
  }
  mandatory false;
 }
 leaf USNOTSCHRBGRSRPOFFSET {
  type int8 {
   range "-15..6";
  }
  mandatory false;
 }
 leaf USNOTSCHRBGRSRPTHLD {
  type int16 {
   range "-130..-90";
  }
  mandatory false;
 }
 leaf USPAPCOFF {
  type enumeration {
   enum val-0;
   enum val-1;
   enum val-2;
   enum val-3;
   enum val-4;
   enum val-5;
   enum val-6;
   enum val-7;
  }
  mandatory false;
 }
 leaf USPUCCHRSRPHIGHTHDOFFSET {
  type uint8 {
   range "0..20";
  }
  mandatory false;
 }
 leaf USPUCCHSINRTARGETOFFSET {
  type uint8 {
   range "0..20";
  }
  mandatory false;
 }
 leaf USPUSCHSINRHIGHTHDOFFSET {
  type uint8 {
   range "0..20";
  }
  mandatory false;
 }
 leaf USSMOOTHHOCOMPTHLDOFS {
  type int8 {
   range "-30..30";
  }
  mandatory false;
 }
 leaf USSRSGUARANTEESWITCH {
  type enumeration {
   enum val-0;
   enum val-1;
   enum val-2;
   enum val-3;
  }
  mandatory false;
 }
 leaf USUEDLADAPTPWRBOOSTTHLD {
  type uint8 {
   range "0..90";
  }
  mandatory false;
 }
 leaf USUENCELLGUARANTEETIMER {
  type uint16 {
   range "1000..60000";
  }
  mandatory false;
 }
 leaf USUEPRACHREUSETHLD {
  type int16 {
   range "-300..300";
  }
  mandatory false;
 }
 leaf USULMINGBR {
  type uint16 {
   range "0..12500";
  }
  mandatory false;
 }
 leaf USULPRIORITYRATIO {
  type uint16 {
   range "0..1000";
  }
  mandatory false;
 }
 leaf USVOIPKEEPONLEN {
  type uint16 {
   range "0..65535";
  }
  mandatory false;
 }
 leaf USVOIPPREALLOCSIZE {
  type uint16 {
   range "45..1500";
  }
  mandatory false;
 }
 leaf USVOIPRATFREQPRIGROUPID {
  type uint8 {
   range "0..255";
  }
  mandatory false;
 }
 leaf USVOIPCOMPENSCHPERIOD {
  type enumeration {
   enum val-0;
   enum val-1;
   enum val-2;
   enum val-3;
   enum val-4;
   enum val-5;
   enum val-6;
   enum val-7;
   enum val-8;
  }
  mandatory false;
 }
 leaf USVOIPINITDLIBLERTARGET {
  type uint8 {
   range "0..100";
  }
  mandatory false;
 }
 leaf USVOIPPDCCHSINROFFSET {
  type uint8 {
   range "0..30";
  }
  mandatory false;
 }
 leaf USVOLTEALGOSWITCH {
  type string;
  mandatory false;
 }
 leaf USWITHGAPMODE {
  type boolean;
  mandatory false;
 }
 leaf VOLTESILDELAYHORSRPTHLD {
  type union {
   type int16 {
    range "-140..255";
   }
  }
  mandatory false;
 }
 leaf VOLTESILDELAYHORSRQTHLD {
  type int8 {
   range "-40..-6";
  }
  mandatory false;
 }
 }
 grouping CELLVMS-attributes {
 leaf LOCALCELLNAME {
  type string;
  mandatory false;
 }
 leaf LOCALCELLID {
  type union {
   type int16 {
    range "-1..255";
   }
  }
  mandatory false;
 }
 leaf VMSA3OFFSET {
  type uint8 {
   range "0..20";
  }
  mandatory false;
 }
 leaf VMSHOUENUMTH {
  type uint8 {
   range "1..10";
  }
  mandatory false;
 }
 leaf VMSPRBDIFFTH {
  type uint8 {
   range "1..99";
  }
  mandatory false;
 }
 leaf VMSPRBLOADTH {
  type uint8 {
   range "1..99";
  }
  mandatory false;
 }
 }
 grouping CELLWTTXPARACFG-attributes {
 leaf LOCALCELLNAME {
  type string;
  mandatory false;
 }
 leaf DLPRBUSAGETHLD {
  type uint8 {
   range "0..100";
  }
  mandatory false;
 }
 leaf DLSCHMAXDYNWEIGHT {
  type uint16 {
   range "10..1000";
  }
  mandatory false;
 }
 leaf DYNCTRLMBBUEPRBTHLD {
  type uint8 {
   range "0..99";
  }
  mandatory false;
 }
 leaf DYNCTRLUECNTHIGHPCTTHLD {
  type uint16 {
   range "1..1000";
  }
  mandatory false;
 }
 leaf DYNCTRLUECNTLOWPCTTHLD {
  type uint16 {
   range "1..1000";
  }
  mandatory false;
 }
 leaf IPTVGUARANTEEUSERCOUNT {
  type uint8 {
   range "0..50";
  }
  mandatory false;
 }
 leaf LOCALCELLID {
  type union {
   type int16 {
    range "-1..255";
   }
  }
  mandatory false;
 }
 leaf MBBCONGESTDELAYTHLD {
  type uint8 {
   range "30..100";
  }
  mandatory false;
 }
 leaf MBBUSERDLPRBUPLIMIT {
  type uint8 {
   range "0..100";
  }
  mandatory false;
 }
 leaf MBBUSERULPRBUPLIMIT {
  type uint8 {
   range "0..100";
  }
  mandatory false;
 }
 leaf PRBUPLIMITCTRLMODE {
  type enumeration {
   enum val-0;
   enum val-1;
   enum val-2;
   enum val-3;
   enum val-4;
   enum val-5;
  }
  mandatory false;
 }
 leaf ULPRBUSAGETHLD {
  type uint8 {
   range "0..100";
  }
  mandatory false;
 }
 leaf ULSCHMAXDYNWEIGHT {
  type uint16 {
   range "10..1000";
  }
  mandatory false;
 }
 leaf WBBMULTICARRIERCOORDA2OFS {
  type uint8 {
   range "0..10";
  }
  mandatory false;
 }
 leaf WBBORMBBUSERDEFMODE {
  type boolean;
  mandatory false;
 }
 leaf WBBPERFORMANCEOPTSWITCH {
  type string;
  mandatory false;
 }
 leaf WBBRESALLOCCOEFF {
  type uint8 {
   range "20..100";
  }
  mandatory false;
 }
 leaf WBBUSERDLPRBUPLIMIT {
  type uint8 {
   range "0..100";
  }
  mandatory false;
 }
 leaf WBBUSERULPRBUPLIMIT {
  type uint8 {
   range "0..100";
  }
  mandatory false;
 }
 }
 grouping CELLWUSCONFIG-attributes {
 leaf LOCALCELLNAME {
  type string;
  mandatory false;
 }
 leaf IDLEDRXOFFSETTIME {
  type enumeration {
   enum val-0;
   enum val-1;
   enum val-2;
   enum val-3;
  }
  mandatory false;
 }
 leaf IDLEEDRXLONGOFFSETTIME {
  type enumeration {
   enum val-0;
   enum val-1;
   enum val-2;
  }
  mandatory false;
 }
 leaf IDLEEDRXSHORTOFFSETTIME {
  type enumeration {
   enum val-0;
   enum val-1;
   enum val-2;
   enum val-3;
  }
  mandatory false;
 }
 leaf LOCALCELLID {
  type union {
   type int16 {
    range "-1..255";
   }
  }
  mandatory false;
 }
 leaf MAXNUMOFDRXCYCLE {
  type enumeration {
   enum val-0;
   enum val-1;
   enum val-2;
   enum val-3;
  }
  mandatory false;
 }
 leaf MAXNUMBEROFPO {
  type enumeration {
   enum val-0;
   enum val-1;
   enum val-2;
  }
  mandatory false;
 }
 leaf WUSACTUALTXSFRATIOTHLD {
  type uint8 {
   range "50..80";
  }
  mandatory false;
 }
 leaf WUSALGOSWITCH {
  type string;
  mandatory false;
 }
 }
 grouping CEPUCCHCFG-attributes {
 leaf LOCALCELLNAME {
  type string;
  mandatory false;
 }
 leaf COVERAGELEVEL {
  type enumeration {
   enum val--1;
   enum val-0;
   enum val-1;
   enum val-2;
   enum val-3;
  }
  mandatory false;
 }
 leaf EMTCSRIPERIODADAPTSW {
  type enumeration {
   enum val-0;
   enum val-1;
   enum val-2;
  }
  mandatory false;
 }
 leaf FULLDUPLEXVOLTEPUCCHREPNUM {
  type enumeration {
   enum val-0;
   enum val-1;
   enum val-2;
   enum val-3;
  }
  mandatory false;
 }
 leaf HALFDUPLEXVOLTEPUCCHREPNUM {
  type enumeration {
   enum val-0;
   enum val-1;
   enum val-2;
   enum val-3;
  }
  mandatory false;
 }
 leaf LOCALCELLID {
  type union {
   type int16 {
    range "-1..255";
   }
  }
  mandatory false;
 }
 leaf PUCCHREPNUM {
  type enumeration {
   enum val-0;
   enum val-1;
   enum val-2;
   enum val-3;
   enum val-4;
   enum val-5;
  }
  mandatory false;
 }
 }
 grouping CERACHCFG-attributes {
 leaf LOCALCELLNAME {
  type string;
  mandatory false;
 }
 leaf ADAPTIVERACHHIGHLOADTHLD {
  type union {
   type uint8 {
    range "0..255";
   }
  }
  mandatory false;
 }
 leaf CONTENTIONRESOLUTIONTIMER {
  type enumeration {
   enum val-0;
   enum val-1;
   enum val-2;
   enum val-3;
   enum val-4;
   enum val-5;
   enum val-6;
   enum val-7;
  }
  mandatory false;
 }
 leaf COVERAGELEVEL {
  type enumeration {
   enum val--1;
   enum val-0;
   enum val-1;
   enum val-2;
   enum val-3;
  }
  mandatory false;
 }
 leaf LOCALCELLID {
  type union {
   type int16 {
    range "-1..255";
   }
  }
  mandatory false;
 }
 leaf MAXNUMPRBATTEMPT {
  type enumeration {
   enum val-0;
   enum val-1;
   enum val-2;
   enum val-3;
   enum val-4;
   enum val-5;
   enum val-6;
  }
  mandatory false;
 }
 leaf PREAMBLERATIO {
  type uint8 {
   range "0..100";
  }
  mandatory false;
 }
 leaf PREAMBLEREPETITIONNUM {
  type enumeration {
   enum val-0;
   enum val-1;
   enum val-2;
   enum val-3;
   enum val-4;
   enum val-5;
   enum val-6;
   enum val-7;
  }
  mandatory false;
 }
 leaf RACHTHLDINCREASECOEFF {
  type int16 {
   range "-100..1000";
  }
  mandatory false;
 }
 leaf RANDOMPREAMBLERATIO {
  type uint8 {
   range "1..100";
  }
  mandatory false;
 }
 }
 grouping CLKDETECT-attributes {
 leaf CLKASYNCDETECTSWITCH {
  type boolean;
  mandatory false;
 }
 leaf CLKASYNCINTERFRPTTHLD {
  type int16 {
   range "-130..-50";
  }
  mandatory false;
 }
 leaf CLKASYNCPRBUSAGETHLD {
  type uint8 {
   range "0..100";
  }
  mandatory false;
 }
 leaf CLKASYNCREPORTPERIOD {
  type enumeration {
   enum val-0;
   enum val-1;
   enum val-2;
   enum val-3;
   enum val-4;
   enum val-5;
   enum val-6;
   enum val-7;
   enum val-8;
   enum val-9;
  }
  mandatory false;
 }
 leaf CLKASYNCSILDETINFDIFTHLD {
  type int8 {
   range "-10..30";
  }
  mandatory false;
 }
 leaf CLKASYNCSILDETINFTHLD {
  type int16 {
   range "-130..-50";
  }
  mandatory false;
 }
 leaf POSTPROCESSINGMEASURE {
  type boolean;
  mandatory false;
 }
 }
 grouping CLUSTER-attributes {
 leaf OLD_CLUSTERID {
  type union {
   type int32 {
    range "-1..65535";
   }
  }
  mandatory false;
 }
 leaf CLUSTERID {
  type union {
   type int32 {
    range "-1..65535";
   }
  }
  mandatory false;
 }
 leaf CLUSTERTYPE {
  type enumeration {
   enum val-0;
   enum val-1;
   enum val-2;
   enum val-3;
  }
  mandatory false;
 }
 }
 grouping CLUSTERCELL-attributes {
 leaf OLD_CELLID {
  type union {
   type int16 {
    range "-1..255";
   }
  }
  mandatory false;
 }
 leaf CELLID {
  type union {
   type int16 {
    range "-1..255";
   }
  }
  mandatory false;
 }
 leaf OLD_CLUSTERID {
  type union {
   type int32 {
    range "-1..65535";
   }
  }
  mandatory false;
 }
 leaf CLUSTERID {
  type union {
   type int32 {
    range "-1..65535";
   }
  }
  mandatory false;
 }
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf OLD_ENODEBID {
  type union {
   type int32 {
    range "-1..1048575";
   }
  }
  mandatory false;
 }
 leaf ENODEBID {
  type union {
   type int32 {
    range "-1..1048575";
   }
  }
  mandatory false;
 }
 }
 grouping CLZEROBUFFERZONE-attributes {
 leaf LOCALCELLNAME {
  type string;
  mandatory false;
 }
 leaf CLSHAREDFREQENDRB1 {
  type uint8 {
   range "0..99";
  }
  mandatory false;
 }
 leaf CLSHAREDFREQENDRB2 {
  type uint8 {
   range "0..99";
  }
  mandatory false;
 }
 leaf CLSHAREDFREQSTARTRB1 {
  type uint8 {
   range "0..99";
  }
  mandatory false;
 }
 leaf CLSHAREDFREQSTARTRB2 {
  type uint8 {
   range "0..99";
  }
  mandatory false;
 }
 leaf CLZEROBUFFERZONEULPRBOST {
  type uint8 {
   range "0..100";
  }
  mandatory false;
 }
 leaf CLZEROBUFFERZONEULPRBTHD {
  type uint8 {
   range "0..100";
  }
  mandatory false;
 }
 leaf CLZEROBUFZONEDLSHAREDIND {
  type enumeration {
   enum val-0;
   enum val-1;
   enum val-2;
  }
  mandatory false;
 }
 leaf CLZEROBUFZONEULSHAREDIND {
  type boolean;
  mandatory false;
 }
 leaf DLNEARPTUSERRSRPTHD {
  type int16 {
   range "-140..-43";
  }
  mandatory false;
 }
 leaf LOCALCELLID {
  type union {
   type int16 {
    range "-1..255";
   }
  }
  mandatory false;
 }
 leaf ULNEARPTUSERRSRPTHD {
  type int16 {
   range "-140..-43";
  }
  mandatory false;
 }
 }
 grouping CNOPERATOR-attributes {
 leaf OLD_CNOPERATORID {
  type union {
   type int8 {
    range "-1..5";
   }
  }
  mandatory false;
 }
 leaf CNOPERATORID {
  type union {
   type int8 {
    range "-1..5";
   }
  }
  mandatory false;
 }
 leaf CNOPERATORNAME {
  type string {
   length "1..32";
  }
  mandatory false;
 }
 leaf CNOPERATORTYPE {
  type boolean;
  mandatory false;
 }
 leaf GTEEPAGINGCAPACITYRATIO {
  type uint8 {
   range "0..100";
  }
  mandatory false;
 }
 leaf MCC {
  type string {
   length "3";
  }
  mandatory false;
 }
 leaf MNC {
  type string {
   length "2..3";
  }
  mandatory false;
 }
 leaf NRSCGFREQPRIORITYGROUPID {
  type union {
   type uint16 {
    range "0..65535";
   }
  }
  mandatory false;
 }
 leaf OPERATORFUNSWITCH {
  type string;
  mandatory false;
 }
 leaf PLMNMODE {
  type boolean;
  mandatory false;
 }
 leaf UECAPRRCSEGALLOWEDTHLD {
  type uint16 {
   range "0..24000";
  }
  mandatory false;
 }
 }
 grouping CNOPERATORHOCFG-attributes {
 leaf BLINDHOA1A2TRIGQUAN {
  type enumeration {
   enum val-0;
   enum val-1;
   enum val-2;
   enum val-3;
  }
  mandatory false;
 }
 leaf CNOPERATORID {
  type union {
   type int8 {
    range "-1..5";
   }
  }
  mandatory false;
 }
 leaf COVIFHOA4A5RPTQUAN {
  type enumeration {
   enum val-0;
   enum val-1;
   enum val-2;
  }
  mandatory false;
 }
 leaf FDDIFHOA2THDRSRPOFFSET {
  type union {
   type int8 {
    range "-100..20";
   }
  }
  mandatory false;
 }
 leaf FIRSTRATPRI {
  type enumeration {
   enum val-1;
   enum val-2;
   enum val-3;
  }
  mandatory false;
 }
 leaf GERANA2THDRSRPOFFSET {
  type union {
   type int8 {
    range "-100..20";
   }
  }
  mandatory false;
 }
 leaf INTERFREQHOA1A2TRIGQUAN {
  type enumeration {
   enum val-0;
   enum val-1;
   enum val-2;
   enum val-3;
  }
  mandatory false;
 }
 leaf NRA2THLDRSRPOFFSET {
  type int8 {
   range "-20..20";
  }
  mandatory false;
 }
 leaf PSINTERRATHIGHESTPRI {
  type enumeration {
   enum val-0;
   enum val-1;
   enum val-2;
  }
  mandatory false;
 }
 leaf PSINTERRATLOWESTPRI {
  type enumeration {
   enum val-0;
   enum val-1;
   enum val-2;
   enum val-3;
  }
  mandatory false;
 }
 leaf PSINTERRATSECONDPRI {
  type enumeration {
   enum val-0;
   enum val-1;
   enum val-2;
   enum val-3;
  }
  mandatory false;
 }
 leaf SECONDRATPRI {
  type enumeration {
   enum val-1;
   enum val-2;
   enum val-4;
  }
  mandatory false;
 }
 leaf SRVCCWITHPSBASEDCELLCAPSW {
  type boolean;
  mandatory false;
 }
 leaf TDDIFHOA2THDRSRPOFFSET {
  type union {
   type int8 {
    range "-100..20";
   }
  }
  mandatory false;
 }
 leaf UTRANA2THDRSRPOFFSET {
  type union {
   type int8 {
    range "-100..20";
   }
  }
  mandatory false;
 }
 }
 grouping CNOPERATORIPPATH-attributes {
 leaf CNOPERATORID {
  type uint8 {
   range "0..5";
  }
  mandatory false;
 }
 leaf IPPATHID {
  type union {
   type int32 {
    range "-1..65535";
   }
  }
  mandatory false;
 }
 }
 grouping CNOPERATORQCIPARA-attributes {
 leaf OLD_CNOPERATORID {
  type union {
   type int8 {
    range "-1..5";
   }
  }
  mandatory false;
 }
 leaf CNOPERATORID {
  type union {
   type int8 {
    range "-1..5";
   }
  }
  mandatory false;
 }
 leaf DLSCHPRIORITYWEIGHTFACTOR {
  type union {
   type uint16 {
    range "1..65535";
   }
  }
  mandatory false;
 }
 leaf INTERFREQA2RSRPTHLDOFFSET {
  type int8 {
   range "-80..80";
  }
  mandatory false;
 }
 leaf INTERRATA2RSRPTHLDOFFSET {
  type int8 {
   range "-20..20";
  }
  mandatory false;
 }
 leaf LOCALQCIARP {
  type uint8 {
   range "0..15";
  }
  mandatory false;
 }
 leaf NRA1RSRPTHLDOFFSET {
  type int8 {
   range "-20..20";
  }
  mandatory false;
 }
 leaf NRA2RSRPTHLDOFFSET {
  type int8 {
   range "-20..20";
  }
  mandatory false;
 }
 leaf OLD_QCI {
  type union {
   type int16 {
    range "-1..254";
   }
  }
  mandatory false;
 }
 leaf QCI {
  type union {
   type int16 {
    range "-1..254";
   }
  }
  mandatory false;
 }
 leaf QCIALGOSWITCH {
  type string;
  mandatory false;
 }
 leaf SERVICEHOBEARERPOLICY {
  type boolean;
  mandatory false;
 }
 leaf SERVICEHONRPOLICYGROUPID {
  type uint8 {
   range "0..9";
  }
  mandatory false;
 }
 leaf SERVICEIFHOCFGGROUPID {
  type uint8 {
   range "0..9";
  }
  mandatory false;
 }
 leaf SERVICEIRHOCFGGROUPID {
  type uint8 {
   range "0..9";
  }
  mandatory false;
 }
 leaf UDTNO {
  type union {
   type uint16 {
    range "0..65535";
   }
  }
  mandatory false;
 }
 leaf ULSCHPRIORITYWEIGHTFACTOR {
  type union {
   type uint16 {
    range "1..65535";
   }
  }
  mandatory false;
 }
 }
 grouping CNOPERATORSPIDCFG-attributes {
 leaf CNOPERATORID {
  type union {
   type int8 {
    range "-1..5";
   }
  }
  mandatory false;
 }
 leaf OFFLOADSWITCH {
  type string;
  mandatory false;
 }
 leaf RATFREQPRIORITYGROUPID {
  type uint8 {
   range "0..255";
  }
  mandatory false;
 }
 leaf RATFREQPRIORITYIND {
  type boolean;
  mandatory false;
 }
 leaf SPID {
  type union {
   type int16 {
    range "-1..256";
   }
  }
  mandatory false;
 }
 }
 grouping CNOPERATORTA-attributes {
 leaf CNOPERATORID {
  type uint8 {
   range "0..5";
  }
  mandatory false;
 }
 leaf NBIOTTAFLAG {
  type boolean;
  mandatory false;
 }
 leaf TAC {
  type union {
   type uint16 {
    range "1..65535";
   }
  }
  mandatory false;
 }
 leaf OLD_TRACKINGAREAID {
  type union {
   type int32 {
    range "-1..65535";
   }
  }
  mandatory false;
 }
 leaf TRACKINGAREAID {
  type union {
   type int32 {
    range "-1..65535";
   }
  }
  mandatory false;
 }
 }
 grouping CNOPQCIEVENTPARAM-attributes {
 leaf OLD_CNOPERATORID {
  type union {
   type int8 {
    range "-1..5";
   }
  }
  mandatory false;
 }
 leaf CNOPERATORID {
  type union {
   type int8 {
    range "-1..5";
   }
  }
  mandatory false;
 }
 leaf OLD_EVENTTYPE {
  type enumeration {
   enum val--1;
   enum val-0;
   enum val-1;
   enum val-2;
   enum val-3;
   enum val-4;
   enum val-5;
   enum val-6;
   enum val-7;
   enum val-8;
   enum val-9;
   enum val-10;
   enum val-11;
   enum val-12;
   enum val-13;
  }
  mandatory false;
 }
 leaf EVENTTYPE {
  type enumeration {
   enum val--1;
   enum val-0;
   enum val-1;
   enum val-2;
   enum val-3;
   enum val-4;
   enum val-5;
   enum val-6;
   enum val-7;
   enum val-8;
   enum val-9;
   enum val-10;
   enum val-11;
   enum val-12;
   enum val-13;
  }
  mandatory false;
 }
 leaf HANDOVERRSRQTHLDOFFSET {
  type int8 {
   range "-40..40";
  }
  mandatory false;
 }
 leaf HANDOVERTHLDOFFSET {
  type int8 {
   range "-80..80";
  }
  mandatory false;
 }
 leaf OLD_QCI {
  type union {
   type int16 {
    range "-1..255";
   }
  }
  mandatory false;
 }
 leaf QCI {
  type union {
   type int16 {
    range "-1..255";
   }
  }
  mandatory false;
 }
 leaf USERTYPE {
  type string;
  mandatory false;
 }
 }
 grouping CNOPSHARINGGROUP-attributes {
 leaf OLD_CNOPSHARINGGROUPID {
  type union {
   type int8 {
    range "-1..5";
   }
  }
  mandatory false;
 }
 leaf CNOPSHARINGGROUPID {
  type union {
   type int8 {
    range "-1..5";
   }
  }
  mandatory false;
 }
 leaf PRIMARYOPERATORID {
  type uint8 {
   range "0..5";
  }
  mandatory false;
 }
 }
 grouping CNOPUSERATTRIBUTE-attributes {
 leaf ARP {
  type union {
   type int8 {
    range "-1..15";
   }
  }
  mandatory false;
 }
 leaf CNOPERATORID {
  type union {
   type int8 {
    range "-1..5";
   }
  }
  mandatory false;
 }
 leaf USERPRIORITY {
  type enumeration {
   enum val-1;
   enum val-2;
   enum val-3;
   enum val-4;
  }
  mandatory false;
 }
 }
 grouping CNOPUSERQCIPARA-attributes {
 leaf CNOPERATORID {
  type union {
   type int8 {
    range "-1..5";
   }
  }
  mandatory false;
 }
 leaf DLSCHPRIORITYWEIGHTFACTOR {
  type uint16 {
   range "1..1000";
  }
  mandatory false;
 }
 leaf QCI {
  type union {
   type int8 {
    range "-1..9";
   }
  }
  mandatory false;
 }
 leaf ULSCHPRIORITYWEIGHTFACTOR {
  type uint16 {
   range "1..1000";
  }
  mandatory false;
 }
 leaf USERPRIORITY {
  type enumeration {
   enum val--1;
   enum val-1;
   enum val-2;
   enum val-3;
   enum val-4;
  }
  mandatory false;
 }
 }
 grouping CONTIGINTRABANDCARR-attributes {
 leaf LOCALCELLNAME {
  type string;
  mandatory false;
 }
 leaf CONTIGINTRABANDCARRSW {
  type string;
  mandatory false;
 }
 leaf FIXEDEXCLUSIVERESRATE {
  type union {
   type uint8 {
    range "80..255";
   }
  }
  mandatory false;
 }
 leaf LOCALCELLID {
  type union {
   type int16 {
    range "-1..255";
   }
  }
  mandatory false;
 }
 }
 grouping COPROCRES-attributes {
 leaf BASEBANDEQMID {
  type union {
   type uint8 {
    range "0..255";
   }
  }
  mandatory false;
 }
 leaf BUNDLINGCLUSTERTYPE {
  type enumeration {
   enum val-0;
   enum val-1;
   enum val-2;
   enum val-3;
   enum val-4;
  }
  mandatory false;
 }
 leaf OLD_COPROCRESID {
  type union {
   type int8 {
    range "-1..12";
   }
  }
  mandatory false;
 }
 leaf COPROCRESID {
  type union {
   type int8 {
    range "-1..12";
   }
  }
  mandatory false;
 }
 leaf WORKMODE {
  type string;
  mandatory false;
 }
 }
 grouping COUNTERCHECKPARA-attributes {
 leaf COUNTERCHECKCOUNTNUM {
  type union {
   type uint32 {
    range "0..4294967295";
   }
  }
  mandatory false;
 }
 leaf COUNTERCHECKDLVRFORBIDSW {
  type boolean;
  mandatory false;
 }
 leaf COUNTERCHECKTIMER {
  type union {
   type uint16 {
    range "0..600";
   }
  }
  mandatory false;
 }
 leaf COUNTERCHECKUSERRELSWITCH {
  type boolean;
  mandatory false;
 }
 }
 grouping CQIADAPTIVECFG-attributes {
 leaf PUCCHPERIODICCQIOPTSWITCH {
  type boolean;
  mandatory false;
 }
 leaf SIMULACKNACKANDCQIFMT3SW {
  type boolean;
  mandatory false;
 }
 }
 grouping CSFALLBACKBLINDHOCFG-attributes {
 leaf CDMALCSCAP {
  type boolean;
  mandatory false;
 }
 leaf CNOPERATORID {
  type union {
   type int8 {
    range "-1..5";
   }
  }
  mandatory false;
 }
 leaf GERANLCSCAP {
  type boolean;
  mandatory false;
 }
 leaf IDLECSFBHIGHESTPRI {
  type enumeration {
   enum val-0;
   enum val-1;
   enum val-2;
  }
  mandatory false;
 }
 leaf IDLECSFBLOWESTPRI {
  type enumeration {
   enum val-0;
   enum val-1;
   enum val-2;
   enum val-3;
  }
  mandatory false;
 }
 leaf IDLECSFBSECONDPRI {
  type enumeration {
   enum val-0;
   enum val-1;
   enum val-2;
   enum val-3;
  }
  mandatory false;
 }
 leaf INTERRATHIGHESTPRI {
  type enumeration {
   enum val-0;
   enum val-1;
   enum val-2;
  }
  mandatory false;
 }
 leaf INTERRATLOWESTPRI {
  type enumeration {
   enum val-0;
   enum val-1;
   enum val-2;
   enum val-3;
  }
  mandatory false;
 }
 leaf INTERRATSECONDPRI {
  type enumeration {
   enum val-0;
   enum val-1;
   enum val-2;
   enum val-3;
  }
  mandatory false;
 }
 leaf UTRANLCSCAP {
  type boolean;
  mandatory false;
 }
 }
 grouping CSFALLBACKHO-attributes {
 leaf LOCALCELLNAME {
  type string;
  mandatory false;
 }
 leaf BLINDHOA1THDRSRP {
  type int16 {
   range "-140..-43";
  }
  mandatory false;
 }
 leaf CSFBHOCDMAB1THDPS {
  type int8 {
   range "-63..0";
  }
  mandatory false;
 }
 leaf CSFBHOCDMATIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf CSFBHOGERANB1THD {
  type int8 {
   range "-110..-48";
  }
  mandatory false;
 }
 leaf CSFBHOGERANTIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf CSFBHOUTRANB1THDECN0 {
  type int8 {
   range "-48..0";
  }
  mandatory false;
 }
 leaf CSFBHOUTRANB1THDRSCP {
  type int8 {
   range "-120..-25";
  }
  mandatory false;
 }
 leaf CSFBHOUTRANTIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf CSFBPROTECTTIMER {
  type uint8 {
   range "0..100";
  }
  mandatory false;
 }
 leaf LOCALCELLID {
  type union {
   type int16 {
    range "-1..255";
   }
  }
  mandatory false;
 }
 }
 grouping CSFALLBACKPOLICYCFG-attributes {
 leaf CSFBHOPOLICYCFG {
  type string;
  mandatory false;
 }
 leaf CSFBUSERARPCFGSWITCH {
  type boolean;
  mandatory false;
 }
 leaf IDLEMODECSFBHOPOLICYCFG {
  type string;
  mandatory false;
 }
 leaf NORMALCSFBUSERARP {
  type uint8 {
   range "1..15";
  }
  mandatory false;
 }
 }
 grouping CSPCALGOPARA-attributes {
 leaf CSPCALGOSWITCH {
  type boolean;
  mandatory false;
 }
 leaf CSPCCAPACITYFACTOR {
  type uint8 {
   range "0..100";
  }
  mandatory false;
 }
 leaf CSPCCLUSTERMODE {
  type boolean;
  mandatory false;
 }
 leaf CSPCENABLEDLPRBRATIOTHD {
  type uint8 {
   range "0..100";
  }
  mandatory false;
 }
 leaf CSPCPOWERCONFIGDELAY {
  type uint8 {
   range "2..10";
  }
  mandatory false;
 }
 leaf CSPCRSRPMEASMODE {
  type boolean;
  mandatory false;
 }
 leaf CSPCSCHEDULEUESPEC {
  type uint8 {
   range "1..25";
  }
  mandatory false;
 }
 leaf TDDCSPCALGOSWITCH {
  type string;
  mandatory false;
 }
 }
 grouping DDCELLGROUP-attributes {
 leaf OLD_DDBANDWIDTH {
  type enumeration {
   enum val--1;
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
  }
  mandatory false;
 }
 leaf DDBANDWIDTH {
  type enumeration {
   enum val--1;
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
  }
  mandatory false;
 }
 leaf OLD_LOCALCELLID1 {
  type union {
   type int16 {
    range "-1..255";
   }
  }
  mandatory false;
 }
 leaf LOCALCELLID1 {
  type union {
   type int16 {
    range "-1..255";
   }
  }
  mandatory false;
 }
 leaf OLD_LOCALCELLID2 {
  type union {
   type int16 {
    range "-1..255";
   }
  }
  mandatory false;
 }
 leaf LOCALCELLID2 {
  type union {
   type int16 {
    range "-1..255";
   }
  }
  mandatory false;
 }
 }
 grouping DEFAULTDCNCFG-attributes {
 leaf OLD_CNOPERATORID {
  type union {
   type int8 {
    range "-1..5";
   }
  }
  mandatory false;
 }
 leaf CNOPERATORID {
  type union {
   type int8 {
    range "-1..5";
   }
  }
  mandatory false;
 }
 leaf OLD_DEFAULTDCNMMEGROUPID {
  type union {
   type int32 {
    range "-1..65535";
   }
  }
  mandatory false;
 }
 leaf DEFAULTDCNMMEGROUPID {
  type union {
   type int32 {
    range "-1..65535";
   }
  }
  mandatory false;
 }
 }
 grouping DISTBASEDHO-attributes {
 leaf LOCALCELLNAME {
  type string;
  mandatory false;
 }
 leaf DISTBASEDHOTHD {
  type union {
   type uint16 {
    range "1..3281";
   }
  }
  mandatory false;
 }
 leaf DISTBASEDMEASOBJTYPE {
  type string;
  mandatory false;
 }
 leaf LOCALCELLID {
  type union {
   type int16 {
    range "-1..255";
   }
  }
  mandatory false;
 }
 }
 grouping DMIMOALGO-attributes {
 leaf LOCALCELLNAME {
  type string;
  mandatory false;
 }
 leaf DMIMOA3RSRPOFFSET {
  type int8 {
   range "-30..30";
  }
  mandatory false;
 }
 leaf DMIMOJTCELLRSRPDIFFTHLD {
  type int8 {
   range "-30..30";
  }
  mandatory false;
 }
 leaf LOCALCELLID {
  type union {
   type int16 {
    range "-1..255";
   }
  }
  mandatory false;
 }
 }
 grouping DMIMOCLUSTER-attributes {
 leaf BFWEIGHTNORMALIZEMODE {
  type boolean;
  mandatory false;
 }
 leaf COPROCRESID {
  type union {
   type uint8 {
    range "0..255";
   }
  }
  mandatory false;
 }
 leaf OLD_DMIMOCLUSTERID {
  type union {
   type int32 {
    range "-1..65535";
   }
  }
  mandatory false;
 }
 leaf DMIMOCLUSTERID {
  type union {
   type int32 {
    range "-1..65535";
   }
  }
  mandatory false;
 }
 }
 grouping DMIMOCLUSTERCELL-attributes {
 leaf OLD_CELLID {
  type union {
   type int16 {
    range "-1..255";
   }
  }
  mandatory false;
 }
 leaf CELLID {
  type union {
   type int16 {
    range "-1..255";
   }
  }
  mandatory false;
 }
 leaf OLD_DMIMOCLUSTERID {
  type union {
   type int32 {
    range "-1..65535";
   }
  }
  mandatory false;
 }
 leaf DMIMOCLUSTERID {
  type union {
   type int32 {
    range "-1..65535";
   }
  }
  mandatory false;
 }
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf OLD_ENODEBID {
  type union {
   type int32 {
    range "-1..1048575";
   }
  }
  mandatory false;
 }
 leaf ENODEBID {
  type union {
   type int32 {
    range "-1..1048575";
   }
  }
  mandatory false;
 }
 }
 grouping DRX-attributes {
 leaf DRXFLEXCTRLSWITCH {
  type boolean;
  mandatory false;
 }
 }
 grouping DRXPARAGROUP-attributes {
 leaf LOCALCELLNAME {
  type string;
  mandatory false;
 }
 leaf CATTYPE {
  type enumeration {
   enum val-0;
   enum val-1;
   enum val-2;
   enum val-3;
  }
  mandatory false;
 }
 leaf DRXINACTIVITYTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
  }
  mandatory false;
 }
 leaf OLD_DRXPARAGROUPID {
  type union {
   type int8 {
    range "-1..49";
   }
  }
  mandatory false;
 }
 leaf DRXPARAGROUPID {
  type union {
   type int8 {
    range "-1..49";
   }
  }
  mandatory false;
 }
 leaf DRXRETXTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf DRXSHORTCYCLETIMER {
  type uint8 {
   range "1..16";
  }
  mandatory false;
 }
 leaf DRXULRETXTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
  }
  mandatory false;
 }
 leaf ENTERDRXSWITCH {
  type boolean;
  mandatory false;
 }
 leaf EXTENDLONGDRXCYCLE {
  type boolean;
  mandatory false;
 }
 leaf EXTENDLONGDRXCYCLESWITCH {
  type boolean;
  mandatory false;
 }
 leaf OLD_LOCALCELLID {
  type union {
   type int16 {
    range "-1..255";
   }
  }
  mandatory false;
 }
 leaf LOCALCELLID {
  type union {
   type int16 {
    range "-1..255";
   }
  }
  mandatory false;
 }
 leaf LONGDRXCYCLE {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf NBDRXINACTIVITYTIMER {
  type enumeration {
   enum val-0;
   enum val-1;
   enum val-2;
   enum val-3;
   enum val-4;
   enum val-5;
   enum val-6;
   enum val-7;
  }
  mandatory false;
 }
 leaf NBDRXRETXTIMER {
  type enumeration {
   enum val-0;
   enum val-1;
   enum val-2;
   enum val-3;
   enum val-4;
   enum val-5;
   enum val-6;
   enum val-7;
   enum val-8;
  }
  mandatory false;
 }
 leaf NBDRXULRETXTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
  }
  mandatory false;
 }
 leaf NBLONGDRXCYCLE {
  type enumeration {
   enum val-0;
   enum val-1;
   enum val-2;
   enum val-3;
   enum val-4;
   enum val-5;
   enum val-6;
   enum val-7;
   enum val-8;
   enum val-9;
   enum val-10;
   enum val-11;
  }
  mandatory false;
 }
 leaf NBONDURATIONTIMER {
  type enumeration {
   enum val-0;
   enum val-1;
   enum val-2;
   enum val-3;
   enum val-4;
   enum val-5;
   enum val-6;
  }
  mandatory false;
 }
 leaf ONDURATIONTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
  }
  mandatory false;
 }
 leaf SHORTDRXCYCLE {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf SUPPORTSHORTDRX {
  type boolean;
  mandatory false;
 }
 }
 grouping ECO-attributes {
 leaf CPEPGROUPID {
  type uint16 {
   range "0..65535";
  }
  mandatory false;
 }
 leaf OLD_ECOID {
  type union {
   type int8 {
    range "-1..0";
   }
  }
  mandatory false;
 }
 leaf ECOID {
  type union {
   type int8 {
    range "-1..0";
   }
  }
  mandatory false;
 }
 leaf EPGROUPCFGFLAG {
  type enumeration {
   enum val-0;
   enum val-1;
   enum val-2;
  }
  mandatory false;
 }
 leaf UPEPGROUPID {
  type uint16 {
   range "0..65535";
  }
  mandatory false;
 }
 leaf USERLABEL {
  type string {
   length "0..256";
  }
  mandatory false;
 }
 }
 grouping EMC-attributes {
 leaf CNOPERATORID {
  type union {
   type int8 {
    range "-1..5";
   }
  }
  mandatory false;
 }
 leaf EMCDEDICATEDBEARERARP {
  type uint8 {
   range "1..15";
  }
  mandatory false;
 }
 leaf EMCDEFAULTBEARERARP {
  type uint8 {
   range "1..15";
  }
  mandatory false;
 }
 leaf EMCENABLE {
  type boolean;
  mandatory false;
 }
 leaf EMCENABLEINLIMITEDMODE {
  type boolean;
  mandatory false;
 }
 leaf EMERGCALLOPTIMIZATIONSW {
  type string;
  mandatory false;
 }
 }
 grouping EMTCCESCHCFG-attributes {
 leaf LOCALCELLNAME {
  type string;
  mandatory false;
 }
 leaf COVERAGELEVEL {
  type enumeration {
   enum val--1;
   enum val-0;
   enum val-1;
   enum val-2;
   enum val-3;
  }
  mandatory false;
 }
 leaf LOCALCELLID {
  type union {
   type int16 {
    range "-1..255";
   }
  }
  mandatory false;
 }
 leaf MPDCCHINITREPNUM {
  type enumeration {
   enum val-0;
   enum val-1;
   enum val-2;
   enum val-3;
   enum val-4;
  }
  mandatory false;
 }
 leaf MPDCCHINITREPNUMTYPE1CSS {
  type enumeration {
   enum val-0;
   enum val-1;
   enum val-2;
   enum val-3;
   enum val-4;
  }
  mandatory false;
 }
 leaf MPDCCHMAXREPNUM {
  type enumeration {
   enum val-0;
   enum val-1;
   enum val-2;
   enum val-3;
   enum val-4;
   enum val-5;
   enum val-6;
   enum val-7;
   enum val-8;
  }
  mandatory false;
 }
 leaf PDSCHINITREPNUM {
  type enumeration {
   enum val-0;
   enum val-1;
   enum val-2;
   enum val-3;
   enum val-4;
   enum val-5;
   enum val-6;
   enum val-7;
   enum val-8;
  }
  mandatory false;
 }
 leaf PDSCHINITREPNUMTYPE1CSS {
  type enumeration {
   enum val-0;
   enum val-1;
   enum val-2;
   enum val-3;
   enum val-4;
   enum val-5;
   enum val-6;
   enum val-7;
   enum val-8;
  }
  mandatory false;
 }
 leaf PUSCHINITREPNUM {
  type enumeration {
   enum val-0;
   enum val-1;
   enum val-2;
   enum val-3;
   enum val-4;
   enum val-5;
   enum val-6;
   enum val-7;
   enum val-8;
  }
  mandatory false;
 }
 }
 grouping EMTCSIBCONFIG-attributes {
 leaf LOCALCELLNAME {
  type string;
  mandatory false;
 }
 leaf EMTCSIBID {
  type enumeration {
   enum val--1;
   enum val-0;
   enum val-1;
   enum val-2;
   enum val-3;
   enum val-4;
  }
  mandatory false;
 }
 leaf EMTCSIBPERIOD {
  type enumeration {
   enum val-0;
   enum val-1;
   enum val-2;
   enum val-3;
   enum val-4;
   enum val-5;
   enum val-6;
   enum val-255;
  }
  mandatory false;
 }
 leaf LOCALCELLID {
  type union {
   type int16 {
    range "-1..255";
   }
  }
  mandatory false;
 }
 }
 grouping ENBRSVDPARA-attributes {
 leaf RSVDPARA36 {
  type uint8 {
   range "0..255";
  }
  mandatory false;
 }
 leaf RSVDPARA37 {
  type uint8 {
   range "0..255";
  }
  mandatory false;
 }
 leaf RSVDPARA41 {
  type uint32 {
   range "0..4294967295";
  }
  mandatory false;
 }
 leaf RSVDPARA44 {
  type uint16 {
   range "0..65535";
  }
  mandatory false;
 }
 leaf RSVDPARA45 {
  type uint16 {
   range "0..65535";
  }
  mandatory false;
 }
 leaf RSVDPARA47 {
  type uint8 {
   range "0..255";
  }
  mandatory false;
 }
 leaf RSVDPARA48 {
  type uint8 {
   range "0..255";
  }
  mandatory false;
 }
 leaf RSVDPARA49 {
  type uint8 {
   range "0..255";
  }
  mandatory false;
 }
 leaf RSVDPARA50 {
  type uint8 {
   range "0..255";
  }
  mandatory false;
 }
 leaf RSVDPARA51 {
  type uint8 {
   range "0..255";
  }
  mandatory false;
 }
 leaf RSVDPARA52 {
  type uint8 {
   range "0..255";
  }
  mandatory false;
 }
 leaf RSVDPARA53 {
  type uint8 {
   range "0..255";
  }
  mandatory false;
 }
 leaf RSVDPARA55 {
  type uint8 {
   range "0..255";
  }
  mandatory false;
 }
 leaf RSVDPARA59 {
  type uint8 {
   range "0..255";
  }
  mandatory false;
 }
 leaf RSVDPARA60 {
  type uint8 {
   range "0..255";
  }
  mandatory false;
 }
 leaf RSVDPARA61 {
  type uint8 {
   range "0..255";
  }
  mandatory false;
 }
 leaf RSVDPARA62 {
  type uint8 {
   range "0..255";
  }
  mandatory false;
 }
 leaf RSVDPARA63 {
  type uint8 {
   range "0..255";
  }
  mandatory false;
 }
 leaf RSVDPARA64 {
  type uint8 {
   range "0..255";
  }
  mandatory false;
 }
 leaf RSVDPARA65 {
  type uint8 {
   range "0..255";
  }
  mandatory false;
 }
 leaf RSVDPARA66 {
  type uint8 {
   range "0..255";
  }
  mandatory false;
 }
 leaf RSVDPARA67 {
  type uint8 {
   range "0..255";
  }
  mandatory false;
 }
 leaf RSVDPARA68 {
  type uint8 {
   range "0..255";
  }
  mandatory false;
 }
 leaf RSVDPARA70 {
  type uint16 {
   range "0..65535";
  }
  mandatory false;
 }
 leaf RSVDPARA72 {
  type uint16 {
   range "0..65535";
  }
  mandatory false;
 }
 leaf RSVDPARA76 {
  type uint16 {
   range "0..65535";
  }
  mandatory false;
 }
 leaf RSVDPARA77 {
  type uint16 {
   range "0..65535";
  }
  mandatory false;
 }
 leaf RSVDPARA78 {
  type uint16 {
   range "0..65535";
  }
  mandatory false;
 }
 leaf RSVDPARA79 {
  type uint32 {
   range "0..4294967295";
  }
  mandatory false;
 }
 leaf RSVDPARA80 {
  type uint32 {
   range "0..4294967295";
  }
  mandatory false;
 }
 leaf RSVDPARA81 {
  type uint32 {
   range "0..4294967295";
  }
  mandatory false;
 }
 leaf RSVDPARA82 {
  type uint32 {
   range "0..4294967295";
  }
  mandatory false;
 }
 leaf RSVDPARA83 {
  type uint32 {
   range "0..4294967295";
  }
  mandatory false;
 }
 leaf RSVDPARA89 {
  type uint32 {
   range "0..4294967295";
  }
  mandatory false;
 }
 leaf RSVDPARA90 {
  type uint32 {
   range "0..4294967295";
  }
  mandatory false;
 }
 leaf RSVDPARA91 {
  type uint32 {
   range "0..4294967295";
  }
  mandatory false;
 }
 leaf RSVDPARA92 {
  type uint32 {
   range "0..4294967295";
  }
  mandatory false;
 }
 leaf RSVDPARA93 {
  type uint32 {
   range "0..4294967295";
  }
  mandatory false;
 }
 leaf RSVDPARA94 {
  type uint32 {
   range "0..4294967295";
  }
  mandatory false;
 }
 leaf RSVDPARA95 {
  type uint32 {
   range "0..4294967295";
  }
  mandatory false;
 }
 leaf RSVDPARA96 {
  type uint32 {
   range "0..4294967295";
  }
  mandatory false;
 }
 leaf RSVDSWPARA0 {
  type string;
  mandatory false;
 }
 leaf RSVDSWPARA1 {
  type string;
  mandatory false;
 }
 leaf RSVDSWPARA10 {
  type string;
  mandatory false;
 }
 leaf RSVDSWPARA11 {
  type string;
  mandatory false;
 }
 leaf RSVDSWPARA2 {
  type string;
  mandatory false;
 }
 leaf RSVDSWPARA3 {
  type string;
  mandatory false;
 }
 leaf RSVDSWPARA4 {
  type string;
  mandatory false;
 }
 leaf RSVDSWPARA5 {
  type string;
  mandatory false;
 }
 leaf RSVDSWPARA6 {
  type string;
  mandatory false;
 }
 leaf RSVDSWPARA7 {
  type string;
  mandatory false;
 }
 leaf RSVDSWPARA8 {
  type string;
  mandatory false;
 }
 leaf RSVDSWPARA9 {
  type string;
  mandatory false;
 }
 leaf RSVDU16PARA1 {
  type uint16 {
   range "0..65535";
  }
  mandatory false;
 }
 leaf RSVDU16PARA10 {
  type uint16 {
   range "0..65535";
  }
  mandatory false;
 }
 leaf RSVDU16PARA2 {
  type uint16 {
   range "0..65535";
  }
  mandatory false;
 }
 leaf RSVDU16PARA3 {
  type uint16 {
   range "0..65535";
  }
  mandatory false;
 }
 leaf RSVDU16PARA4 {
  type uint16 {
   range "0..65535";
  }
  mandatory false;
 }
 leaf RSVDU16PARA5 {
  type uint16 {
   range "0..65535";
  }
  mandatory false;
 }
 leaf RSVDU16PARA6 {
  type uint16 {
   range "0..65535";
  }
  mandatory false;
 }
 leaf RSVDU16PARA7 {
  type uint16 {
   range "0..65535";
  }
  mandatory false;
 }
 leaf RSVDU16PARA8 {
  type uint16 {
   range "0..65535";
  }
  mandatory false;
 }
 leaf RSVDU16PARA9 {
  type uint16 {
   range "0..65535";
  }
  mandatory false;
 }
 leaf RSVDU8PARA1 {
  type uint8 {
   range "0..255";
  }
  mandatory false;
 }
 leaf RSVDU8PARA10 {
  type uint8 {
   range "0..255";
  }
  mandatory false;
 }
 leaf RSVDU8PARA11 {
  type uint8 {
   range "0..255";
  }
  mandatory false;
 }
 leaf RSVDU8PARA12 {
  type uint8 {
   range "0..255";
  }
  mandatory false;
 }
 leaf RSVDU8PARA13 {
  type uint8 {
   range "0..255";
  }
  mandatory false;
 }
 leaf RSVDU8PARA14 {
  type uint8 {
   range "0..255";
  }
  mandatory false;
 }
 leaf RSVDU8PARA2 {
  type uint8 {
   range "0..255";
  }
  mandatory false;
 }
 leaf RSVDU8PARA3 {
  type uint8 {
   range "0..255";
  }
  mandatory false;
 }
 leaf RSVDU8PARA4 {
  type uint8 {
   range "0..255";
  }
  mandatory false;
 }
 leaf RSVDU8PARA5 {
  type uint8 {
   range "0..255";
  }
  mandatory false;
 }
 leaf RSVDU8PARA6 {
  type uint8 {
   range "0..255";
  }
  mandatory false;
 }
 leaf RSVDU8PARA7 {
  type uint8 {
   range "0..255";
  }
  mandatory false;
 }
 leaf RSVDU8PARA8 {
  type uint8 {
   range "0..255";
  }
  mandatory false;
 }
 leaf RSVDU8PARA9 {
  type uint8 {
   range "0..255";
  }
  mandatory false;
 }
 }
 grouping ENDCBANDGAPFREECFG-attributes {
 leaf OLD_BANDINDEX {
  type union {
   type int8 {
    range "-1..14";
   }
  }
  mandatory false;
 }
 leaf BANDINDEX {
  type union {
   type int8 {
    range "-1..14";
   }
  }
  mandatory false;
 }
 leaf BANDTYPE {
  type enumeration {
   enum val-0;
   enum val-1;
   enum val-2;
   enum val-3;
  }
  mandatory false;
 }
 leaf OLD_ENDCGAPFREECOMBID {
  type union {
   type int8 {
    range "-1..31";
   }
  }
  mandatory false;
 }
 leaf ENDCGAPFREECOMBID {
  type union {
   type int8 {
    range "-1..31";
   }
  }
  mandatory false;
 }
 leaf FREQUENCYBANDID {
  type uint16 {
   range "1..266";
  }
  mandatory false;
 }
 }
 grouping ENDCX2BLACKWHITELIST-attributes {
 leaf LISTTYPE {
  type boolean;
  mandatory false;
 }
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf OLD_GNODEBID {
  type union {
   type int64 {
    range "-1..4294967295";
   }
  }
  mandatory false;
 }
 leaf GNODEBID {
  type union {
   type int64 {
    range "-1..4294967295";
   }
  }
  mandatory false;
 }
 }
 grouping ENODEBALGOEXTSWITCH-attributes {
 leaf ANROPTSWITCH {
  type string;
  mandatory false;
 }
 leaf BLACKLISTEDNFREQDIFFIND {
  type union {
   type uint8 {
    range "0..255";
   }
  }
  mandatory false;
 }
 leaf BRDRESRECYCLESW {
  type string;
  mandatory false;
 }
 leaf BTRUNCFUNSWITCH {
  type string;
  mandatory false;
 }
 leaf CAALGOSWITCH {
  type string;
  mandatory false;
 }
 leaf CAFLEXCTRLOPTTHLDOFFSET {
  type union {
   type uint8 {
    range "0..255";
   }
  }
  mandatory false;
 }
 leaf CONN5GCNCONFIG {
  type string;
  mandatory false;
 }
 leaf DEDINETWORKFUNSWITCH {
  type string;
  mandatory false;
 }
 leaf EXTENDEDQCIMAPPINGINDEX {
  type enumeration {
   enum val-6;
   enum val-7;
   enum val-8;
   enum val-9;
  }
  mandatory false;
 }
 leaf FASTMOVUEMAXBRDCSTSITENUM {
  type union {
   type uint8 {
    range "1..255";
   }
  }
  mandatory false;
 }
 leaf FASTUEMIGRATEUENUMDIFFTHLD {
  type uint16 {
   range "0..65535";
  }
  mandatory false;
 }
 leaf GNBX2DYNBLKLISTAGINGTIMER {
  type uint16 {
   range "30..10080";
  }
  mandatory false;
 }
 leaf GNBX2INITFAILDELSWITCH {
  type boolean;
  mandatory false;
 }
 leaf GROUPPREEMPTSWITCH {
  type string;
  mandatory false;
 }
 leaf IPENTRYDETECTIONINTERVAL {
  type uint16 {
   range "5..3600";
  }
  mandatory false;
 }
 leaf IPEXITDETECTIONTIMES {
  type uint16 {
   range "1..500";
  }
  mandatory false;
 }
 leaf L4SALGOSWITCH {
  type string;
  mandatory false;
 }
 leaf L4SCONGESTCHECKPERIOD {
  type uint8 {
   range "1..20";
  }
  mandatory false;
 }
 leaf LTES1HOREQUECAPBSIZE {
  type uint16 {
   range "0..480";
  }
  mandatory false;
 }
 leaf LTETONRPLMNSELECTIONMODE {
  type enumeration {
   enum val-0;
   enum val-1;
   enum val-2;
  }
  mandatory false;
 }
 leaf MANAULCELLDEACOUNTERRSVSW {
  type boolean;
  mandatory false;
 }
 leaf MULTINETWORKINGOPTIONOPTSW {
  type string;
  mandatory false;
 }
 leaf NETWORKPRFMOPTEXTSWITCH {
  type string;
  mandatory false;
 }
 leaf NETWORKPRFMOPTSWITCH {
  type string;
  mandatory false;
 }
 leaf NRHANDOVERALGOSWITCH {
  type string;
  mandatory false;
 }
 leaf NRHOREQUECAPBSIZE {
  type uint16 {
   range "0..480";
  }
  mandatory false;
 }
 leaf NRMFBIALGOSWITCH {
  type string;
  mandatory false;
 }
 leaf NRSCGBLINDCONFIGPROTECTTMR {
  type uint16 {
   range "0..65535";
  }
  mandatory false;
 }
 leaf NRSCGINACTIVITYRELSTRATEGY {
  type enumeration {
   enum val-0;
   enum val-1;
   enum val-2;
  }
  mandatory false;
 }
 leaf NRSCGRELEASEPROTECTTMR {
  type uint16 {
   range "0..65535";
  }
  mandatory false;
 }
 leaf NSADCALGOEXTSWITCH {
  type string;
  mandatory false;
 }
 leaf NSADCALGOSWITCH {
  type string;
  mandatory false;
 }
 leaf NSAPROTOCOLCOMPATSW {
  type string;
  mandatory false;
 }
 leaf NSAS1PROCCONFLICTOPTTMR {
  type uint16 {
   range "0..65535";
  }
  mandatory false;
 }
 leaf OVERLAPUEIDENTTHLD {
  type union {
   type int8 {
    range "-10..127";
   }
  }
  mandatory false;
 }
 leaf PDCPHOTRANSMAXRATE {
  type union {
   type uint16 {
    range "1..65535";
   }
  }
  mandatory false;
 }
 leaf PROTOCOLCOMPATIBILITYEXTSW {
  type string;
  mandatory false;
 }
 leaf REINFORCEMENTLEARNINGMODE {
  type boolean;
  mandatory false;
 }
 leaf RELAYENHSWITCH {
  type string;
  mandatory false;
 }
 leaf ULABNPDCPSNPKTNUMTHLD {
  type uint32 {
   range "1..131072";
  }
  mandatory false;
 }
 leaf ULPDCPSNABNDETTHLD {
  type union {
   type uint32 {
    range "0..131072";
   }
  }
  mandatory false;
 }
 leaf ULPDCPSNOUTROWINPKTNUMTHLD {
  type uint32 {
   range "1..131072";
  }
  mandatory false;
 }
 leaf VGMDLFLOWCTRLPOLICY {
  type boolean;
  mandatory false;
 }
 leaf WAITNSADCUEPDCPSTSRPTTMR {
  type uint8 {
   range "20..200";
  }
  mandatory false;
 }
 leaf X2NSACOUNTERPERIOD {
  type enumeration {
   enum val-0;
   enum val-1;
   enum val-2;
  }
  mandatory false;
 }
 leaf X2SONDELTIMERFORLNX2FAULT {
  type uint16 {
   range "0..50400";
  }
  mandatory false;
 }
 leaf X2SONDELTIMERFORLNX2USAGE {
  type uint16 {
   range "0..50400";
  }
  mandatory false;
 }
 leaf X2SONDELETEGNBADDCNTTHLD {
  type uint16 {
   range "0..65535";
  }
  mandatory false;
 }
 }
 grouping ENODEBALGOSWITCH-attributes {
 leaf ANRSWITCH {
  type string;
  mandatory false;
 }
 leaf ANTCALIBRATIONTIMESWITCH {
  type boolean;
  mandatory false;
 }
 leaf BLINDNCELLOPTSWITCH {
  type string;
  mandatory false;
 }
 leaf CAALGOEXTSWITCH {
  type string;
  mandatory false;
 }
 leaf CAALGOSWITCH {
  type string;
  mandatory false;
 }
 leaf CALBALGOSWITCH {
  type string;
  mandatory false;
 }
 leaf CALIBRATIONALGOSWITCH {
  type string;
  mandatory false;
 }
 leaf CLKJUMPCELLRESTARTSWITCH {
  type boolean;
  mandatory false;
 }
 leaf CLOCKCHECKENHSENSITIVITY {
  type enumeration {
   enum val-0;
   enum val-1;
   enum val-2;
  }
  mandatory false;
 }
 leaf CLOCKCHECKENHSWITCH {
  type boolean;
  mandatory false;
 }
 leaf COMPATIBILITYCTRLSWITCH {
  type string;
  mandatory false;
 }
 leaf DLICICSWITCH {
  type enumeration {
   enum val-0;
   enum val-1;
   enum val-2;
  }
  mandatory false;
 }
 leaf DROPPKTSSTATSWITCH {
  type string;
  mandatory false;
 }
 leaf E2EVQIALGOSWITCH {
  type boolean;
  mandatory false;
 }
 leaf EUTRANVOIPSUPPORTSWITCH {
  type boolean;
  mandatory false;
 }
 leaf FASTENHANCEPCCANCHORSWITCH {
  type boolean;
  mandatory false;
 }
 leaf FLTRRPTRRCCONREQEXTDSWITCH {
  type boolean;
  mandatory false;
 }
 leaf GROUPSCHALGOSWITCH {
  type string;
  mandatory false;
 }
 leaf HIGHLOADNETOPTSWITCH {
  type string;
  mandatory false;
 }
 leaf HIGHSPEEDROOTSEQCSSWITCH {
  type boolean;
  mandatory false;
 }
 leaf HOALGOSWITCH {
  type string;
  mandatory false;
 }
 leaf HOCOMMOPTSWITCH {
  type string;
  mandatory false;
 }
 leaf HOMODESWITCH {
  type string;
  mandatory false;
 }
 leaf HOSIGNALINGOPTSWITCH {
  type string;
  mandatory false;
 }
 leaf HOWITHSCCCFGADDBLINDSWITCH {
  type boolean;
  mandatory false;
 }
 leaf HWCAPABILITYEXTSWITCH {
  type string;
  mandatory false;
 }
 leaf IOPTALGOSWITCH {
  type string;
  mandatory false;
 }
 leaf INTRFOPTSWITCH {
  type string;
  mandatory false;
 }
 leaf IOTCLKJUMPCELLRESETSW {
  type string;
  mandatory false;
 }
 leaf LTEPREEMPTNBSWITCH {
  type boolean;
  mandatory false;
 }
 leaf LCSSWITCH {
  type string;
  mandatory false;
 }
 leaf MACASSEMBLYOPTSWITCH {
  type boolean;
  mandatory false;
 }
 leaf MFBIAUTOCFGSWITCH {
  type string;
  mandatory false;
 }
 leaf MLBALGOSWITCH {
  type string;
  mandatory false;
 }
 leaf MULTIOPCTRLSWITCH {
  type string;
  mandatory false;
 }
 leaf NCELLRANKINGSWITCH {
  type string;
  mandatory false;
 }
 leaf OPERATORSPECIFICALGOSWITCH {
  type string;
  mandatory false;
 }
 leaf OVERBBUSSWITCH {
  type string;
  mandatory false;
 }
 leaf PCICONFLICTALMSWITCH {
  type boolean;
  mandatory false;
 }
 leaf PCICONFLICTDETECTSWITCH {
  type string;
  mandatory false;
 }
 leaf PIMSWITCH {
  type string;
  mandatory false;
 }
 leaf POWERSAVESWITCH {
  type string;
  mandatory false;
 }
 leaf PRACHTIMESTAGSWITCH {
  type boolean;
  mandatory false;
 }
 leaf RANSHARINGANRSWITCH {
  type string;
  mandatory false;
 }
 leaf REDIRECTSWITCH {
  type string;
  mandatory false;
 }
 leaf RIMONECOSWITCH {
  type boolean;
  mandatory false;
 }
 leaf RIMSWITCH {
  type string;
  mandatory false;
 }
 leaf ROOTSEQCONFLICTDETSWITCH {
  type boolean;
  mandatory false;
 }
 leaf RRULOCATIONSWITCH {
  type string;
  mandatory false;
 }
 leaf SFSSWITCH {
  type string;
  mandatory false;
 }
 leaf SSRDALGOSWITCH {
  type string;
  mandatory false;
 }
 leaf SCHOPTSWITCH {
  type string;
  mandatory false;
 }
 leaf SERVICEHOMULTITARGETFREQSW {
  type boolean;
  mandatory false;
 }
 leaf SPIDSELECTPLMNALGOSWITCH {
  type boolean;
  mandatory false;
 }
 leaf TLFREQFRAMEOFFSETSWITCH {
  type boolean;
  mandatory false;
 }
 leaf TPESWITCH {
  type string;
  mandatory false;
 }
 leaf TRMSWITCH {
  type string;
  mandatory false;
 }
 leaf UENUMPREEMPTSWITCH {
  type string;
  mandatory false;
 }
 leaf ULICICFREQSWITCH {
  type enumeration {
   enum val-0;
   enum val-1;
   enum val-2;
  }
  mandatory false;
 }
 leaf ULRESMANAGEOPTSW {
  type string;
  mandatory false;
 }
 leaf ULSCHOPTSWITCH {
  type boolean;
  mandatory false;
 }
 leaf V2XALGOSWITCH {
  type string;
  mandatory false;
 }
 leaf VQMALGOSWITCH {
  type enumeration {
   enum val-0;
   enum val-1;
   enum val-2;
  }
  mandatory false;
 }
 }
 grouping ENODEBALMCFG-attributes {
 leaf ALARMSWITCH {
  type string;
  mandatory false;
 }
 leaf CODRALGOSWITCH {
  type string;
  mandatory false;
 }
 leaf DEVABNCELLUNAVBLNOTIFYSW {
  type string;
  mandatory false;
 }
 leaf DLTXPWRFAULTDURTHLD {
  type union {
   type uint8 {
    range "1..255";
   }
  }
  mandatory false;
 }
 leaf NOTFCALMULRXFAULTDURTHLD {
  type union {
   type uint16 {
    range "15..65535";
   }
  }
  mandatory false;
 }
 leaf SERVOLALMRECOVERDETECTDUR {
  type uint16 {
   range "20..10080";
  }
  mandatory false;
 }
 leaf SERVOVERLOADALMTRIGGERTHLD {
  type uint8 {
   range "1..100";
  }
  mandatory false;
 }
 leaf SRVINTFALMCFGSW {
  type string;
  mandatory false;
 }
 leaf TRAFFICFAULTYDETECTPERIOD {
  type uint16 {
   range "0..4320";
  }
  mandatory false;
 }
 }
 grouping ENODEBAUTOPOWEROFF-attributes {
 leaf AUTOPOWEROFFSWITCH {
  type boolean;
  mandatory false;
 }
 leaf POWEROFFTIME {
  type hwat:HH_MM_SS_Time;
  mandatory false;
 }
 leaf POWERONTIME {
  type hwat:HH_MM_SS_Time;
  mandatory false;
 }
 }
 grouping ENODEBCIPHERCAP-attributes {
 leaf FOURTHCIPHERALGO {
  type enumeration {
   enum val-0;
   enum val-1;
   enum val-2;
   enum val-3;
   enum val-4;
  }
  mandatory false;
 }
 leaf PRIMARYCIPHERALGO {
  type enumeration {
   enum val-0;
   enum val-1;
   enum val-2;
   enum val-3;
   enum val-4;
  }
  mandatory false;
 }
 leaf SECONDCIPHERALGO {
  type enumeration {
   enum val-0;
   enum val-1;
   enum val-2;
   enum val-3;
   enum val-4;
  }
  mandatory false;
 }
 leaf THIRDCIPHERALGO {
  type enumeration {
   enum val-0;
   enum val-1;
   enum val-2;
   enum val-3;
   enum val-4;
  }
  mandatory false;
 }
 }
 grouping ENODEBCLUSTER-attributes {
 leaf MCC {
  type string {
   length "3";
  }
  mandatory false;
 }
 leaf MNC {
  type string {
   length "2..3";
  }
  mandatory false;
 }
 leaf ENODEBID {
  type uint32 {
   range "0..1048575";
  }
  mandatory false;
 }
 leaf OLD_ENODEBINDEX {
  type union {
   type int8 {
    range "-1..60";
   }
  }
  mandatory false;
 }
 leaf ENODEBINDEX {
  type union {
   type int8 {
    range "-1..60";
   }
  }
  mandatory false;
 }
 }
 grouping ENODEBCONNSTATETIMER-attributes {
 leaf AMRLCRXWINABNDETECTTIMETHD {
  type union {
   type uint8 {
    range "0..60";
   }
  }
  mandatory false;
 }
 leaf BEARERACTIVITYTHD {
  type union {
   type uint16 {
    range "0..65535";
   }
  }
  mandatory false;
 }
 leaf CDMA1XRTTHOCOMPLETETIMER {
  type uint16 {
   range "1..65535";
  }
  mandatory false;
 }
 leaf CDMA1XRTTHOS1WAITINGTIMER {
  type uint16 {
   range "1..65535";
  }
  mandatory false;
 }
 leaf CDMA1XRTTHOUUPREPARETIMER {
  type uint16 {
   range "1..65535";
  }
  mandatory false;
 }
 leaf CDMAHRPDHOCOMPLETETIMER {
  type uint16 {
   range "1..65535";
  }
  mandatory false;
 }
 leaf CDMAHRPDHOS1WAITINGTIMER {
  type uint16 {
   range "1..65535";
  }
  mandatory false;
 }
 leaf CDMAHRPDHOUUPREPARETIMER {
  type uint16 {
   range "1..65535";
  }
  mandatory false;
 }
 leaf ECIDWAITINGTIMER {
  type uint16 {
   range "500..60000";
  }
  mandatory false;
 }
 leaf ENDMARKERTIMER {
  type uint16 {
   range "0..1000";
  }
  mandatory false;
 }
 leaf ERABMODINDRETRANSTIMER {
  type uint8 {
   range "0..20";
  }
  mandatory false;
 }
 leaf FIRSTFORWARDPACKETTIMER {
  type uint16 {
   range "0..1000";
  }
  mandatory false;
 }
 leaf GTPUERRORRELTIMER {
  type uint8 {
   range "1..5";
  }
  mandatory false;
 }
 leaf NSADCX2MESSAGEWAITINGTIMER {
  type uint8 {
   range "1..200";
  }
  mandatory false;
 }
 leaf RRCREESTACTIVITYTHLD {
  type uint8 {
   range "0..10";
  }
  mandatory false;
 }
 leaf S1MESSAGEWAITINGTIMER {
  type uint8 {
   range "1..200";
  }
  mandatory false;
 }
 leaf S1MSGWAITINGTIMERQCI1 {
  type uint8 {
   range "1..200";
  }
  mandatory false;
 }
 leaf S1SETUPRSPWAITINGTIMER {
  type uint8 {
   range "1..60";
  }
  mandatory false;
 }
 leaf SECCMPWAITINGTIMER {
  type uint8 {
   range "1..200";
  }
  mandatory false;
 }
 leaf UPUECAPINFOWAITINGTIMER {
  type uint8 {
   range "1..200";
  }
  mandatory false;
 }
 leaf UUMESSAGEWAITINGTIMER {
  type uint8 {
   range "1..200";
  }
  mandatory false;
 }
 leaf UUMESSAGEWAITINGTIMERQCI1 {
  type uint8 {
   range "1..200";
  }
  mandatory false;
 }
 leaf WAITRRCCONNSETUPCMPTIMER {
  type uint8 {
   range "3..15";
  }
  mandatory false;
 }
 leaf X2MESSAGEWAITINGTIMER {
  type uint8 {
   range "1..200";
  }
  mandatory false;
 }
 leaf X2MESSAGEWAITINGTIMERQCI1 {
  type uint8 {
   range "1..200";
  }
  mandatory false;
 }
 }
 grouping ENODEBCOUNTERPARAGRP-attributes {
 leaf AMBRCOUNTERMEASPOLICY {
  type enumeration {
   enum val-0;
   enum val-1;
   enum val-2;
  }
  mandatory false;
 }
 leaf ENODEBCOUNTERALGOSWITCH {
  type string;
  mandatory false;
 }
 leaf PMOBJACTBASEDONCFGOBJ {
  type string;
  mandatory false;
 }
 leaf VOLTECOUNTERALGOSWITCH {
  type string;
  mandatory false;
 }
 }
 grouping ENODEBFEATUREFREQCFG-attributes {
 leaf OLD_DLEARFCN {
  type union {
   type int32 {
    range "-1..229575";
   }
  }
  mandatory false;
 }
 leaf DLEARFCN {
  type union {
   type int32 {
    range "-1..229575";
   }
  }
  mandatory false;
 }
 leaf ENODEBFEATUREFREQIND {
  type string;
  mandatory false;
 }
 }
 grouping ENODEBFLOWCTRLPARA-attributes {
 leaf ADAPTUNSYNCTIMERLEN {
  type uint8 {
   range "1..20";
  }
  mandatory false;
 }
 leaf ADAPTUNSYNCUSERNUMTHD {
  type uint8 {
   range "50..100";
  }
  mandatory false;
 }
 leaf CAFLOWCTRLTHLD {
  type uint8 {
   range "40..80";
  }
  mandatory false;
 }
 leaf CONGFLOWCTRLSWITCH {
  type string;
  mandatory false;
 }
 leaf CPULOADTHD {
  type uint8 {
   range "50..100";
  }
  mandatory false;
 }
 leaf DYNACBARPOLICYMODE {
  type boolean;
  mandatory false;
 }
 leaf DYNACBARRINGTRIGALLCELLSW {
  type boolean;
  mandatory false;
 }
 leaf INTERENBSCELLFLOWCTRLTHLD {
  type uint8 {
   range "40..75";
  }
  mandatory false;
 }
 leaf MCPTTMSGCNTSWITCH {
  type enumeration {
   enum val-0;
   enum val-1;
   enum val-2;
   enum val-3;
  }
  mandatory false;
 }
 leaf NSAFLOWCTRLSTRATEGY {
  type boolean;
  mandatory false;
 }
 }
 grouping ENODEBFUNCTION-attributes {
 leaf TEMPLATENAME {
  type string;
  mandatory false;
 }
 leaf APPLICATIONREF {
  type uint8 {
   range "1..255";
  }
  mandatory false;
 }
 leaf USERLABEL {
  type string {
   length "0..256";
  }
  mandatory false;
 }
 leaf ENODEBFUNCTIONNAME {
  type string {
   length "1..128";
  }
  mandatory false;
 }
 leaf ENODEBID {
  type uint32 {
   range "0..1048575";
  }
  mandatory false;
 }
 leaf ENODEBMODE {
  type boolean;
  mandatory false;
 }
 }
 grouping ENODEBIDBLACKLIST-attributes {
 leaf OLD_ENODEBID {
  type union {
   type int32 {
    range "-1..1048575";
   }
  }
  mandatory false;
 }
 leaf ENODEBID {
  type union {
   type int32 {
    range "-1..1048575";
   }
  }
  mandatory false;
 }
 }
 grouping ENODEBINTEGRITYCAP-attributes {
 leaf NULLALGO {
  type enumeration {
   enum val-0;
   enum val-2;
  }
  mandatory false;
 }
 leaf PRIMARYINTEGRITYALGO {
  type enumeration {
   enum val-1;
   enum val-2;
   enum val-3;
   enum val-4;
  }
  mandatory false;
 }
 leaf SECONDINTEGRITYALGO {
  type enumeration {
   enum val-1;
   enum val-2;
   enum val-3;
   enum val-4;
  }
  mandatory false;
 }
 leaf THIRDINTEGRITYALGO {
  type enumeration {
   enum val-1;
   enum val-2;
   enum val-3;
   enum val-4;
  }
  mandatory false;
 }
 }
 grouping ENODEBMLB-attributes {
 leaf CAUEMINDATAVOLRATIO {
  type uint8 {
   range "0..99";
  }
  mandatory false;
 }
 leaf DLCALBMAXCCNUM {
  type boolean;
  mandatory false;
 }
 leaf INTERFREQBEAMMLBTHLD {
  type uint8 {
   range "0..250";
  }
  mandatory false;
 }
 leaf INTERFREQIDLEMLBINTERVAL {
  type uint16 {
   range "0..10080";
  }
  mandatory false;
 }
 leaf INTERFREQIDLEMLBSTATHD {
  type uint16 {
   range "1..10000";
  }
  mandatory false;
 }
 }
 grouping ENODEBMPRUES-attributes {
 leaf DORMANCYALGOSWITCH {
  type string;
  mandatory false;
 }
 leaf MPRUDORMANCYDLEARFCN {
  type union {
   type int32 {
    range "-2..229575";
   }
  }
  mandatory false;
 }
 leaf MPRUDORMANCYDLPRBUSAGETHLD {
  type uint8 {
   range "0..15";
  }
  mandatory false;
 }
 leaf MPRUDORMANCYMINIMUMRSRP {
  type int8 {
   range "-115..-105";
  }
  mandatory false;
 }
 leaf MPRUDORMANCYSTARTTIME {
  type hwat:HH_MM_SS_Time;
  mandatory false;
 }
 leaf MPRUDORMANCYSTOPTIME {
  type hwat:HH_MM_SS_Time;
  mandatory false;
 }
 leaf NOUEDURATIONTHLD {
  type uint8 {
   range "1..12";
  }
  mandatory false;
 }
 leaf SNIFFINGTAC {
  type union {
   type uint16 {
    range "0..65535";
   }
  }
  mandatory false;
 }
 leaf UEDETPRRUDORMANCYENDTIME {
  type hwat:HH_MM_SS_Time;
  mandatory false;
 }
 leaf UEDETPRRUDORMANCYSTARTTIME {
  type hwat:HH_MM_SS_Time;
  mandatory false;
 }
 }
 grouping ENODEBMTFLOWCONTROL-attributes {
 leaf BASEBANDOMFLOWCTRLTHLDCOEF {
  type uint8 {
   range "0..100";
  }
  mandatory false;
 }
 leaf CHRFLOWCONTROLSWITCH {
  type string;
  mandatory false;
 }
 leaf HIGHPRIUEMTFLOWCTRLLEVEL {
  type uint8 {
   range "0..5";
  }
  mandatory false;
 }
 leaf SIGLOGMTFLOWCTRLLEVEL {
  type uint8 {
   range "0..5";
  }
  mandatory false;
 }
 leaf TRACETASKFLOWCONTROLOPTSWITCH {
  type string;
  mandatory false;
 }
 leaf TRCLOGMTFLOWCTRLLEVEL {
  type uint8 {
   range "0..5";
  }
  mandatory false;
 }
 }
 grouping ENODEBNBPARA-attributes {
 leaf NBEXTENDEDPAGINGOPTSWITCH {
  type boolean;
  mandatory false;
 }
 leaf NBRSVMINUSERNUMRATIO {
  type uint8 {
   range "0..100";
  }
  mandatory false;
 }
 }
 grouping ENODEBPATH-attributes {
 leaf APPTYPE {
  type boolean;
  mandatory false;
 }
 leaf IPPATHID {
  type union {
   type int32 {
    range "-1..65535";
   }
  }
  mandatory false;
 }
 leaf X2INTERFACEID {
  type uint16 {
   range "0..65535";
  }
  mandatory false;
 }
 }
 grouping ENODEBPWRSAVINGALGO-attributes {
 leaf ASUESCCADDTIMER {
  type uint8 {
   range "2..60";
  }
  mandatory false;
 }
 leaf CELLLOADFILTERMODE {
  type boolean;
  mandatory false;
 }
 leaf DLPDCPFIRSTPKTLATTARGET {
  type uint8 {
   range "2..20";
  }
  mandatory false;
 }
 leaf DLPERCEIVEDRATETARGET {
  type uint8 {
   range "0..100";
  }
  mandatory false;
 }
 leaf DORMANCYSWITCH {
  type string;
  mandatory false;
 }
 leaf EECARRSELMODE {
  type boolean;
  mandatory false;
 }
 leaf EECARRSELSTARTTIME {
  type hwat:HH_MM_SS_Time;
  mandatory false;
 }
 leaf EECARRSELSTOPTIME {
  type hwat:HH_MM_SS_Time;
  mandatory false;
 }
 leaf EEDATASPLITSTARTTIME {
  type hwat:HH_MM_SS_Time;
  mandatory false;
 }
 leaf EEDATASPLITSTOPTIME {
  type hwat:HH_MM_SS_Time;
  mandatory false;
 }
 leaf PWRSAVINGALGOSWITCH {
  type string;
  mandatory false;
 }
 }
 grouping ENODEBRESMODEALGO-attributes {
 leaf BACKPLANEBWLACKPROTECTSW {
  type boolean;
  mandatory false;
 }
 leaf BBPCPRISHARINGSWITCH {
  type boolean;
  mandatory false;
 }
 leaf BBPRESAUTOCONFIGSW {
  type enumeration {
   enum val-0;
   enum val-1;
   enum val-2;
  }
  mandatory false;
 }
 leaf BBPRESAUTORECFGTIMER {
  type uint16 {
   range "0..65535";
  }
  mandatory false;
 }
 leaf DATAPLANERTCMODESW {
  type boolean;
  mandatory false;
 }
 leaf ENBCELLDSTDEPLOYSW {
  type boolean;
  mandatory false;
 }
 leaf FDDBBPRESDEPLOYALGO {
  type enumeration {
   enum val-0;
   enum val-1;
   enum val-2;
   enum val-3;
  }
  mandatory false;
 }
 leaf NBCARRIERINTERBBPDEPLOYSW {
  type boolean;
  mandatory false;
 }
 leaf PARAMCFGPROTECTSW {
  type string;
  mandatory false;
 }
 leaf SERVICEMODE {
  type string;
  mandatory false;
 }
 leaf TDDBBPRESDEPLOYALGO {
  type enumeration {
   enum val-0;
   enum val-1;
   enum val-2;
  }
  mandatory false;
 }
 leaf ENBCELLNUMCAPABILITYMODE {
  type boolean;
  mandatory false;
 }
 leaf ENODEBDATAFORWARDPOLICYSW {
  type boolean;
  mandatory false;
 }
 }
 grouping ENODEBRLALGOCONFIG-attributes {
 leaf RLCASETYPE {
  type enumeration {
   enum val--1;
   enum val-0;
   enum val-1;
   enum val-2;
   enum val-3;
   enum val-4;
   enum val-5;
   enum val-6;
  }
  mandatory false;
 }
 leaf RLMAXDURATION {
  type uint16 {
   range "1..65535";
  }
  mandatory false;
 }
 }
 grouping ENODEBSHARINGMODE-attributes {
 leaf ENODEBSHARINGMODE {
  type enumeration {
   enum val-0;
   enum val-1;
   enum val-2;
   enum val-3;
   enum val-4;
  }
  mandatory false;
 }
 }
 grouping ENODEBSIGSECCONFIG-attributes {
 leaf EMTCSIGCTRLTHLD {
  type uint16 {
   range "100..65535";
  }
  mandatory false;
 }
 leaf ENODEBSIGSECPOLICYSWITCH {
  type string;
  mandatory false;
 }
 leaf LTESIGCTRLTHLD {
  type uint16 {
   range "100..65535";
  }
  mandatory false;
 }
 leaf MAXNUMLOGGEDMDTMEASREPORT {
  type uint8 {
   range "1..255";
  }
  mandatory false;
 }
 leaf NBSIGCTRLTHLD {
  type uint16 {
   range "100..65535";
  }
  mandatory false;
 }
 leaf UECAPBMAXSEGMENTNUM {
  type uint8 {
   range "6..16";
  }
  mandatory false;
 }
 }
 grouping ENODEBSONDBCFG-attributes {
 leaf STARTTIME {
  type hwat:HH_MM_SS_Time;
  mandatory false;
 }
 }
 grouping ENODEBUSPARACFG-attributes {
 leaf BIGPACKAGEIDENTIFY {
  type boolean;
  mandatory false;
 }
 leaf IPDETECTINTERVAL {
  type uint16 {
   range "0..3600";
  }
  mandatory false;
 }
 leaf IPBASEDUSIDENTSTARTTIME {
  type inet:ip-address;
  mandatory false;
 }
 leaf IPBASEDUSIDENTVALIDPERIOD {
  type uint8 {
   range "0..60";
  }
  mandatory false;
 }
 leaf NBUSUESCHPRIWEIGHTFACTOR {
  type uint8 {
   range "0..31";
  }
  mandatory false;
 }
 leaf NSADCUSUECARRSELALGOSW {
  type string;
  mandatory false;
 }
 leaf NSADCUSUESPLITSTRATEGY {
  type enumeration {
   enum val-0;
   enum val-1;
   enum val-2;
   enum val-3;
  }
  mandatory false;
 }
 leaf ULDLUSUSERDETECTPERIOD {
  type uint8 {
   range "0..5";
  }
  mandatory false;
 }
 leaf USLPKTULSCHPRIFACTOR {
  type uint16 {
   range "1..1000";
  }
  mandatory false;
 }
 leaf USNBUESTATUSRESPONSETIMER {
  type uint16 {
   range "0..60000";
  }
  mandatory false;
 }
 leaf USSPKTULSCHPRIFACTOR {
  type uint16 {
   range "1..1000";
  }
  mandatory false;
 }
 leaf USSTRATEGY {
  type string;
  mandatory false;
 }
 leaf USUESTMSIKEEPALIVETIMER {
  type uint8 {
   range "0..120";
  }
  mandatory false;
 }
 leaf USUEDLPRIORITYFACTOR {
  type uint16 {
   range "1..1000";
  }
  mandatory false;
 }
 leaf USUEEXITDETECTIONTIMES {
  type uint16 {
   range "1..600";
  }
  mandatory false;
 }
 leaf USUEINACTIVETIMER {
  type uint16 {
   range "0..3600";
  }
  mandatory false;
 }
 }
 grouping EUCELLALMCFG-attributes {
 leaf LOCALCELLNAME {
  type string;
  mandatory false;
 }
 leaf LOCALCELLID {
  type union {
   type int16 {
    range "-1..255";
   }
  }
  mandatory false;
 }
 leaf RXCHANNELNOISEDETECTMODE {
  type enumeration {
   enum val-0;
   enum val-1;
   enum val-2;
  }
  mandatory false;
 }
 leaf RXNOISEPWRTHD {
  type uint16 {
   range "0..320";
  }
  mandatory false;
 }
 }
 grouping EUCELLSECTOREQM-attributes {
 leaf LOCALCELLNAME {
  type string;
  mandatory false;
 }
 leaf AGGREGATIONATTRIBUTE {
  type string;
  mandatory false;
 }
 leaf ANTENNAPORTMAPPING {
  type string {
   length "0..8";
  }
  mandatory false;
 }
 leaf AUTOCFGFLAG {
  type boolean;
  mandatory false;
 }
 leaf BASEBANDEQMID {
  type union {
   type uint8 {
    range "0..255";
   }
  }
  mandatory false;
 }
 leaf CELLBEAMAZIMUTHOFFSET {
  type int8 {
   range "-30..30";
  }
  mandatory false;
 }
 leaf CELLBEAMMODE {
  type enumeration {
   enum val-0;
   enum val-1;
   enum val-2;
   enum val-3;
  }
  mandatory false;
 }
 leaf LOCALCELLID {
  type union {
   type int16 {
    range "-1..255";
   }
  }
  mandatory false;
 }
 leaf POLESITEAZIMUTHOFFSET {
  type int16 {
   range "-150..150";
  }
  mandatory false;
 }
 leaf REFERENCESIGNALPWR {
  type union {
   type int16 {
    range "-600..32767";
   }
  }
  mandatory false;
 }
 leaf REFERENCESIGNALPWRMARGIN {
  type uint8 {
   range "0..60";
  }
  mandatory false;
 }
 leaf SECTORCPRICOMPRESSION {
  type enumeration {
   enum val-0;
   enum val-1;
   enum val-2;
   enum val-4;
   enum val-5;
   enum val-255;
  }
  mandatory false;
 }
 leaf SECTOREQMCOMBINEGRPID {
  type union {
   type uint8 {
    range "0..255";
   }
  }
  mandatory false;
 }
 leaf SECTOREQMID {
  type union {
   type int32 {
    range "-1..65535";
   }
  }
  mandatory false;
 }
 leaf TILT {
  type int16 {
   range "-150..150";
  }
  mandatory false;
 }
 leaf TXPOWEROFFSETANT0 {
  type int8 {
   range "-100..100";
  }
  mandatory false;
 }
 leaf TXPOWEROFFSETANT1 {
  type int8 {
   range "-100..100";
  }
  mandatory false;
 }
 leaf TXPOWEROFFSETANT2 {
  type int8 {
   range "-100..100";
  }
  mandatory false;
 }
 leaf TXPOWEROFFSETANT3 {
  type int8 {
   range "-100..100";
  }
  mandatory false;
 }
 leaf TXRXMODE {
  type enumeration {
   enum val-2;
   enum val-255;
  }
  mandatory false;
 }
 leaf VISUALCELLID {
  type uint16 {
   range "0..503";
  }
  mandatory false;
 }
 leaf WEIGHTNO {
  type uint8 {
   range "0..255";
  }
  mandatory false;
 }
 }
 grouping EUCOSCHDLCOMPCFG-attributes {
 leaf CORDINFOEFFDELAY {
  type uint8 {
   range "3..20";
  }
  mandatory false;
 }
 leaf EUCOSCHUESPEC {
  type uint8 {
   range "1..25";
  }
  mandatory false;
 }
 leaf INTERENBDLCOMPSWITCH {
  type boolean;
  mandatory false;
 }
 }
 grouping EUCOSCHULICSCFG-attributes {
 leaf ULICSALGOSWITCH {
  type boolean;
  mandatory false;
 }
 }
 grouping EUEPCINFO-attributes {
 leaf FULLNAMEFORNETWORK {
  type string {
   length "0..64";
  }
  mandatory false;
 }
 leaf OLD_LOCALEPCID {
  type union {
   type int16 {
    range "-1..255";
   }
  }
  mandatory false;
 }
 leaf LOCALEPCID {
  type union {
   type int16 {
    range "-1..255";
   }
  }
  mandatory false;
 }
 leaf MMECODE {
  type uint8 {
   range "0..255";
  }
  mandatory false;
 }
 leaf MMEGROUPID {
  type uint16 {
   range "32768..65535";
  }
  mandatory false;
 }
 leaf SHORTNAMEFORNETWORK {
  type string {
   length "0..64";
  }
  mandatory false;
 }
 }
 grouping EUPRBSECTOREQM-attributes {
 leaf LOCALCELLNAME {
  type string;
  mandatory false;
 }
 leaf AUTOCONFIGFLAG {
  type boolean;
  mandatory false;
 }
 leaf BASEBANDEQMID {
  type union {
   type uint8 {
    range "0..255";
   }
  }
  mandatory false;
 }
 leaf LOCALCELLID {
  type union {
   type int16 {
    range "-1..255";
   }
  }
  mandatory false;
 }
 leaf NPRSID {
  type union {
   type uint16 {
    range "0..65535";
   }
  }
  mandatory false;
 }
 leaf PRBID {
  type union {
   type int16 {
    range "-1..255";
   }
  }
  mandatory false;
 }
 leaf REFERENCESIGNALPWR {
  type union {
   type int16 {
    range "-600..32767";
   }
  }
  mandatory false;
 }
 leaf SECTOREQMID {
  type union {
   type int32 {
    range "-1..65535";
   }
  }
  mandatory false;
 }
 }
 grouping EUPRBSECTOREQMGROUP-attributes {
 leaf LOCALCELLNAME {
  type string;
  mandatory false;
 }
 leaf AUTOCONFIGFLAG {
  type boolean;
  mandatory false;
 }
 leaf BASEBANDEQMID {
  type union {
   type uint8 {
    range "0..255";
   }
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf OLD_PRBID {
  type union {
   type int16 {
    range "-1..255";
   }
  }
  mandatory false;
 }
 leaf PRBID {
  type union {
   type int16 {
    range "-1..255";
   }
  }
  mandatory false;
 }
 leaf REFERENCESIGNALPWR {
  type union {
   type int16 {
    range "-600..32767";
   }
  }
  mandatory false;
 }
 leaf OLD_SECTOREQMGROUPID {
  type union {
   type int8 {
    range "-1..35";
   }
  }
  mandatory false;
 }
 leaf SECTOREQMGROUPID {
  type union {
   type int8 {
    range "-1..35";
   }
  }
  mandatory false;
 }
 }
 grouping EURRN-attributes {
 leaf DHCPSERVERIP {
  type inet:ipv4-address;
  mandatory false;
 }
 leaf ENHANCEDFUNCTIONSWITCH {
  type string;
  mandatory false;
 }
 leaf EXTENDEDDHCPSERVERIP {
  type inet:ipv4-address;
  mandatory false;
 }
 leaf LOCALSUBSCRIBERID {
  type union {
   type int32 {
    range "-1..65535";
   }
  }
  mandatory false;
 }
 leaf LOCALWAPCHANNELNUMBER {
  type enumeration {
   enum val-1;
   enum val-2;
   enum val-3;
   enum val-4;
   enum val-5;
   enum val-6;
   enum val-7;
   enum val-8;
   enum val-9;
   enum val-10;
   enum val-11;
   enum val-12;
   enum val-13;
   enum val-14;
   enum val-255;
  }
  mandatory false;
 }
 leaf LOCALWAPPOLICY {
  type enumeration {
   enum val-0;
   enum val-1;
   enum val-2;
  }
  mandatory false;
 }
 leaf LOCALWAPREGIONCODE {
  type enumeration {
   enum val-0;
   enum val-1;
   enum val-2;
   enum val-3;
   enum val-255;
  }
  mandatory false;
 }
 leaf OMINTFID {
  type uint8 {
   range "1..32";
  }
  mandatory false;
 }
 leaf OMIP {
  type inet:ipv4-address;
  mandatory false;
 }
 leaf OMIPMASK {
  type inet:ipv4-address;
  mandatory false;
 }
 leaf RELAYTYPE {
  type boolean;
  mandatory false;
 }
 leaf RRNMACAT {
  type uint16 {
   range "0..3825";
  }
  mandatory false;
 }
 leaf RRNTYPE {
  type enumeration {
   enum val-0;
   enum val-1;
   enum val-2;
   enum val-3;
   enum val-4;
  }
  mandatory false;
 }
 leaf RRNVLANID {
  type uint16 {
   range "1..4094";
  }
  mandatory false;
 }
 leaf RRNVLANPRI {
  type uint8 {
   range "0..7";
  }
  mandatory false;
 }
 leaf RRNVLANTAGSWITCH {
  type boolean;
  mandatory false;
 }
 leaf SEVICEINTFID {
  type uint8 {
   range "1..32";
  }
  mandatory false;
 }
 leaf SYNCETHCLOCKSWITCH {
  type boolean;
  mandatory false;
 }
 }
 grouping EURRNLANIP-attributes {
 leaf OLD_LANIP {
  type inet:ipv4-address;
  mandatory false;
 }
 leaf LANIP {
  type inet:ipv4-address;
  mandatory false;
 }
 leaf LANMASK {
  type inet:ipv4-address;
  mandatory false;
 }
 leaf OLD_LOCALSUBSCRIBERID {
  type union {
   type int32 {
    range "-1..65535";
   }
  }
  mandatory false;
 }
 leaf LOCALSUBSCRIBERID {
  type union {
   type int32 {
    range "-1..65535";
   }
  }
  mandatory false;
 }
 }
 grouping EURRNPORT-attributes {
 leaf LOCALSUBSCRIBERID {
  type union {
   type int32 {
    range "-1..65535";
   }
  }
  mandatory false;
 }
 leaf PN {
  type union {
   type int8 {
    range "-1..1";
   }
  }
  mandatory false;
 }
 leaf PORTSWITCH {
  type boolean;
  mandatory false;
 }
 }
 grouping EURRNRT-attributes {
 leaf DSTIP {
  type inet:ipv4-address;
  mandatory false;
 }
 leaf DSTMASK {
  type inet:ipv4-address;
  mandatory false;
 }
 leaf LOCALSUBSCRIBERID {
  type uint16 {
   range "0..65535";
  }
  mandatory false;
 }
 leaf NEXTHOP {
  type inet:ipv4-address;
  mandatory false;
 }
 leaf OLD_RTID {
  type union {
   type int32 {
    range "-1..65535";
   }
  }
  mandatory false;
 }
 leaf RTID {
  type union {
   type int32 {
    range "-1..65535";
   }
  }
  mandatory false;
 }
 }
 grouping EUSECTOREQMGROUP-attributes {
 leaf LOCALCELLNAME {
  type string;
  mandatory false;
 }
 leaf AUTOCFGFLAG {
  type boolean;
  mandatory false;
 }
 leaf BASEBANDEQMID {
  type union {
   type uint8 {
    range "0..255";
   }
  }
  mandatory false;
 }
 leaf LOCALCELLID {
  type union {
   type int16 {
    range "-1..255";
   }
  }
  mandatory false;
 }
 leaf REFERENCESIGNALPWR {
  type union {
   type int16 {
    range "-600..32767";
   }
  }
  mandatory false;
 }
 leaf SECTOREQMGROUPID {
  type union {
   type int8 {
    range "-1..35";
   }
  }
  mandatory false;
 }
 leaf SECTOREQMGRPCOMBINEID {
  type union {
   type uint8 {
    range "0..255";
   }
  }
  mandatory false;
 }
 leaf SECTORGROUPCPRICOMPRESSION {
  type enumeration {
   enum val-0;
   enum val-1;
   enum val-2;
   enum val-3;
   enum val-255;
  }
  mandatory false;
 }
 leaf SECTORGROUPLINKCOMPRESSION {
  type enumeration {
   enum val-0;
   enum val-1;
   enum val-255;
  }
  mandatory false;
 }
 leaf VISUALCELLID {
  type uint16 {
   range "0..503";
  }
  mandatory false;
 }
 }
 grouping EUSUBSCRIBER-attributes {
 leaf CELLID {
  type uint8 {
   range "0..255";
  }
  mandatory false;
 }
 leaf DLAMBR {
  type uint32 {
   range "1..4294967295";
  }
  mandatory false;
 }
 leaf KI {
  type string {
   length "32";
  }
  mandatory false;
 }
 leaf OLD_LOCALSUBSCRIBERID {
  type union {
   type int32 {
    range "-1..65535";
   }
  }
  mandatory false;
 }
 leaf LOCALSUBSCRIBERID {
  type union {
   type int32 {
    range "-1..65535";
   }
  }
  mandatory false;
 }
 leaf OP {
  type string {
   length "32";
  }
  mandatory false;
 }
 leaf RRNID {
  type string {
   length "15";
  }
  mandatory false;
 }
 leaf SUBSCRIBERDESC {
  type string {
   length "0..79";
  }
  mandatory false;
 }
 leaf ULAMBR {
  type uint32 {
   range "1..4294967295";
  }
  mandatory false;
 }
 }
 grouping EUTRANBLKNCELL-attributes {
 leaf LOCALCELLNAME {
  type string;
  mandatory false;
 }
 leaf AUTOCFGFLAG {
  type boolean;
  mandatory false;
 }
 leaf CELLID {
  type union {
   type int16 {
    range "-1..255";
   }
  }
  mandatory false;
 }
 leaf CTRLMODE {
  type boolean;
  mandatory false;
 }
 leaf LOCALCELLID {
  type union {
   type int16 {
    range "-1..255";
   }
  }
  mandatory false;
 }
 leaf MCC {
  type string {
   length "3";
  }
  mandatory false;
 }
 leaf MNC {
  type string {
   length "2..3";
  }
  mandatory false;
 }
 leaf ENODEBID {
  type union {
   type int32 {
    range "-1..1048575";
   }
  }
  mandatory false;
 }
 }
 grouping EUTRANEXTERNALCELL-attributes {
 leaf AGGREGATIONATTRIBUTE {
  type string;
  mandatory false;
 }
 leaf ANRFLAG {
  type boolean;
  mandatory false;
 }
 leaf CELLID {
  type union {
   type int16 {
    range "-1..255";
   }
  }
  mandatory false;
 }
 leaf CELLNAME {
  type string {
   length "0..99";
  }
  mandatory false;
 }
 leaf CTRLMODE {
  type boolean;
  mandatory false;
 }
 leaf DLEARFCN {
  type union {
   type uint32 {
    range "0..229575";
   }
  }
  mandatory false;
 }
 leaf DLFREQOFFSET {
  type enumeration {
   enum val-8;
   enum val-9;
   enum val-10;
   enum val-11;
   enum val-12;
  }
  mandatory false;
 }
 leaf MCC {
  type string {
   length "3";
  }
  mandatory false;
 }
 leaf MNC {
  type string {
   length "2..3";
  }
  mandatory false;
 }
 leaf NBCELLFLAG {
  type boolean;
  mandatory false;
 }
 leaf NCLUPDATEMODE {
  type string;
  mandatory false;
 }
 leaf PHYCELLID {
  type uint16 {
   range "0..503";
  }
  mandatory false;
 }
 leaf ROAMINGAREAHOIND {
  type boolean;
  mandatory false;
 }
 leaf SPECIFIEDCELLFLAG {
  type enumeration {
   enum val-0;
   enum val-1;
   enum val-2;
  }
  mandatory false;
 }
 leaf SUPPORTEMTCFLAG {
  type enumeration {
   enum val-0;
   enum val-1;
   enum val-2;
  }
  mandatory false;
 }
 leaf TAC {
  type uint16 {
   range "0..65535";
  }
  mandatory false;
 }
 leaf ULEARFCN {
  type union {
   type uint32 {
    range "18000..229575";
   }
  }
  mandatory false;
 }
 leaf ULEARFCNCFGIND {
  type boolean;
  mandatory false;
 }
 leaf ULFREQOFFSET {
  type enumeration {
   enum val-0;
   enum val-1;
   enum val-2;
   enum val-3;
   enum val-4;
   enum val-5;
   enum val-6;
   enum val-7;
   enum val-8;
   enum val-9;
   enum val-11;
   enum val-12;
   enum val-13;
   enum val-14;
   enum val-15;
   enum val-16;
   enum val-17;
   enum val-18;
   enum val-19;
   enum val-20;
  }
  mandatory false;
 }
 leaf ENODEBID {
  type union {
   type int32 {
    range "-1..1048575";
   }
  }
  mandatory false;
 }
 }
 grouping EUTRANEXTERNALCELLPLMN-attributes {
 leaf CELLNAME {
  type string;
  mandatory false;
 }
 leaf AGGREGATIONATTRIBUTE {
  type string;
  mandatory false;
 }
 leaf CELLID {
  type union {
   type int16 {
    range "-1..255";
   }
  }
  mandatory false;
 }
 leaf MCC {
  type string {
   length "3";
  }
  mandatory false;
 }
 leaf MNC {
  type string {
   length "2..3";
  }
  mandatory false;
 }
 leaf SHAREMCC {
  type string {
   length "3";
  }
  mandatory false;
 }
 leaf SHAREMNC {
  type string {
   length "2..3";
  }
  mandatory false;
 }
 leaf ENODEBID {
  type union {
   type int32 {
    range "-1..1048575";
   }
  }
  mandatory false;
 }
 }
 grouping EUTRANEXTERNALCELL_MULTIBAND-attributes {
 leaf CELLNAME {
  type string;
  mandatory false;
 }
 leaf CELLID {
  type union {
   type int16 {
    range "-1..255";
   }
  }
  mandatory false;
 }
 leaf FREQBAND {
  type union {
   type int16 {
    range "-1..256";
   }
  }
  mandatory false;
 }
 leaf MCC {
  type string {
   length "3";
  }
  mandatory false;
 }
 leaf MNC {
  type string {
   length "2..3";
  }
  mandatory false;
 }
 leaf ENODEBID {
  type union {
   type int32 {
    range "-1..1048575";
   }
  }
  mandatory false;
 }
 }
 grouping EUTRANINTERFREQNCELL-attributes {
 leaf AGGREGATIONPROPERTY {
  type string;
  mandatory false;
 }
 leaf ANRFLAG {
  type boolean;
  mandatory false;
 }
 leaf BLINDHOPRIORITY {
  type uint8 {
   range "0..32";
  }
  mandatory false;
 }
 leaf CELLID {
  type union {
   type int16 {
    range "-1..255";
   }
  }
  mandatory false;
 }
 leaf CELLINDIVIDUALOFFSET {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf CELLMEASPRIORITY {
  type boolean;
  mandatory false;
 }
 leaf CELLQOFFSET {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf CTRLMODE {
  type boolean;
  mandatory false;
 }
 leaf HIGHSPEEDINTERFAVOIDFLAG {
  type boolean;
  mandatory false;
 }
 leaf LOCALCELLID {
  type union {
   type int16 {
    range "-1..255";
   }
  }
  mandatory false;
 }
 leaf LOCALCELLNAME {
  type string {
   length "0..99";
  }
  mandatory false;
 }
 leaf MCC {
  type string {
   length "3";
  }
  mandatory false;
 }
 leaf MNC {
  type string {
   length "2..3";
  }
  mandatory false;
 }
 leaf NCELLCLASSLABEL {
  type boolean;
  mandatory false;
 }
 leaf NEIGHBOURCELLNAME {
  type string {
   length "0..99";
  }
  mandatory false;
 }
 leaf NOHOFLAG {
  type boolean;
  mandatory false;
 }
 leaf NORMVFLAG {
  type boolean;
  mandatory false;
 }
 leaf NSADCCELLINDIVIDUALOFFSET {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf OVERLAPIND {
  type boolean;
  mandatory false;
 }
 leaf OVERLAPINDICATOREXTENSION {
  type string;
  mandatory false;
 }
 leaf OVERLAPRANGE {
  type enumeration {
   enum val-0;
   enum val-1;
   enum val-2;
   enum val-3;
  }
  mandatory false;
 }
 leaf OVERLAPRATE {
  type uint8 {
   range "0..100";
  }
  mandatory false;
 }
 leaf ENODEBID {
  type union {
   type int32 {
    range "-1..1048575";
   }
  }
  mandatory false;
 }
 }
 grouping EUTRANINTERNFREQ-attributes {
 leaf LOCALCELLNAME {
  type string;
  mandatory false;
 }
 leaf A3INTERFHOSERVINGRSRPOFS {
  type int8 {
   range "-25..25";
  }
  mandatory false;
 }
 leaf AGGREGATIONATTRIBUTE {
  type string;
  mandatory false;
 }
 leaf ANRIND {
  type boolean;
  mandatory false;
 }
 leaf BACKOFFTARGETIND {
  type boolean;
  mandatory false;
 }
 leaf CELLRESELPRIORITY {
  type uint8 {
   range "0..7";
  }
  mandatory false;
 }
 leaf CELLRESELPRIORITYCFGIND {
  type boolean;
  mandatory false;
 }
 leaf CONNFREQPRIORITY {
  type uint8 {
   range "0..16";
  }
  mandatory false;
 }
 leaf COVIFHOA5VOLTETHLD1RSRPOFS {
  type int8 {
   range "-20..20";
  }
  mandatory false;
 }
 leaf COVIFHOA5VOLTETHLD2RSRPOFS {
  type int8 {
   range "-20..20";
  }
  mandatory false;
 }
 leaf DLEARFCN {
  type union {
   type int32 {
    range "-1..229575";
   }
  }
  mandatory false;
 }
 leaf DLFREQOFFSET {
  type enumeration {
   enum val-8;
   enum val-9;
   enum val-10;
   enum val-11;
   enum val-12;
  }
  mandatory false;
 }
 leaf EMTCINTERFREQCELLRESELPRI {
  type union {
   type uint8 {
    range "0..255";
   }
  }
  mandatory false;
 }
 leaf EUTRANRESELTIME {
  type uint8 {
   range "0..7";
  }
  mandatory false;
 }
 leaf FREQPRIBASEDHOMEASFLAG {
  type boolean;
  mandatory false;
 }
 leaf FREQPRIHOA4THLDRSRPOFFSET {
  type int8 {
   range "-30..30";
  }
  mandatory false;
 }
 leaf IDLEMLBUERELEASERATIO {
  type uint8 {
   range "0..100";
  }
  mandatory false;
 }
 leaf IDLEMLBEMTCUERELEASERATIO {
  type uint8 {
   range "0..100";
  }
  mandatory false;
 }
 leaf IFBACKOFFTHDRSRPOFFSET {
  type int8 {
   range "-20..20";
  }
  mandatory false;
 }
 leaf IFBACKOFFTHDRSRQOFFSET {
  type int8 {
   range "-20..20";
  }
  mandatory false;
 }
 leaf IFHOTHDRSRPOFFSET {
  type int8 {
   range "-100..100";
  }
  mandatory false;
 }
 leaf IFMLBTHDRSRPOFFSET {
  type int8 {
   range "-20..20";
  }
  mandatory false;
 }
 leaf IFSRVHOTHDRSRPOFFSET {
  type int8 {
   range "-20..20";
  }
  mandatory false;
 }
 leaf IFSRVHOTHDRSRQOFFSET {
  type int8 {
   range "-20..20";
  }
  mandatory false;
 }
 leaf INTERFREQ4TIND {
  type boolean;
  mandatory false;
 }
 leaf INTERFREQCIOADJLIMITCFGIND {
  type enumeration {
   enum val-0;
   enum val-1;
   enum val-2;
  }
  mandatory false;
 }
 leaf INTERFREQCIOADJLOWERLIMIT {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf INTERFREQCIOADJUPPERLIMIT {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf INTERFREQHIGHSPEEDFLAG {
  type enumeration {
   enum val-0;
   enum val-1;
   enum val-2;
   enum val-3;
  }
  mandatory false;
 }
 leaf INTERFREQHOA5THD1RSRPOFS {
  type int8 {
   range "-20..20";
  }
  mandatory false;
 }
 leaf INTERFREQHOA5THD1RSRQOFS {
  type int8 {
   range "-20..20";
  }
  mandatory false;
 }
 leaf INTERFREQHOEVENTTYPE {
  type enumeration {
   enum val-0;
   enum val-1;
   enum val-2;
  }
  mandatory false;
 }
 leaf INTERFREQMLBDLPRBOFFSET {
  type uint8 {
   range "0..100";
  }
  mandatory false;
 }
 leaf INTERFREQMLBULPRBOFFSET {
  type uint8 {
   range "0..100";
  }
  mandatory false;
 }
 leaf INTERFREQPRDCMRFREQGRPID {
  type uint8 {
   range "0..7";
  }
  mandatory false;
 }
 leaf INTERFREQRANSHARINGIND {
  type boolean;
  mandatory false;
 }
 leaf INTERFREQREDIRECTIONSWITCH {
  type boolean;
  mandatory false;
 }
 leaf LOCALCELLID {
  type union {
   type int16 {
    range "-1..255";
   }
  }
  mandatory false;
 }
 leaf MASTERBANDFLAG {
  type boolean;
  mandatory false;
 }
 leaf MEASBANDWIDTH {
  type enumeration {
   enum val-0;
   enum val-1;
   enum val-2;
   enum val-3;
   enum val-4;
   enum val-5;
  }
  mandatory false;
 }
 leaf MEASFREQPRIORITY {
  type uint8 {
   range "0..16";
  }
  mandatory false;
 }
 leaf MEASPERFORMANCEDEMAND {
  type enumeration {
   enum val-0;
   enum val-1;
   enum val-2;
  }
  mandatory false;
 }
 leaf MEASPRIORITYFORFREQPRIHO {
  type uint8 {
   range "0..16";
  }
  mandatory false;
 }
 leaf MLBFREQPRIORITY {
  type uint8 {
   range "0..15";
  }
  mandatory false;
 }
 leaf MLBFREQULPRIORITY {
  type uint8 {
   range "0..15";
  }
  mandatory false;
 }
 leaf MLBINTERFREQEFFIRATIO {
  type uint16 {
   range "1..10000";
  }
  mandatory false;
 }
 leaf MLBINTERFREQHOA3OFFSET {
  type int8 {
   range "-30..30";
  }
  mandatory false;
 }
 leaf MLBINTERFREQHOEVENTTYPE {
  type enumeration {
   enum val-0;
   enum val-1;
   enum val-2;
  }
  mandatory false;
 }
 leaf MLBTARGETIND {
  type enumeration {
   enum val-0;
   enum val-1;
   enum val-2;
   enum val-3;
  }
  mandatory false;
 }
 leaf MOBILITYTARGETIND {
  type string;
  mandatory false;
 }
 leaf NCELLNUMFORANR {
  type uint16 {
   range "0..256";
  }
  mandatory false;
 }
 leaf NEIGHCELLCONFIG {
  type enumeration {
   enum val-0;
   enum val-1;
   enum val-2;
   enum val-3;
  }
  mandatory false;
 }
 leaf NSACOVIFHOSERVCELLRSRPOFS {
  type int8 {
   range "-25..25";
  }
  mandatory false;
 }
 leaf PMAX {
  type int8 {
   range "-30..33";
  }
  mandatory false;
 }
 leaf PMAXCFGIND {
  type boolean;
  mandatory false;
 }
 leaf PRESENCEANTENNAPORT1 {
  type boolean;
  mandatory false;
 }
 leaf PSPRIORITY {
  type uint8 {
   range "0..16";
  }
  mandatory false;
 }
 leaf PWROFFSETFORRESELTOINTERNB {
  type enumeration {
   enum val-0;
   enum val-1;
   enum val-2;
   enum val-3;
   enum val-4;
   enum val-5;
   enum val-255;
  }
  mandatory false;
 }
 leaf PWROFSFORNBINTERFREQREDIR {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-255;
  }
  mandatory false;
 }
 leaf QQUALMINFORCEMODEA {
  type union {
   type int8 {
    range "-34..0";
   }
  }
  mandatory false;
 }
 leaf QQUALMINFORCEMODEB {
  type union {
   type int8 {
    range "-34..0";
   }
  }
  mandatory false;
 }
 leaf QRXLEVMIN {
  type int8 {
   range "-78..-22";
  }
  mandatory false;
 }
 leaf QRXLEVMINFORCEMODEA {
  type int8 {
   range "-70..-22";
  }
  mandatory false;
 }
 leaf QRXLEVMINFORCEMODEB {
  type int8 {
   range "-78..-22";
  }
  mandatory false;
 }
 leaf QOFFSETFREQ {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf QOFFSETFREQCONN {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf QQUALMIN {
  type int8 {
   range "-34..-3";
  }
  mandatory false;
 }
 leaf QQUALMINCFGIND {
  type boolean;
  mandatory false;
 }
 leaf SNRBASEDUESELECTIONMODE {
  type enumeration {
   enum val-0;
   enum val-1;
   enum val-2;
  }
  mandatory false;
 }
 leaf SPEEDDEPENDSPCFGIND {
  type boolean;
  mandatory false;
 }
 leaf TRESELEUTRANSFHIGH {
  type enumeration {
   enum val-0;
   enum val-1;
   enum val-2;
   enum val-3;
  }
  mandatory false;
 }
 leaf TRESELEUTRANSFMEDIUM {
  type enumeration {
   enum val-0;
   enum val-1;
   enum val-2;
   enum val-3;
  }
  mandatory false;
 }
 leaf THRESHXHIGH {
  type uint8 {
   range "0..31";
  }
  mandatory false;
 }
 leaf THRESHXHIGHQ {
  type uint8 {
   range "0..31";
  }
  mandatory false;
 }
 leaf THRESHXLOW {
  type uint8 {
   range "0..31";
  }
  mandatory false;
 }
 leaf THRESHXLOWQ {
  type uint8 {
   range "0..31";
  }
  mandatory false;
 }
 leaf ULEARFCN {
  type union {
   type uint32 {
    range "18000..229575";
   }
  }
  mandatory false;
 }
 leaf ULEARFCNCFGIND {
  type boolean;
  mandatory false;
 }
 leaf ULFREQOFFSET {
  type enumeration {
   enum val-0;
   enum val-1;
   enum val-2;
   enum val-3;
   enum val-4;
   enum val-5;
   enum val-6;
   enum val-7;
   enum val-8;
   enum val-9;
   enum val-11;
   enum val-12;
   enum val-13;
   enum val-14;
   enum val-15;
   enum val-16;
   enum val-17;
   enum val-18;
   enum val-19;
   enum val-20;
  }
  mandatory false;
 }
 leaf ULTRAFFICMLBPRIORITY {
  type uint8 {
   range "0..15";
  }
  mandatory false;
 }
 leaf ULTRAFFICMLBTARGETIND {
  type boolean;
  mandatory false;
 }
 leaf VOLTEQUALITYIFHOTARGETIND {
  type boolean;
  mandatory false;
 }
 leaf VOIPPRIORITY {
  type uint8 {
   range "0..16";
  }
  mandatory false;
 }
 leaf VOLTEHOTARGETIND {
  type boolean;
  mandatory false;
 }
 }
 grouping EUTRANINTRAFREQNCELL-attributes {
 leaf AGGREGATIONATTRIBUTE {
  type string;
  mandatory false;
 }
 leaf ANRFLAG {
  type boolean;
  mandatory false;
 }
 leaf ATTACHCELLSWITCH {
  type boolean;
  mandatory false;
 }
 leaf CELLID {
  type union {
   type int16 {
    range "-1..255";
   }
  }
  mandatory false;
 }
 leaf CELLINDIVIDUALOFFSET {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf CELLMEASPRIORITY {
  type boolean;
  mandatory false;
 }
 leaf CELLQOFFSET {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf CELLRANGEEXPANSION {
  type uint8 {
   range "0..15";
  }
  mandatory false;
 }
 leaf CTRLMODE {
  type boolean;
  mandatory false;
 }
 leaf HIGHSPEEDCELLINDOFFSET {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf LOCALCELLID {
  type union {
   type int16 {
    range "-1..255";
   }
  }
  mandatory false;
 }
 leaf LOCALCELLNAME {
  type string {
   length "0..99";
  }
  mandatory false;
 }
 leaf MCC {
  type string {
   length "3";
  }
  mandatory false;
 }
 leaf MNC {
  type string {
   length "2..3";
  }
  mandatory false;
 }
 leaf NCELLCLASSLABEL {
  type boolean;
  mandatory false;
 }
 leaf NEIGHBOURCELLNAME {
  type string {
   length "0..99";
  }
  mandatory false;
 }
 leaf NOHOFLAG {
  type boolean;
  mandatory false;
 }
 leaf NORMVFLAG {
  type boolean;
  mandatory false;
 }
 leaf NSADCCELLINDIVIDUALOFFSET {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf VECTORCELLFLAG {
  type boolean;
  mandatory false;
 }
 leaf ENODEBID {
  type union {
   type int32 {
    range "-1..1048575";
   }
  }
  mandatory false;
 }
 }
 grouping EUTRANNFREQRANSHARE-attributes {
 leaf LOCALCELLNAME {
  type string;
  mandatory false;
 }
 leaf CELLRESELPRIORITY {
  type uint8 {
   range "0..7";
  }
  mandatory false;
 }
 leaf CELLRESELPRIORITYCFGIND {
  type boolean;
  mandatory false;
 }
 leaf DLEARFCN {
  type union {
   type int32 {
    range "-1..229575";
   }
  }
  mandatory false;
 }
 leaf LOCALCELLID {
  type union {
   type int16 {
    range "-1..255";
   }
  }
  mandatory false;
 }
 leaf MCC {
  type string {
   length "3";
  }
  mandatory false;
 }
 leaf MNC {
  type string {
   length "2..3";
  }
  mandatory false;
 }
 }
 grouping EUTRANNFREQSCELLOP-attributes {
 leaf LOCALCELLNAME {
  type string;
  mandatory false;
 }
 leaf CELLRESELDEDIPRI {
  type uint8 {
   range "0..7";
  }
  mandatory false;
 }
 leaf CELLRESELDEDIPRICFGIND {
  type boolean;
  mandatory false;
 }
 leaf CNOPERATORID {
  type union {
   type int8 {
    range "-1..5";
   }
  }
  mandatory false;
 }
 leaf DLEARFCN {
  type union {
   type int32 {
    range "-1..229575";
   }
  }
  mandatory false;
 }
 leaf LOCALCELLID {
  type union {
   type int16 {
    range "-1..255";
   }
  }
  mandatory false;
 }
 }
 grouping EUTRANSPEPCICELL-attributes {
 leaf OLD_DLEARFCN {
  type union {
   type int32 {
    range "-1..229575";
   }
  }
  mandatory false;
 }
 leaf DLEARFCN {
  type union {
   type int32 {
    range "-1..229575";
   }
  }
  mandatory false;
 }
 leaf SPEPHYCELLIDRANGE {
  type uint16 {
   range "1..504";
  }
  mandatory false;
 }
 leaf SPECPCIGROUPPOLICYSW {
  type string;
  mandatory false;
 }
 leaf OLD_STAPHYCELLID {
  type union {
   type int16 {
    range "-1..503";
   }
  }
  mandatory false;
 }
 leaf STAPHYCELLID {
  type union {
   type int16 {
    range "-1..503";
   }
  }
  mandatory false;
 }
 }
 grouping EUULCOSCHCFG-attributes {
 leaf ULINTERENBCAMCSW {
  type boolean;
  mandatory false;
 }
 }
 grouping EX2-attributes {
 leaf BACKHAULTYPE {
  type enumeration {
   enum val-0;
   enum val-1;
   enum val-2;
  }
  mandatory false;
 }
 leaf CPEPGROUPID {
  type union {
   type uint32 {
    range "0..70999";
   }
  }
  mandatory false;
 }
 leaf EPGROUPCFGFLAG {
  type enumeration {
   enum val-2;
  }
  mandatory false;
 }
 leaf UPEPGROUPID {
  type union {
   type uint32 {
    range "0..70999";
   }
  }
  mandatory false;
 }
 leaf USERLABEL {
  type string {
   length "0..256";
  }
  mandatory false;
 }
 leaf OLD_EX2ID {
  type union {
   type int8 {
    range "-1..10";
   }
  }
  mandatory false;
 }
 leaf EX2ID {
  type union {
   type int8 {
    range "-1..10";
   }
  }
  mandatory false;
 }
 }
 grouping FDDRESMODE-attributes {
 leaf BBCAPABILITYMODE {
  type boolean;
  mandatory false;
 }
 leaf BBRESEXCLUSIVESWITCH {
  type enumeration {
   enum val-0;
   enum val-1;
   enum val-2;
  }
  mandatory false;
 }
 }
 grouping FLEXCOUNTERPARAMGRP-attributes {
 leaf ARP {
  type union {
   type uint8 {
    range "1..255";
   }
  }
  mandatory false;
 }
 leaf CNOPERATORID {
  type union {
   type uint8 {
    range "0..255";
   }
  }
  mandatory false;
 }
 leaf OLD_INDEX {
  type enumeration {
   enum val--1;
   enum val-0;
   enum val-1;
   enum val-2;
   enum val-3;
   enum val-4;
   enum val-5;
   enum val-6;
   enum val-7;
   enum val-8;
   enum val-9;
  }
  mandatory false;
 }
 leaf INDEX {
  type enumeration {
   enum val--1;
   enum val-0;
   enum val-1;
   enum val-2;
   enum val-3;
   enum val-4;
   enum val-5;
   enum val-6;
   enum val-7;
   enum val-8;
   enum val-9;
  }
  mandatory false;
 }
 leaf QCI {
  type union {
   type uint8 {
    range "1..255";
   }
  }
  mandatory false;
 }
 leaf SPID {
  type union {
   type uint16 {
    range "0..65535";
   }
  }
  mandatory false;
 }
 }
 grouping FREQLAYERGROUP-attributes {
 leaf OLD_FREQLAYEREARFCN {
  type union {
   type int32 {
    range "-1..262143";
   }
  }
  mandatory false;
 }
 leaf FREQLAYEREARFCN {
  type union {
   type int32 {
    range "-1..262143";
   }
  }
  mandatory false;
 }
 leaf OLD_FREQLAYERGROUPID {
  type union {
   type int8 {
    range "-1..35";
   }
  }
  mandatory false;
 }
 leaf FREQLAYERGROUPID {
  type union {
   type int8 {
    range "-1..35";
   }
  }
  mandatory false;
 }
 }
 grouping GERANEXTERNALCELL-attributes {
 leaf ANRFLAG {
  type boolean;
  mandatory false;
 }
 leaf BANDINDICATOR {
  type boolean;
  mandatory false;
 }
 leaf BASESTATIONCOLOURCODE {
  type uint8 {
   range "0..7";
  }
  mandatory false;
 }
 leaf CELLNAME {
  type string {
   length "0..99";
  }
  mandatory false;
 }
 leaf CSPSHOIND {
  type boolean;
  mandatory false;
 }
 leaf CTRLMODE {
  type boolean;
  mandatory false;
 }
 leaf DTMIND {
  type boolean;
  mandatory false;
 }
 leaf GERANARFCN {
  type uint16 {
   range "0..1023";
  }
  mandatory false;
 }
 leaf GERANCELLID {
  type union {
   type int32 {
    range "-1..65535";
   }
  }
  mandatory false;
 }
 leaf LAC {
  type union {
   type int32 {
    range "-1..65535";
   }
  }
  mandatory false;
 }
 leaf MCC {
  type string {
   length "3";
  }
  mandatory false;
 }
 leaf MNC {
  type string {
   length "2..3";
  }
  mandatory false;
 }
 leaf NETWORKCOLOURCODE {
  type uint8 {
   range "0..7";
  }
  mandatory false;
 }
 leaf RAC {
  type uint8 {
   range "0..255";
  }
  mandatory false;
 }
 leaf RACCFGIND {
  type boolean;
  mandatory false;
 }
 leaf ROAMINGAREAHOIND {
  type boolean;
  mandatory false;
 }
 leaf ULTRAFLASHCSFBIND {
  type boolean;
  mandatory false;
 }
 }
 grouping GERANEXTERNALCELLPLMN-attributes {
 leaf CELLNAME {
  type string;
  mandatory false;
 }
 leaf GERANCELLID {
  type union {
   type int32 {
    range "-1..65535";
   }
  }
  mandatory false;
 }
 leaf LAC {
  type union {
   type int32 {
    range "-1..65535";
   }
  }
  mandatory false;
 }
 leaf MCC {
  type string {
   length "3";
  }
  mandatory false;
 }
 leaf MNC {
  type string {
   length "2..3";
  }
  mandatory false;
 }
 leaf SHAREMCC {
  type string {
   length "3";
  }
  mandatory false;
 }
 leaf SHAREMNC {
  type string {
   length "2..3";
  }
  mandatory false;
 }
 }
 grouping GERANINTERFARFCN-attributes {
 leaf LOCALCELLNAME {
  type string;
  mandatory false;
 }
 leaf INTERFGERANCARBANDIND {
  type boolean;
  mandatory false;
 }
 leaf OLD_INTERFGERANCELLBCCHARFCN {
  type union {
   type int16 {
    range "-1..1023";
   }
  }
  mandatory false;
 }
 leaf INTERFGERANCELLBCCHARFCN {
  type union {
   type int16 {
    range "-1..1023";
   }
  }
  mandatory false;
 }
 leaf OLD_LOCALCELLID {
  type union {
   type int16 {
    range "-1..255";
   }
  }
  mandatory false;
 }
 leaf LOCALCELLID {
  type union {
   type int16 {
    range "-1..255";
   }
  }
  mandatory false;
 }
 }
 grouping GERANINTERFCFG-attributes {
 leaf LOCALCELLNAME {
  type string;
  mandatory false;
 }
 leaf DLGERANINTEFRBNUM {
  type uint8 {
   range "1..10";
  }
  mandatory false;
 }
 leaf DLRBAVAILSINRTHD {
  type int8 {
   range "-6..12";
  }
  mandatory false;
 }
 leaf LOCALCELLID {
  type union {
   type int16 {
    range "-1..255";
   }
  }
  mandatory false;
 }
 }
 grouping GERANNCELL-attributes {
 leaf ANRFLAG {
  type boolean;
  mandatory false;
 }
 leaf BLINDHOPRIORITY {
  type uint8 {
   range "0..32";
  }
  mandatory false;
 }
 leaf CTRLMODE {
  type boolean;
  mandatory false;
 }
 leaf GERANCELLID {
  type union {
   type int32 {
    range "-1..65535";
   }
  }
  mandatory false;
 }
 leaf LAC {
  type union {
   type int32 {
    range "-1..65535";
   }
  }
  mandatory false;
 }
 leaf LOCALCELLID {
  type union {
   type int16 {
    range "-1..255";
   }
  }
  mandatory false;
 }
 leaf LOCALCELLNAME {
  type string {
   length "0..99";
  }
  mandatory false;
 }
 leaf MCC {
  type string {
   length "3";
  }
  mandatory false;
 }
 leaf MNC {
  type string {
   length "2..3";
  }
  mandatory false;
 }
 leaf NCELLMEASPRIORITY {
  type uint8 {
   range "0..128";
  }
  mandatory false;
 }
 leaf NEIGHBOURCELLNAME {
  type string {
   length "0..99";
  }
  mandatory false;
 }
 leaf NOHOFLAG {
  type boolean;
  mandatory false;
 }
 leaf NORMVFLAG {
  type boolean;
  mandatory false;
 }
 leaf OVERLAPIND {
  type boolean;
  mandatory false;
 }
 }
 grouping GERANNETWORKCAPCFG-attributes {
 leaf OLD_LAC {
  type union {
   type int64 {
    range "-1..4294967295";
   }
  }
  mandatory false;
 }
 leaf LAC {
  type union {
   type int64 {
    range "-1..4294967295";
   }
  }
  mandatory false;
 }
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf NETWORKCAPCFG {
  type string;
  mandatory false;
 }
 }
 grouping GERANNFGROUPSCELLOP-attributes {
 leaf LOCALCELLNAME {
  type string;
  mandatory false;
 }
 leaf BCCHGROUPID {
  type union {
   type int8 {
    range "-1..31";
   }
  }
  mandatory false;
 }
 leaf CELLRESELDEDIPRI {
  type uint8 {
   range "0..7";
  }
  mandatory false;
 }
 leaf CELLRESELDEDIPRICFGIND {
  type boolean;
  mandatory false;
 }
 leaf CNOPERATORID {
  type union {
   type int8 {
    range "-1..5";
   }
  }
  mandatory false;
 }
 leaf LOCALCELLID {
  type union {
   type int16 {
    range "-1..255";
   }
  }
  mandatory false;
 }
 }
 grouping GERANNFREQGROUP-attributes {
 leaf LOCALCELLNAME {
  type string;
  mandatory false;
 }
 leaf ANRIND {
  type boolean;
  mandatory false;
 }
 leaf BANDINDICATOR {
  type boolean;
  mandatory false;
 }
 leaf BCCHGROUPID {
  type union {
   type int8 {
    range "-1..31";
   }
  }
  mandatory false;
 }
 leaf CELLRESELPRIORITY {
  type uint8 {
   range "0..7";
  }
  mandatory false;
 }
 leaf CELLRESELPRIORITYCFGIND {
  type boolean;
  mandatory false;
 }
 leaf CONNFREQPRIORITY {
  type uint8 {
   range "0..8";
  }
  mandatory false;
 }
 leaf CONTINUCOVERAGEINDICATION {
  type boolean;
  mandatory false;
 }
 leaf GERANRANSHARINGIND {
  type boolean;
  mandatory false;
 }
 leaf GERANVERSION {
  type enumeration {
   enum val-0;
   enum val-1;
   enum val-2;
  }
  mandatory false;
 }
 leaf LOCALCELLID {
  type union {
   type int16 {
    range "-1..255";
   }
  }
  mandatory false;
 }
 leaf NCCPERMITTED {
  type uint8 {
   range "0..255";
  }
  mandatory false;
 }
 leaf OFFSETFREQ {
  type int8 {
   range "-15..15";
  }
  mandatory false;
 }
 leaf PMAXGERAN {
  type uint8 {
   range "0..39";
  }
  mandatory false;
 }
 leaf PMAXGERANCFGIND {
  type boolean;
  mandatory false;
 }
 leaf QRXLEVMIN {
  type uint8 {
   range "0..45";
  }
  mandatory false;
 }
 leaf STARTINGARFCN {
  type uint16 {
   range "0..1023";
  }
  mandatory false;
 }
 leaf THRESHXHIGH {
  type uint8 {
   range "0..31";
  }
  mandatory false;
 }
 leaf THRESHXLOW {
  type uint8 {
   range "0..31";
  }
  mandatory false;
 }
 }
 grouping GERANNFREQGROUPARFCN-attributes {
 leaf LOCALCELLNAME {
  type string;
  mandatory false;
 }
 leaf BCCHGROUPID {
  type union {
   type int8 {
    range "-1..31";
   }
  }
  mandatory false;
 }
 leaf GERANARFCN {
  type union {
   type int16 {
    range "-1..1023";
   }
  }
  mandatory false;
 }
 leaf LOCALCELLID {
  type union {
   type int16 {
    range "-1..255";
   }
  }
  mandatory false;
 }
 }
 grouping GERANRANSHARE-attributes {
 leaf LOCALCELLNAME {
  type string;
  mandatory false;
 }
 leaf BCCHGROUPID {
  type union {
   type int8 {
    range "-1..31";
   }
  }
  mandatory false;
 }
 leaf CELLRESELPRIORITY {
  type uint8 {
   range "0..7";
  }
  mandatory false;
 }
 leaf CELLRESELPRIORITYCFGIND {
  type boolean;
  mandatory false;
 }
 leaf LOCALCELLID {
  type union {
   type int16 {
    range "-1..255";
   }
  }
  mandatory false;
 }
 leaf MCC {
  type string {
   length "3";
  }
  mandatory false;
 }
 leaf MNC {
  type string {
   length "2..3";
  }
  mandatory false;
 }
 }
 grouping GLOBALPROCSWITCH-attributes {
 leaf CSFBFLOWOPTSWITCH {
  type string;
  mandatory false;
 }
 leaf CTRLMSGFWDTYPE {
  type enumeration {
   enum val-0;
   enum val-1;
   enum val-2;
   enum val-3;
  }
  mandatory false;
 }
 leaf DIFFOPWITHSAMEMMECSWITCH {
  type boolean;
  mandatory false;
 }
 leaf EMTCRRCCONNPUNISHMENTTHLD {
  type uint16 {
   range "0..3600";
  }
  mandatory false;
 }
 leaf ENBTRIGMMELOADREBALSWITCH {
  type boolean;
  mandatory false;
 }
 leaf ENHANCEDPHRRPTCTRLSW {
  type boolean;
  mandatory false;
 }
 leaf ENHANCEDRRCREESTPROTECTTHD {
  type uint16 {
   range "0..65535";
  }
  mandatory false;
 }
 leaf EPSFBHOINUECAPBQRYDELAY {
  type uint16 {
   range "0..1000";
  }
  mandatory false;
 }
 leaf EUTRANLOADTRANSSWITCH {
  type string;
  mandatory false;
 }
 leaf EX2DELETETIMERFOREX2USAGE {
  type union {
   type uint16 {
    range "0..10080";
   }
  }
  mandatory false;
 }
 leaf HOERABCONFLPROCESSINGSTRAT {
  type enumeration {
   enum val-0;
   enum val-1;
   enum val-2;
  }
  mandatory false;
 }
 leaf HOPROCCTRLSWITCH {
  type string;
  mandatory false;
 }
 leaf INACTVTYTMREXPNPROCSTRAT {
  type enumeration {
   enum val-0;
   enum val-1;
   enum val-2;
  }
  mandatory false;
 }
 leaf INITMSGPROTECTTHLD {
  type uint16 {
   range "0..65535";
  }
  mandatory false;
 }
 leaf INITMSGRATIOTHLDDT {
  type uint8 {
   range "0..100";
  }
  mandatory false;
 }
 leaf INITMSGRATIOTHLDHIGHPRI {
  type uint8 {
   range "0..100";
  }
  mandatory false;
 }
 leaf INITMSGRATIOTHLDMODATA {
  type uint8 {
   range "0..100";
  }
  mandatory false;
 }
 leaf INITMSGRATIOTHLDMOSIG {
  type uint8 {
   range "0..100";
  }
  mandatory false;
 }
 leaf INTERENODEBX2SPECEXCLURATE {
  type uint8 {
   range "0..100";
  }
  mandatory false;
 }
 leaf INTERRATLINKSETUPSWITCH {
  type string;
  mandatory false;
 }
 leaf INTERRATPOWERSHARINGTIME {
  type string;
  mandatory false;
 }
 leaf INTERFACESETUPPOLICYSW {
  type string;
  mandatory false;
 }
 leaf INTRAENODEBHOSTATICSW {
  type boolean;
  mandatory false;
 }
 leaf ITFTYPEFORNONIDEALMODESERV {
  type boolean;
  mandatory false;
 }
 leaf L2GUHOWITHLCAPSWITCH {
  type boolean;
  mandatory false;
 }
 leaf LCGPROFILE {
  type enumeration {
   enum val-0;
   enum val-1;
   enum val-2;
   enum val-3;
  }
  mandatory false;
 }
 leaf LTENRPOWERSHARINGTIME {
  type string;
  mandatory false;
 }
 leaf LTERRCCONNPUNISHMENTTHLD {
  type uint16 {
   range "0..3600";
  }
  mandatory false;
 }
 leaf MMEDOMNAMEMODE {
  type boolean;
  mandatory false;
 }
 leaf MAXSYNCUSERNUMPERBBI {
  type enumeration {
   enum val-0;
   enum val-1;
   enum val-2;
   enum val-3;
   enum val-4;
  }
  mandatory false;
 }
 leaf MMESELECTPROCSWITCH {
  type string;
  mandatory false;
 }
 leaf MOVOICECALLUECAPBQRYDELAY {
  type uint16 {
   range "0..10000";
  }
  mandatory false;
 }
 leaf NBRRCCONNPUNISHMENTTHLD {
  type uint16 {
   range "0..3600";
  }
  mandatory false;
 }
 leaf NONIDEALMODECOORDSERVQCI {
  type uint8 {
   range "6..9";
  }
  mandatory false;
 }
 leaf PEERREQBASEDX2DELSWITCH {
  type boolean;
  mandatory false;
 }
 leaf PIMINTERFDETECTDURATION {
  type uint16 {
   range "5..480";
  }
  mandatory false;
 }
 leaf PIMINTERFDETECTINTERVAL {
  type uint8 {
   range "1..90";
  }
  mandatory false;
 }
 leaf PIMINTERFDETECTSTARTTIME {
  type hwat:HH_MM_SS_Time;
  mandatory false;
 }
 leaf PIMINTRFCANCTRAININGINTVL {
  type enumeration {
   enum val-1;
   enum val-2;
   enum val-3;
   enum val-4;
   enum val-5;
   enum val-6;
   enum val-7;
   enum val-8;
  }
  mandatory false;
 }
 leaf PROCTYPEFORNONIDEALSERVDATA {
  type boolean;
  mandatory false;
 }
 leaf PROTOCOLCOMPATIBILITYSW {
  type string;
  mandatory false;
 }
 leaf PROTOCOLMSGOPTEXTSWITCH {
  type string;
  mandatory false;
 }
 leaf PROTOCOLMSGOPTSWITCH {
  type string;
  mandatory false;
 }
 leaf PROTOCOLSUPPORTSWITCH {
  type inet:port-number;
  mandatory false;
 }
 leaf QCIUPDPARACHECKSWITCH {
  type boolean;
  mandatory false;
 }
 leaf RIMCODINGPOLICY {
  type boolean;
  mandatory false;
 }
 leaf RIMFIRSTMULTIREPORTSWITCH {
  type boolean;
  mandatory false;
 }
 leaf RNCPOOLHORIMSWITCH {
  type boolean;
  mandatory false;
 }
 leaf RRCCONNREQSTATSWITCH {
  type string;
  mandatory false;
 }
 leaf RRCREESTOPTSWITCH {
  type string;
  mandatory false;
 }
 leaf S1DEFAULTPAGINGDRXFORNB {
  type enumeration {
   enum val-0;
   enum val-1;
   enum val-2;
   enum val-3;
  }
  mandatory false;
 }
 leaf S1DEFAULTPAGINGDRXSELECT {
  type enumeration {
   enum val-0;
   enum val-1;
   enum val-2;
   enum val-3;
  }
  mandatory false;
 }
 leaf S1FAULTCELLDEACTWAITTIME {
  type uint8 {
   range "0..3";
  }
  mandatory false;
 }
 leaf S1FAULTSELFRECOVERYSWITCH {
  type string;
  mandatory false;
 }
 leaf S1HOINDATAFWDSWITCH {
  type boolean;
  mandatory false;
 }
 leaf S1MMESONSWITCH {
  type string;
  mandatory false;
 }
 leaf S1MMEPRIVFEATUREIND {
  type string;
  mandatory false;
 }
 leaf S1OFFLINECOMMITSWITCH {
  type boolean;
  mandatory false;
 }
 leaf SCTPABORTSMOOTHSWITCH {
  type string;
  mandatory false;
 }
 leaf SECKEYRECFGSWITCH {
  type boolean;
  mandatory false;
 }
 leaf SIGPOOLOPTPOLICY {
  type boolean;
  mandatory false;
 }
 leaf SINGLEPLMNHOSTSPLITSWITCH {
  type string;
  mandatory false;
 }
 leaf TARGETOPBASEDX2SWITCH {
  type boolean;
  mandatory false;
 }
 leaf UECAPRRCSEGALLOWEDTHLD {
  type uint16 {
   range "0..24000";
  }
  mandatory false;
 }
 leaf UECOMPATSWITCH {
  type string;
  mandatory false;
 }
 leaf UEEUTRACAPBIESIZETHLD {
  type union {
   type uint16 {
    range "0..8000";
   }
  }
  mandatory false;
 }
 leaf UELINKABNORMALDETECTSWITCH {
  type boolean;
  mandatory false;
 }
 leaf UERELCHKLOSTSWITCH {
  type boolean;
  mandatory false;
 }
 leaf UERELRESYNTIMES {
  type enumeration {
   enum val-0;
   enum val-1;
   enum val-2;
   enum val-3;
   enum val-4;
   enum val-5;
  }
  mandatory false;
 }
 leaf ULPDCPSDURCVSTATSENDSWITCH {
  type boolean;
  mandatory false;
 }
 leaf UTRANLOADTRANSCHAN {
  type enumeration {
   enum val-0;
   enum val-1;
   enum val-2;
  }
  mandatory false;
 }
 leaf UUMSGSIMULSENDSWITCH {
  type boolean;
  mandatory false;
 }
 leaf UUMSGTIMEOUTRELCAUSE {
  type boolean;
  mandatory false;
 }
 leaf VOIPWITHGAPMODE {
  type boolean;
  mandatory false;
 }
 leaf X2BASEDUPTENODEBPOLICY {
  type string;
  mandatory false;
 }
 leaf X2BASEDUPTNCELLCFGSWITCH {
  type string;
  mandatory false;
 }
 leaf X2DYNBLACKLISTAGINGTIMER {
  type uint16 {
   range "30..10080";
  }
  mandatory false;
 }
 leaf X2INITFAILDELSWITCH {
  type boolean;
  mandatory false;
 }
 leaf X2SCTPESTTYPE {
  type boolean;
  mandatory false;
 }
 leaf X2SERVEDCELLTYPE {
  type boolean;
  mandatory false;
 }
 leaf X2SETUPFAILURENUMTHD {
  type uint16 {
   range "0..2000";
  }
  mandatory false;
 }
 leaf X2SETUPFAILURENUMTIMER {
  type uint16 {
   range "5..50400";
  }
  mandatory false;
 }
 leaf X2SETUPFAILURETIMETOWAIT {
  type enumeration {
   enum val-0;
   enum val-1;
   enum val-2;
   enum val-3;
   enum val-4;
   enum val-5;
   enum val-6;
   enum val-7;
  }
  mandatory false;
 }
 leaf X2SONDELETEHOINNUMTHD {
  type uint16 {
   range "0..10000";
  }
  mandatory false;
 }
 leaf X2SONDELETEHOOUTNUMTHD {
  type uint16 {
   range "0..10000";
  }
  mandatory false;
 }
 leaf X2SONDELETEMODE {
  type boolean;
  mandatory false;
 }
 leaf X2SONDELETESWITCH {
  type string;
  mandatory false;
 }
 leaf X2SONDELETETIMER {
  type uint16 {
   range "0..50400";
  }
  mandatory false;
 }
 leaf X2SONDELETETIMERFORX2FAULT {
  type uint16 {
   range "1..50400";
  }
  mandatory false;
 }
 leaf X2SONDELETETIMERFORX2USAGE {
  type uint16 {
   range "1..50400";
  }
  mandatory false;
 }
 leaf X2SONLINKSETUPTYPE {
  type boolean;
  mandatory false;
 }
 leaf X2SONSETUPNUMTHD {
  type uint16 {
   range "1..10000";
  }
  mandatory false;
 }
 leaf X2SONSETUPSWITCH {
  type boolean;
  mandatory false;
 }
 leaf X2SONSETUPTIMER {
  type uint16 {
   range "1..50400";
  }
  mandatory false;
 }
 leaf X2SONTNLSELECTMODE {
  type enumeration {
   enum val-1;
   enum val-2;
  }
  mandatory false;
 }
 leaf X2SPECSHARINGSW {
  type boolean;
  mandatory false;
 }
 leaf EX2AUTODELETESWITCH {
  type string;
  mandatory false;
 }
 leaf EX2AUTODELETETIMERFORFAULT {
  type uint16 {
   range "60..50400";
  }
  mandatory false;
 }
 leaf EX2AUTOSETUPSWITCH {
  type string;
  mandatory false;
 }
 leaf EX2DYNBLACKLISTAGINGTIMER {
  type uint16 {
   range "30..10080";
  }
  mandatory false;
 }
 leaf EX2DYNBLACKLISTSWITCH {
  type string;
  mandatory false;
 }
 }
 grouping GNODEBBLACKLIST-attributes {
 leaf OLD_GNODEBID {
  type union {
   type int64 {
    range "-1..4294967295";
   }
  }
  mandatory false;
 }
 leaf GNODEBID {
  type union {
   type int64 {
    range "-1..4294967295";
   }
  }
  mandatory false;
 }
 }
 grouping GSMINTERFARFCNCFG-attributes {
 leaf OLD_GSMARFCN {
  type union {
   type int16 {
    range "-1..1023";
   }
  }
  mandatory false;
 }
 leaf GSMARFCN {
  type union {
   type int16 {
    range "-1..1023";
   }
  }
  mandatory false;
 }
 leaf OLD_GSMARFCNGROUPID {
  type union {
   type int16 {
    range "-1..255";
   }
  }
  mandatory false;
 }
 leaf GSMARFCNGROUPID {
  type union {
   type int16 {
    range "-1..255";
   }
  }
  mandatory false;
 }
 }
 grouping HENBTACRANGEGROUP-attributes {
 leaf OLD_HENBTACRAGID {
  type union {
   type int8 {
    range "-1..9";
   }
  }
  mandatory false;
 }
 leaf HENBTACRAGID {
  type union {
   type int8 {
    range "-1..9";
   }
  }
  mandatory false;
 }
 leaf TACEND {
  type union {
   type uint16 {
    range "1..65535";
   }
  }
  mandatory false;
 }
 leaf TACSTART {
  type union {
   type uint16 {
    range "1..65535";
   }
  }
  mandatory false;
 }
 }
 grouping HIGHSPDADAPTIONPARA-attributes {
 leaf LOCALCELLNAME {
  type string;
  mandatory false;
 }
 leaf DOPPLERFACTOR {
  type uint8 {
   range "1..100";
  }
  mandatory false;
 }
 leaf HIGHSPEEDCELLSLEEPMODE {
  type boolean;
  mandatory false;
 }
 leaf HIGHSPEEDOPTSWITCH {
  type string;
  mandatory false;
 }
 leaf HIGHSPEEDOVERLAPBANDIND {
  type enumeration {
   enum val-0;
   enum val-1;
   enum val-2;
   enum val-3;
   enum val-4;
   enum val-5;
   enum val-6;
  }
  mandatory false;
 }
 leaf HIGHSPEEDUSERNUMTHD {
  type uint8 {
   range "1..200";
  }
  mandatory false;
 }
 leaf HIGHSPDVECTORUPDATEPERIOD {
  type uint8 {
   range "1..168";
  }
  mandatory false;
 }
 leaf HIGHSPDVECTORUPDATESWITCH {
  type boolean;
  mandatory false;
 }
 leaf HOHISJUDGEHIGHTHD {
  type uint8 {
   range "3..120";
  }
  mandatory false;
 }
 leaf INTERFAVOIDCELLNUM {
  type uint8 {
   range "1..15";
  }
  mandatory false;
 }
 leaf INTERFAVOIDMODE {
  type string;
  mandatory false;
 }
 leaf INTERFBASEDPOWEROFF {
  type uint8 {
   range "0..30";
  }
  mandatory false;
 }
 leaf INTERFBASEDRBRATIO {
  type uint8 {
   range "0..100";
  }
  mandatory false;
 }
 leaf LOCALCELLID {
  type union {
   type int16 {
    range "-1..255";
   }
  }
  mandatory false;
 }
 leaf LOWSPEEDUEJUDGECAMPDURTHLD {
  type union {
   type uint16 {
    range "0..65535";
   }
  }
  mandatory false;
 }
 leaf USERLOWSPEEDJUDGENUM {
  type uint8 {
   range "1..30";
  }
  mandatory false;
 }
 }
 grouping HOMEASCOMM-attributes {
 leaf GERANFILTERCOEFF {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf NCRHIGHCONNMODE {
  type uint8 {
   range "1..16";
  }
  mandatory false;
 }
 leaf NCRMEDIUMCONNMODE {
  type uint8 {
   range "1..16";
  }
  mandatory false;
 }
 leaf NONRESHOPREFAILPUNISHTIMES {
  type uint8 {
   range "0..200";
  }
  mandatory false;
 }
 leaf NONRESHOPREFAILRETRYTIMES {
  type uint8 {
   range "0..200";
  }
  mandatory false;
 }
 leaf NRHORESPREPFAILPENALTYTMR {
  type uint8 {
   range "0..50";
  }
  mandatory false;
 }
 leaf OPTHOPREFAILPUNISHTIMER {
  type uint8 {
   range "0..20";
  }
  mandatory false;
 }
 leaf PWRSAVHOPREFAILPENALTYTHLD {
  type uint8 {
   range "0..200";
  }
  mandatory false;
 }
 leaf RESHOPREFAILPUNISHTIMER {
  type uint8 {
   range "0..50";
  }
  mandatory false;
 }
 leaf SMEASURE {
  type int16 {
   range "-140..-43";
  }
  mandatory false;
 }
 leaf SMEASUREIND {
  type boolean;
  mandatory false;
 }
 leaf SPEEDDEPPARAIND {
  type boolean;
  mandatory false;
 }
 leaf SRVCCHOFAILUREPENALTYTIMER {
  type uint16 {
   range "0..1440";
  }
  mandatory false;
 }
 leaf TCRMAXCONNMODE {
  type enumeration {
   enum val-0;
   enum val-1;
   enum val-2;
   enum val-3;
   enum val-4;
  }
  mandatory false;
 }
 leaf TCRMAXHYSTCONNMODE {
  type enumeration {
   enum val-0;
   enum val-1;
   enum val-2;
   enum val-3;
   enum val-4;
  }
  mandatory false;
 }
 leaf TTTSFHIGH {
  type enumeration {
   enum val-0;
   enum val-1;
   enum val-2;
   enum val-3;
  }
  mandatory false;
 }
 leaf TTTSFMEDIUM {
  type enumeration {
   enum val-0;
   enum val-1;
   enum val-2;
   enum val-3;
  }
  mandatory false;
 }
 leaf UTRANFILTERCOEFFECN0 {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf UTRANFILTERCOEFFRSCP {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf VOLTEREDIRECTIONCAUSE {
  type enumeration {
   enum val-0;
   enum val-1;
   enum val-2;
  }
  mandatory false;
 }
 leaf VOLTEUSERREDIRECTCAUSE {
  type enumeration {
   enum val-0;
   enum val-1;
   enum val-2;
  }
  mandatory false;
 }
 }
 grouping INCRCFG-attributes {
 leaf DHCPSERVERIPV4 {
  type inet:ipv4-address;
  mandatory false;
 }
 leaf DHCPSERVERIPV6 {
  type inet:ipv6-address;
  mandatory false;
 }
 leaf INCRACCESSENHSW {
  type string;
  mandatory false;
 }
 leaf OLD_INCRCFGID {
  type union {
   type int32 {
    range "-1..65535";
   }
  }
  mandatory false;
 }
 leaf INCRCFGID {
  type union {
   type int32 {
    range "-1..65535";
   }
  }
  mandatory false;
 }
 }
 grouping INTERFREQBLKCELL-attributes {
 leaf LOCALCELLNAME {
  type string;
  mandatory false;
 }
 leaf APPLICATIONSCOPE {
  type union {
   type uint16 {
    range "0..65535";
   }
  }
  mandatory false;
 }
 leaf CELLNAME {
  type string {
   length "0..99";
  }
  mandatory false;
 }
 leaf DLEARFCN {
  type union {
   type int32 {
    range "-1..229575";
   }
  }
  mandatory false;
 }
 leaf LOCALCELLID {
  type union {
   type int16 {
    range "-1..255";
   }
  }
  mandatory false;
 }
 leaf PHYCELLID {
  type union {
   type int16 {
    range "-1..503";
   }
  }
  mandatory false;
 }
 leaf PHYCELLIDRANGE {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 }
 grouping INTERFREQHOGROUP-attributes {
 leaf LOCALCELLNAME {
  type string;
  mandatory false;
 }
 leaf A3INTERFREQHOA1A2TRIGQUAN {
  type enumeration {
   enum val-0;
   enum val-1;
   enum val-2;
  }
  mandatory false;
 }
 leaf A3INTERFREQHOA1THDRSRP {
  type int16 {
   range "-140..-43";
  }
  mandatory false;
 }
 leaf A3INTERFREQHOA1THDRSRQ {
  type int8 {
   range "-40..-6";
  }
  mandatory false;
 }
 leaf A3INTERFREQHOA2THDRSRP {
  type int16 {
   range "-140..-43";
  }
  mandatory false;
 }
 leaf A3INTERFREQHOA2THDRSRQ {
  type int8 {
   range "-40..-6";
  }
  mandatory false;
 }
 leaf A3INTERFREQHOA2THLDRSRPCEA {
  type int16 {
   range "-140..-43";
  }
  mandatory false;
 }
 leaf A3INTERFREQHOA2THLDRSRQCEA {
  type int8 {
   range "-40..-6";
  }
  mandatory false;
 }
 leaf A4A5IFHOA1A2TRIGQUAN {
  type enumeration {
   enum val-0;
   enum val-1;
   enum val-2;
  }
  mandatory false;
 }
 leaf FREQPRIINTERFREQHOA1THDRSRP {
  type int16 {
   range "-140..-43";
  }
  mandatory false;
 }
 leaf FREQPRIINTERFREQHOA1THDRSRQ {
  type int8 {
   range "-40..-6";
  }
  mandatory false;
 }
 leaf FREQPRIINTERFREQHOA2THDRSRP {
  type int16 {
   range "-140..-43";
  }
  mandatory false;
 }
 leaf FREQPRIINTERFREQHOA2THDRSRQ {
  type int8 {
   range "-40..-6";
  }
  mandatory false;
 }
 leaf IFHOA1A2RSRQTIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
  }
  mandatory false;
 }
 leaf INTERFREQA3HOHYST {
  type union {
   type uint8 {
    range "0..254";
   }
  }
  mandatory false;
 }
 leaf INTERFREQHOA1A2HYST {
  type uint8 {
   range "0..30";
  }
  mandatory false;
 }
 leaf INTERFREQHOA1A2TIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf INTERFREQHOA1THDRSRP {
  type int16 {
   range "-140..-43";
  }
  mandatory false;
 }
 leaf INTERFREQHOA1THDRSRPCE {
  type int16 {
   range "-140..-43";
  }
  mandatory false;
 }
 leaf INTERFREQHOA1THDRSRQ {
  type int8 {
   range "-40..-6";
  }
  mandatory false;
 }
 leaf INTERFREQHOA2THDRSRP {
  type int16 {
   range "-140..-43";
  }
  mandatory false;
 }
 leaf INTERFREQHOA2THDRSRPCE {
  type int16 {
   range "-140..-43";
  }
  mandatory false;
 }
 leaf INTERFREQHOA2THDRSRQ {
  type int8 {
   range "-40..-6";
  }
  mandatory false;
 }
 leaf INTERFREQHOA2THLDRSRQCEA {
  type int8 {
   range "-40..-6";
  }
  mandatory false;
 }
 leaf INTERFREQHOA3OFFSET {
  type int8 {
   range "-30..30";
  }
  mandatory false;
 }
 leaf INTERFREQHOA3RPTQUAN {
  type boolean;
  mandatory false;
 }
 leaf INTERFREQHOA3RSRQOFFSET {
  type int8 {
   range "-40..40";
  }
  mandatory false;
 }
 leaf INTERFREQHOA3TIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf INTERFREQHOA4A5RPTQUAN {
  type boolean;
  mandatory false;
 }
 leaf INTERFREQHOA4HYST {
  type uint8 {
   range "0..30";
  }
  mandatory false;
 }
 leaf INTERFREQHOA4THDRSRP {
  type int16 {
   range "-140..-43";
  }
  mandatory false;
 }
 leaf INTERFREQHOA4THDRSRQ {
  type int8 {
   range "-40..-6";
  }
  mandatory false;
 }
 leaf INTERFREQHOA4THLDRSRPFORCE {
  type int16 {
   range "-140..-43";
  }
  mandatory false;
 }
 leaf INTERFREQHOA4THLDRSRQCEA {
  type int8 {
   range "-40..-6";
  }
  mandatory false;
 }
 leaf INTERFREQHOA4TIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf INTERFREQHOA5THD1RSRP {
  type int16 {
   range "-140..-43";
  }
  mandatory false;
 }
 leaf INTERFREQHOA5THD1RSRQ {
  type int8 {
   range "-40..-6";
  }
  mandatory false;
 }
 leaf OLD_INTERFREQHOGROUPID {
  type union {
   type int8 {
    range "-1..19";
   }
  }
  mandatory false;
 }
 leaf INTERFREQHOGROUPID {
  type union {
   type int8 {
    range "-1..19";
   }
  }
  mandatory false;
 }
 leaf INTERFREQLOADBASEDHOA4THDRSRP {
  type int16 {
   range "-140..-43";
  }
  mandatory false;
 }
 leaf INTERFREQLOADBASEDHOA4THDRSRQ {
  type int8 {
   range "-40..-6";
  }
  mandatory false;
 }
 leaf INTERFREQMLBA1A2THDRSRP {
  type int16 {
   range "-141..-43";
  }
  mandatory false;
 }
 leaf INTERFREQSERVHOA2THLDRSRP {
  type union {
   type int16 {
    range "-140..0";
   }
  }
  mandatory false;
 }
 leaf INTERFREQSERVHOA2THLDRSRQ {
  type union {
   type int8 {
    range "-40..0";
   }
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf MLBINTERFREQHOA5THD1RSRP {
  type int16 {
   range "-140..-43";
  }
  mandatory false;
 }
 leaf MLBINTERFREQHOA5THD1RSRQ {
  type int8 {
   range "-40..-6";
  }
  mandatory false;
 }
 leaf MMLOADSTEERINGA4THLDRSRP {
  type int16 {
   range "-140..-43";
  }
  mandatory false;
 }
 leaf SRVREQHOA4THDRSRP {
  type int16 {
   range "-140..-43";
  }
  mandatory false;
 }
 leaf SRVREQHOA4THDRSRQ {
  type int8 {
   range "-40..-6";
  }
  mandatory false;
 }
 leaf ULBADQUALHOA4OFFSET {
  type int8 {
   range "-20..20";
  }
  mandatory false;
 }
 leaf ULHEAVYTRAFFICMLBA4THDRSRP {
  type int16 {
   range "-140..-43";
  }
  mandatory false;
 }
 leaf ULHEAVYTRAFFICMLBA4THDRSRQ {
  type int8 {
   range "-40..-6";
  }
  mandatory false;
 }
 }
 grouping INTERPLMNHOLIST-attributes {
 leaf OLD_CNOPERATORID {
  type union {
   type int8 {
    range "-1..5";
   }
  }
  mandatory false;
 }
 leaf CNOPERATORID {
  type union {
   type int8 {
    range "-1..5";
   }
  }
  mandatory false;
 }
 leaf OLD_TARMCC {
  type string {
   length "3";
  }
  mandatory false;
 }
 leaf TARMCC {
  type string {
   length "3";
  }
  mandatory false;
 }
 leaf OLD_TARMNC {
  type string {
   length "2..3";
  }
  mandatory false;
 }
 leaf TARMNC {
  type string {
   length "2..3";
  }
  mandatory false;
 }
 }
 grouping INTERRATCELLSHUTDOWN-attributes {
 leaf LOCALCELLNAME {
  type string;
  mandatory false;
 }
 leaf BEARNUMTHD {
  type uint16 {
   range "0..5000";
  }
  mandatory false;
 }
 leaf DLPRBTHD {
  type uint8 {
   range "0..100";
  }
  mandatory false;
 }
 leaf EXITJUDGEPERIOD {
  type uint8 {
   range "4..12";
  }
  mandatory false;
 }
 leaf FORCESHUTDOWNSWITCH {
  type boolean;
  mandatory false;
 }
 leaf GERANCELLLOADOFFSET {
  type uint8 {
   range "0..100";
  }
  mandatory false;
 }
 leaf GERANCELLLOADTHD {
  type uint8 {
   range "0..100";
  }
  mandatory false;
 }
 leaf HIGHPRIARPTHD {
  type uint8 {
   range "1..15";
  }
  mandatory false;
 }
 leaf LOCALCELLID {
  type union {
   type int16 {
    range "-1..255";
   }
  }
  mandatory false;
 }
 leaf SHUTDOWNTYPE {
  type enumeration {
   enum val-0;
   enum val-1;
   enum val-2;
   enum val-3;
  }
  mandatory false;
 }
 leaf STARTTIME {
  type hwat:HH_MM_SS_Time;
  mandatory false;
 }
 leaf STOPTIME {
  type hwat:HH_MM_SS_Time;
  mandatory false;
 }
 leaf ULPRBTHD {
  type uint8 {
   range "0..100";
  }
  mandatory false;
 }
 leaf UTRANCELLDLLOADOFFSET {
  type uint8 {
   range "0..100";
  }
  mandatory false;
 }
 leaf UTRANCELLDLLOADTHD {
  type uint8 {
   range "0..100";
  }
  mandatory false;
 }
 leaf UTRANCELLULLOADOFFSET {
  type uint8 {
   range "0..100";
  }
  mandatory false;
 }
 leaf UTRANCELLULLOADTHD {
  type uint8 {
   range "0..100";
  }
  mandatory false;
 }
 }
 grouping INTERRATHOCDMAHRPDGROUP-attributes {
 leaf LOCALCELLNAME {
  type string;
  mandatory false;
 }
 leaf CDMA2000HRPDB2THD1RSRP {
  type int16 {
   range "-140..-43";
  }
  mandatory false;
 }
 leaf CDMA2000HRPDB2THD1RSRQ {
  type int8 {
   range "-40..-6";
  }
  mandatory false;
 }
 leaf CDMA2000HRPDNONB2THDRSRP {
  type int16 {
   range "-140..-43";
  }
  mandatory false;
 }
 leaf CDMA2000HRPDNONB2THDRSRQ {
  type int8 {
   range "-40..-6";
  }
  mandatory false;
 }
 leaf INTERRATHOCDMAB1HYST {
  type uint8 {
   range "0..30";
  }
  mandatory false;
 }
 leaf INTERRATHOCDMAB1THDPS {
  type int8 {
   range "-63..0";
  }
  mandatory false;
 }
 leaf INTERRATHOCDMAB1TIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf OLD_INTERRATHOCDMAHRPDGROUPID {
  type union {
   type int8 {
    range "-1..9";
   }
  }
  mandatory false;
 }
 leaf INTERRATHOCDMAHRPDGROUPID {
  type union {
   type int8 {
    range "-1..9";
   }
  }
  mandatory false;
 }
 leaf OLD_LOCALCELLID {
  type union {
   type int16 {
    range "-1..255";
   }
  }
  mandatory false;
 }
 leaf LOCALCELLID {
  type union {
   type int16 {
    range "-1..255";
   }
  }
  mandatory false;
 }
 }
 grouping INTERRATHOCOMM-attributes {
 leaf CDMA20001XRTTFREQSELMODE {
  type boolean;
  mandatory false;
 }
 leaf CDMA2000HRPDFREQSELMODE {
  type boolean;
  mandatory false;
 }
 leaf CDMAHRPDSECTORIDSELMODE {
  type boolean;
  mandatory false;
 }
 leaf CELLINFOMAXGERANCELLNUM {
  type uint8 {
   range "1..32";
  }
  mandatory false;
 }
 leaf CELLINFOMAXUTRANCELLNUM {
  type uint8 {
   range "1..16";
  }
  mandatory false;
 }
 leaf GERANCELLNUMFOREMCREDIRECT {
  type uint8 {
   range "0..32";
  }
  mandatory false;
 }
 leaf IRATBLINDREDIRPLMNCFGSIMSW {
  type boolean;
  mandatory false;
 }
 leaf INTERRATCDMAHRPDRPRTINTERVAL {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf INTERRATHOA1A2TRIGQUAN {
  type enumeration {
   enum val-0;
   enum val-1;
   enum val-2;
  }
  mandatory false;
 }
 leaf INTERRATHOCDMAHRPDB1MEASQUAN {
  type boolean;
  mandatory false;
 }
 leaf INTERRATHOEVENTTYPE {
  type boolean;
  mandatory false;
 }
 leaf INTERRATHOGERANRPRTINTERVAL {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf INTERRATHOMAXRPRTCELL {
  type uint8 {
   range "1..8";
  }
  mandatory false;
 }
 leaf INTERRATHONREVENTTYPE {
  type boolean;
  mandatory false;
 }
 leaf INTERRATHORPRTAMOUNT {
  type enumeration {
   enum val-0;
   enum val-1;
   enum val-2;
   enum val-3;
   enum val-4;
   enum val-5;
   enum val-6;
   enum val-7;
  }
  mandatory false;
 }
 leaf INTERRATHOUTRANB1MEASQUAN {
  type enumeration {
   enum val-0;
   enum val-1;
   enum val-2;
  }
  mandatory false;
 }
 leaf INTERRATHOUTRANRPRTINTERVAL {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf NRMEASREPORTINGINTERVAL {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf NSADCSANRHONOGAPB1RPTINTVL {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf UTRANCELLNUMFOREMCREDIRECT {
  type uint8 {
   range "0..16";
  }
  mandatory false;
 }
 }
 grouping INTERRATHOCOMMGROUP-attributes {
 leaf LOCALCELLNAME {
  type string;
  mandatory false;
 }
 leaf A2BASEDINTERRATHOTRIGQUAN {
  type enumeration {
   enum val-0;
   enum val-1;
   enum val-2;
  }
  mandatory false;
 }
 leaf DELIFMEASA2THDRSRPOFFSET {
  type int8 {
   range "-20..0";
  }
  mandatory false;
 }
 leaf DELIFMEASA2THDRSRQOFFSET {
  type int8 {
   range "-20..0";
  }
  mandatory false;
 }
 leaf GERANB2THD1RSRP {
  type int16 {
   range "-140..-43";
  }
  mandatory false;
 }
 leaf GERANB2THD1RSRQ {
  type int8 {
   range "-40..-6";
  }
  mandatory false;
 }
 leaf INTERRATHOA1A2HYST {
  type uint8 {
   range "0..30";
  }
  mandatory false;
 }
 leaf INTERRATHOA1A2TIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf INTERRATHOA1THDRSRP {
  type int16 {
   range "-140..-43";
  }
  mandatory false;
 }
 leaf INTERRATHOA1THDRSRQ {
  type int8 {
   range "-40..-6";
  }
  mandatory false;
 }
 leaf INTERRATHOA2THDRSRP {
  type int16 {
   range "-140..-43";
  }
  mandatory false;
 }
 leaf INTERRATHOA2THDRSRQ {
  type int8 {
   range "-40..-6";
  }
  mandatory false;
 }
 leaf OLD_INTERRATHOCOMMGROUPID {
  type union {
   type int8 {
    range "-1..19";
   }
  }
  mandatory false;
 }
 leaf INTERRATHOCOMMGROUPID {
  type union {
   type int8 {
    range "-1..19";
   }
  }
  mandatory false;
 }
 leaf INTERRATHONRA1THLDRSRP {
  type int16 {
   range "-140..-43";
  }
  mandatory false;
 }
 leaf INTERRATHONRA2THLDRSRP {
  type int16 {
   range "-140..-43";
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf NRB2THLD1RSRP {
  type int16 {
   range "-140..-43";
  }
  mandatory false;
 }
 leaf UTRANB2THD1RSRP {
  type int16 {
   range "-140..-43";
  }
  mandatory false;
 }
 leaf UTRANB2THD1RSRQ {
  type int8 {
   range "-40..-6";
  }
  mandatory false;
 }
 }
 grouping INTERRATHOGERANGROUP-attributes {
 leaf LOCALCELLNAME {
  type string;
  mandatory false;
 }
 leaf INTERRATHOGERANB1HYST {
  type uint8 {
   range "0..30";
  }
  mandatory false;
 }
 leaf INTERRATHOGERANB1THD {
  type int8 {
   range "-110..-48";
  }
  mandatory false;
 }
 leaf INTERRATHOGERANB1TIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf OLD_INTERRATHOGERANGROUPID {
  type union {
   type int8 {
    range "-1..19";
   }
  }
  mandatory false;
 }
 leaf INTERRATHOGERANGROUPID {
  type union {
   type int8 {
    range "-1..19";
   }
  }
  mandatory false;
 }
 leaf LDSVBASEDHOGERANB1THD {
  type int8 {
   range "-110..-48";
  }
  mandatory false;
 }
 leaf OLD_LOCALCELLID {
  type union {
   type int16 {
    range "-1..255";
   }
  }
  mandatory false;
 }
 leaf LOCALCELLID {
  type union {
   type int16 {
    range "-1..255";
   }
  }
  mandatory false;
 }
 }
 grouping INTERRATHONRPARAMGRP-attributes {
 leaf LOCALCELLNAME {
  type string;
  mandatory false;
 }
 leaf COVBASEDNRB1RSRPTHLD {
  type int16 {
   range "-156..-31";
  }
  mandatory false;
 }
 leaf COVBASEDNRB1RSRQTHLD {
  type int8 {
   range "-87..40";
  }
  mandatory false;
 }
 leaf FASTRETURNB1TIMETOTRIGGER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf NRB1B2HYSTERESIS {
  type uint8 {
   range "0..30";
  }
  mandatory false;
 }
 leaf NRB1B2TIMETOTRIGGER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf OLD_NRHOPARAMGROUPID {
  type union {
   type int8 {
    range "-1..9";
   }
  }
  mandatory false;
 }
 leaf NRHOPARAMGROUPID {
  type union {
   type int8 {
    range "-1..9";
   }
  }
  mandatory false;
 }
 leaf NSADCSANRHONOGAPB1TTT {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf SERVBASEDNRB1RSRPTHLD {
  type int16 {
   range "-156..-31";
  }
  mandatory false;
 }
 leaf SERVBASEDNRB1RSRQTHLD {
  type int8 {
   range "-87..40";
  }
  mandatory false;
 }
 }
 grouping INTERRATHOUTRANGROUP-attributes {
 leaf LOCALCELLNAME {
  type string;
  mandatory false;
 }
 leaf HSINTERRATHOUTRANB1TIMETRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf INTERRATHOUTRANB1HYST {
  type uint8 {
   range "0..30";
  }
  mandatory false;
 }
 leaf INTERRATHOUTRANB1THDECN0 {
  type int8 {
   range "-48..0";
  }
  mandatory false;
 }
 leaf INTERRATHOUTRANB1THDRSCP {
  type int8 {
   range "-120..-25";
  }
  mandatory false;
 }
 leaf INTERRATHOUTRANB1TIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf OLD_INTERRATHOUTRANGROUPID {
  type union {
   type int8 {
    range "-1..19";
   }
  }
  mandatory false;
 }
 leaf INTERRATHOUTRANGROUPID {
  type union {
   type int8 {
    range "-1..19";
   }
  }
  mandatory false;
 }
 leaf LDSVBASEDHOUTRANB1THDECN0 {
  type int8 {
   range "-48..0";
  }
  mandatory false;
 }
 leaf LDSVBASEDHOUTRANB1THDRSCP {
  type int8 {
   range "-120..-25";
  }
  mandatory false;
 }
 leaf OLD_LOCALCELLID {
  type union {
   type int16 {
    range "-1..255";
   }
  }
  mandatory false;
 }
 leaf LOCALCELLID {
  type union {
   type int16 {
    range "-1..255";
   }
  }
  mandatory false;
 }
 }
 grouping INTERRATPOLICYCFGGROUP-attributes {
 leaf CDMAHRPDHOCFG {
  type string;
  mandatory false;
 }
 leaf GERANGPRSEDGEHOCFG {
  type string;
  mandatory false;
 }
 leaf GERANGSMHOCFG {
  type string;
  mandatory false;
 }
 leaf OLD_INTERRATPOLICYCFGGROUPID {
  type union {
   type int8 {
    range "-1..39";
   }
  }
  mandatory false;
 }
 leaf INTERRATPOLICYCFGGROUPID {
  type union {
   type int8 {
    range "-1..39";
   }
  }
  mandatory false;
 }
 leaf NOHOFLAG {
  type boolean;
  mandatory false;
 }
 leaf NRHOCFG {
  type string;
  mandatory false;
 }
 leaf UTRANHOCFG {
  type string;
  mandatory false;
 }
 }
 grouping INTERVENDORMLBALGO-attributes {
 leaf LOCALCELLNAME {
  type string;
  mandatory false;
 }
 leaf DLCCEUSAGEADMISSIONTHLD {
  type uint8 {
   range "1..100";
  }
  mandatory false;
 }
 leaf DLCCEUSAGEOFFSET {
  type uint8 {
   range "1..100";
  }
  mandatory false;
 }
 leaf DLPRBUSAGEADMISSIONTHLD {
  type uint8 {
   range "1..100";
  }
  mandatory false;
 }
 leaf LOCALCELLID {
  type union {
   type int16 {
    range "-1..255";
   }
  }
  mandatory false;
 }
 leaf MLBENHPARAMADJUSTMENTRANGE {
  type uint8 {
   range "1..6";
  }
  mandatory false;
 }
 leaf MLBENHPARAMROLLBACKEVALPRD {
  type uint8 {
   range "1..180";
  }
  mandatory false;
 }
 leaf PRBUSAGEOFFSET {
  type uint8 {
   range "1..100";
  }
  mandatory false;
 }
 leaf RRCCONNUENUMRATEADMTHLD {
  type uint8 {
   range "1..100";
  }
  mandatory false;
 }
 leaf RRCCONNUENUMRATEOFFSET {
  type uint8 {
   range "1..100";
  }
  mandatory false;
 }
 leaf RRCCONNUENUMRATETRIGTHLD {
  type uint8 {
   range "1..100";
  }
  mandatory false;
 }
 leaf ULCCEUSAGEADMISSIONTHLD {
  type uint8 {
   range "1..100";
  }
  mandatory false;
 }
 leaf ULCCEUSAGEOFFSET {
  type uint8 {
   range "1..100";
  }
  mandatory false;
 }
 leaf ULPRBUSAGEADMISSIONTHLD {
  type uint8 {
   range "1..100";
  }
  mandatory false;
 }
 }
 grouping INTRAFREQBLKCELL-attributes {
 leaf LOCALCELLNAME {
  type string;
  mandatory false;
 }
 leaf APPLICATIONSCOPE {
  type union {
   type uint16 {
    range "0..65535";
   }
  }
  mandatory false;
 }
 leaf CELLNAME {
  type string {
   length "0..99";
  }
  mandatory false;
 }
 leaf LOCALCELLID {
  type union {
   type int16 {
    range "-1..255";
   }
  }
  mandatory false;
 }
 leaf PHYCELLID {
  type union {
   type int16 {
    range "-1..503";
   }
  }
  mandatory false;
 }
 leaf PHYCELLIDRANGE {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 }
 grouping INTRAFREQHOGROUP-attributes {
 leaf LOCALCELLNAME {
  type string;
  mandatory false;
 }
 leaf EMTCHANDOVERA3TIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf HIGHSPEEDA3TIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf INTRAFREQHOA2THLDRSRPCE {
  type int16 {
   range "-140..-43";
  }
  mandatory false;
 }
 leaf INTRAFREQHOA2THLDRSRQCEA {
  type int8 {
   range "-40..-6";
  }
  mandatory false;
 }
 leaf INTRAFREQHOA3HYST {
  type uint8 {
   range "0..30";
  }
  mandatory false;
 }
 leaf INTRAFREQHOA3OFFSET {
  type int8 {
   range "-30..30";
  }
  mandatory false;
 }
 leaf INTRAFREQHOA3TIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf OLD_INTRAFREQHOGROUPID {
  type union {
   type int8 {
    range "-1..19";
   }
  }
  mandatory false;
 }
 leaf INTRAFREQHOGROUPID {
  type union {
   type int8 {
    range "-1..19";
   }
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf MODEAADJA1RSRPTHLD {
  type int16 {
   range "-140..-43";
  }
  mandatory false;
 }
 leaf MODEAADJA2RSRPTHLD {
  type int16 {
   range "-140..-43";
  }
  mandatory false;
 }
 leaf MODEBADJA2RSRPTHLD {
  type int16 {
   range "-140..-43";
  }
  mandatory false;
 }
 leaf NCADJA1RSRPTHLD {
  type int16 {
   range "-140..-43";
  }
  mandatory false;
 }
 }
 grouping INTRARATHOCOMM-attributes {
 leaf A3INTERFREQHOA1A2TRIGQUAN {
  type enumeration {
   enum val-0;
   enum val-1;
   enum val-2;
  }
  mandatory false;
 }
 leaf COVBASEDIFHOWAITINGTIMER {
  type uint16 {
   range "0..5000";
  }
  mandatory false;
 }
 leaf DEDNETWORKPINGPONGAVOIDTMR {
  type uint16 {
   range "0..600";
  }
  mandatory false;
 }
 leaf ECGIMEASSCGREADDWAITTMR {
  type uint8 {
   range "0..10";
  }
  mandatory false;
 }
 leaf FREQPRIHOCANDIDATEUESELPER {
  type uint16 {
   range "0..500";
  }
  mandatory false;
 }
 leaf FREQPRIIFHOWAITINGTIMER {
  type uint8 {
   range "0..30";
  }
  mandatory false;
 }
 leaf FREQPRIINHOPROTECTIONTIMER {
  type uint8 {
   range "0..30";
  }
  mandatory false;
 }
 leaf FREQPRIINTERFREQHOA1TRIGQUAN {
  type enumeration {
   enum val-0;
   enum val-1;
   enum val-2;
  }
  mandatory false;
 }
 leaf INTERFREQHOA1A2TRIGQUAN {
  type enumeration {
   enum val-0;
   enum val-1;
   enum val-2;
  }
  mandatory false;
 }
 leaf INTERFREQHOA4RPRTQUAN {
  type boolean;
  mandatory false;
 }
 leaf INTERFREQHOA4TRIGQUAN {
  type enumeration {
   enum val-0;
   enum val-1;
   enum val-2;
  }
  mandatory false;
 }
 leaf INTERFREQHORPRTINTERVAL {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf INTRAFREQHOA3RPRTQUAN {
  type boolean;
  mandatory false;
 }
 leaf INTRAFREQHOA3TRIGQUAN {
  type boolean;
  mandatory false;
 }
 leaf INTRAFREQHORPRTINTERVAL {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf INTRARATHOA1A2TRIGQUANCE {
  type boolean;
  mandatory false;
 }
 leaf INTRARATHOMAXRPRTCELL {
  type uint8 {
   range "1..8";
  }
  mandatory false;
 }
 leaf INTRARATHORPRTAMOUNT {
  type enumeration {
   enum val-0;
   enum val-1;
   enum val-2;
   enum val-3;
   enum val-4;
   enum val-5;
   enum val-6;
   enum val-7;
  }
  mandatory false;
 }
 leaf MAXNUMHOFWDPDCPPKTWITHSN {
  type uint16 {
   range "1..2000";
  }
  mandatory false;
 }
 leaf STUEDSSFLEXREFARMRSRPOFS {
  type uint8 {
   range "0..30";
  }
  mandatory false;
 }
 }
 grouping IOPSCFG-attributes {
 leaf ENTERIOPSTHD {
  type uint16 {
   range "0..300";
  }
  mandatory false;
 }
 leaf EXITIOPSTHD {
  type uint16 {
   range "0..300";
  }
  mandatory false;
 }
 leaf IOPSSWITCH {
  type boolean;
  mandatory false;
 }
 }
 grouping IPSERVICEQOS-attributes {
 leaf APPLICATIONRANGE {
  type string;
  mandatory false;
 }
 leaf DESCRIPTION {
  type string {
   length "0..64";
  }
  mandatory false;
 }
 leaf OLD_DSCP {
  type union {
   type int8 {
    range "-1..63";
   }
  }
  mandatory false;
 }
 leaf DSCP {
  type union {
   type int8 {
    range "-1..63";
   }
  }
  mandatory false;
 }
 leaf FIRQOSPOLICYID {
  type union {
   type uint8 {
    range "0..255";
   }
  }
  mandatory false;
 }
 leaf FIRQOSPOLICYTIMELENGTH {
  type uint16 {
   range "0..65535";
  }
  mandatory false;
 }
 leaf QOSPOLICYTIMESWITCH {
  type boolean;
  mandatory false;
 }
 leaf SECQOSPOLICYID {
  type union {
   type uint8 {
    range "0..255";
   }
  }
  mandatory false;
 }
 }
 grouping IRATNCELLCLASSMGT-attributes {
 leaf NCELLMEASNUMTHD {
  type uint16 {
   range "0..10000";
  }
  mandatory false;
 }
 leaf RATTYPE {
  type enumeration {
   enum val--1;
   enum val-0;
   enum val-1;
  }
  mandatory false;
 }
 leaf STATPERIODFORNCELLCLASS {
  type uint16 {
   range "1..50400";
  }
  mandatory false;
 }
 }
 grouping LAAEXTERNALCELL-attributes {
 leaf CELLID {
  type union {
   type int16 {
    range "-1..255";
   }
  }
  mandatory false;
 }
 leaf ENODEBID {
  type union {
   type int32 {
    range "-1..1048575";
   }
  }
  mandatory false;
 }
 leaf MCC {
  type string {
   length "3";
  }
  mandatory false;
 }
 leaf MNC {
  type string {
   length "2..3";
  }
  mandatory false;
 }
 leaf TAC {
  type uint16 {
   range "0..65535";
  }
  mandatory false;
 }
 }
 grouping LICENSESHARINGPOLICY-attributes {
 leaf CNOPERATORID {
  type union {
   type int8 {
    range "-1..5";
   }
  }
  mandatory false;
 }
 leaf MAXUSERNUMRATE {
  type uint8 {
   range "1..100";
  }
  mandatory false;
 }
 leaf USERNUMSHARINGGROUPID {
  type union {
   type uint8 {
    range "1..255";
   }
  }
  mandatory false;
 }
 leaf USERNUMSHARINGRATE {
  type uint8 {
   range "0..100";
  }
  mandatory false;
 }
 }
 grouping LICRATIOSHAREPOLICY-attributes {
 leaf CNOPERATORID {
  type union {
   type int8 {
    range "-1..5";
   }
  }
  mandatory false;
 }
 leaf TRFRATIO {
  type uint8 {
   range "0..100";
  }
  mandatory false;
 }
 leaf TRFSHARINGRATIO {
  type uint8 {
   range "0..100";
  }
  mandatory false;
 }
 }
 grouping LIOPTATOMRULE-attributes {
 leaf ATOMRULEID {
  type union {
   type int32 {
    range "-1..65535";
   }
  }
  mandatory false;
 }
 leaf CONDITIONTYPE {
  type enumeration {
   enum val-0;
   enum val-1;
   enum val-2;
   enum val-3;
   enum val-4;
   enum val-5;
  }
  mandatory false;
 }
 leaf MEASUREOBJTYPE {
  type boolean;
  mandatory false;
 }
 leaf MEASUREOBJECT {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf THRESHOLDFORNUMPARA {
  type int32 {
   range "-2147483647..2147483647";
  }
  mandatory false;
 }
 }
 grouping LIOPTFEATURE-attributes {
 leaf IOPTFEATUREID {
  type union {
   type int32 {
    range "-1..65535";
   }
  }
  mandatory false;
 }
 leaf IOPTFEATURENAME {
  type string {
   length "0..64";
  }
  mandatory false;
 }
 }
 grouping LIOPTFUNCTION-attributes {
 leaf IOPTFEATUREID {
  type uint16 {
   range "0..65535";
  }
  mandatory false;
 }
 leaf IOPTFUNCTIONID {
  type union {
   type int32 {
    range "-1..65535";
   }
  }
  mandatory false;
 }
 leaf IOPTFUNCTIONNAME {
  type string {
   length "0..64";
  }
  mandatory false;
 }
 leaf MEASUREOBJTYPE {
  type boolean;
  mandatory false;
 }
 }
 grouping LIOPTRULE-attributes {
 leaf ACTION {
  type string {
   length "0..500";
  }
  mandatory false;
 }
 leaf ACTIONTYPE {
  type boolean;
  mandatory false;
 }
 leaf ACTIVESTATUS {
  type boolean;
  mandatory false;
 }
 leaf ADAPTIVERAT {
  type enumeration {
   enum val-0;
   enum val-1;
   enum val-2;
  }
  mandatory false;
 }
 leaf ATOMRULERELATIONTYPE {
  type boolean;
  mandatory false;
 }
 leaf IOPTFUNCTIONID {
  type uint16 {
   range "0..65535";
  }
  mandatory false;
 }
 leaf PENALTYTIME {
  type uint16 {
   range "0..65535";
  }
  mandatory false;
 }
 leaf PERIOD {
  type uint16 {
   range "0..65535";
  }
  mandatory false;
 }
 leaf RULEID {
  type union {
   type int32 {
    range "-1..65535";
   }
  }
  mandatory false;
 }
 }
 grouping LIOPTRULEMEMBER-attributes {
 leaf ACTIVESTATUS {
  type boolean;
  mandatory false;
 }
 leaf ATOMRULEID {
  type union {
   type int32 {
    range "-1..65535";
   }
  }
  mandatory false;
 }
 leaf RULEID {
  type union {
   type int32 {
    range "-1..65535";
   }
  }
  mandatory false;
 }
 }
 grouping LNRCARRIERSELECTION-attributes {
 leaf INTRAFREQMEASA3TIMETOTRIG {
  type enumeration {
   enum val-0;
   enum val-1;
   enum val-2;
   enum val-3;
   enum val-4;
   enum val-5;
   enum val-6;
   enum val-7;
   enum val-8;
  }
  mandatory false;
 }
 leaf LNRCARRIERSELECTIONSW {
  type string;
  mandatory false;
 }
 leaf PREDUNNECNRHOMEASRSRPTHLD {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf PROBMDLBADPOINTTHLD {
  type uint8 {
   range "0..99";
  }
  mandatory false;
 }
 leaf PROBMDLGOODPOINTTHLD {
  type uint8 {
   range "1..100";
  }
  mandatory false;
 }
 leaf SAMPLEUENUM {
  type enumeration {
   enum val-0;
   enum val-1;
   enum val-2;
  }
  mandatory false;
 }
 leaf VGMDLHOSUCCRATETHLD {
  type uint8 {
   range "0..100";
  }
  mandatory false;
 }
 leaf VGMDLKPIMONITORTHLD {
  type uint8 {
   range "0..100";
  }
  mandatory false;
 }
 leaf VGMDLMAXBUILDDURATION {
  type union {
   type uint8 {
    range "0..28";
   }
  }
  mandatory false;
 }
 leaf VGMDLPREDNRSCGMEASRSRPTHLD {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 }
 grouping LNRFREQCOMB-attributes {
 leaf OLD_DLEARFCN {
  type union {
   type int32 {
    range "-1..229575";
   }
  }
  mandatory false;
 }
 leaf DLEARFCN {
  type union {
   type int32 {
    range "-1..229575";
   }
  }
  mandatory false;
 }
 leaf OLD_DLNRARFCN {
  type union {
   type int32 {
    range "-1..3279165";
   }
  }
  mandatory false;
 }
 leaf DLNRARFCN {
  type union {
   type int32 {
    range "-1..3279165";
   }
  }
  mandatory false;
 }
 leaf FREQCOMBID {
  type uint8 {
   range "0..31";
  }
  mandatory false;
 }
 }
 grouping LNRFREQRELATIONSHIP-attributes {
 leaf DLEARFCN {
  type union {
   type uint32 {
    range "0..229575";
   }
  }
  mandatory false;
 }
 leaf FREQRELATIONSHIP {
  type enumeration {
   enum val-0;
   enum val-1;
   enum val-2;
   enum val-3;
   enum val-4;
   enum val-5;
  }
  mandatory false;
 }
 leaf NRDLARFCN {
  type uint32 {
   range "0..3279165";
  }
  mandatory false;
 }
 leaf NRDLBANDWIDTH {
  type string;
  mandatory false;
 }
 leaf OLD_RELATIONSHIPID {
  type union {
   type int8 {
    range "-1..127";
   }
  }
  mandatory false;
 }
 leaf RELATIONSHIPID {
  type union {
   type int8 {
    range "-1..127";
   }
  }
  mandatory false;
 }
 }
 grouping LTENRSPCTSHRCELLGRP-attributes {
 leaf COMMONUEREVRESRATIO {
  type enumeration {
   enum val-0;
   enum val-1;
   enum val-2;
   enum val-3;
   enum val-4;
   enum val-5;
  }
  mandatory false;
 }
 leaf CRSOVERHEADOPTTHLD {
  type uint8 {
   range "1..10";
  }
  mandatory false;
 }
 leaf DSSFLEXREFARMGRPID {
  type union {
   type uint8 {
    range "0..255";
   }
  }
  mandatory false;
 }
 leaf DSSFLEXREFARMPOLICY {
  type boolean;
  mandatory false;
 }
 leaf DSSPDCCHSHROPTPRBUSAGETHLD {
  type uint8 {
   range "0..100";
  }
  mandatory false;
 }
 leaf LTEBIGEVENTUENUMTHLD {
  type uint16 {
   range "0..1200";
  }
  mandatory false;
 }
 leaf LTEBIGEVENTUENUMTHLDOFFSET {
  type uint16 {
   range "0..600";
  }
  mandatory false;
 }
 leaf LTECRSSYM1PWRREDUCEFACTOR {
  type enumeration {
   enum val-0;
   enum val-1;
   enum val-2;
  }
  mandatory false;
 }
 leaf LTEGUARANTEEPUSCHRBNUM {
  type uint8 {
   range "0..100";
  }
  mandatory false;
 }
 leaf LTENRCOCARRCOCPRIDATASW {
  type boolean;
  mandatory false;
 }
 leaf LTENRPRBUSAGEDIFFTHLD {
  type uint8 {
   range "0..100";
  }
  mandatory false;
 }
 leaf LTENRSPCTHOPROTDURATION {
  type uint8 {
   range "1..120";
  }
  mandatory false;
 }
 leaf LTENRSPCTSHRLTEPRIRESRATIO {
  type uint8 {
   range "0..100";
  }
  mandatory false;
 }
 leaf LTENRSPCTSHRSWITCH {
  type string;
  mandatory false;
 }
 leaf LTENRSPECTSHRUENUMTHLD {
  type uint16 {
   range "0..300";
  }
  mandatory false;
 }
 leaf LTENRSPECTRUMSHRCELLGRPID {
  type union {
   type int8 {
    range "-1..23";
   }
  }
  mandatory false;
 }
 leaf LTENRULSPECTRUMSHRPRIORITY {
  type enumeration {
   enum val-0;
   enum val-1;
   enum val-2;
  }
  mandatory false;
 }
 leaf LTEPDCCHAVAILCCENUMUPPRLMT {
  type union {
   type uint8 {
    range "8..255";
   }
  }
  mandatory false;
 }
 leaf LTEPDCCHSYM2PSDRDCFACTOR {
  type enumeration {
   enum val-0;
   enum val-1;
   enum val-2;
   enum val-3;
  }
  mandatory false;
 }
 leaf LTEPDCCHSYM2PSDTHLD {
  type uint8 {
   range "0..30";
  }
  mandatory false;
 }
 leaf NRGUARANTEEPUSCHRBNUM {
  type uint8 {
   range "0..100";
  }
  mandatory false;
 }
 leaf PRBUSAGETHLD {
  type uint8 {
   range "0..80";
  }
  mandatory false;
 }
 leaf PRBUSAGETHLDOFFSET {
  type uint8 {
   range "0..30";
  }
  mandatory false;
 }
 leaf RRCCONNNSACAPBUENUMTHLD {
  type uint8 {
   range "0..200";
  }
  mandatory false;
 }
 leaf RRCCONNNSACAPBUENUMTHLDOFS {
  type uint8 {
   range "0..100";
  }
  mandatory false;
 }
 leaf RRCCONNUENUMTHLD {
  type uint16 {
   range "0..300";
  }
  mandatory false;
 }
 leaf RRCCONNUENUMTHLDOFFSET {
  type uint8 {
   range "0..150";
  }
  mandatory false;
 }
 leaf ULPRBUSAGETHLD {
  type uint8 {
   range "20..80";
  }
  mandatory false;
 }
 leaf ULPRBUSAGETHLDOFFSET {
  type uint8 {
   range "0..30";
  }
  mandatory false;
 }
 }
 grouping LTESPSGRP-attributes {
 leaf LTESPSAVGPRD {
  type uint32 {
   range "1..86400";
  }
  mandatory false;
 }
 leaf OLD_LTESPSGRPID {
  type union {
   type int32 {
    range "-1..65534";
   }
  }
  mandatory false;
 }
 leaf LTESPSGRPID {
  type union {
   type int32 {
    range "-1..65534";
   }
  }
  mandatory false;
 }
 leaf SPSALGOSWITCH {
  type string;
  mandatory false;
 }
 leaf SPSTYPE {
  type boolean;
  mandatory false;
 }
 }
 grouping LWAMGTCFG-attributes {
 leaf LOCALCELLNAME {
  type string;
  mandatory false;
 }
 leaf CELLLWAALGOSWITCH {
  type string;
  mandatory false;
 }
 leaf LOCALCELLID {
  type union {
   type int16 {
    range "-1..255";
   }
  }
  mandatory false;
 }
 leaf LTEWLANAGGRW1THDRSSI {
  type int8 {
   range "-100..39";
  }
  mandatory false;
 }
 leaf LTEWLANAGGRW2THD1RSSI {
  type int8 {
   range "-100..39";
  }
  mandatory false;
 }
 leaf LTEWLANAGGRW3THDRSSI {
  type int8 {
   range "-100..39";
  }
  mandatory false;
 }
 leaf LWAW1TIMETOTRIGGER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf LWAW2TIMETOTRIGGER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf LWAW3TIMETOTRIGGER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf WLANMEASHYST {
  type uint8 {
   range "0..30";
  }
  mandatory false;
 }
 }
 grouping M1-attributes {
 leaf M1EPGROUPID {
  type uint16 {
   range "0..65535";
  }
  mandatory false;
 }
 leaf OLD_M1ID {
  type union {
   type int8 {
    range "-1..1";
   }
  }
  mandatory false;
 }
 leaf M1ID {
  type union {
   type int8 {
    range "-1..1";
   }
  }
  mandatory false;
 }
 leaf M1NETWORKTYPE {
  type boolean;
  mandatory false;
 }
 leaf USERLABEL {
  type string {
   length "0..256";
  }
  mandatory false;
 }
 }
 grouping M2-attributes {
 leaf M2EPGROUPID {
  type uint16 {
   range "0..65535";
  }
  mandatory false;
 }
 leaf OLD_M2ID {
  type union {
   type int8 {
    range "-1..1";
   }
  }
  mandatory false;
 }
 leaf M2ID {
  type union {
   type int8 {
    range "-1..1";
   }
  }
  mandatory false;
 }
 leaf M2NETWORKTYPE {
  type boolean;
  mandatory false;
 }
 leaf USERLABEL {
  type string {
   length "0..256";
  }
  mandatory false;
 }
 }
 grouping M3-attributes {
 leaf INTERFACESETUPINITIND {
  type boolean;
  mandatory false;
 }
 leaf OLD_LOCALMCEID {
  type union {
   type int8 {
    range "-1..5";
   }
  }
  mandatory false;
 }
 leaf LOCALMCEID {
  type union {
   type int8 {
    range "-1..5";
   }
  }
  mandatory false;
 }
 leaf M3ENDPOINTGROUPID {
  type uint16 {
   range "0..65535";
  }
  mandatory false;
 }
 leaf OLD_M3ID {
  type union {
   type int8 {
    range "-1..5";
   }
  }
  mandatory false;
 }
 leaf M3ID {
  type union {
   type int8 {
    range "-1..5";
   }
  }
  mandatory false;
 }
 leaf MCC {
  type string {
   length "3";
  }
  mandatory false;
 }
 leaf MNC {
  type string {
   length "2..3";
  }
  mandatory false;
 }
 }
 grouping MBMSPARA-attributes {
 leaf M2DISCONNPROTECTTIME {
  type uint16 {
   range "1..1440";
  }
  mandatory false;
 }
 leaf MBMSCTRLSWITCH {
  type string;
  mandatory false;
 }
 leaf SYNCPERIOD {
  type uint8 {
   range "1..58";
  }
  mandatory false;
 }
 }
 grouping MBSFNAREA-attributes {
 leaf COMMONSUBFRAMEALLOCPERIOD {
  type enumeration {
   enum val-0;
   enum val-1;
   enum val-2;
   enum val-3;
   enum val-4;
   enum val-5;
   enum val-6;
  }
  mandatory false;
 }
 leaf DOWNLINKBANDWIDTH {
  type enumeration {
   enum val-0;
   enum val-1;
   enum val-2;
   enum val-3;
  }
  mandatory false;
 }
 leaf FDDTDDIND {
  type boolean;
  mandatory false;
 }
 leaf OLD_LOCALMCEID {
  type union {
   type int8 {
    range "-1..5";
   }
  }
  mandatory false;
 }
 leaf LOCALMCEID {
  type union {
   type int8 {
    range "-1..5";
   }
  }
  mandatory false;
 }
 leaf OLD_MBSFNAREAID {
  type union {
   type int16 {
    range "-1..255";
   }
  }
  mandatory false;
 }
 leaf MBSFNAREAID {
  type union {
   type int16 {
    range "-1..255";
   }
  }
  mandatory false;
 }
 leaf ULDLSUBFRAMECONFIG {
  type enumeration {
   enum val-0;
   enum val-1;
   enum val-2;
   enum val-3;
   enum val-4;
   enum val-5;
   enum val-6;
  }
  mandatory false;
 }
 }
 grouping MBSFNAREACELL-attributes {
 leaf OLD_CELLID {
  type union {
   type int16 {
    range "-1..255";
   }
  }
  mandatory false;
 }
 leaf CELLID {
  type union {
   type int16 {
    range "-1..255";
   }
  }
  mandatory false;
 }
 leaf OLD_ENODEBID {
  type union {
   type int32 {
    range "-1..1048575";
   }
  }
  mandatory false;
 }
 leaf ENODEBID {
  type union {
   type int32 {
    range "-1..1048575";
   }
  }
  mandatory false;
 }
 leaf OLD_LOCALMCEID {
  type union {
   type int8 {
    range "-1..5";
   }
  }
  mandatory false;
 }
 leaf LOCALMCEID {
  type union {
   type int8 {
    range "-1..5";
   }
  }
  mandatory false;
 }
 leaf OLD_MBSFNAREAID {
  type union {
   type int16 {
    range "-1..255";
   }
  }
  mandatory false;
 }
 leaf MBSFNAREAID {
  type union {
   type int16 {
    range "-1..255";
   }
  }
  mandatory false;
 }
 leaf MCC {
  type string {
   length "3";
  }
  mandatory false;
 }
 leaf MNC {
  type string {
   length "2..3";
  }
  mandatory false;
 }
 leaf RESERVEDCELLINDICATION {
  type boolean;
  mandatory false;
 }
 }
 grouping MBSFNSUBFRAME-attributes {
 leaf FOURFRAMEALLOCATION {
  type uint32 {
   range "0..16777215";
  }
  mandatory false;
 }
 leaf OLD_LOCALMCEID {
  type union {
   type int8 {
    range "-1..5";
   }
  }
  mandatory false;
 }
 leaf LOCALMCEID {
  type union {
   type int8 {
    range "-1..5";
   }
  }
  mandatory false;
 }
 leaf OLD_MBSFNAREAID {
  type union {
   type int8 {
    range "-1..71";
   }
  }
  mandatory false;
 }
 leaf MBSFNAREAID {
  type union {
   type int8 {
    range "-1..71";
   }
  }
  mandatory false;
 }
 leaf OLD_MBSFNSFCONFIGID {
  type union {
   type int8 {
    range "-1..7";
   }
  }
  mandatory false;
 }
 leaf MBSFNSFCONFIGID {
  type union {
   type int8 {
    range "-1..7";
   }
  }
  mandatory false;
 }
 leaf ONEFRAMEALLOCATION {
  type uint8 {
   range "0..63";
  }
  mandatory false;
 }
 leaf RADIOFRAMEALLOCOFS {
  type uint8 {
   range "0..7";
  }
  mandatory false;
 }
 leaf RADIOFRAMEALLOCPRD {
  type enumeration {
   enum val-0;
   enum val-1;
   enum val-2;
   enum val-3;
   enum val-4;
   enum val-5;
  }
  mandatory false;
 }
 leaf SUBFRAMEALLOCATIONMODE {
  type boolean;
  mandatory false;
 }
 }
 grouping MCCH-attributes {
 leaf LOCALMCEID {
  type union {
   type int8 {
    range "-1..5";
   }
  }
  mandatory false;
 }
 leaf MBSFNAREAID {
  type union {
   type int16 {
    range "-1..255";
   }
  }
  mandatory false;
 }
 leaf MCS {
  type enumeration {
   enum val-0;
   enum val-1;
   enum val-2;
   enum val-3;
  }
  mandatory false;
 }
 leaf MODIFICATIONPERIOD {
  type boolean;
  mandatory false;
 }
 leaf PDCCHLENGTH {
  type boolean;
  mandatory false;
 }
 leaf REPETITIONPERIOD {
  type enumeration {
   enum val-0;
   enum val-1;
   enum val-2;
   enum val-3;
  }
  mandatory false;
 }
 leaf REPETITIONPERIODOFFSET {
  type uint8 {
   range "0..10";
  }
  mandatory false;
 }
 leaf SUBFRAMEALLOCATIONINFO {
  type uint8 {
   range "0..63";
  }
  mandatory false;
 }
 }
 grouping MCE-attributes {
 leaf OLD_LOCALMCEID {
  type union {
   type int8 {
    range "-1..5";
   }
  }
  mandatory false;
 }
 leaf LOCALMCEID {
  type union {
   type int8 {
    range "-1..5";
   }
  }
  mandatory false;
 }
 leaf MCEID {
  type uint32 {
   range "0..16777215";
  }
  mandatory false;
 }
 leaf MCENAME {
  type string {
   length "1..150";
  }
  mandatory false;
 }
 leaf MCETYPE {
  type string;
  mandatory false;
 }
 }
 grouping MLBQCIGROUP-attributes {
 leaf DLMINQOSBITRATE {
  type uint16 {
   range "0..50000";
  }
  mandatory false;
 }
 leaf OLD_MLBQCIGROUPID {
  type union {
   type int8 {
    range "-1..9";
   }
  }
  mandatory false;
 }
 leaf MLBQCIGROUPID {
  type union {
   type int8 {
    range "-1..9";
   }
  }
  mandatory false;
 }
 leaf ULMINQOSBITRATE {
  type uint16 {
   range "0..50000";
  }
  mandatory false;
 }
 }
 grouping MMECAPINFO-attributes {
 leaf OLD_MMECAPCFGID {
  type union {
   type int8 {
    range "-1..63";
   }
  }
  mandatory false;
 }
 leaf MMECAPCFGID {
  type union {
   type int8 {
    range "-1..63";
   }
  }
  mandatory false;
 }
 leaf MMENSADCCAPABILITY {
  type boolean;
  mandatory false;
 }
 leaf MMESUPPORTEMTCDEDEPCCAP {
  type boolean;
  mandatory false;
 }
 leaf NBCIOTEPSOPTCAP {
  type enumeration {
   enum val-0;
   enum val-1;
   enum val-2;
  }
  mandatory false;
 }
 leaf NBLTESUPPORTCAP {
  type boolean;
  mandatory false;
 }
 leaf S1CFGTYPE {
  type boolean;
  mandatory false;
 }
 leaf S1ID {
  type uint8 {
   range "0..63";
  }
  mandatory false;
 }
 leaf S1INTERFACEID {
  type uint16 {
   range "0..65534";
  }
  mandatory false;
 }
 }
 grouping MMEDOMAINNAME-attributes {
 leaf CNOPERATORID {
  type uint8 {
   range "0..5";
  }
  mandatory false;
 }
 leaf MMEDOMNAME {
  type string {
   length "1..127";
  }
  mandatory false;
 }
 leaf OLD_MMEDOMNAMEID {
  type union {
   type int8 {
    range "-1..63";
   }
  }
  mandatory false;
 }
 leaf MMEDOMNAMEID {
  type union {
   type int8 {
    range "-1..63";
   }
  }
  mandatory false;
 }
 }
 grouping MMEFEATURECFG-attributes {
 leaf CTRLMODE {
  type boolean;
  mandatory false;
 }
 leaf MDTENABLE {
  type boolean;
  mandatory false;
 }
 leaf S1INTERFACEID {
  type union {
   type int32 {
    range "-1..65534";
   }
  }
  mandatory false;
 }
 }
 grouping MRO-attributes {
 leaf COVERABNORMALTHD {
  type uint8 {
   range "0..100";
  }
  mandatory false;
 }
 leaf INTERFREQA2ROLLBACKPERIOD {
  type uint8 {
   range "1..30";
  }
  mandatory false;
 }
 leaf INTERFREQA2ROLLBACKTHD {
  type uint8 {
   range "0..100";
  }
  mandatory false;
 }
 leaf INTERFREQMEASTOOLATEHOTHD {
  type uint8 {
   range "0..100";
  }
  mandatory false;
 }
 leaf INTERRATA2RSRPMINTHD {
  type int16 {
   range "-141..-43";
  }
  mandatory false;
 }
 leaf INTERRATABNORMALHORATIOTHD {
  type uint8 {
   range "0..100";
  }
  mandatory false;
 }
 leaf INTERRATMEASTOOLATEHOTHD {
  type uint8 {
   range "0..100";
  }
  mandatory false;
 }
 leaf INTERRATSTATNUMTHD {
  type uint16 {
   range "0..10000";
  }
  mandatory false;
 }
 leaf INTRARATABNORMALRATIOTHD {
  type uint8 {
   range "0..100";
  }
  mandatory false;
 }
 leaf INTRARATHOTOOEARLYTIMETHD {
  type uint8 {
   range "1..60";
  }
  mandatory false;
 }
 leaf INTRARATTOOEARLYHORATIOTHD {
  type uint8 {
   range "0..100";
  }
  mandatory false;
 }
 leaf INTRARATTOOLATEHORATIOTHD {
  type uint8 {
   range "0..100";
  }
  mandatory false;
 }
 leaf MROOPTMODE {
  type boolean;
  mandatory false;
 }
 leaf NCELLOPTTHD {
  type uint8 {
   range "0..100";
  }
  mandatory false;
 }
 leaf NEIGHBORRSRPTHD {
  type int16 {
   range "-140..-44";
  }
  mandatory false;
 }
 leaf OPTPERIOD {
  type uint32 {
   range "1..70000";
  }
  mandatory false;
 }
 leaf PINGPONGRATIOTHD {
  type uint8 {
   range "0..100";
  }
  mandatory false;
 }
 leaf PINGPONGTIMETHD {
  type uint8 {
   range "1..60";
  }
  mandatory false;
 }
 leaf SERVINGRSRPTHD {
  type int16 {
   range "-140..-44";
  }
  mandatory false;
 }
 leaf STATNUMTHD {
  type uint16 {
   range "0..10000";
  }
  mandatory false;
 }
 leaf UEPINGPONGNUMTHD {
  type uint8 {
   range "1..7";
  }
  mandatory false;
 }
 leaf UNNECINTERRATHOMEASTIME {
  type uint8 {
   range "0..100";
  }
  mandatory false;
 }
 leaf UNNECINTERRATHOOPTTHD {
  type uint8 {
   range "0..100";
  }
  mandatory false;
 }
 leaf UNNECINTERRATHORATIOTHD {
  type uint8 {
   range "0..100";
  }
  mandatory false;
 }
 leaf UNNECINTERRATHORSRPTHD {
  type int16 {
   range "-140..-44";
  }
  mandatory false;
 }
 }
 grouping MULTIBAND-attributes {
 leaf LOCALCELLNAME {
  type string;
  mandatory false;
 }
 leaf FREQBAND {
  type union {
   type int16 {
    range "-1..256";
   }
  }
  mandatory false;
 }
 leaf LOCALCELLID {
  type union {
   type int16 {
    range "-1..255";
   }
  }
  mandatory false;
 }
 }
 grouping MULTICARRUNIFIEDSCH-attributes {
 leaf BANDWIDTHHYSTERESIS {
  type union {
   type uint8 {
    range "0..255";
   }
  }
  mandatory false;
 }
 leaf CARRIERCAPABILITYHYSTERESIS {
  type uint8 {
   range "0..100";
  }
  mandatory false;
 }
 leaf FASTMOVEUEDLBIGPKTBWTHLD {
  type uint16 {
   range "0..4096";
  }
  mandatory false;
 }
 leaf FASTMOVEUEDLCOMPKTBWTHLD {
  type uint16 {
   range "0..4096";
  }
  mandatory false;
 }
 leaf FASTMOVEUEULBIGPKTBWTHLD {
  type uint16 {
   range "0..4096";
  }
  mandatory false;
 }
 leaf FASTMOVINGUECARRCAPBHYST {
  type uint8 {
   range "0..100";
  }
  mandatory false;
 }
 leaf FASTMOVINGUEGUARANTEETIMER {
  type uint16 {
   range "2..1440";
  }
  mandatory false;
 }
 leaf FASTMOVINGUEULCARRCAPBHYST {
  type uint8 {
   range "0..100";
  }
  mandatory false;
 }
 leaf FSSPRBRATIOTHLD {
  type uint8 {
   range "0..30";
  }
  mandatory false;
 }
 leaf GFACTORTHLDFORHOTRGCELL {
  type union {
   type int16 {
    range "-150..32767";
   }
  }
  mandatory false;
 }
 leaf GFACTORTHLDFORLOWFREQHOTRG {
  type union {
   type int16 {
    range "-150..32767";
   }
  }
  mandatory false;
 }
 leaf INTRAFREQMEASA3TIMETOTRIG {
  type enumeration {
   enum val-0;
   enum val-1;
   enum val-2;
   enum val-3;
   enum val-4;
   enum val-5;
   enum val-6;
   enum val-7;
   enum val-8;
  }
  mandatory false;
 }
 leaf LNRSCHPRIADJTIMEOFFSET {
  type int8 {
   range "-30..30";
  }
  mandatory false;
 }
 leaf MULTICARRUNIFIEDSCHOPTSW {
  type string;
  mandatory false;
 }
 leaf MULTICARRIERUNIFIEDSCHENSW {
  type string;
  mandatory false;
 }
 leaf MULTICARRIERUNIFIEDSCHSW {
  type string;
  mandatory false;
 }
 leaf PREBALANCINGLOADRATIOTHLD {
  type union {
   type uint8 {
    range "10..255";
   }
  }
  mandatory false;
 }
 leaf PREDICTIVECAPBGAINTHLD {
  type uint8 {
   range "0..100";
  }
  mandatory false;
 }
 leaf SERVICEDROPRATECFGPOLICY {
  type boolean;
  mandatory false;
 }
 leaf SERVICEDROPRATETARGET {
  type uint16 {
   range "0..20000";
  }
  mandatory false;
 }
 leaf ULCARRIERCAPABILITYHYST {
  type uint8 {
   range "0..100";
  }
  mandatory false;
 }
 leaf VGMDLPREDNECHOMEASRSRPTHLD {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf VGMODELPREDHOMEASRSRPTHLD {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf VGMODELPREDSCCMEASRSRPTHLD {
  type enumeration {
   enum val-0;
   enum val-1;
   enum val-2;
   enum val-3;
   enum val-4;
   enum val-5;
   enum val-6;
  }
  mandatory false;
 }
 }
 grouping NBCELLDYNPWRSHRPARA-attributes {
 leaf LOCALCELLNAME {
  type string;
  mandatory false;
 }
 leaf DLPRBUSAGETHLD {
  type uint8 {
   range "0..30";
  }
  mandatory false;
 }
 leaf ENDTIME {
  type hwat:HH_MM_SS_Time;
  mandatory false;
 }
 leaf LOCALCELLID {
  type union {
   type int16 {
    range "-1..255";
   }
  }
  mandatory false;
 }
 leaf STARTTIME {
  type hwat:HH_MM_SS_Time;
  mandatory false;
 }
 }
 grouping NBCELLMULTIPRBCONFIG-attributes {
 leaf LOCALCELLNAME {
  type string;
  mandatory false;
 }
 leaf LOCALCELLID {
  type union {
   type int16 {
    range "-1..255";
   }
  }
  mandatory false;
 }
 leaf MULTICARRIEROPTSWITCH {
  type string;
  mandatory false;
 }
 leaf NBMPRURFCARRIERSTRATEGY {
  type boolean;
  mandatory false;
 }
 leaf NBRFCARRIERSTRATEGY {
  type enumeration {
   enum val-0;
   enum val-1;
   enum val-2;
  }
  mandatory false;
 }
 leaf PRBDLSCUSAGEDIFFTHLD {
  type uint8 {
   range "0..100";
  }
  mandatory false;
 }
 leaf PRBDLSUBCARRIERUSAGETHLD {
  type uint8 {
   range "0..100";
  }
  mandatory false;
 }
 leaf PRBUENUMBEROFFSET {
  type uint16 {
   range "0..10000";
  }
  mandatory false;
 }
 leaf PRBULSCUSAGEDIFFTHLD {
  type uint8 {
   range "0..100";
  }
  mandatory false;
 }
 leaf PRBULSUBCARRIERUSAGETHLD {
  type uint8 {
   range "0..100";
  }
  mandatory false;
 }
 }
 grouping NBPRBDYNAMICMGMT-attributes {
 leaf LOCALCELLNAME {
  type string;
  mandatory false;
 }
 leaf LOCALCELLID {
  type union {
   type int16 {
    range "-1..255";
   }
  }
  mandatory false;
 }
 leaf NBDLSUBCARRIERUSAGEOFFSET {
  type uint8 {
   range "0..100";
  }
  mandatory false;
 }
 leaf NBDLSUBCARRIERUSAGETHLD {
  type uint8 {
   range "20..100";
  }
  mandatory false;
 }
 leaf NBLOADESTIMATIONPERIOD {
  type uint16 {
   range "10..300";
  }
  mandatory false;
 }
 leaf NBPRACHSUBCARRIERUSAGETHLD {
  type uint8 {
   range "20..100";
  }
  mandatory false;
 }
 leaf NBPRBDYNMGMTALGOSW {
  type string;
  mandatory false;
 }
 leaf NBULSUBCARRIERUSAGEOFFSET {
  type uint8 {
   range "0..100";
  }
  mandatory false;
 }
 leaf NBULSUBCARRIERUSAGETHLD {
  type uint8 {
   range "20..100";
  }
  mandatory false;
 }
 leaf PRBSHRINKPROTECTIONTIMER {
  type uint8 {
   range "2..30";
  }
  mandatory false;
 }
 }
 grouping NBRGNODEBPOLICY-attributes {
 leaf GNODEBID {
  type union {
   type int64 {
    range "-1..4294967295";
   }
  }
  mandatory false;
 }
 leaf LTETONRPLMNSELECTIONMODE {
  type enumeration {
   enum val-0;
   enum val-1;
   enum val-2;
   enum val-3;
  }
  mandatory false;
 }
 leaf MCC {
  type string {
   length "3";
  }
  mandatory false;
 }
 leaf MNC {
  type string {
   length "2..3";
  }
  mandatory false;
 }
 }
 grouping NBSHARINGPOLICY-attributes {
 leaf CNOPERATORID {
  type union {
   type int8 {
    range "-1..5";
   }
  }
  mandatory false;
 }
 leaf UECONTEXTPROPORTION {
  type uint8 {
   range "1..100";
  }
  mandatory false;
 }
 }
 grouping NCELLCLASSMGT-attributes {
 leaf CASCELLCFGTHD {
  type uint16 {
   range "1..10000";
  }
  mandatory false;
 }
 leaf HOATTEMPTTHD {
  type uint16 {
   range "0..10000";
  }
  mandatory false;
 }
 leaf HOSUCCTHD {
  type uint16 {
   range "0..10000";
  }
  mandatory false;
 }
 leaf INTRARATNCELLMGTMODE {
  type boolean;
  mandatory false;
 }
 leaf STATPERIODFORNCELLCLASS {
  type uint16 {
   range "1..50400";
  }
  mandatory false;
 }
 }
 grouping NCELLDLRSRPMEASPARA-attributes {
 leaf LOCALCELLNAME {
  type string;
  mandatory false;
 }
 leaf DLRSRPAUTONCELLMEASSWITCH {
  type boolean;
  mandatory false;
 }
 leaf DLRSRPNCELLMEASA6OFFSET {
  type union {
   type int8 {
    range "-30..127";
   }
  }
  mandatory false;
 }
 leaf LOCALCELLID {
  type union {
   type int16 {
    range "-1..255";
   }
  }
  mandatory false;
 }
 leaf NCELLDLRSRPMEASA3OFFSET {
  type int8 {
   range "-30..30";
  }
  mandatory false;
 }
 leaf NCELLINFOEXCHANGEASSISTSW {
  type string;
  mandatory false;
 }
 }
 grouping NCELLPARACFG-attributes {
 leaf LOCALCELLNAME {
  type string;
  mandatory false;
 }
 leaf CELLANROPTMODE {
  type boolean;
  mandatory false;
 }
 leaf HOSTATTHD {
  type uint16 {
   range "0..10000";
  }
  mandatory false;
 }
 leaf HOSUCCTHD {
  type uint8 {
   range "0..100";
  }
  mandatory false;
 }
 leaf LOCALCELLID {
  type union {
   type int16 {
    range "-1..255";
   }
  }
  mandatory false;
 }
 leaf NCELLODDISTHD {
  type union {
   type uint32 {
    range "0..1640400";
   }
  }
  mandatory false;
 }
 leaf NCELLNUMFORANR {
  type uint16 {
   range "0..256";
  }
  mandatory false;
 }
 leaf NSADCSCGADDMODATTTHD {
  type uint16 {
   range "0..10000";
  }
  mandatory false;
 }
 leaf NSADCSCGADDMODSUCCTHD {
  type uint8 {
   range "0..100";
  }
  mandatory false;
 }
 leaf RATTYPE {
  type enumeration {
   enum val--1;
   enum val-0;
   enum val-1;
   enum val-2;
   enum val-3;
  }
  mandatory false;
 }
 }
 grouping NCELLPLMNLIST-attributes {
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf PLMNLISTTYPE {
  type enumeration {
   enum val-0;
   enum val-1;
   enum val-2;
  }
  mandatory false;
 }
 leaf OLD_RATTYPE {
  type enumeration {
   enum val--1;
   enum val-0;
   enum val-1;
   enum val-2;
   enum val-3;
  }
  mandatory false;
 }
 leaf RATTYPE {
  type enumeration {
   enum val--1;
   enum val-0;
   enum val-1;
   enum val-2;
   enum val-3;
  }
  mandatory false;
 }
 leaf GNBIDLENGTH {
  type uint8 {
   range "22..32";
  }
  mandatory false;
 }
 }
 grouping NCELLSRSMEASPARA-attributes {
 leaf LOCALCELLNAME {
  type string;
  mandatory false;
 }
 leaf LOCALCELLID {
  type union {
   type int16 {
    range "-1..255";
   }
  }
  mandatory false;
 }
 leaf NCELLMEASSWITCH {
  type string;
  mandatory false;
 }
 leaf NCELLSRSMEASA3OFFSET {
  type int8 {
   range "-30..30";
  }
  mandatory false;
 }
 leaf SRSAUTONCELLMEASSWITCH {
  type boolean;
  mandatory false;
 }
 }
 grouping NREXTERNALCELL-attributes {
 leaf CELLNAME {
  type string;
  mandatory false;
 }
 leaf ADDITIONALFREQUENCYBAND {
  type enumeration {
   enum val-0;
   enum val-1;
   enum val-2;
   enum val-5;
   enum val-18;
   enum val-25;
   enum val-26;
   enum val-38;
   enum val-39;
   enum val-41;
   enum val-48;
   enum val-65;
   enum val-77;
   enum val-78;
   enum val-90;
   enum val-96;
   enum val-101;
   enum val-102;
   enum val-104;
   enum val-257;
   enum val-258;
   enum val-259;
   enum val-260;
   enum val-261;
  }
  mandatory false;
 }
 leaf AGGREGATIONATTRIBUTE {
  type string;
  mandatory false;
 }
 leaf CELLBARREDREDCAP {
  type enumeration {
   enum val-0;
   enum val-1;
   enum val-2;
   enum val-3;
  }
  mandatory false;
 }
 leaf CELLID {
  type union {
   type int16 {
    range "-1..16383";
   }
  }
  mandatory false;
 }
 leaf DLARFCN {
  type uint32 {
   range "0..3279165";
  }
  mandatory false;
 }
 leaf FREQUENCYBAND {
  type enumeration {
   enum val-0;
   enum val-1;
   enum val-2;
   enum val-3;
   enum val-5;
   enum val-7;
   enum val-8;
   enum val-12;
   enum val-13;
   enum val-14;
   enum val-18;
   enum val-20;
   enum val-25;
   enum val-26;
   enum val-28;
   enum val-30;
   enum val-34;
   enum val-38;
   enum val-39;
   enum val-40;
   enum val-41;
   enum val-48;
   enum val-50;
   enum val-51;
   enum val-53;
   enum val-65;
   enum val-66;
   enum val-70;
   enum val-71;
   enum val-74;
   enum val-75;
   enum val-76;
   enum val-77;
   enum val-78;
   enum val-79;
   enum val-90;
   enum val-91;
   enum val-92;
   enum val-93;
   enum val-94;
   enum val-96;
   enum val-100;
   enum val-101;
   enum val-102;
   enum val-104;
   enum val-257;
   enum val-258;
   enum val-259;
   enum val-260;
   enum val-261;
   enum val-263;
  }
  mandatory false;
 }
 leaf GNODEBID {
  type union {
   type int64 {
    range "-1..4294967295";
   }
  }
  mandatory false;
 }
 leaf MASTERPLMNRESERVEDFLAG {
  type boolean;
  mandatory false;
 }
 leaf MCC {
  type string {
   length "3";
  }
  mandatory false;
 }
 leaf MNC {
  type string {
   length "2..3";
  }
  mandatory false;
 }
 leaf NRNETWORKINGOPTION {
  type enumeration {
   enum val-0;
   enum val-1;
   enum val-2;
   enum val-3;
  }
  mandatory false;
 }
 leaf PHYCELLID {
  type uint16 {
   range "0..1007";
  }
  mandatory false;
 }
 leaf TAC {
  type union {
   type uint32 {
    range "0..4294967295";
   }
  }
  mandatory false;
 }
 leaf ULARFCN {
  type uint32 {
   range "0..3279165";
  }
  mandatory false;
 }
 leaf ULARFCNCONFIGIND {
  type boolean;
  mandatory false;
 }
 }
 grouping NREXTERNALCELLPLMN-attributes {
 leaf CELLNAME {
  type string;
  mandatory false;
 }
 leaf CELLID {
  type union {
   type int16 {
    range "-1..16383";
   }
  }
  mandatory false;
 }
 leaf GNODEBID {
  type union {
   type int64 {
    range "-1..4294967295";
   }
  }
  mandatory false;
 }
 leaf MCC {
  type string {
   length "3";
  }
  mandatory false;
 }
 leaf MNC {
  type string {
   length "2..3";
  }
  mandatory false;
 }
 leaf NRNETWORKINGOPTION {
  type enumeration {
   enum val-0;
   enum val-1;
   enum val-2;
   enum val-3;
  }
  mandatory false;
 }
 leaf SHAREDMCC {
  type string {
   length "3";
  }
  mandatory false;
 }
 leaf SHAREDMNC {
  type string {
   length "2..3";
  }
  mandatory false;
 }
 leaf SHAREDPLMNCELLID {
  type union {
   type uint16 {
    range "0..65535";
   }
  }
  mandatory false;
 }
 leaf SHAREDPLMNGNODEBID {
  type uint32 {
   range "0..4294967295";
  }
  mandatory false;
 }
 leaf TAC {
  type union {
   type uint32 {
    range "0..4294967295";
   }
  }
  mandatory false;
 }
 }
 grouping NRMFBIFREQ-attributes {
 leaf ADDITIONALFREQUENCYBAND {
  type enumeration {
   enum val-0;
   enum val-1;
   enum val-2;
   enum val-5;
   enum val-18;
   enum val-25;
   enum val-26;
   enum val-38;
   enum val-39;
   enum val-41;
   enum val-48;
   enum val-65;
   enum val-77;
   enum val-78;
   enum val-90;
   enum val-96;
   enum val-101;
   enum val-102;
   enum val-104;
   enum val-257;
   enum val-258;
   enum val-259;
   enum val-260;
   enum val-261;
  }
  mandatory false;
 }
 leaf OLD_DLARFCN {
  type union {
   type int32 {
    range "-1..3279165";
   }
  }
  mandatory false;
 }
 leaf DLARFCN {
  type union {
   type int32 {
    range "-1..3279165";
   }
  }
  mandatory false;
 }
 leaf FREQUENCYBAND {
  type enumeration {
   enum val-1;
   enum val-2;
   enum val-5;
   enum val-7;
   enum val-12;
   enum val-13;
   enum val-14;
   enum val-18;
   enum val-20;
   enum val-25;
   enum val-26;
   enum val-28;
   enum val-30;
   enum val-34;
   enum val-38;
   enum val-39;
   enum val-40;
   enum val-41;
   enum val-48;
   enum val-50;
   enum val-51;
   enum val-65;
   enum val-66;
   enum val-70;
   enum val-74;
   enum val-75;
   enum val-76;
   enum val-77;
   enum val-78;
   enum val-90;
   enum val-91;
   enum val-92;
   enum val-93;
   enum val-94;
   enum val-96;
   enum val-101;
   enum val-102;
   enum val-104;
   enum val-257;
   enum val-258;
   enum val-259;
   enum val-260;
   enum val-261;
  }
  mandatory false;
 }
 }
 grouping NRNFREQ-attributes {
 leaf LOCALCELLNAME {
  type string;
  mandatory false;
 }
 leaf AGGREGATIONATTRIBUTE {
  type string;
  mandatory false;
 }
 leaf BLINDREDIRECTIONPRIORITY {
  type uint8 {
   range "0..16";
  }
  mandatory false;
 }
 leaf CONNFREQPRIORITY {
  type uint8 {
   range "0..16";
  }
  mandatory false;
 }
 leaf OLD_DLARFCN {
  type union {
   type int32 {
    range "-1..3279165";
   }
  }
  mandatory false;
 }
 leaf DLARFCN {
  type union {
   type int32 {
    range "-1..3279165";
   }
  }
  mandatory false;
 }
 leaf FREQSPECIFICOFFSET {
  type int8 {
   range "-15..15";
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf MAXALLOWEDTXPOWER {
  type int8 {
   range "-30..33";
  }
  mandatory false;
 }
 leaf MAXRSQTYFORCELLQLTYCALC {
  type uint8 {
   range "1..16";
  }
  mandatory false;
 }
 leaf MINRXLEVEL {
  type int8 {
   range "-70..-22";
  }
  mandatory false;
 }
 leaf MINRXSIGNALQUALITY {
  type union {
   type int8 {
    range "-43..0";
   }
  }
  mandatory false;
 }
 leaf NRDLBANDWIDTH {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
  }
  mandatory false;
 }
 leaf NRDLMINCARRIERBW {
  type enumeration {
   enum val-0;
   enum val-10;
   enum val-15;
   enum val-20;
   enum val-30;
   enum val-40;
   enum val-50;
   enum val-60;
   enum val-70;
   enum val-80;
   enum val-90;
  }
  mandatory false;
 }
 leaf NRFREQABSOLUTEPRIORITY {
  type enumeration {
   enum val-0;
   enum val-1;
   enum val-2;
  }
  mandatory false;
 }
 leaf NRFREQHIGHPRIRESELTHLD {
  type uint8 {
   range "0..31";
  }
  mandatory false;
 }
 leaf NRFREQHIGHPRIRESELTHLDRSRQ {
  type union {
   type uint8 {
    range "0..255";
   }
  }
  mandatory false;
 }
 leaf NRFREQLOWPRIRESELTHLD {
  type uint8 {
   range "0..31";
  }
  mandatory false;
 }
 leaf NRFREQLOWPRIRESELTHLDRSRQ {
  type union {
   type uint8 {
    range "0..255";
   }
  }
  mandatory false;
 }
 leaf NRFREQRESELPRIORITY {
  type union {
   type uint8 {
    range "0..255";
   }
  }
  mandatory false;
 }
 leaf NRFREQRESELSUBPRIORITY {
  type enumeration {
   enum val-0;
   enum val-2;
   enum val-4;
   enum val-6;
   enum val-8;
  }
  mandatory false;
 }
 leaf NRULBANDWIDTH {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
  }
  mandatory false;
 }
 leaf NRULMINCARRIERBW {
  type enumeration {
   enum val-0;
   enum val-10;
   enum val-15;
   enum val-20;
   enum val-30;
   enum val-40;
   enum val-50;
   enum val-60;
   enum val-70;
   enum val-80;
   enum val-90;
  }
  mandatory false;
 }
 leaf RSQLTYTHLDFORCELLQLTYCALC {
  type int16 {
   range "-156..-31";
  }
  mandatory false;
 }
 leaf SSBMEASUREMENTDURATION {
  type enumeration {
   enum val-0;
   enum val-1;
   enum val-2;
   enum val-3;
   enum val-4;
  }
  mandatory false;
 }
 leaf SSBOFFSET {
  type uint8 {
   range "0..159";
  }
  mandatory false;
 }
 leaf SSBPERIOD {
  type enumeration {
   enum val-0;
   enum val-1;
   enum val-2;
   enum val-3;
   enum val-4;
   enum val-5;
  }
  mandatory false;
 }
 leaf SUBCARRIERSPACING {
  type enumeration {
   enum val-0;
   enum val-1;
   enum val-2;
   enum val-3;
  }
  mandatory false;
 }
 leaf ULARFCN {
  type uint32 {
   range "0..3279165";
  }
  mandatory false;
 }
 leaf ULARFCNCONFIGIND {
  type boolean;
  mandatory false;
 }
 leaf VONRPRIORITY {
  type union {
   type uint8 {
    range "0..255";
   }
  }
  mandatory false;
 }
 }
 grouping NRNFREQSCELLOP-attributes {
 leaf LOCALCELLNAME {
  type string;
  mandatory false;
 }
 leaf CELLRESELPRIORITY {
  type uint8 {
   range "0..7";
  }
  mandatory false;
 }
 leaf CELLRESELPRIORITYCONFIGIND {
  type boolean;
  mandatory false;
 }
 leaf CELLRESELSUBPRIORITY {
  type enumeration {
   enum val-0;
   enum val-2;
   enum val-4;
   enum val-6;
   enum val-8;
  }
  mandatory false;
 }
 leaf CNOPERATORID {
  type union {
   type int8 {
    range "-1..5";
   }
  }
  mandatory false;
 }
 leaf DLARFCN {
  type union {
   type int32 {
    range "-1..3279165";
   }
  }
  mandatory false;
 }
 leaf LOCALCELLID {
  type union {
   type int16 {
    range "-1..255";
   }
  }
  mandatory false;
 }
 }
 grouping NRNRELATIONSHIP-attributes {
 leaf LOCALCELLNAME {
  type string;
  mandatory false;
 }
 leaf AGGREGATIONATTRIBUTE {
  type string;
  mandatory false;
 }
 leaf ANRFLAG {
  type boolean;
  mandatory false;
 }
 leaf BLINDCONFIGINDICATOR {
  type boolean;
  mandatory false;
 }
 leaf CELLID {
  type union {
   type int16 {
    range "-1..16383";
   }
  }
  mandatory false;
 }
 leaf GNODEBID {
  type union {
   type int64 {
    range "-1..4294967295";
   }
  }
  mandatory false;
 }
 leaf LOCALCELLID {
  type union {
   type int16 {
    range "-1..255";
   }
  }
  mandatory false;
 }
 leaf MCC {
  type string {
   length "3";
  }
  mandatory false;
 }
 leaf MNC {
  type string {
   length "2..3";
  }
  mandatory false;
 }
 }
 grouping NRSCGFREQCONFIG-attributes {
 leaf AGGREGATIONATTRIBUTE {
  type string;
  mandatory false;
 }
 leaf CAUESCGADDRSRPTHLDOFFSET {
  type int8 {
   range "-100..100";
  }
  mandatory false;
 }
 leaf FORBIDDENSPIDGRPID {
  type union {
   type uint16 {
    range "0..65535";
   }
  }
  mandatory false;
 }
 leaf NRB1REPORTWAITINGTIMER {
  type uint8 {
   range "1..15";
  }
  mandatory false;
 }
 leaf NRB1TIMETOTRIGGER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf NRFREQUENCYBAND {
  type string;
  mandatory false;
 }
 leaf NSADCB1THLDRSRP {
  type int16 {
   range "-156..-31";
  }
  mandatory false;
 }
 leaf NSADCB1THLDRSRQ {
  type union {
   type int8 {
    range "-127..40";
   }
  }
  mandatory false;
 }
 leaf NSADCLTENRSIMULHOTHLD {
  type uint8 {
   range "0..30";
  }
  mandatory false;
 }
 leaf NSADCSULB1THLDRSRP {
  type int16 {
   range "-156..-31";
  }
  mandatory false;
 }
 leaf NSADCUEMCGULMAXTXPWROFS {
  type uint8 {
   range "0..3";
  }
  mandatory false;
 }
 leaf OLD_PCCDLEARFCN {
  type union {
   type int32 {
    range "-1..229575";
   }
  }
  mandatory false;
 }
 leaf PCCDLEARFCN {
  type union {
   type int32 {
    range "-1..229575";
   }
  }
  mandatory false;
 }
 leaf SCGCOVADAPTRSRPTHLD {
  type int16 {
   range "-156..-31";
  }
  mandatory false;
 }
 leaf OLD_SCGDLARFCN {
  type union {
   type int32 {
    range "-1..3279165";
   }
  }
  mandatory false;
 }
 leaf SCGDLARFCN {
  type union {
   type int32 {
    range "-1..3279165";
   }
  }
  mandatory false;
 }
 leaf SCGDLARFCNPRIORITY {
  type uint8 {
   range "1..8";
  }
  mandatory false;
 }
 leaf ULEXPNREVALCOEF {
  type uint8 {
   range "0..100";
  }
  mandatory false;
 }
 leaf ULEXPSCGADDRSRPTHLDOFFSET {
  type int8 {
   range "-100..100";
  }
  mandatory false;
 }
 }
 grouping NRSCGFREQMGMT-attributes {
 leaf LOCALCELLNAME {
  type string;
  mandatory false;
 }
 leaf OLD_LOCALCELLID {
  type union {
   type int16 {
    range "-1..255";
   }
  }
  mandatory false;
 }
 leaf LOCALCELLID {
  type union {
   type int16 {
    range "-1..255";
   }
  }
  mandatory false;
 }
 leaf OLD_SCGDLARFCN {
  type union {
   type int32 {
    range "-1..3279165";
   }
  }
  mandatory false;
 }
 leaf SCGDLARFCN {
  type union {
   type int32 {
    range "-1..3279165";
   }
  }
  mandatory false;
 }
 leaf SCGMGMTALGOSWITCH {
  type string;
  mandatory false;
 }
 }
 grouping NRSCGFREQPRIGRP-attributes {
 leaf OLD_NRSCGDLARFCN {
  type union {
   type int32 {
    range "-1..3279165";
   }
  }
  mandatory false;
 }
 leaf NRSCGDLARFCN {
  type union {
   type int32 {
    range "-1..3279165";
   }
  }
  mandatory false;
 }
 leaf NRSCGDLARFCNPRIORITY {
  type uint8 {
   range "1..8";
  }
  mandatory false;
 }
 leaf OLD_NRSCGFREQPRIORITYGROUPID {
  type union {
   type int16 {
    range "-1..255";
   }
  }
  mandatory false;
 }
 leaf NRSCGFREQPRIORITYGROUPID {
  type union {
   type int16 {
    range "-1..255";
   }
  }
  mandatory false;
 }
 leaf OLD_PCCDLEARFCN {
  type union {
   type int32 {
    range "-1..229575";
   }
  }
  mandatory false;
 }
 leaf PCCDLEARFCN {
  type union {
   type int32 {
    range "-1..229575";
   }
  }
  mandatory false;
 }
 }
 grouping NSADCALGOPARAM-attributes {
 leaf ABNDLDATASPLITPENALTYPRD {
  type uint8 {
   range "1..60";
  }
  mandatory false;
 }
 leaf AMDRBINTRACELLHOSWITCH {
  type boolean;
  mandatory false;
 }
 leaf DLDATASPLITPENALTYPERIOD {
  type uint8 {
   range "1..60";
  }
  mandatory false;
 }
 leaf DLDATASPLITSNOFFSET {
  type uint8 {
   range "1..100";
  }
  mandatory false;
 }
 leaf FASTMOVUENSADCBWDIFFTHLD {
  type uint16 {
   range "0..500";
  }
  mandatory false;
 }
 leaf FASTMOVUENSALTEBWDIFFTHLD {
  type uint16 {
   range "0..500";
  }
  mandatory false;
 }
 leaf HONSABANDCOMBSELECTPOLICY {
  type boolean;
  mandatory false;
 }
 leaf LAAMEASGUARANTEETIMER {
  type uint8 {
   range "0..3";
  }
  mandatory false;
 }
 leaf LNRCOMEASLTEMEASDURATION {
  type uint8 {
   range "0..6";
  }
  mandatory false;
 }
 leaf NRSCGADDAFTERHOPOLICY {
  type enumeration {
   enum val-0;
   enum val-1;
   enum val-2;
  }
  mandatory false;
 }
 leaf NRTDDSCCRSRPTHLD {
  type union {
   type int16 {
    range "-156..255";
   }
  }
  mandatory false;
 }
 leaf NSADCALGOEXTSWITCH {
  type string;
  mandatory false;
 }
 leaf NSADCALGOSWITCH {
  type string;
  mandatory false;
 }
 leaf NSADCBWDIFFTHLD {
  type uint16 {
   range "0..500";
  }
  mandatory false;
 }
 leaf NSADCNRCABWEVALIND {
  type enumeration {
   enum val-0;
   enum val-1;
   enum val-2;
  }
  mandatory false;
 }
 leaf NSADCULBWDIFFTHLD {
  type uint8 {
   range "0..100";
  }
  mandatory false;
 }
 leaf NSALTEBWDIFFTHLD {
  type uint16 {
   range "0..500";
  }
  mandatory false;
 }
 leaf NSALTECARRSELPOLICY {
  type boolean;
  mandatory false;
 }
 leaf NSALTESTABLEBWDIFFTHLD {
  type uint8 {
   range "0..100";
  }
  mandatory false;
 }
 leaf NSALTEULBWDIFFTHLD {
  type uint8 {
   range "0..100";
  }
  mandatory false;
 }
 leaf NSAS1PROCCONFLCOMPATPOLICY {
  type enumeration {
   enum val-0;
   enum val-1;
   enum val-2;
  }
  mandatory false;
 }
 leaf SCGFASTADDUETYPE {
  type enumeration {
   enum val-0;
   enum val-1;
   enum val-2;
   enum val-3;
  }
  mandatory false;
 }
 leaf STOPSPLITRATERATIOTHLD {
  type uint8 {
   range "1..100";
  }
  mandatory false;
 }
 leaf STOPSPLITTIMETOTRIGGER {
  type uint8 {
   range "1..200";
  }
  mandatory false;
 }
 leaf X2TRANSMAXRATE {
  type uint8 {
   range "1..100";
  }
  mandatory false;
 }
 }
 grouping NSADCMGMTCONFIG-attributes {
 leaf LOCALCELLNAME {
  type string;
  mandatory false;
 }
 leaf DLDATASPLITDELAYTHLD {
  type uint8 {
   range "0..100";
  }
  mandatory false;
 }
 leaf DLPRBTHLDFORNSAPCCANCHOR {
  type uint8 {
   range "0..100";
  }
  mandatory false;
 }
 leaf EXCEPTIONTIMESTHLD {
  type uint16 {
   range "0..300";
  }
  mandatory false;
 }
 leaf FIRSTACKRLCPDUDELAYTHLD {
  type uint8 {
   range "0..30";
  }
  mandatory false;
 }
 leaf HARMONICINTRFAVOIDRANGE {
  type boolean;
  mandatory false;
 }
 leaf IDLEMODENSAPCCANCHORPOLICY {
  type boolean;
  mandatory false;
 }
 leaf IMDINTRFFREQAVOIDANCETYPE {
  type boolean;
  mandatory false;
 }
 leaf LOCALCELLID {
  type union {
   type int16 {
    range "-1..255";
   }
  }
  mandatory false;
 }
 leaf MEASGAPSHARINGSCHEME {
  type enumeration {
   enum val-0;
   enum val-1;
   enum val-2;
   enum val-3;
   enum val-4;
  }
  mandatory false;
 }
 leaf NRDATAVOLUMERPTCFG {
  type union {
   type uint16 {
    range "0..65535";
   }
  }
  mandatory false;
 }
 leaf NRSCCRELCARRSELPUNISHTIMER {
  type uint8 {
   range "0..60";
  }
  mandatory false;
 }
 leaf NRUEOFFLOADSHORTPERIOD {
  type enumeration {
   enum val-0;
   enum val-1;
   enum val-2;
   enum val-3;
   enum val-4;
  }
  mandatory false;
 }
 leaf NRUEOFFLOADSWITCH {
  type string;
  mandatory false;
 }
 leaf NSADCALGOENHSWITCH {
  type string;
  mandatory false;
 }
 leaf NSADCALGOEXTSWITCH {
  type string;
  mandatory false;
 }
 leaf NSADCALGOSWITCH {
  type string;
  mandatory false;
 }
 leaf NSADCDLSPLITLTEINITRATE {
  type uint16 {
   range "1..3000";
  }
  mandatory false;
 }
 leaf NSADCDLSPLITNRINITRATE {
  type uint16 {
   range "1..3000";
  }
  mandatory false;
 }
 leaf NSADCDLSPLITRLCRATE {
  type uint16 {
   range "0..1000";
  }
  mandatory false;
 }
 leaf NSADCFASTRETRANSTRIGTHLD {
  type uint16 {
   range "0..5000";
  }
  mandatory false;
 }
 leaf NSADCFASTSCGADDA1RSRPTHLD {
  type union {
   type int16 {
    range "-140..255";
   }
  }
  mandatory false;
 }
 leaf NSADCLTESCELLACTBFRDELTHLD {
  type uint16 {
   range "0..300";
  }
  mandatory false;
 }
 leaf NSADCLTESCELLACTBFRLENTHLD {
  type uint16 {
   range "0..65535";
  }
  mandatory false;
 }
 leaf NSADCLTESCELLCONFIGINTVL {
  type uint16 {
   range "5..3600";
  }
  mandatory false;
 }
 leaf NSADCLTESCELLMEASDURATION {
  type uint8 {
   range "2..60";
  }
  mandatory false;
 }
 leaf NSADCPCCANCHORA1RSRPTHLD {
  type union {
   type int16 {
    range "-140..255";
   }
  }
  mandatory false;
 }
 leaf NSADCPCCANCHORINGPOLICY {
  type boolean;
  mandatory false;
 }
 leaf NSADCSCGADDITIONPOLICY {
  type boolean;
  mandatory false;
 }
 leaf NSADCUELTEFUNACTIVATIONSW {
  type string;
  mandatory false;
 }
 leaf NSADCUEMCGULAMBRRATIO {
  type union {
   type uint8 {
    range "0..255";
   }
  }
  mandatory false;
 }
 leaf NSADCUEMCGULMAXIMUMPOWER {
  type int8 {
   range "-30..33";
  }
  mandatory false;
 }
 leaf NSADCUEPREUSERCNTTHLD {
  type uint16 {
   range "0..1250";
  }
  mandatory false;
 }
 leaf NSADCUESCGULMAXIMUMPOWER {
  type int8 {
   range "-30..33";
  }
  mandatory false;
 }
 leaf NSADCULPATHTOLTERATECOEFF {
  type uint16 {
   range "1..50000";
  }
  mandatory false;
 }
 leaf NSADCULPATHTONRRATECOEFF {
  type uint16 {
   range "1..50000";
  }
  mandatory false;
 }
 leaf NSALTESCELLDEACTBFRLENTHLD {
  type uint8 {
   range "1..10";
  }
  mandatory false;
 }
 leaf NSALTESCELLDEACTTHPTTHLD {
  type uint16 {
   range "10..1000";
  }
  mandatory false;
 }
 leaf NSALTESELPKTSTATPROTTIMER {
  type uint8 {
   range "0..50";
  }
  mandatory false;
 }
 leaf NSALTESELPUNISHTIMER {
  type uint8 {
   range "0..60";
  }
  mandatory false;
 }
 leaf NSATDMPCTRIGSINRTHLD {
  type int8 {
   range "-100..100";
  }
  mandatory false;
 }
 leaf NSAULBFRLENTHLD {
  type uint16 {
   range "0..65535";
  }
  mandatory false;
 }
 leaf NSAULCAA1RSRPTHLD {
  type int16 {
   range "-140..-43";
  }
  mandatory false;
 }
 leaf NSAULCAA2RSRPTHLD {
  type int16 {
   range "-140..-43";
  }
  mandatory false;
 }
 leaf PCELLA1RSRPTHLD {
  type int16 {
   range "-140..-43";
  }
  mandatory false;
 }
 leaf PCELLA2RSRPTHLD {
  type int16 {
   range "-140..-43";
  }
  mandatory false;
 }
 leaf PDCPSNOFFSETSWITCH {
  type boolean;
  mandatory false;
 }
 leaf PERCEIVEDRATETHLD {
  type uint16 {
   range "0..10000";
  }
  mandatory false;
 }
 leaf PTTUESCGMGMTSTRATEGY {
  type enumeration {
   enum val-0;
   enum val-1;
   enum val-2;
  }
  mandatory false;
 }
 leaf SATONSAPCCACTIVEUENUMTHLD {
  type uint16 {
   range "0..65535";
  }
  mandatory false;
 }
 leaf SATONSAPCCULINTRFTHLD {
  type int8 {
   range "-120..-80";
  }
  mandatory false;
 }
 leaf SATONSAPCCULPRBUSAGETHLD {
  type uint8 {
   range "0..100";
  }
  mandatory false;
 }
 leaf SCGABNRELNUMTHLD {
  type uint16 {
   range "1..1000";
  }
  mandatory false;
 }
 leaf SCGABNRELPUNISHTIMER {
  type uint16 {
   range "1..3600";
  }
  mandatory false;
 }
 leaf SCGABNRELSTATDURATION {
  type uint16 {
   range "1..3600";
  }
  mandatory false;
 }
 leaf SCGADDPENALTYDURATION {
  type union {
   type uint16 {
    range "0..600";
   }
  }
  mandatory false;
 }
 leaf SCGADDPENALTYPERIODCOUNT {
  type uint8 {
   range "0..255";
  }
  mandatory false;
 }
 leaf SCGADDTORELEASETIMETHLD {
  type uint16 {
   range "1..5000";
  }
  mandatory false;
 }
 leaf SCGADDITIONBUFFERDELAYTHLD {
  type uint16 {
   range "0..300";
  }
  mandatory false;
 }
 leaf SCGADDITIONBUFFERLENTHLD {
  type uint16 {
   range "0..65535";
  }
  mandatory false;
 }
 leaf SCGADDITIONINTERVAL {
  type uint8 {
   range "5..60";
  }
  mandatory false;
 }
 leaf SCGRELFREQMEASPUNISHTIMER {
  type uint8 {
   range "0..60";
  }
  mandatory false;
 }
 leaf SHORTPRDNOTFCSCGADDINTVL {
  type uint8 {
   range "4..60";
  }
  mandatory false;
 }
 leaf ULQUALITYTHLDFORSCGRELEASE {
  type int16 {
   range "-200..200";
  }
  mandatory false;
 }
 leaf UPPERLAYERINDICATIONSWITCH {
  type enumeration {
   enum val-0;
   enum val-1;
   enum val-2;
  }
  mandatory false;
 }
 leaf USERNUMULTRAHIGHLOADTHLD {
  type uint32 {
   range "1..75000";
  }
  mandatory false;
 }
 leaf USERNUMBERHIGHLOADTHLD {
  type uint16 {
   range "1..65535";
  }
  mandatory false;
 }
 leaf VOLTEPLRTHLDFORSCGRELEASE {
  type uint8 {
   range "0..99";
  }
  mandatory false;
 }
 leaf VOLTEUESCGMGMTSTRATEGY {
  type enumeration {
   enum val-0;
   enum val-1;
   enum val-2;
  }
  mandatory false;
 }
 }
 grouping NSADCQCIPARAMGROUP-attributes {
 leaf LOCALCELLNAME {
  type string;
  mandatory false;
 }
 leaf DLDATAPDCPSPLITMODE {
  type enumeration {
   enum val-0;
   enum val-1;
   enum val-2;
   enum val-3;
   enum val-4;
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf NSADCB1RSRPTHLDOFFSET {
  type int8 {
   range "-20..20";
  }
  mandatory false;
 }
 leaf OLD_NSADCQCIPARAMGROUPID {
  type union {
   type int8 {
    range "-1..9";
   }
  }
  mandatory false;
 }
 leaf NSADCQCIPARAMGROUPID {
  type union {
   type int8 {
    range "-1..9";
   }
  }
  mandatory false;
 }
 leaf ULDATASPLITPRIMARYPATH {
  type boolean;
  mandatory false;
 }
 leaf ULDATASPLITTHRESHOLD {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
  }
  mandatory false;
 }
 }
 grouping OPERATORBAND-attributes {
 leaf BANDATTRIBUTE {
  type enumeration {
   enum val-0;
   enum val-1;
   enum val-2;
  }
  mandatory false;
 }
 leaf OLD_BANDID {
  type union {
   type int16 {
    range "-1..261";
   }
  }
  mandatory false;
 }
 leaf BANDID {
  type union {
   type int16 {
    range "-1..261";
   }
  }
  mandatory false;
 }
 leaf OLD_BANDTYPE {
  type enumeration {
   enum val--1;
   enum val-0;
   enum val-1;
  }
  mandatory false;
 }
 leaf BANDTYPE {
  type enumeration {
   enum val--1;
   enum val-0;
   enum val-1;
  }
  mandatory false;
 }
 leaf CNOPERATORLIST {
  type string {
   length "6";
  }
  mandatory false;
 }
 }
 grouping PARAAUTOOPTCFG-attributes {
 leaf ACHEFFECTIVETYPE {
  type string;
  mandatory false;
 }
 leaf HOTIMESTHD {
  type uint16 {
   range "0..65535";
  }
  mandatory false;
 }
 leaf P0NOMINALPUCCH4AUTOOPT {
  type int8 {
   range "-127..-96";
  }
  mandatory false;
 }
 leaf PUCCHPCSINROFFSET4AUTOOPT {
  type uint8 {
   range "0..15";
  }
  mandatory false;
 }
 leaf PUSCHRSRPHIGHTHD4AUTOOPT {
  type int8 {
   range "-126..24";
  }
  mandatory false;
 }
 }
 grouping PCCFREQCFG-attributes {
 leaf NSADCPCCA4RSRPTHLD {
  type int16 {
   range "-140..-43";
  }
  mandatory false;
 }
 leaf NSADCPCCA4RSRQTHLD {
  type int8 {
   range "-40..-6";
  }
  mandatory false;
 }
 leaf NSAPCCANCHORINGPRIORITY {
  type uint8 {
   range "0..31";
  }
  mandatory false;
 }
 leaf PCCA4RSRPTHD {
  type int16 {
   range "-140..-43";
  }
  mandatory false;
 }
 leaf PCCA4RSRQTHD {
  type int8 {
   range "-40..-6";
  }
  mandatory false;
 }
 leaf OLD_PCCDLEARFCN {
  type union {
   type int32 {
    range "-1..229575";
   }
  }
  mandatory false;
 }
 leaf PCCDLEARFCN {
  type union {
   type int32 {
    range "-1..229575";
   }
  }
  mandatory false;
 }
 leaf PCCULEXPEVALRSRPTHLDOFS {
  type int8 {
   range "-100..100";
  }
  mandatory false;
 }
 leaf PCCULEXPERIENCECOEFF {
  type uint8 {
   range "0..100";
  }
  mandatory false;
 }
 leaf PREFERREDPCCPRIORITY {
  type uint8 {
   range "0..15";
  }
  mandatory false;
 }
 }
 grouping PCCHCFG-attributes {
 leaf LOCALCELLNAME {
  type string;
  mandatory false;
 }
 leaf DEFAULTPAGINGCYCLE {
  type enumeration {
   enum val-0;
   enum val-1;
   enum val-2;
   enum val-3;
  }
  mandatory false;
 }
 leaf DEFAULTPAGINGCYCLEFOREMTC {
  type enumeration {
   enum val-0;
   enum val-1;
   enum val-2;
   enum val-3;
  }
  mandatory false;
 }
 leaf DEFAULTPAGINGCYCLEFORNB {
  type enumeration {
   enum val-0;
   enum val-1;
   enum val-2;
   enum val-3;
  }
  mandatory false;
 }
 leaf EMTCPAGINGTIMOUTDISCARDTMR {
  type uint8 {
   range "0..255";
  }
  mandatory false;
 }
 leaf ENHPAGINGCR {
  type uint16 {
   range "10..930";
  }
  mandatory false;
 }
 leaf ENHPAGINGSWITCH {
  type string;
  mandatory false;
 }
 leaf LOCALCELLID {
  type union {
   type int16 {
    range "-1..255";
   }
  }
  mandatory false;
 }
 leaf MAXPAGINGQUEUEBUFFERLENGTH {
  type uint16 {
   range "0..4000";
  }
  mandatory false;
 }
 leaf MAXPAGINGRECORDSNUM {
  type uint8 {
   range "1..16";
  }
  mandatory false;
 }
 leaf NB {
  type enumeration {
   enum val-0;
   enum val-1;
   enum val-2;
   enum val-3;
   enum val-4;
   enum val-5;
   enum val-6;
   enum val-7;
  }
  mandatory false;
 }
 leaf NBDEFAULTPAGINGCOVLEVEL {
  type enumeration {
   enum val-0;
   enum val-1;
   enum val-2;
  }
  mandatory false;
 }
 leaf NBFORNBIOT {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf PAGINGSENTNUM {
  type uint8 {
   range "1..3";
  }
  mandatory false;
 }
 leaf PAGINGSTRATEGY {
  type enumeration {
   enum val-0;
   enum val-1;
   enum val-2;
   enum val-3;
  }
  mandatory false;
 }
 leaf PAGINGTIMEOUTDISCARDTIMER {
  type uint8 {
   range "0..255";
  }
  mandatory false;
 }
 leaf UESPECIFICMINDRXCYCLEFORNB {
  type enumeration {
   enum val-0;
   enum val-1;
   enum val-2;
   enum val-3;
   enum val-4;
   enum val-5;
   enum val-255;
  }
  mandatory false;
 }
 leaf VOICEPAGINGPRIORITY {
  type string;
  mandatory false;
 }
 leaf VOICEPAGINGSENDNUM {
  type uint8 {
   range "1..3";
  }
  mandatory false;
 }
 }
 grouping PDCPROHCPARA-attributes {
 leaf HIGHESTMODE {
  type enumeration {
   enum val-1;
   enum val-2;
   enum val-3;
  }
  mandatory false;
 }
 leaf PROFILES {
  type string;
  mandatory false;
 }
 leaf ROHCOPTIMIZATIONSWITCH {
  type string;
  mandatory false;
 }
 leaf ROHCTCPSINRTRIGGERTHLD {
  type int8 {
   range "-5..10";
  }
  mandatory false;
 }
 }
 grouping PDSCHCFG-attributes {
 leaf LOCALCELLNAME {
  type string;
  mandatory false;
 }
 leaf CELLPOWERLIMIT {
  type uint16 {
   range "0..65500";
  }
  mandatory false;
 }
 leaf CRSPOWERBOOSTINGAMPLITUDE {
  type enumeration {
   enum val-0;
   enum val-1;
   enum val-2;
  }
  mandatory false;
 }
 leaf CRSPWRREDUCTIONAMOUNT {
  type enumeration {
   enum val-0;
   enum val-1;
   enum val-2;
   enum val-3;
   enum val-4;
   enum val-5;
   enum val-6;
  }
  mandatory false;
 }
 leaf EMFPOWERLIMITSWITCH {
  type boolean;
  mandatory false;
 }
 leaf LOCALCELLID {
  type union {
   type int16 {
    range "-1..255";
   }
  }
  mandatory false;
 }
 leaf LOGICALPORTSWAPSWITCH {
  type boolean;
  mandatory false;
 }
 leaf MMUENUMOPTSWITCH {
  type boolean;
  mandatory false;
 }
 leaf PB {
  type uint8 {
   range "0..3";
  }
  mandatory false;
 }
 leaf PDSCHPOWERBOOSTINGSWITCH {
  type boolean;
  mandatory false;
 }
 leaf PWROPTLEVEL {
  type enumeration {
   enum val-0;
   enum val-1;
   enum val-2;
   enum val-3;
  }
  mandatory false;
 }
 leaf PWROPTTBSINDEXTHLD {
  type union {
   type uint8 {
    range "25..255";
   }
  }
  mandatory false;
 }
 leaf REFERENCESIGNALPWR {
  type int16 {
   range "-600..500";
  }
  mandatory false;
 }
 leaf REFERENCESIGNALPWRMARGIN {
  type uint8 {
   range "0..60";
  }
  mandatory false;
 }
 leaf TXCHNPOWERCFGSW {
  type string;
  mandatory false;
 }
 leaf TXPOWEROFFSETANT0 {
  type union {
   type int16 {
    range "-100..255";
   }
  }
  mandatory false;
 }
 leaf TXPOWEROFFSETANT1 {
  type union {
   type int16 {
    range "-100..255";
   }
  }
  mandatory false;
 }
 leaf TXPOWEROFFSETANT2 {
  type union {
   type int16 {
    range "-100..255";
   }
  }
  mandatory false;
 }
 leaf TXPOWEROFFSETANT3 {
  type union {
   type int16 {
    range "-100..255";
   }
  }
  mandatory false;
 }
 }
 grouping PHICHCFG-attributes {
 leaf LOCALCELLNAME {
  type string;
  mandatory false;
 }
 leaf LOCALCELLID {
  type union {
   type int16 {
    range "-1..255";
   }
  }
  mandatory false;
 }
 leaf PHICHDURATION {
  type boolean;
  mandatory false;
 }
 leaf PHICHRESOURCE {
  type enumeration {
   enum val-0;
   enum val-1;
   enum val-2;
   enum val-3;
  }
  mandatory false;
 }
 }
 grouping PIMFREQCFG-attributes {
 leaf OLD_PIMDLEARFCN {
  type union {
   type int32 {
    range "-1..262143";
   }
  }
  mandatory false;
 }
 leaf PIMDLEARFCN {
  type union {
   type int32 {
    range "-1..262143";
   }
  }
  mandatory false;
 }
 leaf OLD_PIMFREQGROUPID {
  type union {
   type int8 {
    range "-1..5";
   }
  }
  mandatory false;
 }
 leaf PIMFREQGROUPID {
  type union {
   type int8 {
    range "-1..5";
   }
  }
  mandatory false;
 }
 }
 grouping PIMFREQGROUP-attributes {
 leaf OLD_PIMFREQGROUPID {
  type union {
   type int8 {
    range "-1..5";
   }
  }
  mandatory false;
 }
 leaf PIMFREQGROUPID {
  type union {
   type int8 {
    range "-1..5";
   }
  }
  mandatory false;
 }
 leaf PIMMITIGATIONMODE {
  type boolean;
  mandatory false;
 }
 }
 grouping PIMINTERFSMARTAVOID-attributes {
 leaf LOCALCELLNAME {
  type string;
  mandatory false;
 }
 leaf LOCALCELLID {
  type union {
   type int16 {
    range "-1..255";
   }
  }
  mandatory false;
 }
 leaf PIMALGOSWITCH {
  type string;
  mandatory false;
 }
 leaf PIMCHNSHUTDOWNINTRFTHLD {
  type uint8 {
   range "0..100";
  }
  mandatory false;
 }
 leaf PIMDLPWRREDUCTIONLEVEL {
  type enumeration {
   enum val-0;
   enum val-1;
   enum val-2;
   enum val-3;
  }
  mandatory false;
 }
 leaf PIMDLPWRREDUCTIONTHLD {
  type uint8 {
   range "0..100";
  }
  mandatory false;
 }
 leaf PIMDLRBAVOIDRATIO {
  type uint8 {
   range "0..30";
  }
  mandatory false;
 }
 leaf PIMINTERFTHLD {
  type uint8 {
   range "0..50";
  }
  mandatory false;
 }
 leaf PIMINTRFDETECTPRBUSAGETHLD {
  type uint8 {
   range "5..20";
  }
  mandatory false;
 }
 }
 grouping PMCH-attributes {
 leaf ALLOCATIONENDSUBFRAME {
  type uint16 {
   range "0..1535";
  }
  mandatory false;
 }
 leaf DATAMCS {
  type uint8 {
   range "0..28";
  }
  mandatory false;
 }
 leaf OLD_LOCALMCEID {
  type union {
   type int8 {
    range "-1..5";
   }
  }
  mandatory false;
 }
 leaf LOCALMCEID {
  type union {
   type int8 {
    range "-1..5";
   }
  }
  mandatory false;
 }
 leaf OLD_MBSFNAREAID {
  type union {
   type int16 {
    range "-1..255";
   }
  }
  mandatory false;
 }
 leaf MBSFNAREAID {
  type union {
   type int16 {
    range "-1..255";
   }
  }
  mandatory false;
 }
 leaf MCHSCHEDULINGPERIOD {
  type enumeration {
   enum val-0;
   enum val-1;
   enum val-2;
   enum val-3;
   enum val-4;
   enum val-5;
   enum val-6;
   enum val-7;
  }
  mandatory false;
 }
 leaf OLD_PMCHID {
  type union {
   type int8 {
    range "-1..14";
   }
  }
  mandatory false;
 }
 leaf PMCHID {
  type union {
   type int8 {
    range "-1..14";
   }
  }
  mandatory false;
 }
 leaf QCI {
  type uint8 {
   range "0..255";
  }
  mandatory false;
 }
 }
 grouping PMCHALLOCPOLICY-attributes {
 leaf DATAMCS {
  type uint8 {
   range "0..28";
  }
  mandatory false;
 }
 leaf DLMINGBR {
  type enumeration {
   enum val-0;
   enum val-8000;
   enum val-16000;
   enum val-32000;
   enum val-64000;
   enum val-128000;
   enum val-256000;
   enum val-512000;
   enum val-1024000;
   enum val-2048000;
   enum val-4096000;
   enum val-8192000;
   enum val-12288000;
   enum val-16384000;
   enum val-20480000;
  }
  mandatory false;
 }
 leaf OLD_LOCALMCEID {
  type union {
   type int8 {
    range "-1..5";
   }
  }
  mandatory false;
 }
 leaf LOCALMCEID {
  type union {
   type int8 {
    range "-1..5";
   }
  }
  mandatory false;
 }
 leaf OLD_MBSFNAREAID {
  type union {
   type int16 {
    range "-1..255";
   }
  }
  mandatory false;
 }
 leaf MBSFNAREAID {
  type union {
   type int16 {
    range "-1..255";
   }
  }
  mandatory false;
 }
 leaf MCHSCHEDULINGPERIOD {
  type enumeration {
   enum val-0;
   enum val-1;
   enum val-2;
   enum val-3;
   enum val-4;
   enum val-5;
   enum val-6;
   enum val-7;
  }
  mandatory false;
 }
 leaf OLD_QCI {
  type union {
   type int16 {
    range "-1..255";
   }
  }
  mandatory false;
 }
 leaf QCI {
  type union {
   type int16 {
    range "-1..255";
   }
  }
  mandatory false;
 }
 }
 grouping PRB-attributes {
 leaf LOCALCELLNAME {
  type string;
  mandatory false;
 }
 leaf ANCHORCARRIERFLAG {
  type boolean;
  mandatory false;
 }
 leaf DEPLOYMODE {
  type enumeration {
   enum val-0;
   enum val-1;
   enum val-2;
  }
  mandatory false;
 }
 leaf DLEARFCN {
  type union {
   type uint32 {
    range "0..262143";
   }
  }
  mandatory false;
 }
 leaf DLFREQOFFSET {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
  }
  mandatory false;
 }
 leaf FREQBAND {
  type uint16 {
   range "1..256";
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf LTEBANDWIDTH {
  type enumeration {
   enum val-2;
   enum val-3;
   enum val-4;
   enum val-5;
  }
  mandatory false;
 }
 leaf LTECELLID {
  type uint8 {
   range "0..255";
  }
  mandatory false;
 }
 leaf LTEDLEARFCN {
  type union {
   type uint32 {
    range "0..262143";
   }
  }
  mandatory false;
 }
 leaf LTEDLRBINDEX {
  type union {
   type uint8 {
    range "0..255";
   }
  }
  mandatory false;
 }
 leaf LTEULRBINDEX {
  type union {
   type uint8 {
    range "0..255";
   }
  }
  mandatory false;
 }
 leaf NBDYNAMICPRBMODE {
  type enumeration {
   enum val-0;
   enum val-1;
   enum val-2;
  }
  mandatory false;
 }
 leaf NPRSPARAGROUPID {
  type union {
   type uint8 {
    range "0..255";
   }
  }
  mandatory false;
 }
 leaf NRCELLDLARFCN {
  type union {
   type uint32 {
    range "123400..2279165";
   }
  }
  mandatory false;
 }
 leaf NRCELLDLBANDWIDTH {
  type enumeration {
   enum val-2;
   enum val-3;
   enum val-4;
   enum val-5;
   enum val-6;
   enum val-7;
   enum val-8;
  }
  mandatory false;
 }
 leaf NRCELLGBCFGIND {
  type boolean;
  mandatory false;
 }
 leaf PRACHCOVERAGELEVELTYPE {
  type string;
  mandatory false;
 }
 leaf PRBBLOCKPRIORITY {
  type enumeration {
   enum val-0;
   enum val-1;
   enum val-2;
   enum val-3;
  }
  mandatory false;
 }
 leaf OLD_PRBID {
  type union {
   type int16 {
    range "-1..255";
   }
  }
  mandatory false;
 }
 leaf PRBID {
  type union {
   type int16 {
    range "-1..255";
   }
  }
  mandatory false;
 }
 leaf STANDALONEDEPLOYSWITCH {
  type string;
  mandatory false;
 }
 leaf ULALLSYMBOLSENDFLAG {
  type boolean;
  mandatory false;
 }
 leaf ULEARFCN {
  type union {
   type uint32 {
    range "18000..134181";
   }
  }
  mandatory false;
 }
 leaf ULEARFCNCFGIND {
  type boolean;
  mandatory false;
 }
 leaf ULFREQOFFSET {
  type enumeration {
   enum val-0;
   enum val-1;
   enum val-2;
   enum val-3;
   enum val-4;
   enum val-5;
   enum val-6;
   enum val-7;
   enum val-8;
   enum val-9;
   enum val-11;
   enum val-12;
   enum val-13;
   enum val-14;
   enum val-15;
   enum val-16;
   enum val-17;
   enum val-18;
   enum val-19;
   enum val-20;
  }
  mandatory false;
 }
 leaf WORKMODE {
  type enumeration {
   enum val-0;
   enum val-1;
   enum val-2;
  }
  mandatory false;
 }
 }
 grouping PRBDLGAPCONFIG-attributes {
 leaf LOCALCELLNAME {
  type string;
  mandatory false;
 }
 leaf DLGAPDURATIONCOEFF {
  type enumeration {
   enum val-0;
   enum val-1;
   enum val-2;
   enum val-3;
  }
  mandatory false;
 }
 leaf DLGAPPERIOD {
  type enumeration {
   enum val-0;
   enum val-1;
   enum val-2;
   enum val-3;
  }
  mandatory false;
 }
 leaf DLGAPTHRESHOLD {
  type enumeration {
   enum val-0;
   enum val-1;
   enum val-2;
   enum val-3;
  }
  mandatory false;
 }
 leaf LOCALCELLID {
  type union {
   type int16 {
    range "-1..255";
   }
  }
  mandatory false;
 }
 leaf PRBID {
  type union {
   type int16 {
    range "-1..255";
   }
  }
  mandatory false;
 }
 }
 grouping PRBDLSCHCEALGO-attributes {
 leaf LOCALCELLNAME {
  type string;
  mandatory false;
 }
 leaf COVERAGELEVEL {
  type enumeration {
   enum val--1;
   enum val-0;
   enum val-1;
   enum val-2;
  }
  mandatory false;
 }
 leaf DLAMCMCSADJUSTSTEP {
  type uint16 {
   range "0..400";
  }
  mandatory false;
 }
 leaf DLAMCPLADJUSTSTEP {
  type uint16 {
   range "0..500";
  }
  mandatory false;
 }
 leaf DLINITIALMCS {
  type enumeration {
   enum val-0;
   enum val-1;
   enum val-2;
   enum val-3;
   enum val-4;
   enum val-5;
   enum val-6;
   enum val-7;
   enum val-8;
   enum val-9;
   enum val-10;
   enum val-11;
   enum val-12;
   enum val-13;
  }
  mandatory false;
 }
 leaf DLINITIALTRANSRPTCOUNT {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf DLRSRPTHLD {
  type int16 {
   range "-141..-44";
  }
  mandatory false;
 }
 leaf DLSCHDURATIONPROPORTION {
  type uint8 {
   range "5..100";
  }
  mandatory false;
 }
 leaf LOCALCELLID {
  type union {
   type int16 {
    range "-1..255";
   }
  }
  mandatory false;
 }
 leaf PRBID {
  type union {
   type int16 {
    range "-1..255";
   }
  }
  mandatory false;
 }
 leaf PWRDIFFTHLD {
  type union {
   type int8 {
    range "-128..3";
   }
  }
  mandatory false;
 }
 leaf UUMESSAGEWAITINGTIMER {
  type uint8 {
   range "0..200";
  }
  mandatory false;
 }
 }
 grouping PRBPDCCHCECONFIG-attributes {
 leaf LOCALCELLNAME {
  type string;
  mandatory false;
 }
 leaf CONSECUTIVEACKNACKCOUNT {
  type uint8 {
   range "5..30";
  }
  mandatory false;
 }
 leaf COVERAGELEVEL {
  type enumeration {
   enum val--1;
   enum val-0;
   enum val-1;
   enum val-2;
  }
  mandatory false;
 }
 leaf LOCALCELLID {
  type union {
   type int16 {
    range "-1..255";
   }
  }
  mandatory false;
 }
 leaf PDCCHMAXREPETITIONCNT {
  type enumeration {
   enum val-0;
   enum val-1;
   enum val-2;
   enum val-3;
   enum val-4;
   enum val-5;
   enum val-6;
   enum val-7;
   enum val-8;
   enum val-9;
   enum val-10;
   enum val-11;
  }
  mandatory false;
 }
 leaf PDCCHOFFSET {
  type enumeration {
   enum val-0;
   enum val-1;
   enum val-2;
   enum val-3;
  }
  mandatory false;
 }
 leaf PDCCHPERIODFACTOR {
  type enumeration {
   enum val-0;
   enum val-1;
   enum val-2;
   enum val-3;
   enum val-4;
   enum val-5;
   enum val-6;
   enum val-7;
  }
  mandatory false;
 }
 leaf PDCCHTRANSRPTCNTFACTOR {
  type enumeration {
   enum val-0;
   enum val-1;
   enum val-2;
   enum val-3;
  }
  mandatory false;
 }
 leaf PRBID {
  type union {
   type int16 {
    range "-1..255";
   }
  }
  mandatory false;
 }
 leaf WUSINITIALTRANSRPTCOUNT {
  type enumeration {
   enum val-0;
   enum val-1;
   enum val-2;
   enum val-3;
   enum val-4;
   enum val-5;
   enum val-6;
   enum val-7;
   enum val-8;
   enum val-9;
   enum val-10;
  }
  mandatory false;
 }
 }
 grouping PRBRACHCECONFIG-attributes {
 leaf LOCALCELLNAME {
  type string;
  mandatory false;
 }
 leaf BACKOFFHIGHLOADTHLD {
  type uint8 {
   range "1..100";
  }
  mandatory false;
 }
 leaf BACKOFFLOWLOADTHLD {
  type uint8 {
   range "1..100";
  }
  mandatory false;
 }
 leaf COVERAGELEVEL {
  type enumeration {
   enum val--1;
   enum val-0;
   enum val-1;
   enum val-2;
  }
  mandatory false;
 }
 leaf EDTPRACHSUBCARRIEROFFSET {
  type enumeration {
   enum val-0;
   enum val-1;
   enum val-2;
   enum val-3;
   enum val-4;
   enum val-5;
   enum val-6;
  }
  mandatory false;
 }
 leaf LOCALCELLID {
  type union {
   type int16 {
    range "-1..255";
   }
  }
  mandatory false;
 }
 leaf MTNPRACHRANGEMSG3INITTONE {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf PRACHALGOSW {
  type string;
  mandatory false;
 }
 leaf PRACHCBRASUBCARRIERNUMBER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf PRACHDETECTIONTHLD {
  type enumeration {
   enum val-0;
   enum val-1;
   enum val-2;
   enum val-3;
  }
  mandatory false;
 }
 leaf PRACHPROBABILITYFORANCHOR {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-255;
  }
  mandatory false;
 }
 leaf PRACHREPETITIONCOUNT {
  type enumeration {
   enum val-0;
   enum val-1;
   enum val-2;
   enum val-3;
   enum val-4;
   enum val-5;
   enum val-6;
   enum val-7;
  }
  mandatory false;
 }
 leaf PRACHSTARTTIME {
  type enumeration {
   enum val-0;
   enum val-1;
   enum val-2;
   enum val-3;
   enum val-4;
   enum val-5;
   enum val-6;
   enum val-7;
  }
  mandatory false;
 }
 leaf PRACHSUBCARRIERNUMBER {
  type enumeration {
   enum val-0;
   enum val-1;
   enum val-2;
   enum val-3;
  }
  mandatory false;
 }
 leaf PRACHSUBCARRIEROFFSET {
  type enumeration {
   enum val-0;
   enum val-1;
   enum val-2;
   enum val-3;
   enum val-4;
   enum val-5;
   enum val-6;
  }
  mandatory false;
 }
 leaf PRACHTRANSMISSIONPERIOD {
  type enumeration {
   enum val-0;
   enum val-1;
   enum val-2;
   enum val-3;
   enum val-4;
   enum val-5;
   enum val-6;
   enum val-7;
  }
  mandatory false;
 }
 leaf PRBID {
  type union {
   type int16 {
    range "-1..255";
   }
  }
  mandatory false;
 }
 }
 grouping PRBSCHCONFIG-attributes {
 leaf LOCALCELLNAME {
  type string;
  mandatory false;
 }
 leaf DLSCHEDULINGSWITCH {
  type string;
  mandatory false;
 }
 leaf DLSUBCARRIERUSAGEOFFSET {
  type uint8 {
   range "0..100";
  }
  mandatory false;
 }
 leaf LOCALCELLID {
  type union {
   type int16 {
    range "-1..255";
   }
  }
  mandatory false;
 }
 leaf MAXNUMREPETITIONFORPAGING {
  type enumeration {
   enum val-0;
   enum val-1;
   enum val-2;
   enum val-3;
   enum val-4;
   enum val-5;
   enum val-6;
   enum val-7;
   enum val-8;
   enum val-9;
   enum val-10;
   enum val-11;
   enum val-255;
  }
  mandatory false;
 }
 leaf NBDLBITMAP10 {
  type uint16 {
   range "0..1023";
  }
  mandatory false;
 }
 leaf NBDLBITMAP30 {
  type uint32 {
   range "0..1073741823";
  }
  mandatory false;
 }
 leaf NBDLBITMAPSIZE {
  type boolean;
  mandatory false;
 }
 leaf PAGINGWEIGHT {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-255;
  }
  mandatory false;
 }
 leaf PRBID {
  type union {
   type int16 {
    range "-1..255";
   }
  }
  mandatory false;
 }
 leaf PRBINDEXOFDLPDCCHCARRIER {
  type union {
   type uint16 {
    range "0..65535";
   }
  }
  mandatory false;
 }
 leaf ULSUBCARRIERUSAGEOFFSET {
  type uint8 {
   range "0..100";
  }
  mandatory false;
 }
 leaf WUSMAXDURATIONFACTOR {
  type enumeration {
   enum val-0;
   enum val-1;
   enum val-2;
   enum val-3;
   enum val-4;
   enum val-5;
   enum val-6;
  }
  mandatory false;
 }
 }
 grouping PRBSECTOREQMGRPITEM-attributes {
 leaf LOCALCELLNAME {
  type string;
  mandatory false;
 }
 leaf LOCALCELLID {
  type union {
   type int16 {
    range "-1..255";
   }
  }
  mandatory false;
 }
 leaf PRBID {
  type union {
   type int16 {
    range "-1..255";
   }
  }
  mandatory false;
 }
 leaf SECTOREQMGROUPID {
  type union {
   type int8 {
    range "-1..35";
   }
  }
  mandatory false;
 }
 leaf SECTOREQMID {
  type union {
   type int32 {
    range "-1..65535";
   }
  }
  mandatory false;
 }
 }
 grouping PRBULSCHCEALGO-attributes {
 leaf LOCALCELLNAME {
  type string;
  mandatory false;
 }
 leaf ACKNACKTRANSRPTCOUNT {
  type enumeration {
   enum val-0;
   enum val-1;
   enum val-2;
   enum val-3;
   enum val-4;
   enum val-5;
   enum val-6;
   enum val-7;
  }
  mandatory false;
 }
 leaf ACKNACKTRANSRPTCOUNTMSG4 {
  type enumeration {
   enum val-0;
   enum val-1;
   enum val-2;
   enum val-3;
   enum val-4;
   enum val-5;
   enum val-6;
   enum val-7;
  }
  mandatory false;
 }
 leaf COVERAGELEVEL {
  type enumeration {
   enum val--1;
   enum val-0;
   enum val-1;
   enum val-2;
  }
  mandatory false;
 }
 leaf EDTMAXTBS {
  type enumeration {
   enum val-0;
   enum val-1;
   enum val-2;
   enum val-3;
   enum val-4;
   enum val-5;
   enum val-6;
   enum val-7;
  }
  mandatory false;
 }
 leaf EDTMSG3MCS {
  type enumeration {
   enum val-0;
   enum val-1;
   enum val-2;
   enum val-3;
   enum val-4;
  }
  mandatory false;
 }
 leaf EDTULTRANSRPTCOUNT {
  type enumeration {
   enum val-0;
   enum val-1;
   enum val-2;
   enum val-3;
   enum val-4;
   enum val-5;
   enum val-6;
   enum val-7;
  }
  mandatory false;
 }
 leaf INITIALMSG3MCS {
  type enumeration {
   enum val-0;
   enum val-1;
   enum val-2;
  }
  mandatory false;
 }
 leaf LOCALCELLID {
  type union {
   type int16 {
    range "-1..255";
   }
  }
  mandatory false;
 }
 leaf NBBSRRETRANSMISSIONTIMER {
  type enumeration {
   enum val-0;
   enum val-1;
   enum val-2;
   enum val-3;
   enum val-4;
   enum val-5;
   enum val-6;
  }
  mandatory false;
 }
 leaf NBLOGICCHSRPROHIBITTIMER {
  type enumeration {
   enum val-0;
   enum val-1;
   enum val-2;
   enum val-3;
   enum val-4;
   enum val-5;
   enum val-6;
   enum val-7;
  }
  mandatory false;
 }
 leaf PRBID {
  type union {
   type int16 {
    range "-1..255";
   }
  }
  mandatory false;
 }
 leaf ULINITIALMCS {
  type enumeration {
   enum val-0;
   enum val-1;
   enum val-2;
   enum val-3;
   enum val-4;
   enum val-5;
   enum val-6;
   enum val-7;
   enum val-8;
   enum val-9;
   enum val-10;
   enum val-11;
   enum val-12;
   enum val-13;
  }
  mandatory false;
 }
 leaf ULINITIALTRANSRPTCOUNT {
  type enumeration {
   enum val-0;
   enum val-1;
   enum val-2;
   enum val-3;
   enum val-4;
   enum val-5;
   enum val-6;
   enum val-7;
  }
  mandatory false;
 }
 leaf ULSCHDURATIONPROPORTION {
  type uint8 {
   range "5..100";
  }
  mandatory false;
 }
 leaf ULSPSEXTINACTIVITYTIMER {
  type uint8 {
   range "1..20";
  }
  mandatory false;
 }
 leaf ULSPSINACTIVITYTIMER {
  type union {
   type uint8 {
    range "0..255";
   }
  }
  mandatory false;
 }
 leaf ULSPSINTERVAL {
  type enumeration {
   enum val-0;
   enum val-1;
   enum val-2;
   enum val-3;
   enum val-4;
   enum val-5;
   enum val-6;
   enum val-7;
  }
  mandatory false;
 }
 }
 grouping PRIVATEBAND-attributes {
 leaf BANDTYPE {
  type boolean;
  mandatory false;
 }
 leaf COMBBANDBW {
  type string;
  mandatory false;
 }
 leaf COMBBANDID {
  type uint16 {
   range "1..266";
  }
  mandatory false;
 }
 leaf OLD_COMBBANDINDEX {
  type union {
   type int8 {
    range "-1..8";
   }
  }
  mandatory false;
 }
 leaf COMBBANDINDEX {
  type union {
   type int8 {
    range "-1..8";
   }
  }
  mandatory false;
 }
 leaf OLD_PRIVATECACOMBID {
  type union {
   type int8 {
    range "-1..63";
   }
  }
  mandatory false;
 }
 leaf PRIVATECACOMBID {
  type union {
   type int8 {
    range "-1..63";
   }
  }
  mandatory false;
 }
 }
 grouping PRIVATECABANDCOMB-attributes {
 leaf BWCOMBSETID {
  type uint8 {
   range "0..31";
  }
  mandatory false;
 }
 leaf MAXAGGREGATEDBW {
  type uint16 {
   range "20..300";
  }
  mandatory false;
 }
 leaf NSAFLAG {
  type boolean;
  mandatory false;
 }
 leaf OLD_PRIVATECACOMBID {
  type union {
   type int8 {
    range "-1..63";
   }
  }
  mandatory false;
 }
 leaf PRIVATECACOMBID {
  type union {
   type int8 {
    range "-1..63";
   }
  }
  mandatory false;
 }
 }
 grouping PUCCHCFG-attributes {
 leaf LOCALCELLNAME {
  type string;
  mandatory false;
 }
 leaf CQIRBNUM {
  type uint8 {
   range "0..20";
  }
  mandatory false;
 }
 leaf DELTASHIFT {
  type enumeration {
   enum val-0;
   enum val-1;
   enum val-2;
  }
  mandatory false;
 }
 leaf F1BCSALLOCFAILRATETHLD {
  type uint8 {
   range "0..100";
  }
  mandatory false;
 }
 leaf F1BCSCHUSAGETHLD {
  type uint8 {
   range "0..100";
  }
  mandatory false;
 }
 leaf F3ALLOCFAILRATETHLD {
  type uint8 {
   range "0..100";
  }
  mandatory false;
 }
 leaf F3CHUSAGETHLD {
  type uint8 {
   range "0..100";
  }
  mandatory false;
 }
 leaf FIXEDSRIPERIOD {
  type enumeration {
   enum val-0;
   enum val-1;
   enum val-2;
   enum val-3;
   enum val-4;
   enum val-5;
  }
  mandatory false;
 }
 leaf FORMAT1CHALLOCMODE {
  type enumeration {
   enum val-0;
   enum val-1;
   enum val-2;
   enum val-3;
  }
  mandatory false;
 }
 leaf FORMAT1CODECHNEXPTHLD {
  type uint8 {
   range "0..20";
  }
  mandatory false;
 }
 leaf FORMAT2CHALLOCMODE {
  type enumeration {
   enum val-0;
   enum val-1;
   enum val-2;
  }
  mandatory false;
 }
 leaf FORMAT3RBNUM {
  type uint8 {
   range "0..2";
  }
  mandatory false;
 }
 leaf LOCALCELLID {
  type union {
   type int16 {
    range "-1..255";
   }
  }
  mandatory false;
 }
 leaf MAX2CCACKCHNUM {
  type enumeration {
   enum val-0;
   enum val-1;
   enum val-2;
   enum val-3;
  }
  mandatory false;
 }
 leaf NASRICHNUM {
  type uint16 {
   range "0..1000";
  }
  mandatory false;
 }
 leaf PUCCHALLOCPOLICY {
  type string;
  mandatory false;
 }
 leaf PUCCHEXTENDEDRBNUM {
  type uint8 {
   range "1..24";
  }
  mandatory false;
 }
 leaf PUCCHREDUCEMINSRIPERIOD {
  type enumeration {
   enum val-0;
   enum val-1;
   enum val-2;
   enum val-3;
   enum val-4;
  }
  mandatory false;
 }
 leaf SRIPERIODADAPTIVE {
  type enumeration {
   enum val-0;
   enum val-1;
   enum val-2;
  }
  mandatory false;
 }
 }
 grouping PUSCHCFG-attributes {
 leaf LOCALCELLNAME {
  type string;
  mandatory false;
 }
 leaf CYCLICSHIFT {
  type uint8 {
   range "0..7";
  }
  mandatory false;
 }
 leaf ESTDPOWERREDUCTVALUE256QAM {
  type uint8 {
   range "0..50";
  }
  mandatory false;
 }
 leaf GROUPASSIGNPUSCH {
  type uint8 {
   range "0..29";
  }
  mandatory false;
 }
 leaf GROUPHOPPINGENABLED {
  type boolean;
  mandatory false;
 }
 leaf HOPPINGMODE {
  type boolean;
  mandatory false;
 }
 leaf HOPPINGOFFSET {
  type uint8 {
   range "0..98";
  }
  mandatory false;
 }
 leaf LOCALCELLID {
  type union {
   type int16 {
    range "-1..255";
   }
  }
  mandatory false;
 }
 leaf NSB {
  type uint8 {
   range "1..4";
  }
  mandatory false;
 }
 leaf PUSCHALGOSWITCH {
  type string;
  mandatory false;
 }
 leaf QAM64ENABLED {
  type boolean;
  mandatory false;
 }
 leaf R12QAM64ENABLED {
  type boolean;
  mandatory false;
 }
 leaf SEQHOPPINGENABLED {
  type boolean;
  mandatory false;
 }
 leaf UL256QAMALGOSWITCH {
  type string;
  mandatory false;
 }
 leaf UL256QAMMCSTBLADPPERIOD {
  type uint16 {
   range "1..1000";
  }
  mandatory false;
 }
 leaf UL256QAMMCSTBLCFGSTRATEGY {
  type boolean;
  mandatory false;
 }
 leaf ULENTER256QAMMCSTBLSINRTHD {
  type int16 {
   range "-100..300";
  }
  mandatory false;
 }
 leaf ULEXIT256QAMMCSTBLSINRTHD {
  type int16 {
   range "-100..300";
  }
  mandatory false;
 }
 }
 grouping PWRSAVINGTIMEPOLICY-attributes {
 leaf STARTTIME {
  type hwat:HH_MM_SS_Time;
  mandatory false;
 }
 leaf STOPTIME {
  type hwat:HH_MM_SS_Time;
  mandatory false;
 }
 leaf OLD_TIMEID {
  type union {
   type int8 {
    range "-1..6";
   }
  }
  mandatory false;
 }
 leaf TIMEID {
  type union {
   type int8 {
    range "-1..6";
   }
  }
  mandatory false;
 }
 leaf OLD_TIMEPOLICYID {
  type union {
   type int16 {
    range "-1..256";
   }
  }
  mandatory false;
 }
 leaf TIMEPOLICYID {
  type union {
   type int16 {
    range "-1..256";
   }
  }
  mandatory false;
 }
 }
 grouping QCI5QICONFIG-attributes {
 leaf ASREFLECTIVEQOSSWITCH {
  type boolean;
  mandatory false;
 }
 leaf OLD_NR5QI {
  type union {
   type int16 {
    range "-1..254";
   }
  }
  mandatory false;
 }
 leaf NR5QI {
  type union {
   type int16 {
    range "-1..254";
   }
  }
  mandatory false;
 }
 leaf QCI {
  type uint8 {
   range "1..254";
  }
  mandatory false;
 }
 }
 grouping QCIEUTRANRELATION-attributes {
 leaf LOCALCELLNAME {
  type string;
  mandatory false;
 }
 leaf OLD_DLEARFCN {
  type union {
   type int32 {
    range "-1..229575";
   }
  }
  mandatory false;
 }
 leaf DLEARFCN {
  type union {
   type int32 {
    range "-1..229575";
   }
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf MOBILITYTARGETIND {
  type string;
  mandatory false;
 }
 leaf OLD_QCIEUTRANFREQRELATIONID {
  type union {
   type int8 {
    range "-1..9";
   }
  }
  mandatory false;
 }
 leaf QCIEUTRANFREQRELATIONID {
  type union {
   type int8 {
    range "-1..9";
   }
  }
  mandatory false;
 }
 }
 grouping QCIGERANRELATION-attributes {
 leaf LOCALCELLNAME {
  type string;
  mandatory false;
 }
 leaf OLD_BCCHGROUPID {
  type union {
   type int8 {
    range "-1..31";
   }
  }
  mandatory false;
 }
 leaf BCCHGROUPID {
  type union {
   type int8 {
    range "-1..31";
   }
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf MOBILITYTARGETIND {
  type string;
  mandatory false;
 }
 leaf OLD_QCIGERANFREQRELATIONID {
  type union {
   type int8 {
    range "-1..9";
   }
  }
  mandatory false;
 }
 leaf QCIGERANFREQRELATIONID {
  type union {
   type int8 {
    range "-1..9";
   }
  }
  mandatory false;
 }
 }
 grouping QCIPARA-attributes {
 leaf AGGREGATIONATTRIBUTE {
  type string;
  mandatory false;
 }
 leaf CBTCPACKETDELAYBUDGET {
  type uint16 {
   range "100..1000";
  }
  mandatory false;
 }
 leaf CBTCRLCPDCPPARAGROUPID {
  type union {
   type uint8 {
    range "0..255";
   }
  }
  mandatory false;
 }
 leaf CIOTUEINACTIVETIMER {
  type uint16 {
   range "0..3600";
  }
  mandatory false;
 }
 leaf DLMINGBRFORMODEA {
  type uint32 {
   range "0..2560000";
  }
  mandatory false;
 }
 leaf DLMINGBRFORMODEB {
  type uint32 {
   range "0..2560000";
  }
  mandatory false;
 }
 leaf DLPDBFOREXTENDEDQCI {
  type union {
   type uint16 {
    range "0..500";
   }
  }
  mandatory false;
 }
 leaf DRXPARAGROUPID {
  type union {
   type uint8 {
    range "0..255";
   }
  }
  mandatory false;
 }
 leaf EMTCMODEACL0RLCPARAGROUPID {
  type union {
   type uint8 {
    range "0..255";
   }
  }
  mandatory false;
 }
 leaf EMTCMODEARLCPARAGROUPID {
  type union {
   type uint8 {
    range "0..255";
   }
  }
  mandatory false;
 }
 leaf EMTCMODEBCL2RLCPARAGROUPID {
  type union {
   type uint8 {
    range "0..255";
   }
  }
  mandatory false;
 }
 leaf EMTCMODEBRLCPARAGROUPID {
  type union {
   type uint8 {
    range "0..255";
   }
  }
  mandatory false;
 }
 leaf EMTCUERAIACTIVATIONFLAG {
  type boolean;
  mandatory false;
 }
 leaf EUTRA5GCRLCPDCPPARAMGRPID {
  type union {
   type uint8 {
    range "0..255";
   }
  }
  mandatory false;
 }
 leaf EXTQCICOUNTERINDEX {
  type enumeration {
   enum val-0;
   enum val-1;
   enum val-2;
   enum val-3;
   enum val-4;
   enum val-5;
   enum val-6;
   enum val-7;
   enum val-8;
   enum val-9;
  }
  mandatory false;
 }
 leaf FLOWCTRLTYPE {
  type boolean;
  mandatory false;
 }
 leaf FREEUSERFLAG {
  type boolean;
  mandatory false;
 }
 leaf INTERRATPOLICYCFGGROUPID {
  type uint8 {
   range "0..39";
  }
  mandatory false;
 }
 leaf L4SFLAG {
  type boolean;
  mandatory false;
 }
 leaf LOCALUPIPPOLICY {
  type enumeration {
   enum val-0;
   enum val-1;
   enum val-2;
  }
  mandatory false;
 }
 leaf LOGICALCHANNELPRIORITY {
  type uint8 {
   range "4..16";
  }
  mandatory false;
 }
 leaf LTEPTTDEDICATEDEXTENDEDQCI {
  type boolean;
  mandatory false;
 }
 leaf LTEPTTDOWNLINKPRIORITY {
  type boolean;
  mandatory false;
 }
 leaf LTEPTTUPLINKPRIORITY {
  type boolean;
  mandatory false;
 }
 leaf MULTICARRCFGGROUPID {
  type union {
   type uint8 {
    range "0..255";
   }
  }
  mandatory false;
 }
 leaf NBCE0RLCPDCPPARAGROUPID {
  type union {
   type uint8 {
    range "0..255";
   }
  }
  mandatory false;
 }
 leaf NBCE1RLCPDCPPARAGROUPID {
  type union {
   type uint8 {
    range "0..255";
   }
  }
  mandatory false;
 }
 leaf NBRLCPDCPPARAGROUPID {
  type union {
   type uint8 {
    range "0..255";
   }
  }
  mandatory false;
 }
 leaf NBSCHPRIWEIGHTINGFACTOR {
  type uint8 {
   range "0..7";
  }
  mandatory false;
 }
 leaf NBUEMOBILITY {
  type enumeration {
   enum val-0;
   enum val-1;
   enum val-2;
  }
  mandatory false;
 }
 leaf NBUERAIACTIVATIONFLAG {
  type boolean;
  mandatory false;
 }
 leaf NSADCRLCPDCPPARAMGROUPID {
  type union {
   type uint8 {
    range "0..255";
   }
  }
  mandatory false;
 }
 leaf OLDSCPTRANSPARENTTRANSSW {
  type boolean;
  mandatory false;
 }
 leaf PDCPDISCARDTIMERRECONFIGSW {
  type boolean;
  mandatory false;
 }
 leaf PDCPSNSIZERECONFIGSWITCH {
  type boolean;
  mandatory false;
 }
 leaf PREALLOCATIONWEIGHT {
  type uint8 {
   range "0..10";
  }
  mandatory false;
 }
 leaf PRIORITISEDBITRATE {
  type enumeration {
   enum val-0;
   enum val-1;
   enum val-2;
   enum val-3;
   enum val-4;
   enum val-5;
   enum val-6;
   enum val-7;
   enum val-8;
   enum val-9;
   enum val-10;
  }
  mandatory false;
 }
 leaf OLD_QCI {
  type union {
   type int16 {
    range "-1..254";
   }
  }
  mandatory false;
 }
 leaf QCI {
  type union {
   type int16 {
    range "-1..254";
   }
  }
  mandatory false;
 }
 leaf QCISPECIFICBESTEFFORTGBR {
  type uint16 {
   range "0..65535";
  }
  mandatory false;
 }
 leaf RLCMODERECONFIGSWITCH {
  type boolean;
  mandatory false;
 }
 leaf RLCPDCPPARAGROUPID {
  type uint8 {
   range "0..240";
  }
  mandatory false;
 }
 leaf SERVICETYPE {
  type enumeration {
   enum val-5;
   enum val-7;
   enum val-9;
   enum val-11;
  }
  mandatory false;
 }
 leaf SHORTTTIRLCPARAMGROUPID {
  type union {
   type uint8 {
    range "0..255";
   }
  }
  mandatory false;
 }
 leaf UEINACTIVETIMERFORQCI {
  type uint16 {
   range "0..3600";
  }
  mandatory false;
 }
 leaf UEINACTIVETIMERPRI {
  type uint8 {
   range "0..255";
  }
  mandatory false;
 }
 leaf UEINACTIVITYTIMERDYNDRXQCI {
  type uint16 {
   range "10..3600";
  }
  mandatory false;
 }
 leaf ULFORWARDPACKETWAITTIMER {
  type uint16 {
   range "1..1000";
  }
  mandatory false;
 }
 leaf ULMINGBRFORMODEA {
  type uint32 {
   range "0..2560000";
  }
  mandatory false;
 }
 leaf ULMINGBRFORMODEB {
  type uint32 {
   range "0..2560000";
  }
  mandatory false;
 }
 leaf ULSYNTIMERFORQCI {
  type uint16 {
   range "0..3600";
  }
  mandatory false;
 }
 }
 grouping QCIUETIMERCONFIG-attributes {
 leaf MAXNUMUESYNCOROUTOFSYNCIND {
  type uint8 {
   range "0..200";
  }
  mandatory false;
 }
 leaf OLD_QCI {
  type union {
   type int16 {
    range "-1..254";
   }
  }
  mandatory false;
 }
 leaf QCI {
  type union {
   type int16 {
    range "-1..254";
   }
  }
  mandatory false;
 }
 leaf TIMERDURATION {
  type uint16 {
   range "1..3600";
  }
  mandatory false;
 }
 leaf TIMERDURATIONMILLISECOND {
  type uint32 {
   range "0..240000";
  }
  mandatory false;
 }
 leaf OLD_TIMERTYPE {
  type enumeration {
   enum val--1;
   enum val-0;
   enum val-1;
   enum val-2;
   enum val-3;
   enum val-4;
   enum val-5;
   enum val-6;
  }
  mandatory false;
 }
 leaf TIMERTYPE {
  type enumeration {
   enum val--1;
   enum val-0;
   enum val-1;
   enum val-2;
   enum val-3;
   enum val-4;
   enum val-5;
   enum val-6;
  }
  mandatory false;
 }
 }
 grouping QCIUTRANRELATION-attributes {
 leaf LOCALCELLNAME {
  type string;
  mandatory false;
 }
 leaf OLD_LOCALCELLID {
  type union {
   type int16 {
    range "-1..255";
   }
  }
  mandatory false;
 }
 leaf LOCALCELLID {
  type union {
   type int16 {
    range "-1..255";
   }
  }
  mandatory false;
 }
 leaf MOBILITYTARGETIND {
  type string;
  mandatory false;
 }
 leaf OLD_QCIUTRANFREQRELATIONID {
  type union {
   type int8 {
    range "-1..9";
   }
  }
  mandatory false;
 }
 leaf QCIUTRANFREQRELATIONID {
  type union {
   type int8 {
    range "-1..9";
   }
  }
  mandatory false;
 }
 leaf OLD_UTRANDLARFCN {
  type union {
   type int16 {
    range "-1..16383";
   }
  }
  mandatory false;
 }
 leaf UTRANDLARFCN {
  type union {
   type int16 {
    range "-1..16383";
   }
  }
  mandatory false;
 }
 }
 grouping QOSPOLICY-attributes {
 leaf DLSGBR {
  type uint32 {
   range "0..4294967295";
  }
  mandatory false;
 }
 leaf DLSMBR {
  type uint32 {
   range "0..4294967295";
  }
  mandatory false;
 }
 leaf PRIQUEUEID {
  type enumeration {
   enum val-0;
   enum val-1;
   enum val-2;
   enum val-3;
   enum val-4;
   enum val-5;
   enum val-6;
   enum val-7;
  }
  mandatory false;
 }
 leaf OLD_QOSPOLICYID {
  type union {
   type int8 {
    range "-1..127";
   }
  }
  mandatory false;
 }
 leaf QOSPOLICYID {
  type union {
   type int8 {
    range "-1..127";
   }
  }
  mandatory false;
 }
 leaf RATECONTROLSWITCH {
  type boolean;
  mandatory false;
 }
 leaf TRAFFICTYPE {
  type enumeration {
   enum val-0;
   enum val-1;
   enum val-2;
  }
  mandatory false;
 }
 }
 grouping RACHCFG-attributes {
 leaf LOCALCELLNAME {
  type string;
  mandatory false;
 }
 leaf CONTENTIONRESOLUTIONTIMER {
  type enumeration {
   enum val-4;
   enum val-5;
   enum val-6;
   enum val-7;
  }
  mandatory false;
 }
 leaf EMTCPRACHPERIOD {
  type boolean;
  mandatory false;
 }
 leaf LOCALCELLID {
  type union {
   type int16 {
    range "-1..255";
   }
  }
  mandatory false;
 }
 leaf MAXHARQMSG3TX {
  type uint8 {
   range "1..8";
  }
  mandatory false;
 }
 leaf MESSAGESIZEGROUPA {
  type enumeration {
   enum val-0;
   enum val-1;
   enum val-2;
   enum val-3;
  }
  mandatory false;
 }
 leaf NBCYCLICPREFIXLENGTH {
  type boolean;
  mandatory false;
 }
 leaf NBPATHLOSSCOEFF {
  type enumeration {
   enum val-0;
   enum val-1;
   enum val-2;
   enum val-3;
   enum val-4;
   enum val-5;
   enum val-6;
   enum val-7;
  }
  mandatory false;
 }
 leaf NBRSRPFIRSTTHRESHOLD {
  type int16 {
   range "-141..-44";
  }
  mandatory false;
 }
 leaf NBRSRPSECONDTHRESHOLD {
  type int16 {
   range "-141..-44";
  }
  mandatory false;
 }
 leaf NBSRP0 {
  type int8 {
   range "-126..24";
  }
  mandatory false;
 }
 leaf PRACHCONFIGINDEX {
  type uint8 {
   range "0..63";
  }
  mandatory false;
 }
 leaf PRACHCONFIGINDEXCFGIND {
  type boolean;
  mandatory false;
 }
 leaf PRACHCONFIGPATTERN {
  type enumeration {
   enum val-0;
   enum val-1;
   enum val-2;
  }
  mandatory false;
 }
 leaf PRACHFREQOFFSET {
  type uint8 {
   range "0..94";
  }
  mandatory false;
 }
 leaf PRACHFREQOFFSETSTRATEGY {
  type enumeration {
   enum val-0;
   enum val-1;
   enum val-2;
  }
  mandatory false;
 }
 leaf PRACHSTARTTIMECFGIND {
  type boolean;
  mandatory false;
 }
 leaf PREAMBINITRCVTARGETPWR {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
  }
  mandatory false;
 }
 leaf PREAMBINITRCVTARGETPWRCE1 {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
  }
  mandatory false;
 }
 leaf PREAMBLETRANSMAX {
  type enumeration {
   enum val-0;
   enum val-1;
   enum val-2;
   enum val-3;
   enum val-4;
   enum val-5;
   enum val-6;
   enum val-7;
   enum val-8;
   enum val-9;
   enum val-10;
  }
  mandatory false;
 }
 leaf PWRRAMPINGSTEP {
  type enumeration {
   enum val-0;
   enum val-1;
   enum val-2;
   enum val-3;
  }
  mandatory false;
 }
 leaf PWRRAMPINGSTEPCE1 {
  type enumeration {
   enum val-0;
   enum val-1;
   enum val-2;
   enum val-3;
   enum val-4;
  }
  mandatory false;
 }
 leaf RAPREAMBLEGRPARATIO {
  type uint8 {
   range "6..100";
  }
  mandatory false;
 }
 leaf RANDOMPREAMBLERATIO {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf UERAINFOREPORTRATIOTHD {
  type uint8 {
   range "0..100";
  }
  mandatory false;
 }
 leaf VOLTEHORAMPREAMBLEPWROFS {
  type uint8 {
   range "0..10";
  }
  mandatory false;
 }
 }
 grouping RATFREQPRIORITYGROUP-attributes {
 leaf AGGREGATIONATTRIBUTE {
  type string;
  mandatory false;
 }
 leaf BANDINDICATOR {
  type boolean;
  mandatory false;
 }
 leaf CONNFREQPRIORITY {
  type uint8 {
   range "0..16";
  }
  mandatory false;
 }
 leaf COVBASEDHOEVENTTYPE {
  type enumeration {
   enum val-0;
   enum val-1;
   enum val-2;
   enum val-3;
  }
  mandatory false;
 }
 leaf COVIFHOA5THLD1RSRPOFS {
  type int8 {
   range "-80..80";
  }
  mandatory false;
 }
 leaf COVIFHOA5THLD1RSRQOFS {
  type int8 {
   range "-80..80";
  }
  mandatory false;
 }
 leaf COVIFHORSRPHYST {
  type union {
   type uint8 {
    range "0..254";
   }
  }
  mandatory false;
 }
 leaf COVIFHORSRPTIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
  }
  mandatory false;
 }
 leaf COVIFHORSRQHYST {
  type union {
   type uint8 {
    range "0..254";
   }
  }
  mandatory false;
 }
 leaf COVIFHORSRQTIMETOTRIG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
  }
  mandatory false;
 }
 leaf COVINTERFREQHORSRPTHLDOFS {
  type int8 {
   range "-80..80";
  }
  mandatory false;
 }
 leaf COVINTERFREQHORSRQTHLDOFS {
  type int8 {
   range "-80..80";
  }
  mandatory false;
 }
 leaf OLD_DLEARFCN {
  type union {
   type int32 {
    range "-1..3279165";
   }
  }
  mandatory false;
 }
 leaf DLEARFCN {
  type union {
   type int32 {
    range "-1..3279165";
   }
  }
  mandatory false;
 }
 leaf IMEISVCOVNRB1THDRSRPOFS {
  type int8 {
   range "-100..100";
  }
  mandatory false;
 }
 leaf IMEISVSERVNRB1THDRSRPOFS {
  type int8 {
   range "-100..100";
  }
  mandatory false;
 }
 leaf INTERFREQUENUMOFFLOADTHD {
  type uint16 {
   range "0..65535";
  }
  mandatory false;
 }
 leaf INTERRATUENUMOFFLOADTHD {
  type uint16 {
   range "1..65535";
  }
  mandatory false;
 }
 leaf MEASPRIORITYFORFREQPRIHO {
  type union {
   type uint8 {
    range "0..255";
   }
  }
  mandatory false;
 }
 leaf PRIORITY {
  type uint8 {
   range "0..7";
  }
  mandatory false;
 }
 leaf OLD_RATFREQPRIORITYGROUPID {
  type union {
   type int16 {
    range "-1..255";
   }
  }
  mandatory false;
 }
 leaf RATFREQPRIORITYGROUPID {
  type union {
   type int16 {
    range "-1..255";
   }
  }
  mandatory false;
 }
 leaf OLD_RATTYPE {
  type enumeration {
   enum val--1;
   enum val-0;
   enum val-1;
   enum val-2;
   enum val-3;
   enum val-4;
   enum val-5;
  }
  mandatory false;
 }
 leaf RATTYPE {
  type enumeration {
   enum val--1;
   enum val-0;
   enum val-1;
   enum val-2;
   enum val-3;
   enum val-4;
   enum val-5;
  }
  mandatory false;
 }
 leaf UENUMOFFLOADPROHIBITTHD {
  type uint16 {
   range "0..65535";
  }
  mandatory false;
 }
 leaf VONRPRIORITY {
  type union {
   type uint8 {
    range "0..255";
   }
  }
  mandatory false;
 }
 }
 grouping RELAYEXTENDEDQCI-attributes {
 leaf DEFAULTBEARERIND {
  type boolean;
  mandatory false;
 }
 leaf DLSCHWEIGHT {
  type uint8 {
   range "1..100";
  }
  mandatory false;
 }
 leaf DSCPLOWER {
  type uint8 {
   range "0..63";
  }
  mandatory false;
 }
 leaf DSCPUPPER {
  type uint8 {
   range "0..63";
  }
  mandatory false;
 }
 leaf OLD_EXTENDEDQCI {
  type union {
   type int16 {
    range "-1..254";
   }
  }
  mandatory false;
 }
 leaf EXTENDEDQCI {
  type union {
   type int16 {
    range "-1..254";
   }
  }
  mandatory false;
 }
 leaf PQTYPE {
  type enumeration {
   enum val-0;
   enum val-1;
   enum val-2;
   enum val-3;
  }
  mandatory false;
 }
 leaf RLCPDCPPARAGROUPID {
  type uint8 {
   range "0..230";
  }
  mandatory false;
 }
 leaf RRNPREALLOCATIONWEIGHT {
  type uint8 {
   range "0..10";
  }
  mandatory false;
 }
 leaf SCHTYPE {
  type enumeration {
   enum val-0;
   enum val-1;
   enum val-2;
  }
  mandatory false;
 }
 leaf ULSCHWEIGHT {
  type uint8 {
   range "1..100";
  }
  mandatory false;
 }
 }
 grouping RLCPDCPPARAGROUP-attributes {
 leaf AMPDCPSNSIZE {
  type enumeration {
   enum val-0;
   enum val-1;
   enum val-2;
  }
  mandatory false;
 }
 leaf CAUEREORDERINGTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf CAUERLCPARAADPTIVETHD {
  type uint16 {
   range "0..65535";
  }
  mandatory false;
 }
 leaf CAUESTATPROHTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-47;
   enum val-48;
   enum val-49;
   enum val-50;
   enum val-51;
   enum val-52;
   enum val-53;
   enum val-54;
   enum val-55;
  }
  mandatory false;
 }
 leaf CATTYPE {
  type enumeration {
   enum val-0;
   enum val-1;
   enum val-2;
   enum val-3;
   enum val-4;
   enum val-5;
  }
  mandatory false;
 }
 leaf DISCARDTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf DL4CC5CCUEREORDERINGTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
  }
  mandatory false;
 }
 leaf DL4CC5CCUESTATPROHTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-47;
   enum val-48;
   enum val-49;
   enum val-50;
   enum val-51;
   enum val-52;
   enum val-53;
   enum val-54;
   enum val-55;
  }
  mandatory false;
 }
 leaf DLPDCPDISCARDTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
  }
  mandatory false;
 }
 leaf DLRLCSNSIZE {
  type enumeration {
   enum val-0;
   enum val-1;
   enum val-2;
  }
  mandatory false;
 }
 leaf ENODEBAMREORDERINGTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
  }
  mandatory false;
 }
 leaf ENODEBMAXRETXTHRESHOLD {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf ENODEBPOLLBYTE {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf ENODEBPOLLPDU {
  type enumeration {
   enum val-0;
   enum val-1;
   enum val-2;
   enum val-3;
   enum val-4;
   enum val-5;
   enum val-6;
   enum val-7;
  }
  mandatory false;
 }
 leaf ENODEBPOLLRETRANSMITTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-47;
   enum val-48;
   enum val-49;
   enum val-50;
   enum val-51;
   enum val-52;
   enum val-53;
   enum val-54;
   enum val-55;
   enum val-56;
   enum val-57;
   enum val-58;
  }
  mandatory false;
 }
 leaf ENODEBREORDERINGTIMERADAPT {
  type boolean;
  mandatory false;
 }
 leaf ENODEBSTATUSPROHIBITTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-47;
   enum val-48;
   enum val-49;
   enum val-50;
   enum val-51;
   enum val-52;
   enum val-53;
   enum val-54;
   enum val-55;
   enum val-56;
   enum val-57;
   enum val-58;
   enum val-59;
   enum val-60;
   enum val-61;
  }
  mandatory false;
 }
 leaf ENODEBUMREORDERINGTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
  }
  mandatory false;
 }
 leaf ENODEBPDCPREORDERINGSWITCH {
  type boolean;
  mandatory false;
 }
 leaf ENODEBPDCPREORDERINGTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
  }
  mandatory false;
 }
 leaf NBDLPDCPDISCARDTIMER {
  type enumeration {
   enum val-0;
   enum val-1;
   enum val-2;
   enum val-3;
   enum val-4;
   enum val-5;
  }
  mandatory false;
 }
 leaf NBENODEBMAXRETXTHRESHOLD {
  type enumeration {
   enum val-0;
   enum val-1;
   enum val-2;
   enum val-3;
   enum val-4;
   enum val-5;
   enum val-6;
   enum val-7;
  }
  mandatory false;
 }
 leaf NBENODEBPOLLRETXTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf NBPDCPDISCARDTIMER {
  type enumeration {
   enum val-0;
   enum val-1;
   enum val-2;
   enum val-3;
   enum val-4;
   enum val-5;
  }
  mandatory false;
 }
 leaf NBUEMAXRETXTHRESHOLD {
  type enumeration {
   enum val-0;
   enum val-1;
   enum val-2;
   enum val-3;
   enum val-4;
   enum val-5;
   enum val-6;
   enum val-7;
  }
  mandatory false;
 }
 leaf NBUEPOLLRETXTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf NONSPTUMUEADAPTSWITCH {
  type boolean;
  mandatory false;
 }
 leaf PDCPOUTOFORDERDELIVERYIND {
  type boolean;
  mandatory false;
 }
 leaf PDCPSNSIZE {
  type enumeration {
   enum val-0;
   enum val-1;
   enum val-2;
  }
  mandatory false;
 }
 leaf PDCPSTATUSRPTREQ {
  type boolean;
  mandatory false;
 }
 leaf RLCMODE {
  type enumeration {
   enum val-1;
   enum val-2;
  }
  mandatory false;
 }
 leaf RLCPARAADAPTSWITCH {
  type boolean;
  mandatory false;
 }
 leaf OLD_RLCPDCPPARAGROUPID {
  type union {
   type int16 {
    range "-1..240";
   }
  }
  mandatory false;
 }
 leaf RLCPDCPPARAGROUPID {
  type union {
   type int16 {
    range "-1..240";
   }
  }
  mandatory false;
 }
 leaf UEAMREORDERINGTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
  }
  mandatory false;
 }
 leaf UEMAXRETXTHRESHOLD {
  type enumeration {
   enum val-0;
   enum val-1;
   enum val-2;
   enum val-3;
   enum val-4;
   enum val-5;
   enum val-6;
   enum val-7;
  }
  mandatory false;
 }
 leaf UEPDCPREORDERINGTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
  }
  mandatory false;
 }
 leaf UEPOLLBYTE {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf UEPOLLPDU {
  type enumeration {
   enum val-0;
   enum val-1;
   enum val-2;
   enum val-3;
   enum val-4;
   enum val-5;
   enum val-6;
   enum val-7;
  }
  mandatory false;
 }
 leaf UEPOLLRETRANSMITTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-47;
   enum val-48;
   enum val-49;
   enum val-50;
   enum val-51;
   enum val-52;
   enum val-53;
   enum val-54;
   enum val-55;
   enum val-56;
   enum val-57;
   enum val-58;
  }
  mandatory false;
 }
 leaf UEPOLLRTRTIMERPRESET {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-47;
   enum val-48;
   enum val-49;
   enum val-50;
   enum val-51;
   enum val-52;
   enum val-53;
   enum val-54;
  }
  mandatory false;
 }
 leaf UESTATPROHTIMERPRESET {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-47;
   enum val-48;
   enum val-49;
   enum val-50;
   enum val-51;
   enum val-52;
   enum val-53;
   enum val-54;
   enum val-55;
  }
  mandatory false;
 }
 leaf UESTATUSPROHIBITTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-47;
   enum val-48;
   enum val-49;
   enum val-50;
   enum val-51;
   enum val-52;
   enum val-53;
   enum val-54;
   enum val-55;
   enum val-56;
   enum val-57;
   enum val-58;
   enum val-59;
   enum val-60;
   enum val-61;
  }
  mandatory false;
 }
 leaf UEUMREORDERINGTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
  }
  mandatory false;
 }
 leaf ULDLDISCARDTIMERSWITCH {
  type boolean;
  mandatory false;
 }
 leaf ULRLCSNSIZE {
  type boolean;
  mandatory false;
 }
 leaf ENODEBPOLLRTRTIMERPRESET {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-47;
   enum val-48;
   enum val-49;
   enum val-50;
   enum val-51;
   enum val-52;
   enum val-53;
   enum val-54;
  }
  mandatory false;
 }
 leaf ENODEBSTATPROHTIMERPRESET {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-47;
   enum val-48;
   enum val-49;
   enum val-50;
   enum val-51;
   enum val-52;
   enum val-53;
   enum val-54;
   enum val-55;
  }
  mandatory false;
 }
 }
 grouping RLFTIMERCONSTGROUP-attributes {
 leaf LOCALCELLNAME {
  type string;
  mandatory false;
 }
 leaf OLD_LOCALCELLID {
  type union {
   type int16 {
    range "-1..255";
   }
  }
  mandatory false;
 }
 leaf LOCALCELLID {
  type union {
   type int16 {
    range "-1..255";
   }
  }
  mandatory false;
 }
 leaf N310 {
  type enumeration {
   enum val-0;
   enum val-1;
   enum val-2;
   enum val-3;
   enum val-4;
   enum val-5;
   enum val-6;
   enum val-7;
  }
  mandatory false;
 }
 leaf N311 {
  type enumeration {
   enum val-0;
   enum val-1;
   enum val-2;
   enum val-3;
   enum val-4;
   enum val-5;
   enum val-6;
   enum val-7;
  }
  mandatory false;
 }
 leaf OLD_RLFTIMERCONSTGROUPID {
  type union {
   type int8 {
    range "-1..9";
   }
  }
  mandatory false;
 }
 leaf RLFTIMERCONSTGROUPID {
  type union {
   type int8 {
    range "-1..9";
   }
  }
  mandatory false;
 }
 leaf T301 {
  type enumeration {
   enum val-0;
   enum val-1;
   enum val-2;
   enum val-3;
   enum val-4;
   enum val-5;
   enum val-6;
   enum val-7;
  }
  mandatory false;
 }
 leaf T301CE {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf T310 {
  type enumeration {
   enum val-0;
   enum val-1;
   enum val-2;
   enum val-3;
   enum val-4;
   enum val-5;
   enum val-6;
  }
  mandatory false;
 }
 leaf T310CE {
  type enumeration {
   enum val-0;
   enum val-1;
   enum val-2;
   enum val-3;
   enum val-4;
   enum val-5;
   enum val-6;
   enum val-7;
   enum val-8;
  }
  mandatory false;
 }
 leaf T311 {
  type enumeration {
   enum val-0;
   enum val-1;
   enum val-2;
   enum val-3;
   enum val-4;
   enum val-5;
   enum val-6;
  }
  mandatory false;
 }
 leaf T311CE {
  type enumeration {
   enum val-0;
   enum val-1;
   enum val-2;
   enum val-3;
   enum val-4;
   enum val-5;
   enum val-6;
  }
  mandatory false;
 }
 }
 grouping RRCCONNSTATETIMER-attributes {
 leaf BTRUNCINACTIVETIMER {
  type uint16 {
   range "0..3600";
  }
  mandatory false;
 }
 leaf BWPREFERENCEINDTIMER {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf DRXRRCCONNRELTIMEROFFSET {
  type uint16 {
   range "0..9000";
  }
  mandatory false;
 }
 leaf EMTCRRCCONNRELTIMEROFFSET {
  type uint16 {
   range "0..60000";
  }
  mandatory false;
 }
 leaf EXTENDEDWAITTIME {
  type uint16 {
   range "1..1800";
  }
  mandatory false;
 }
 leaf FILTERREPTRRCCONNREQTIMER {
  type uint8 {
   range "0..15";
  }
  mandatory false;
 }
 leaf NOCONTEXTREESTTIMEROFFSET {
  type uint16 {
   range "0..2000";
  }
  mandatory false;
 }
 leaf OUTOFSYNCRELTIMEROFFSET {
  type uint16 {
   range "0..65535";
  }
  mandatory false;
 }
 leaf OVERHEATINGINDPROHIBITTMR {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf POWERPREFINDICATIONTIMER {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 leaf REPTRRCREESTPROTECTTIMER {
  type uint16 {
   range "0..3600";
  }
  mandatory false;
 }
 leaf RRCCONNRELTIMER {
  type uint16 {
   range "450..10000";
  }
  mandatory false;
 }
 leaf SRLTERRCCONNRELTIMEROFFSET {
  type uint16 {
   range "0..20000";
  }
  mandatory false;
 }
 leaf T302 {
  type uint8 {
   range "1..16";
  }
  mandatory false;
 }
 leaf T304FOREUTRAN {
  type enumeration {
   enum val-0;
   enum val-1;
   enum val-2;
   enum val-3;
   enum val-4;
   enum val-5;
   enum val-6;
  }
  mandatory false;
 }
 leaf T304FORGERAN {
  type enumeration {
   enum val-0;
   enum val-1;
   enum val-2;
   enum val-3;
   enum val-4;
   enum val-5;
   enum val-6;
  }
  mandatory false;
 }
 leaf T320FORLOADBALANCE {
  type enumeration {
   enum val-0;
   enum val-1;
   enum val-2;
   enum val-3;
   enum val-4;
   enum val-5;
   enum val-6;
  }
  mandatory false;
 }
 leaf T320FOROTHER {
  type enumeration {
   enum val-0;
   enum val-1;
   enum val-2;
   enum val-3;
   enum val-4;
   enum val-5;
   enum val-6;
  }
  mandatory false;
 }
 leaf ULSYNTIMERDYNDRX {
  type uint16 {
   range "5..3600";
  }
  mandatory false;
 }
 }
 grouping RRUJOINTCALPARACFG-attributes {
 leaf LOCALCELLNAME {
  type string;
  mandatory false;
 }
 leaf AAUPASSIVEPORTCALIBPERIOD {
  type union {
   type uint16 {
    range "0..65535";
   }
  }
  mandatory false;
 }
 leaf ANTJOINTCHNCALIBASSISTSW {
  type boolean;
  mandatory false;
 }
 leaf DSSPHASECALIBSWITCH {
  type boolean;
  mandatory false;
 }
 leaf EXTERNALCALIBSWITCHFOR4T {
  type boolean;
  mandatory false;
 }
 leaf FDDCHNCALIBOPTSW {
  type string;
  mandatory false;
 }
 leaf LOCALCELLID {
  type union {
   type int16 {
    range "-1..255";
   }
  }
  mandatory false;
 }
 leaf RRUCALIBPORTCBLCONNCHKSW {
  type boolean;
  mandatory false;
 }
 leaf RRUCALIBPORTCBLCONNCHKTHLD {
  type int8 {
   range "-6..10";
  }
  mandatory false;
 }
 leaf TXCHNCALPERIOD {
  type uint16 {
   range "1..1440";
  }
  mandatory false;
 }
 leaf TXCHNCALSWITCH {
  type boolean;
  mandatory false;
 }
 leaf TXCHNCALTIME {
  type hwat:HH_MM_SS_Time;
  mandatory false;
 }
 }
 grouping S1-attributes {
 leaf CNOPSHARINGGROUPID {
  type union {
   type uint8 {
    range "0..255";
   }
  }
  mandatory false;
 }
 leaf CNOPERATORID {
  type uint8 {
   range "0..5";
  }
  mandatory false;
 }
 leaf CPEPGROUPID {
  type uint16 {
   range "0..65535";
  }
  mandatory false;
 }
 leaf DEDICATEDNETWORKIND {
  type string;
  mandatory false;
 }
 leaf EPGROUPCFGFLAG {
  type enumeration {
   enum val-0;
   enum val-1;
   enum val-2;
  }
  mandatory false;
 }
 leaf MDTENABLE {
  type boolean;
  mandatory false;
 }
 leaf MMERELEASE {
  type enumeration {
   enum val-0;
   enum val-1;
   enum val-2;
   enum val-3;
   enum val-4;
   enum val-5;
   enum val-6;
   enum val-7;
   enum val-8;
   enum val-9;
  }
  mandatory false;
 }
 leaf PRIORITY {
  type uint8 {
   range "0..255";
  }
  mandatory false;
 }
 leaf OLD_S1ID {
  type union {
   type int8 {
    range "-1..63";
   }
  }
  mandatory false;
 }
 leaf S1ID {
  type union {
   type int8 {
    range "-1..63";
   }
  }
  mandatory false;
 }
 leaf UPEPGROUPID {
  type uint16 {
   range "0..65535";
  }
  mandatory false;
 }
 leaf USERLABEL {
  type string {
   length "0..256";
  }
  mandatory false;
 }
 }
 grouping S1INTERFACE-attributes {
 leaf AUTOCFGFLAG {
  type boolean;
  mandatory false;
 }
 leaf CNOPSHARINGGROUPID {
  type union {
   type uint8 {
    range "0..255";
   }
  }
  mandatory false;
 }
 leaf CNOPERATORID {
  type uint8 {
   range "0..5";
  }
  mandatory false;
 }
 leaf CTRLMODE {
  type boolean;
  mandatory false;
 }
 leaf DEDICATEDNETWORKIND {
  type string;
  mandatory false;
 }
 leaf MMERELEASE {
  type enumeration {
   enum val-0;
   enum val-1;
   enum val-2;
   enum val-3;
   enum val-4;
   enum val-5;
   enum val-6;
   enum val-7;
   enum val-8;
   enum val-9;
  }
  mandatory false;
 }
 leaf PRIORITY {
  type uint8 {
   range "0..255";
  }
  mandatory false;
 }
 leaf S1CPBEARERID {
  type union {
   type uint32 {
    range "0..79999";
   }
  }
  mandatory false;
 }
 leaf OLD_S1INTERFACEID {
  type union {
   type int32 {
    range "-1..65534";
   }
  }
  mandatory false;
 }
 leaf S1INTERFACEID {
  type union {
   type int32 {
    range "-1..65534";
   }
  }
  mandatory false;
 }
 leaf S1INTERFACEISBLOCK {
  type boolean;
  mandatory false;
 }
 }
 grouping S1REESTTIMER-attributes {
 leaf S1REESTMAXTIMER {
  type uint16 {
   range "1..300";
  }
  mandatory false;
 }
 leaf S1REESTMINTIMER {
  type uint16 {
   range "1..300";
  }
  mandatory false;
 }
 }
 grouping SCAPPPARACFG-attributes {
 leaf APPCFGTARGETIND {
  type string;
  mandatory false;
 }
 leaf APPDNS {
  type string {
   length "1..49";
  }
  mandatory false;
 }
 leaf OLD_APPDNSID {
  type union {
   type int16 {
    range "-1..301";
   }
  }
  mandatory false;
 }
 leaf APPDNSID {
  type union {
   type int16 {
    range "-1..301";
   }
  }
  mandatory false;
 }
 leaf APPIDENTTYPE {
  type enumeration {
   enum val-0;
   enum val-1;
   enum val-2;
   enum val-3;
   enum val-4;
  }
  mandatory false;
 }
 leaf APPIPV4 {
  type inet:ipv4-address;
  mandatory false;
 }
 leaf APPIPV6 {
  type inet:ipv6-address;
  mandatory false;
 }
 leaf APPNAME {
  type string {
   length "0..31";
  }
  mandatory false;
 }
 leaf ASPARAGROUPID {
  type union {
   type uint8 {
    range "0..255";
   }
  }
  mandatory false;
 }
 leaf MAINAPPDNSFLAG {
  type enumeration {
   enum val-0;
   enum val-1;
   enum val-2;
  }
  mandatory false;
 }
 leaf MAINAPPDNSID {
  type union {
   type uint16 {
    range "0..65535";
   }
  }
  mandatory false;
 }
 leaf MATCHRULE {
  type boolean;
  mandatory false;
 }
 leaf PORTNUMBER {
  type uint16 {
   range "0..65535";
  }
  mandatory false;
 }
 leaf PROTOCOLTYPE {
  type enumeration {
   enum val-0;
   enum val-1;
   enum val-2;
  }
  mandatory false;
 }
 leaf SERVICEENDTIMETHD {
  type uint8 {
   range "1..255";
  }
  mandatory false;
 }
 }
 grouping SCCFREQCFG-attributes {
 leaf AGGREGATIONATTRIBUTE {
  type string;
  mandatory false;
 }
 leaf BLINDSCELLADDTHD {
  type uint8 {
   range "0..100";
  }
  mandatory false;
 }
 leaf BLINDSCELLDELTHD {
  type uint8 {
   range "0..100";
  }
  mandatory false;
 }
 leaf CNOPERATORLIST {
  type string {
   length "6";
  }
  mandatory false;
 }
 leaf CTRLMODE {
  type boolean;
  mandatory false;
 }
 leaf OLD_PCCDLEARFCN {
  type union {
   type int32 {
    range "-1..229575";
   }
  }
  mandatory false;
 }
 leaf PCCDLEARFCN {
  type union {
   type int32 {
    range "-1..229575";
   }
  }
  mandatory false;
 }
 leaf SCCA2OFFSET {
  type int8 {
   range "-31..66";
  }
  mandatory false;
 }
 leaf SCCA2RSRPTHLDEXTENDEDOFS {
  type int8 {
   range "-31..0";
  }
  mandatory false;
 }
 leaf SCCA4OFFSET {
  type int8 {
   range "-35..62";
  }
  mandatory false;
 }
 leaf SCCADAPTCOVRSRPTHLDHYS {
  type int8 {
   range "-40..-1";
  }
  mandatory false;
 }
 leaf SCCADAPTCOVRSRPTHLDOFFSET {
  type int8 {
   range "-40..40";
  }
  mandatory false;
 }
 leaf OLD_SCCDLEARFCN {
  type union {
   type int32 {
    range "-1..260894";
   }
  }
  mandatory false;
 }
 leaf SCCDLEARFCN {
  type union {
   type int32 {
    range "-1..260894";
   }
  }
  mandatory false;
 }
 leaf SCCPRIORITY {
  type uint8 {
   range "1..16";
  }
  mandatory false;
 }
 leaf SCCULEXPERIENCECOEFF {
  type uint8 {
   range "0..100";
  }
  mandatory false;
 }
 leaf SPIDGRPID {
  type union {
   type uint16 {
    range "0..65535";
   }
  }
  mandatory false;
 }
 leaf ULEXPSCCADDRSRPTHLDOFFSET {
  type int8 {
   range "-100..100";
  }
  mandatory false;
 }
 leaf ULSPIDGRPID {
  type union {
   type uint16 {
    range "0..65535";
   }
  }
  mandatory false;
 }
 }
 grouping SCPOLICY-attributes {
 leaf IPADDRESSAGINGTIME {
  type uint16 {
   range "0..1500";
  }
  mandatory false;
 }
 leaf SCALGOSWITCH {
  type string;
  mandatory false;
 }
 leaf VIDEOINITBUFTIME {
  type enumeration {
   enum val-0;
   enum val-1;
   enum val-2;
   enum val-3;
   enum val-4;
   enum val-5;
  }
  mandatory false;
 }
 leaf VIDEOSYNACKTOACKDELAYTHLD {
  type uint16 {
   range "1..1000";
  }
  mandatory false;
 }
 }
 grouping SCSERVICEQOS-attributes {
 leaf APPDNS {
  type string {
   length "1..49";
  }
  mandatory false;
 }
 leaf APPIDENTTYPE {
  type enumeration {
   enum val-0;
   enum val-1;
   enum val-2;
  }
  mandatory false;
 }
 leaf APPIPV4 {
  type inet:ipv4-address;
  mandatory false;
 }
 leaf APPIPV6 {
  type inet:ipv6-address;
  mandatory false;
 }
 leaf DLSGBR {
  type uint32 {
   range "0..4294967295";
  }
  mandatory false;
 }
 leaf OLD_SCQOSID {
  type union {
   type int8 {
    range "-1..49";
   }
  }
  mandatory false;
 }
 leaf SCQOSID {
  type union {
   type int8 {
    range "-1..49";
   }
  }
  mandatory false;
 }
 }
 grouping SECONDARYOPIDTYPE-attributes {
 leaf CNOPSHARINGGROUPID {
  type union {
   type int8 {
    range "-1..5";
   }
  }
  mandatory false;
 }
 leaf SECONDARYOPERATORID {
  type union {
   type int8 {
    range "-1..5";
   }
  }
  mandatory false;
 }
 }
 grouping SECTOREQMREFTYPE-attributes {
 leaf LOCALCELLNAME {
  type string;
  mandatory false;
 }
 leaf LOCALCELLID {
  type union {
   type int16 {
    range "-1..255";
   }
  }
  mandatory false;
 }
 leaf SECTOREQMGROUPID {
  type union {
   type int8 {
    range "-1..35";
   }
  }
  mandatory false;
 }
 leaf SECTOREQMID {
  type union {
   type int32 {
    range "-1..65535";
   }
  }
  mandatory false;
 }
 }
 grouping SECTORSPLITCELL-attributes {
 leaf CELLBEAMAZIMUTH {
  type union {
   type int16 {
    range "-60..255";
   }
  }
  mandatory false;
 }
 leaf CELLBEAMAZIMUTHOFFSET {
  type int8 {
   range "-30..30";
  }
  mandatory false;
 }
 leaf CELLBEAMINDEX {
  type uint8 {
   range "0..11";
  }
  mandatory false;
 }
 leaf CELLBEAMPOWER {
  type uint16 {
   range "1..10000";
  }
  mandatory false;
 }
 leaf CELLBEAMTILT {
  type int8 {
   range "-15..15";
  }
  mandatory false;
 }
 leaf CELLBEAMTILTFRACTIONPART {
  type int8 {
   range "-9..9";
  }
  mandatory false;
 }
 leaf CELLBEAMWIDTH {
  type enumeration {
   enum val-0;
   enum val-1;
   enum val-2;
   enum val-3;
   enum val-4;
   enum val-5;
   enum val-6;
   enum val-7;
  }
  mandatory false;
 }
 leaf LOCALCELLID {
  type union {
   type int16 {
    range "-1..255";
   }
  }
  mandatory false;
 }
 leaf LOWFREQULTRALEANSITEWEIGHT {
  type uint16 {
   range "0..7070";
  }
  mandatory false;
 }
 leaf SECTORSPLITGROUPID {
  type union {
   type int16 {
    range "-1..255";
   }
  }
  mandatory false;
 }
 }
 grouping SECTORSPLITCELLEXT-attributes {
 leaf CELLBEAMAZIMUTH {
  type union {
   type int16 {
    range "-60..255";
   }
  }
  mandatory false;
 }
 leaf CELLBEAMAZIMUTHOFFSET {
  type int8 {
   range "-30..30";
  }
  mandatory false;
 }
 leaf CELLBEAMINDEX {
  type uint8 {
   range "0..11";
  }
  mandatory false;
 }
 leaf CELLBEAMPOWER {
  type uint16 {
   range "1..10000";
  }
  mandatory false;
 }
 leaf CELLBEAMTILT {
  type int8 {
   range "-15..15";
  }
  mandatory false;
 }
 leaf CELLBEAMTILTFRACTIONPART {
  type int8 {
   range "-9..9";
  }
  mandatory false;
 }
 leaf CELLBEAMWIDTH {
  type enumeration {
   enum val-0;
   enum val-1;
   enum val-2;
   enum val-3;
   enum val-4;
   enum val-5;
   enum val-6;
   enum val-7;
  }
  mandatory false;
 }
 leaf LOCALCELLID {
  type union {
   type int16 {
    range "-1..255";
   }
  }
  mandatory false;
 }
 leaf MUMIMOMAXPAIRLAYER {
  type enumeration {
   enum val-0;
   enum val-1;
   enum val-2;
   enum val-3;
   enum val-4;
   enum val-5;
   enum val-6;
   enum val-7;
  }
  mandatory false;
 }
 leaf PAPCOFF {
  type enumeration {
   enum val-0;
   enum val-1;
   enum val-2;
   enum val-3;
   enum val-4;
   enum val-5;
   enum val-6;
   enum val-7;
  }
  mandatory false;
 }
 leaf PB {
  type uint8 {
   range "0..3";
  }
  mandatory false;
 }
 leaf SECTORSPLITBEAMNUM {
  type union {
   type int8 {
    range "-1..4";
   }
  }
  mandatory false;
 }
 leaf SECTORSPLITGROUPID {
  type union {
   type int16 {
    range "-1..255";
   }
  }
  mandatory false;
 }
 leaf SINGLEBEAMRSPOWER {
  type int16 {
   range "-600..500";
  }
  mandatory false;
 }
 }
 grouping SECTORSPLITGROUP-attributes {
 leaf ACPBTBSINDEXTHLD {
  type uint8 {
   range "0..33";
  }
  mandatory false;
 }
 leaf BEAMDEPLOYMENTMODE {
  type enumeration {
   enum val-0;
   enum val-1;
   enum val-2;
   enum val-3;
   enum val-5;
   enum val-255;
  }
  mandatory false;
 }
 leaf BEAMOPTPRBUSAGETHLD {
  type uint8 {
   range "0..100";
  }
  mandatory false;
 }
 leaf BEAMSHIFTDIRECTION {
  type enumeration {
   enum val-0;
   enum val-1;
   enum val-2;
  }
  mandatory false;
 }
 leaf BEAMTEMPLATEID {
  type uint8 {
   range "0..255";
  }
  mandatory false;
 }
 leaf CHANNELCALIBPERIOD {
  type boolean;
  mandatory false;
 }
 leaf CLOSEDEPLOYSECTORBEAMSCM {
  type enumeration {
   enum val-0;
   enum val-1;
   enum val-2;
  }
  mandatory false;
 }
 leaf CLOSESECTORLEANCRSMODE {
  type enumeration {
   enum val-0;
   enum val-1;
   enum val-2;
  }
  mandatory false;
 }
 leaf COVERAGESCENARIO {
  type boolean;
  mandatory false;
 }
 leaf DLRANKADAPTEVALUATIONPRD {
  type union {
   type uint16 {
    range "0..3600";
   }
  }
  mandatory false;
 }
 leaf INTELLIGENTBEAMSCHSWITCH {
  type string;
  mandatory false;
 }
 leaf JOINTPATTERNADJPERIOD {
  type uint8 {
   range "1..4";
  }
  mandatory false;
 }
 leaf JOINTPATTERNADJSETID {
  type union {
   type uint8 {
    range "0..255";
   }
  }
  mandatory false;
 }
 leaf LOADBALANCINGRATIOTHLD {
  type int8 {
   range "-100..100";
  }
  mandatory false;
 }
 leaf MASSIVEMIMOBEAMSCHEME {
  type boolean;
  mandatory false;
 }
 leaf MASSIVEMIMOEMFPOWERLIMIT {
  type uint16 {
   range "0..65500";
  }
  mandatory false;
 }
 leaf MMBEAMAZIMUTHADJSTEP {
  type uint8 {
   range "0..60";
  }
  mandatory false;
 }
 leaf MUMIMOMAXPAIRLAYER {
  type enumeration {
   enum val-0;
   enum val-1;
   enum val-2;
   enum val-3;
   enum val-4;
   enum val-5;
   enum val-6;
   enum val-7;
   enum val-8;
  }
  mandatory false;
 }
 leaf OVERLAPPINGAREAUERATIOTHLD {
  type int8 {
   range "-100..100";
  }
  mandatory false;
 }
 leaf POWEROPTSWITCH {
  type string;
  mandatory false;
 }
 leaf POWERSHARINGTM9UEMAXPAOFS {
  type uint8 {
   range "0..90";
  }
  mandatory false;
 }
 leaf PWRSHARINGHIGHLOADTHLD {
  type uint8 {
   range "50..100";
  }
  mandatory false;
 }
 leaf PWRSHARINGLOADMULTIPLETHLD {
  type uint8 {
   range "20..100";
  }
  mandatory false;
 }
 leaf SMBWEIGHTMODE {
  type enumeration {
   enum val-0;
   enum val-1;
   enum val-2;
   enum val-3;
   enum val-4;
  }
  mandatory false;
 }
 leaf OLD_SECTORSPLITGROUPID {
  type union {
   type int16 {
    range "-1..255";
   }
  }
  mandatory false;
 }
 leaf SECTORSPLITGROUPID {
  type union {
   type int16 {
    range "-1..255";
   }
  }
  mandatory false;
 }
 leaf SECTORSPLITSWITCH {
  type string;
  mandatory false;
 }
 leaf SPLITCELLGROUPOPTSWITCH {
  type string;
  mandatory false;
 }
 leaf SPLITCELLPARAGROUPID {
  type uint8 {
   range "0..255";
  }
  mandatory false;
 }
 leaf STUEPWRADJUSTLEVEL {
  type enumeration {
   enum val-0;
   enum val-1;
   enum val-2;
   enum val-3;
  }
  mandatory false;
 }
 leaf TM4POWERSCHEME {
  type enumeration {
   enum val-0;
   enum val-1;
   enum val-2;
  }
  mandatory false;
 }
 leaf TM4WEIGHTSCHEME {
  type enumeration {
   enum val-0;
   enum val-1;
   enum val-2;
  }
  mandatory false;
 }
 leaf TILT {
  type int16 {
   range "-150..150";
  }
  mandatory false;
 }
 leaf TM9SRSMEASTHRESHOLD {
  type union {
   type int8 {
    range "-128..30";
   }
  }
  mandatory false;
 }
 leaf TURBOPILOTPOWEROFFSET {
  type uint8 {
   range "0..30";
  }
  mandatory false;
 }
 leaf ULJOINTSCHEDGEUERBRATETHLD {
  type uint8 {
   range "0..100";
  }
  mandatory false;
 }
 leaf ULJOINTSCHEDGEUESINRTHLD {
  type union {
   type int16 {
    range "-10..255";
   }
  }
  mandatory false;
 }
 }
 grouping SECTORSPLITGROUPEXT-attributes {
 leaf OLD_SECTORSPLITBEAMNUM {
  type union {
   type int8 {
    range "-1..4";
   }
  }
  mandatory false;
 }
 leaf SECTORSPLITBEAMNUM {
  type union {
   type int8 {
    range "-1..4";
   }
  }
  mandatory false;
 }
 leaf OLD_SECTORSPLITGROUPID {
  type union {
   type int16 {
    range "-1..255";
   }
  }
  mandatory false;
 }
 leaf SECTORSPLITGROUPID {
  type union {
   type int16 {
    range "-1..255";
   }
  }
  mandatory false;
 }
 leaf SECTORSPLITSWITCH {
  type string;
  mandatory false;
 }
 leaf TM4WEIGHTSCHEME {
  type enumeration {
   enum val-0;
   enum val-1;
   enum val-2;
  }
  mandatory false;
 }
 leaf TURBOPILOTPOWEROFFSET {
  type uint8 {
   range "0..30";
  }
  mandatory false;
 }
 }
 grouping SERVERCONFIG-attributes {
 leaf IPADDETECTPURPOSECONTROLSW {
  type inet:ip-address;
  mandatory false;
 }
 leaf IPVERSION {
  type boolean;
  mandatory false;
 }
 leaf IPV6SERVERIPADDRESS {
  type inet:ipv6-address;
  mandatory false;
 }
 leaf PROTOCOLTYPE {
  type enumeration {
   enum val-0;
   enum val-1;
   enum val-2;
  }
  mandatory false;
 }
 leaf OLD_SERVERINDEX {
  type union {
   type int8 {
    range "-1..49";
   }
  }
  mandatory false;
 }
 leaf SERVERINDEX {
  type union {
   type int8 {
    range "-1..49";
   }
  }
  mandatory false;
 }
 leaf SERVERIPADDRESS {
  type inet:ipv4-address;
  mandatory false;
 }
 leaf SERVERPORTNUMBER {
  type uint16 {
   range "0..65535";
  }
  mandatory false;
 }
 }
 grouping SERVICEAREAIDREF-attributes {
 leaf LOCALCELLNAME {
  type string;
  mandatory false;
 }
 leaf LOCALCELLID {
  type union {
   type int16 {
    range "-1..255";
   }
  }
  mandatory false;
 }
 leaf SERVICEAREAID {
  type union {
   type int32 {
    range "-1..65535";
   }
  }
  mandatory false;
 }
 }
 grouping SERVICEDIFFSETTING-attributes {
 leaf ENHSCELLBLINDCONFIGUETYPE {
  type enumeration {
   enum val-0;
   enum val-1;
   enum val-2;
   enum val-3;
  }
  mandatory false;
 }
 leaf QUEUEWEIGHT0 {
  type uint8 {
   range "0..100";
  }
  mandatory false;
 }
 leaf QUEUEWEIGHT1 {
  type uint8 {
   range "0..100";
  }
  mandatory false;
 }
 leaf QUEUEWEIGHT2 {
  type uint8 {
   range "0..100";
  }
  mandatory false;
 }
 leaf QUEUEWEIGHT3 {
  type uint8 {
   range "0..100";
  }
  mandatory false;
 }
 leaf QUEUEWEIGHT4 {
  type uint8 {
   range "0..100";
  }
  mandatory false;
 }
 leaf QUEUEWEIGHT5 {
  type uint8 {
   range "0..100";
  }
  mandatory false;
 }
 leaf QUEUEWEIGHT6 {
  type uint8 {
   range "0..100";
  }
  mandatory false;
 }
 leaf QUEUEWEIGHT7 {
  type uint8 {
   range "0..100";
  }
  mandatory false;
 }
 leaf SCHGUARANTEEFSTMOVINGUENUM {
  type uint8 {
   range "0..255";
  }
  mandatory false;
 }
 leaf SERVICEDIFFSWITCH {
  type string;
  mandatory false;
 }
 }
 grouping SERVICEIDENTIFYPARA-attributes {
 leaf ACCELERATIONSERVICEALGOSW {
  type string;
  mandatory false;
 }
 leaf HEARTBEATPACKETLENGTHTHLD {
  type uint16 {
   range "40..1500";
  }
  mandatory false;
 }
 leaf HEARTBEATPACKETNUMBERTHLD {
  type uint8 {
   range "4..50";
  }
  mandatory false;
 }
 leaf LARGEPKTDECTHLDINITVALUE {
  type uint16 {
   range "0..65535";
  }
  mandatory false;
 }
 leaf MASSFLOWBIGPACKETRATETHLD {
  type uint8 {
   range "50..100";
  }
  mandatory false;
 }
 leaf MASSFLOWDURATION {
  type uint8 {
   range "2..60";
  }
  mandatory false;
 }
 leaf MASSFLOWPACKETNUMBERTHLD {
  type uint16 {
   range "50..65535";
  }
  mandatory false;
 }
 leaf USERSERVFEAEXTTIMEWINDOW {
  type uint8 {
   range "1..20";
  }
  mandatory false;
 }
 }
 grouping SERVICEIFDLEARFCNGRP-attributes {
 leaf OLD_CNOPERATORID {
  type union {
   type int8 {
    range "-1..5";
   }
  }
  mandatory false;
 }
 leaf CNOPERATORID {
  type union {
   type int8 {
    range "-1..5";
   }
  }
  mandatory false;
 }
 leaf DLEARFCN {
  type union {
   type uint32 {
    range "0..229575";
   }
  }
  mandatory false;
 }
 leaf OLD_DLEARFCNINDEX {
  type union {
   type int8 {
    range "-1..15";
   }
  }
  mandatory false;
 }
 leaf DLEARFCNINDEX {
  type union {
   type int8 {
    range "-1..15";
   }
  }
  mandatory false;
 }
 leaf SERVICEHOFREQPRIORITY {
  type uint8 {
   range "0..15";
  }
  mandatory false;
 }
 leaf OLD_SERVICEIFHOCFGGROUPID {
  type union {
   type int8 {
    range "-1..9";
   }
  }
  mandatory false;
 }
 leaf SERVICEIFHOCFGGROUPID {
  type union {
   type int8 {
    range "-1..9";
   }
  }
  mandatory false;
 }
 }
 grouping SERVICEIFHOCFGGROUP-attributes {
 leaf A4RPTWAITINGTIMER {
  type union {
   type uint16 {
    range "10..40000";
   }
  }
  mandatory false;
 }
 leaf A4TIMETOTRIGER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf OLD_CNOPERATORID {
  type union {
   type int8 {
    range "-1..5";
   }
  }
  mandatory false;
 }
 leaf CNOPERATORID {
  type union {
   type int8 {
    range "-1..5";
   }
  }
  mandatory false;
 }
 leaf INTERFREQHOSTATE {
  type boolean;
  mandatory false;
 }
 leaf OLD_SERVICEIFHOCFGGROUPID {
  type union {
   type int8 {
    range "-1..9";
   }
  }
  mandatory false;
 }
 leaf SERVICEIFHOCFGGROUPID {
  type union {
   type int8 {
    range "-1..9";
   }
  }
  mandatory false;
 }
 }
 grouping SERVICEIRHOCFGGROUP-attributes {
 leaf OLD_CNOPERATORID {
  type union {
   type int8 {
    range "-1..5";
   }
  }
  mandatory false;
 }
 leaf CNOPERATORID {
  type union {
   type int8 {
    range "-1..5";
   }
  }
  mandatory false;
 }
 leaf INTERRATHOSTATE {
  type enumeration {
   enum val-0;
   enum val-1;
   enum val-2;
  }
  mandatory false;
 }
 leaf OLD_SERVICEIRHOCFGGROUPID {
  type union {
   type int8 {
    range "-1..9";
   }
  }
  mandatory false;
 }
 leaf SERVICEIRHOCFGGROUPID {
  type union {
   type int8 {
    range "-1..9";
   }
  }
  mandatory false;
 }
 leaf SERVICEIRMEASMODE {
  type boolean;
  mandatory false;
 }
 }
 grouping SESSION-attributes {
 leaf OLD_LOCALMCEID {
  type union {
   type int8 {
    range "-1..5";
   }
  }
  mandatory false;
 }
 leaf LOCALMCEID {
  type union {
   type int8 {
    range "-1..5";
   }
  }
  mandatory false;
 }
 leaf OLD_MBSFNAREAID {
  type union {
   type int8 {
    range "-1..71";
   }
  }
  mandatory false;
 }
 leaf MBSFNAREAID {
  type union {
   type int8 {
    range "-1..71";
   }
  }
  mandatory false;
 }
 leaf OLD_PMCHID {
  type union {
   type int8 {
    range "-1..14";
   }
  }
  mandatory false;
 }
 leaf PMCHID {
  type union {
   type int8 {
    range "-1..14";
   }
  }
  mandatory false;
 }
 leaf OLD_SERVICEID {
  type union {
   type int32 {
    range "-1..16777215";
   }
  }
  mandatory false;
 }
 leaf SERVICEID {
  type union {
   type int32 {
    range "-1..16777215";
   }
  }
  mandatory false;
 }
 }
 grouping SFNAUXRESBIND-attributes {
 leaf AUTOCFGFLAG {
  type boolean;
  mandatory false;
 }
 leaf BASEBANDEQMID {
  type union {
   type uint8 {
    range "0..255";
   }
  }
  mandatory false;
 }
 leaf CELLBEAMMODE {
  type boolean;
  mandatory false;
 }
 leaf OLD_LOCALCELLID {
  type union {
   type int16 {
    range "-1..255";
   }
  }
  mandatory false;
 }
 leaf LOCALCELLID {
  type union {
   type int16 {
    range "-1..255";
   }
  }
  mandatory false;
 }
 leaf REFERENCESIGNALPWR {
  type union {
   type int16 {
    range "-600..32767";
   }
  }
  mandatory false;
 }
 leaf REFERENCESIGNALPWRMARGIN {
  type uint8 {
   range "0..60";
  }
  mandatory false;
 }
 leaf SECTORCPRICOMPRESSION {
  type enumeration {
   enum val-0;
   enum val-1;
   enum val-2;
   enum val-4;
   enum val-5;
   enum val-255;
  }
  mandatory false;
 }
 leaf SECTOREQMCOMBINEGRPID {
  type union {
   type uint8 {
    range "0..255";
   }
  }
  mandatory false;
 }
 leaf OLD_SECTOREQMID {
  type union {
   type int32 {
    range "-1..65535";
   }
  }
  mandatory false;
 }
 leaf SECTOREQMID {
  type union {
   type int32 {
    range "-1..65535";
   }
  }
  mandatory false;
 }
 leaf VISUALCELLID {
  type uint16 {
   range "0..503";
  }
  mandatory false;
 }
 leaf OLD_ENODEBID {
  type union {
   type int32 {
    range "-1..1048575";
   }
  }
  mandatory false;
 }
 leaf ENODEBID {
  type union {
   type int32 {
    range "-1..1048575";
   }
  }
  mandatory false;
 }
 }
 grouping SFNAUXRESGRPBIND-attributes {
 leaf AUTOCFGFLAG {
  type boolean;
  mandatory false;
 }
 leaf BASEBANDEQMID {
  type union {
   type uint8 {
    range "0..255";
   }
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf REFERENCESIGNALPWR {
  type union {
   type int16 {
    range "-600..32767";
   }
  }
  mandatory false;
 }
 leaf OLD_SECTOREQMGROUPID {
  type union {
   type int8 {
    range "-1..35";
   }
  }
  mandatory false;
 }
 leaf SECTOREQMGROUPID {
  type union {
   type int8 {
    range "-1..35";
   }
  }
  mandatory false;
 }
 leaf SECTOREQMGRPCOMBINEID {
  type union {
   type uint8 {
    range "0..255";
   }
  }
  mandatory false;
 }
 leaf SECTORGROUPCPRICOMPRESSION {
  type enumeration {
   enum val-0;
   enum val-1;
   enum val-2;
   enum val-255;
  }
  mandatory false;
 }
 leaf SECTORGROUPLINKCOMPRESSION {
  type enumeration {
   enum val-0;
   enum val-1;
   enum val-255;
  }
  mandatory false;
 }
 leaf VISUALCELLID {
  type uint16 {
   range "0..503";
  }
  mandatory false;
 }
 leaf OLD_ENODEBID {
  type union {
   type int32 {
    range "-1..1048575";
   }
  }
  mandatory false;
 }
 leaf ENODEBID {
  type union {
   type int32 {
    range "-1..1048575";
   }
  }
  mandatory false;
 }
 }
 grouping SFNEDGERRURELATION-attributes {
 leaf LOCALCELLNAME {
  type string;
  mandatory false;
 }
 leaf LOCALCELLID {
  type union {
   type int16 {
    range "-1..255";
   }
  }
  mandatory false;
 }
 leaf MCC {
  type string {
   length "3";
  }
  mandatory false;
 }
 leaf MNC {
  type string {
   length "2..3";
  }
  mandatory false;
 }
 leaf NEIGHBORCELLID {
  type uint8 {
   range "0..255";
  }
  mandatory false;
 }
 leaf NEIGHBORSECTOREQMID {
  type uint16 {
   range "0..65535";
  }
  mandatory false;
 }
 leaf SECTOREQMID {
  type union {
   type int32 {
    range "-1..65535";
   }
  }
  mandatory false;
 }
 leaf ENODEBID {
  type uint32 {
   range "0..1048575";
  }
  mandatory false;
 }
 }
 grouping SFNSECTOREQMREFTYPE-attributes {
 leaf LOCALCELLID {
  type union {
   type int16 {
    range "-1..255";
   }
  }
  mandatory false;
 }
 leaf SECTOREQMGROUPID {
  type union {
   type int8 {
    range "-1..35";
   }
  }
  mandatory false;
 }
 leaf SECTOREQMID {
  type union {
   type int32 {
    range "-1..65535";
   }
  }
  mandatory false;
 }
 leaf ENODEBID {
  type union {
   type int32 {
    range "-1..1048575";
   }
  }
  mandatory false;
 }
 }
 grouping SIDELINKV2XCARRIER-attributes {
 leaf MAXSIDELINKV2XTRANSMITPWR {
  type int8 {
   range "-30..33";
  }
  mandatory false;
 }
 leaf SIDELINKV2XBANDWIDTH {
  type enumeration {
   enum val-0;
   enum val-1;
   enum val-2;
   enum val-3;
   enum val-4;
   enum val-5;
  }
  mandatory false;
 }
 leaf OLD_SIDELINKV2XCARRIERID {
  type union {
   type int8 {
    range "-1..1";
   }
  }
  mandatory false;
 }
 leaf SIDELINKV2XCARRIERID {
  type union {
   type int8 {
    range "-1..1";
   }
  }
  mandatory false;
 }
 leaf SIDELINKV2XEARFCN {
  type uint16 {
   range "46790..55239";
  }
  mandatory false;
 }
 }
 grouping SIDELINKV2XPSSCHCFG-attributes {
 leaf OLD_PSSCHCFGINDEX {
  type union {
   type int8 {
    range "-1..1";
   }
  }
  mandatory false;
 }
 leaf PSSCHCFGINDEX {
  type union {
   type int8 {
    range "-1..1";
   }
  }
  mandatory false;
 }
 leaf OLD_SIDELINKV2XCARRIERID {
  type union {
   type int8 {
    range "-1..1";
   }
  }
  mandatory false;
 }
 leaf SIDELINKV2XCARRIERID {
  type union {
   type int8 {
    range "-1..1";
   }
  }
  mandatory false;
 }
 leaf UESPEEDTHLD {
  type enumeration {
   enum val-0;
   enum val-1;
   enum val-2;
   enum val-3;
   enum val-4;
   enum val-5;
   enum val-6;
   enum val-7;
  }
  mandatory false;
 }
 }
 grouping SIDELINKV2XRESPLCFG-attributes {
 leaf OLD_POOLID {
  type union {
   type int8 {
    range "-1..2";
   }
  }
  mandatory false;
 }
 leaf POOLID {
  type union {
   type int8 {
    range "-1..2";
   }
  }
  mandatory false;
 }
 leaf POOLSUBFRAMEBITMAP {
  type uint32 {
   range "0..1048575";
  }
  mandatory false;
 }
 leaf POOLTYPE {
  type boolean;
  mandatory false;
 }
 leaf PSCCHPOOLSTARTRBINDEX {
  type uint8 {
   range "0..99";
  }
  mandatory false;
 }
 leaf PSCCHPSSCHADJACENCY {
  type boolean;
  mandatory false;
 }
 leaf OLD_SIDELINKV2XCARRIERID {
  type union {
   type int8 {
    range "-1..1";
   }
  }
  mandatory false;
 }
 leaf SIDELINKV2XCARRIERID {
  type union {
   type int8 {
    range "-1..1";
   }
  }
  mandatory false;
 }
 leaf SUBCHANNELCOUNT {
  type enumeration {
   enum val-0;
   enum val-1;
   enum val-2;
   enum val-3;
   enum val-4;
   enum val-5;
   enum val-6;
  }
  mandatory false;
 }
 leaf SUBCHANNELPRBCOUNT {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
  }
  mandatory false;
 }
 leaf SUBCHANNELSTARTRBINDEX {
  type uint8 {
   range "0..99";
  }
  mandatory false;
 }
 }
 grouping SIMULOAD-attributes {
 leaf FREQSELSWITCH {
  type boolean;
  mandatory false;
 }
 leaf SIMULOADCFGINDEX {
  type union {
   type int8 {
    range "-1..9";
   }
  }
  mandatory false;
 }
 leaf SIMULOADPWRTHD {
  type uint8 {
   range "0..100";
  }
  mandatory false;
 }
 leaf SIMULOADRBTHD {
  type uint8 {
   range "0..100";
  }
  mandatory false;
 }
 leaf SIMULOADREPORTPERIOD {
  type uint16 {
   range "0..50000";
  }
  mandatory false;
 }
 leaf SIMULOADSTATPERIOD {
  type uint16 {
   range "0..50000";
  }
  mandatory false;
 }
 }
 grouping SIMULOADPMITEMPLATE-attributes {
 leaf LOCALCELLNAME {
  type string;
  mandatory false;
 }
 leaf CELLSIMULOADPMI {
  type uint8 {
   range "0..15";
  }
  mandatory false;
 }
 leaf CELLSIMULOADPMICFGDURATION {
  type uint16 {
   range "1..1000";
  }
  mandatory false;
 }
 leaf CELLSIMULOADPMIEXTEND0 {
  type enumeration {
   enum val-0;
   enum val-1;
   enum val-2;
   enum val-3;
  }
  mandatory false;
 }
 leaf CELLSIMULOADPMIEXTEND1 {
  type enumeration {
   enum val-0;
   enum val-1;
   enum val-2;
   enum val-3;
  }
  mandatory false;
 }
 leaf CELLSIMULOADRANK {
  type enumeration {
   enum val-0;
   enum val-1;
   enum val-2;
   enum val-3;
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf PMITYPE {
  type boolean;
  mandatory false;
 }
 leaf OLD_SIMULOADPMITEMPLATEID {
  type union {
   type int8 {
    range "-1..15";
   }
  }
  mandatory false;
 }
 leaf SIMULOADPMITEMPLATEID {
  type union {
   type int8 {
    range "-1..15";
   }
  }
  mandatory false;
 }
 }
 grouping SPCTCLOUDAUXENODEB-attributes {
 leaf OLD_CELLID {
  type union {
   type int16 {
    range "-1..255";
   }
  }
  mandatory false;
 }
 leaf CELLID {
  type union {
   type int16 {
    range "-1..255";
   }
  }
  mandatory false;
 }
 leaf OLD_ENODEBID {
  type union {
   type int32 {
    range "-1..1048575";
   }
  }
  mandatory false;
 }
 leaf ENODEBID {
  type union {
   type int32 {
    range "-1..1048575";
   }
  }
  mandatory false;
 }
 leaf OLD_LTENRSPECTRUMSHRCELLGRPID {
  type union {
   type int8 {
    range "-1..23";
   }
  }
  mandatory false;
 }
 leaf LTENRSPECTRUMSHRCELLGRPID {
  type union {
   type int8 {
    range "-1..23";
   }
  }
  mandatory false;
 }
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 }
 grouping SPECTRUMCLOUD-attributes {
 leaf LOCALCELLNAME {
  type string;
  mandatory false;
 }
 leaf COCOVGSMSHARINGCARRIERPWR {
  type union {
   type uint16 {
    range "0..65535";
   }
  }
  mandatory false;
 }
 leaf DECREASECFIRATE {
  type uint8 {
   range "0..100";
  }
  mandatory false;
 }
 leaf DLCCHSENDSTRATEGY {
  type enumeration {
   enum val-0;
   enum val-1;
   enum val-2;
   enum val-3;
   enum val-4;
   enum val-5;
   enum val-6;
  }
  mandatory false;
 }
 leaf DLSPSRESTRICTRATIO {
  type uint8 {
   range "0..60";
  }
  mandatory false;
 }
 leaf FORCEDREFARMINGUENUMTHLD {
  type uint8 {
   range "0..10";
  }
  mandatory false;
 }
 leaf GSMARFCNGROUPID {
  type uint8 {
   range "0..255";
  }
  mandatory false;
 }
 leaf INCREASECFIRATE {
  type uint8 {
   range "0..100";
  }
  mandatory false;
 }
 leaf INTERFPFMOPTSWITCH {
  type string;
  mandatory false;
 }
 leaf LNRSPECTRUMSHROPTSWITCH {
  type string;
  mandatory false;
 }
 leaf LOCALCELLID {
  type union {
   type int16 {
    range "-1..255";
   }
  }
  mandatory false;
 }
 leaf LTENRSPECTRUMSHRCELLGRPID {
  type uint8 {
   range "0..23";
  }
  mandatory false;
 }
 leaf LTEPREFRESADAPTDLRESREQTHD {
  type uint8 {
   range "0..100";
  }
  mandatory false;
 }
 leaf LTEPREFRESADAPTULRESREQTHD {
  type uint8 {
   range "0..100";
  }
  mandatory false;
 }
 leaf LTEPREFRESRATIOADAPTFACTOR {
  type uint8 {
   range "0..255";
  }
  mandatory false;
 }
 leaf MULTIRATSHRLNRSPCTCOGRPID {
  type union {
   type uint8 {
    range "0..255";
   }
  }
  mandatory false;
 }
 leaf NEARPOINTUSERPATHLOSSTHLD {
  type uint8 {
   range "0..200";
  }
  mandatory false;
 }
 leaf PDCCHINTRFRECOMPRATE {
  type uint8 {
   range "0..100";
  }
  mandatory false;
 }
 leaf RDCPWRLTENCCOUNT {
  type uint8 {
   range "1..10";
  }
  mandatory false;
 }
 leaf SPCTSHRMODE {
  type boolean;
  mandatory false;
 }
 leaf SPECTRUMCLOUDENHSWITCH {
  type string;
  mandatory false;
 }
 leaf SPECTRUMCLOUDEXTSWITCH {
  type string;
  mandatory false;
 }
 leaf SPECTRUMCLOUDSWITCH {
  type enumeration {
   enum val-0;
   enum val-1;
   enum val-3;
   enum val-4;
   enum val-5;
   enum val-6;
   enum val-7;
   enum val-8;
  }
  mandatory false;
 }
 leaf ULSPECTRUMSHARINGCONFIGID {
  type uint8 {
   range "0..25";
  }
  mandatory false;
 }
 leaf ULMCPTTVOICEGUARANTRBNUM {
  type uint8 {
   range "0..100";
  }
  mandatory false;
 }
 leaf ULVOLTEGUARANTEEDRBNUM {
  type uint8 {
   range "0..100";
  }
  mandatory false;
 }
 }
 grouping SPIDCFG-attributes {
 leaf AGGREGATIONATTRIBUTE {
  type string;
  mandatory false;
 }
 leaf COVBASEDNRB1B2RSRPTHLDOFS {
  type int8 {
   range "-20..20";
  }
  mandatory false;
 }
 leaf DATAINTERFREQHOGROUPID {
  type union {
   type uint8 {
    range "0..255";
   }
  }
  mandatory false;
 }
 leaf DATAINTRAFREQHOGROUPID {
  type union {
   type uint8 {
    range "0..255";
   }
  }
  mandatory false;
 }
 leaf DEDICATEDNETWORKSPIDSWITCH {
  type string;
  mandatory false;
 }
 leaf DLPRBHIGHLOADTHLD {
  type uint8 {
   range "1..100";
  }
  mandatory false;
 }
 leaf DLSCHPRICOEFF {
  type uint16 {
   range "1..10000";
  }
  mandatory false;
 }
 leaf DLSERVICEGBRCOEFF {
  type uint8 {
   range "1..100";
  }
  mandatory false;
 }
 leaf DRXSTATUS {
  type boolean;
  mandatory false;
 }
 leaf HOBACKTOHPLMNSWITCH {
  type boolean;
  mandatory false;
 }
 leaf HOBACKTOHPLMNRETRYINTERVAL {
  type uint8 {
   range "0..90";
  }
  mandatory false;
 }
 leaf HOTOGERANFORBIDSWITCH {
  type boolean;
  mandatory false;
 }
 leaf IDLEMLBSWITCH {
  type boolean;
  mandatory false;
 }
 leaf INTERFREQHOA1RSRPTHDFACTOR {
  type int8 {
   range "-100..100";
  }
  mandatory false;
 }
 leaf INTERFREQHOA2RSRPTHDFACTOR {
  type int8 {
   range "-100..100";
  }
  mandatory false;
 }
 leaf INTERFREQHOA2RSRQTHDFACTOR {
  type int8 {
   range "-20..20";
  }
  mandatory false;
 }
 leaf INTERFREQMLBSWITCH {
  type boolean;
  mandatory false;
 }
 leaf INTERRATA2RSRPTHLDOFFSET {
  type int8 {
   range "-20..20";
  }
  mandatory false;
 }
 leaf INTERRATMLBSWITCH {
  type boolean;
  mandatory false;
 }
 leaf INTERRATNRA1RSRPTHLDOFS {
  type int8 {
   range "-20..20";
  }
  mandatory false;
 }
 leaf INTERRATNRA2RSRPTHLDOFS {
  type int8 {
   range "-20..20";
  }
  mandatory false;
 }
 leaf INTRAFREQHOA3OFFSETFACTOR {
  type int8 {
   range "-20..20";
  }
  mandatory false;
 }
 leaf MAXIMUMNUMBEROFCARRIERS {
  type uint8 {
   range "0..8";
  }
  mandatory false;
 }
 leaf MULTICARRCFGGROUPID {
  type union {
   type uint8 {
    range "0..255";
   }
  }
  mandatory false;
 }
 leaf NRSCGFREQPRIORITYGROUPID {
  type union {
   type uint16 {
    range "0..65535";
   }
  }
  mandatory false;
 }
 leaf NSADCSPIDB1RSRPTHLDOFFSET {
  type int8 {
   range "-20..20";
  }
  mandatory false;
 }
 leaf OFFLOADSWITCH {
  type string;
  mandatory false;
 }
 leaf PREALLOCATIONPARAGROUPID {
  type union {
   type uint8 {
    range "0..255";
   }
  }
  mandatory false;
 }
 leaf PREALLOCATIONSTATUS {
  type boolean;
  mandatory false;
 }
 leaf PUCCHFORMAT3FOR2CCIND {
  type boolean;
  mandatory false;
 }
 leaf RATFREQPRIORITYGROUPID {
  type uint8 {
   range "0..255";
  }
  mandatory false;
 }
 leaf RATFREQPRIORITYIND {
  type boolean;
  mandatory false;
 }
 leaf SERVBASEDNRB1RSRPTHLDOFS {
  type int8 {
   range "-20..20";
  }
  mandatory false;
 }
 leaf SPECIFIEDUSERFLAG {
  type boolean;
  mandatory false;
 }
 leaf SPEEDTURBOAGGATTR {
  type uint16 {
   range "0..65535";
  }
  mandatory false;
 }
 leaf OLD_SPID {
  type union {
   type int16 {
    range "-1..256";
   }
  }
  mandatory false;
 }
 leaf SPID {
  type union {
   type int16 {
    range "-1..256";
   }
  }
  mandatory false;
 }
 leaf SPIDALGOSWITCH {
  type string;
  mandatory false;
 }
 leaf SPIDBASEDAMBRLIMITFACTOR {
  type uint16 {
   range "0..1000";
  }
  mandatory false;
 }
 leaf SPIDUEINACTIVITYTIMER {
  type union {
   type uint16 {
    range "0..65535";
   }
  }
  mandatory false;
 }
 leaf UENUMHIGHLOADTHLD {
  type uint16 {
   range "1..10000";
  }
  mandatory false;
 }
 leaf ULMINGBR {
  type enumeration {
   enum val-0;
   enum val-8000;
   enum val-16000;
   enum val-32000;
   enum val-64000;
   enum val-128000;
   enum val-256000;
   enum val-512000;
   enum val-1024000;
   enum val-2048000;
   enum val-4096000;
   enum val-8192000;
   enum val-12288000;
   enum val-16384000;
   enum val-20480000;
  }
  mandatory false;
 }
 leaf ULPRBHIGHLOADTHLD {
  type uint8 {
   range "1..100";
  }
  mandatory false;
 }
 leaf ULSCHPRICOEFF {
  type uint16 {
   range "1..10000";
  }
  mandatory false;
 }
 leaf VOIPINTERFREQHOGROUPID {
  type union {
   type uint8 {
    range "0..255";
   }
  }
  mandatory false;
 }
 leaf VOIPINTRAFREQHOGROUPID {
  type union {
   type uint8 {
    range "0..255";
   }
  }
  mandatory false;
 }
 leaf VOIPRATFREQPRIORITYGROUPID {
  type uint8 {
   range "0..255";
  }
  mandatory false;
 }
 }
 grouping SPIDGRPCFG-attributes {
 leaf OLD_ENDSPID {
  type union {
   type int16 {
    range "-1..256";
   }
  }
  mandatory false;
 }
 leaf ENDSPID {
  type union {
   type int16 {
    range "-1..256";
   }
  }
  mandatory false;
 }
 leaf OLD_SPIDGRPID {
  type union {
   type int16 {
    range "-1..255";
   }
  }
  mandatory false;
 }
 leaf SPIDGRPID {
  type union {
   type int16 {
    range "-1..255";
   }
  }
  mandatory false;
 }
 leaf OLD_STARTSPID {
  type union {
   type int16 {
    range "-1..256";
   }
  }
  mandatory false;
 }
 leaf STARTSPID {
  type union {
   type int16 {
    range "-1..256";
   }
  }
  mandatory false;
 }
 }
 grouping SPIDHOINPROHPLMNLIST-attributes {
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf OLD_SPID {
  type union {
   type int16 {
    range "-1..256";
   }
  }
  mandatory false;
 }
 leaf SPID {
  type union {
   type int16 {
    range "-1..256";
   }
  }
  mandatory false;
 }
 }
 grouping SPIDHPLMNLIST-attributes {
 leaf OLD_ENDSPID {
  type union {
   type int16 {
    range "-1..256";
   }
  }
  mandatory false;
 }
 leaf ENDSPID {
  type union {
   type int16 {
    range "-1..256";
   }
  }
  mandatory false;
 }
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf OLD_STARTSPID {
  type union {
   type int16 {
    range "-1..256";
   }
  }
  mandatory false;
 }
 leaf STARTSPID {
  type union {
   type int16 {
    range "-1..256";
   }
  }
  mandatory false;
 }
 }
 grouping SPIDPREALLOCPARAGRP-attributes {
 leaf PREALLOCATIONALGOSWITCH {
  type string;
  mandatory false;
 }
 leaf PREALLOCATIONMINPERIOD {
  type uint8 {
   range "1..40";
  }
  mandatory false;
 }
 leaf OLD_PREALLOCATIONPARAGROUPID {
  type union {
   type int8 {
    range "-1..9";
   }
  }
  mandatory false;
 }
 leaf PREALLOCATIONPARAGROUPID {
  type union {
   type int8 {
    range "-1..9";
   }
  }
  mandatory false;
 }
 leaf PREALLOCATIONSIZE {
  type uint16 {
   range "45..1500";
  }
  mandatory false;
 }
 leaf SMARTPREALLOCATIONDURATION {
  type uint16 {
   range "0..2000";
  }
  mandatory false;
 }
 }
 grouping SPIDQCIPARAM-attributes {
 leaf BESTEFFORTGBR {
  type uint16 {
   range "0..65535";
  }
  mandatory false;
 }
 leaf OLD_QCI {
  type union {
   type int16 {
    range "-1..254";
   }
  }
  mandatory false;
 }
 leaf QCI {
  type union {
   type int16 {
    range "-1..254";
   }
  }
  mandatory false;
 }
 leaf RATEGUARANTEETYPE {
  type enumeration {
   enum val-0;
   enum val-1;
   enum val-2;
  }
  mandatory false;
 }
 leaf OLD_SPID {
  type union {
   type int16 {
    range "-1..256";
   }
  }
  mandatory false;
 }
 leaf SPID {
  type union {
   type int16 {
    range "-1..256";
   }
  }
  mandatory false;
 }
 }
 grouping SPLITCELLGROUPPARA-attributes {
 leaf BEAMMODERESTOREA3OFFSET {
  type int8 {
   range "-30..30";
  }
  mandatory false;
 }
 leaf BEAMMODERESTOREDLPRBTHLD {
  type uint8 {
   range "0..30";
  }
  mandatory false;
 }
 leaf BEAMMODERESTOREEVALPRD {
  type uint8 {
   range "5..60";
  }
  mandatory false;
 }
 leaf BEAMMODERESTORERFMUTETHLD {
  type uint8 {
   range "0..100";
  }
  mandatory false;
 }
 leaf BEAMMODERESTOREUENUMTHLD {
  type uint16 {
   range "1..300";
  }
  mandatory false;
 }
 leaf BEAMMODERESTOREULPRBTHLD {
  type uint8 {
   range "0..25";
  }
  mandatory false;
 }
 leaf BEAMMODESHIFTA3OFFSET {
  type int8 {
   range "-30..30";
  }
  mandatory false;
 }
 leaf BEAMMODESHIFTDLPRBTHLD {
  type uint8 {
   range "0..30";
  }
  mandatory false;
 }
 leaf BEAMMODESHIFTEVALPRD {
  type uint8 {
   range "5..60";
  }
  mandatory false;
 }
 leaf BEAMMODESHIFTUENUMTHLD {
  type uint16 {
   range "1..300";
  }
  mandatory false;
 }
 leaf BEAMMODESHIFTULPRBTHLD {
  type uint8 {
   range "0..25";
  }
  mandatory false;
 }
 leaf FORCEBEAMMODESHIFTUENUMTHD {
  type uint8 {
   range "0..10";
  }
  mandatory false;
 }
 leaf PAPCOFF {
  type enumeration {
   enum val-0;
   enum val-1;
   enum val-2;
   enum val-3;
   enum val-4;
   enum val-5;
   enum val-6;
   enum val-7;
  }
  mandatory false;
 }
 leaf PB {
  type uint8 {
   range "0..3";
  }
  mandatory false;
 }
 leaf PUNISHTIME {
  type uint16 {
   range "0..360";
  }
  mandatory false;
 }
 leaf REFERENCESIGNALPWR {
  type int16 {
   range "-600..500";
  }
  mandatory false;
 }
 leaf OLD_SPLITCELLPARAGROUPID {
  type union {
   type int16 {
    range "-1..254";
   }
  }
  mandatory false;
 }
 leaf SPLITCELLPARAGROUPID {
  type union {
   type int16 {
    range "-1..254";
   }
  }
  mandatory false;
 }
 leaf STARTTIME {
  type hwat:HH_MM_SS_Time;
  mandatory false;
 }
 leaf STOPTIME {
  type hwat:HH_MM_SS_Time;
  mandatory false;
 }
 }
 grouping SPLITGRP3DEIRPTHLD-attributes {
 leaf OLD_GRIDGROUPNO {
  type union {
   type int8 {
    range "-1..27";
   }
  }
  mandatory false;
 }
 leaf GRIDGROUPNO {
  type union {
   type int8 {
    range "-1..27";
   }
  }
  mandatory false;
 }
 leaf POWERCONTROLTHRESHOLD {
  type uint32 {
   range "0..100000000";
  }
  mandatory false;
 }
 leaf OLD_SECTORSPLITGROUPID {
  type union {
   type int16 {
    range "-1..255";
   }
  }
  mandatory false;
 }
 leaf SECTORSPLITGROUPID {
  type union {
   type int16 {
    range "-1..255";
   }
  }
  mandatory false;
 }
 }
 grouping SPLITGRPSMARTPWRLOCK-attributes {
 leaf LTESPSGRPID {
  type uint16 {
   range "0..65535";
  }
  mandatory false;
 }
 leaf POWERCONTROLTHRESHOLD {
  type uint32 {
   range "0..100000000";
  }
  mandatory false;
 }
 leaf SECTORSPLITGROUPID {
  type union {
   type int16 {
    range "-1..255";
   }
  }
  mandatory false;
 }
 leaf SMARTPOWERLOCKSW {
  type string;
  mandatory false;
 }
 leaf SMARTPWRLOCKALGOSWITCH {
  type string;
  mandatory false;
 }
 }
 grouping SRBCFG-attributes {
 leaf HOCMDRRCRLSMSGRETXADPSW {
  type boolean;
  mandatory false;
 }
 leaf RRCCONNRELMAXRETXTHD {
  type uint8 {
   range "1..32";
  }
  mandatory false;
 }
 leaf SRBPOLLTIMERADJUSERNUMTHD {
  type uint16 {
   range "0..5000";
  }
  mandatory false;
 }
 leaf SRBPOLLTIMERADJUSTSTEP {
  type uint8 {
   range "1..49";
  }
  mandatory false;
 }
 leaf SRBPOLLTIMERMAXADJUSTVALUE {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-47;
   enum val-48;
   enum val-49;
   enum val-50;
   enum val-51;
   enum val-52;
   enum val-53;
   enum val-54;
  }
  mandatory false;
 }
 leaf SRBPOLLTIMERPRESET {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-47;
   enum val-48;
   enum val-49;
   enum val-50;
   enum val-51;
   enum val-52;
   enum val-53;
   enum val-54;
  }
  mandatory false;
 }
 leaf SRBRLCPARAADAPTSWITCH {
  type boolean;
  mandatory false;
 }
 }
 grouping SRBRLCPDCPCFG-attributes {
 leaf ENODEBAMREORDERINGTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
  }
  mandatory false;
 }
 leaf ENODEBMAXRETXTHRESHOLD {
  type enumeration {
   enum val-0;
   enum val-1;
   enum val-2;
   enum val-3;
   enum val-4;
   enum val-5;
   enum val-6;
   enum val-7;
  }
  mandatory false;
 }
 leaf ENODEBPOLLBYTE {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf ENODEBPOLLPDU {
  type enumeration {
   enum val-0;
   enum val-1;
   enum val-2;
   enum val-3;
   enum val-4;
   enum val-5;
   enum val-6;
   enum val-7;
  }
  mandatory false;
 }
 leaf ENODEBPOLLRETRANSMITTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-47;
   enum val-48;
   enum val-49;
   enum val-50;
   enum val-51;
   enum val-52;
   enum val-53;
   enum val-54;
   enum val-55;
   enum val-56;
   enum val-57;
   enum val-58;
  }
  mandatory false;
 }
 leaf ENODEBSTATUSPROHIBITTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-47;
   enum val-48;
   enum val-49;
   enum val-50;
   enum val-51;
   enum val-52;
   enum val-53;
   enum val-54;
   enum val-55;
   enum val-56;
   enum val-57;
   enum val-58;
   enum val-59;
   enum val-60;
   enum val-61;
  }
  mandatory false;
 }
 leaf NBENODEBPOLLRETRANSTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf NBENODEBMAXRETXTHRESHOLD {
  type enumeration {
   enum val-0;
   enum val-1;
   enum val-2;
   enum val-3;
   enum val-4;
   enum val-5;
   enum val-6;
   enum val-7;
  }
  mandatory false;
 }
 leaf NBUEMAXRETXTHRESHOLD {
  type enumeration {
   enum val-0;
   enum val-1;
   enum val-2;
   enum val-3;
   enum val-4;
   enum val-5;
   enum val-6;
   enum val-7;
  }
  mandatory false;
 }
 leaf NBUEPOLLRETRANSTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf SRBID {
  type enumeration {
   enum val--1;
   enum val-1;
   enum val-2;
   enum val-3;
   enum val-4;
   enum val-5;
   enum val-6;
   enum val-7;
   enum val-9;
   enum val-11;
   enum val-13;
   enum val-14;
   enum val-15;
   enum val-16;
   enum val-17;
   enum val-18;
  }
  mandatory false;
 }
 leaf UEAMREORDERINGTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
  }
  mandatory false;
 }
 leaf UEMAXRETXTHRESHOLD {
  type enumeration {
   enum val-0;
   enum val-1;
   enum val-2;
   enum val-3;
   enum val-4;
   enum val-5;
   enum val-6;
   enum val-7;
  }
  mandatory false;
 }
 leaf UEPOLLBYTE {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf UEPOLLPDU {
  type enumeration {
   enum val-0;
   enum val-1;
   enum val-2;
   enum val-3;
   enum val-4;
   enum val-5;
   enum val-6;
   enum val-7;
  }
  mandatory false;
 }
 leaf UEPOLLRETRANSMITTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-47;
   enum val-48;
   enum val-49;
   enum val-50;
   enum val-51;
   enum val-52;
   enum val-53;
   enum val-54;
   enum val-55;
   enum val-56;
   enum val-57;
   enum val-58;
  }
  mandatory false;
 }
 leaf UESTATUSPROHIBITTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-47;
   enum val-48;
   enum val-49;
   enum val-50;
   enum val-51;
   enum val-52;
   enum val-53;
   enum val-54;
   enum val-55;
   enum val-56;
   enum val-57;
   enum val-58;
   enum val-59;
   enum val-60;
   enum val-61;
  }
  mandatory false;
 }
 leaf VOLTEENODEBMAXRETXTHLD {
  type enumeration {
   enum val-0;
   enum val-1;
   enum val-2;
   enum val-3;
   enum val-4;
   enum val-5;
   enum val-6;
   enum val-7;
   enum val-8;
   enum val-9;
   enum val-10;
   enum val-11;
   enum val-12;
  }
  mandatory false;
 }
 }
 grouping SRSCFG-attributes {
 leaf LOCALCELLNAME {
  type string;
  mandatory false;
 }
 leaf ANSRSSIMUTRANS {
  type boolean;
  mandatory false;
 }
 leaf BOUNDARYBEAMADJUENUMTHLD {
  type uint16 {
   range "0..1000";
  }
  mandatory false;
 }
 leaf EXITSRSMEAUENUMOFFSET {
  type uint8 {
   range "0..50";
  }
  mandatory false;
 }
 leaf FDDSRSCFGMODE {
  type boolean;
  mandatory false;
 }
 leaf LOCALCELLID {
  type union {
   type int16 {
    range "-1..255";
   }
  }
  mandatory false;
 }
 leaf RSVRESSRSPERIOD1 {
  type enumeration {
   enum val-0;
   enum val-1;
   enum val-2;
   enum val-3;
  }
  mandatory false;
 }
 leaf RSVRESSRSPERIOD2 {
  type enumeration {
   enum val-0;
   enum val-1;
   enum val-2;
   enum val-3;
  }
  mandatory false;
 }
 leaf SRSALGOOPTSWITCH {
  type string;
  mandatory false;
 }
 leaf SRSCFGIND {
  type boolean;
  mandatory false;
 }
 leaf SRSCFGPOLICYSWITCH {
  type string;
  mandatory false;
 }
 leaf SRSINTERFAVOIDOPTSWITCH {
  type enumeration {
   enum val-0;
   enum val-1;
   enum val-2;
  }
  mandatory false;
 }
 leaf SRSRESEXPANSIONSWITCH {
  type boolean;
  mandatory false;
 }
 leaf SRSRESOPTSWITCH {
  type boolean;
  mandatory false;
 }
 leaf SRSSUBFRAMECFG {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 leaf STARTSRSMEAUENUMTHLD {
  type union {
   type uint16 {
    range "0..350";
   }
  }
  mandatory false;
 }
 leaf TDDSRSCFGMODE {
  type enumeration {
   enum val-0;
   enum val-1;
   enum val-2;
   enum val-3;
  }
  mandatory false;
 }
 }
 grouping SSRDCELLGROUP-attributes {
 leaf BEAMNUMRESTOREDLPRBTHLD {
  type uint8 {
   range "15..60";
  }
  mandatory false;
 }
 leaf BEAMNUMRESTOREEVALPRD {
  type uint16 {
   range "20..1440";
  }
  mandatory false;
 }
 leaf BEAMNUMRESTOREUENUMTHLD {
  type uint16 {
   range "1..300";
  }
  mandatory false;
 }
 leaf BEAMNUMSHIFTDLPRBTHLD {
  type uint8 {
   range "0..30";
  }
  mandatory false;
 }
 leaf BEAMNUMSHIFTEVALPRD {
  type uint16 {
   range "60..1440";
  }
  mandatory false;
 }
 leaf BEAMNUMSHIFTUENUMTHLD {
  type uint16 {
   range "1..300";
  }
  mandatory false;
 }
 leaf EFFECTIVEBEAMNUM {
  type boolean;
  mandatory false;
 }
 leaf FORCEBEAMNUMSHIFTUENUMTHLD {
  type uint8 {
   range "0..20";
  }
  mandatory false;
 }
 leaf OLD_PRIMARYLOCALCELLID {
  type union {
   type int16 {
    range "-1..255";
   }
  }
  mandatory false;
 }
 leaf PRIMARYLOCALCELLID {
  type union {
   type int16 {
    range "-1..255";
   }
  }
  mandatory false;
 }
 leaf SSRDALGOSWITCH {
  type string;
  mandatory false;
 }
 leaf OLD_SSRDLOCALCELLID {
  type union {
   type int16 {
    range "-1..255";
   }
  }
  mandatory false;
 }
 leaf SSRDLOCALCELLID {
  type union {
   type int16 {
    range "-1..255";
   }
  }
  mandatory false;
 }
 }
 grouping SUPERCOMBCELL-attributes {
 leaf LOCALCELLNAME {
  type string;
  mandatory false;
 }
 leaf LOCALCELLID {
  type union {
   type int16 {
    range "-1..255";
   }
  }
  mandatory false;
 }
 leaf SFNCELLID {
  type uint8 {
   range "0..99";
  }
  mandatory false;
 }
 }
 grouping SYMBOLPWRSAVING-attributes {
 leaf LOCALCELLNAME {
  type string;
  mandatory false;
 }
 leaf CRSDYNMUTEOPTNOAPPSTPTIME {
  type hwat:HH_MM_SS_Time;
  mandatory false;
 }
 leaf CRSDYNMUTEOPTNOAPPSTRTIME {
  type hwat:HH_MM_SS_Time;
  mandatory false;
 }
 leaf CRSDYNMUTINGSTARTTIME {
  type hwat:HH_MM_SS_Time;
  mandatory false;
 }
 leaf CRSDYNMUTINGSTOPTIME {
  type hwat:HH_MM_SS_Time;
  mandatory false;
 }
 leaf CRSDYNMUTINGSYMBOLNUM {
  type uint8 {
   range "0..3";
  }
  mandatory false;
 }
 leaf LOCALCELLID {
  type union {
   type int16 {
    range "-1..255";
   }
  }
  mandatory false;
 }
 leaf MBSFNSHUTDOWNSTARTTIME {
  type hwat:HH_MM_SS_Time;
  mandatory false;
 }
 leaf MBSFNSHUTDOWNSTOPTIME {
  type hwat:HH_MM_SS_Time;
  mandatory false;
 }
 leaf MINCQIPERIOD {
  type enumeration {
   enum val-0;
   enum val-1;
   enum val-2;
   enum val-3;
   enum val-4;
  }
  mandatory false;
 }
 leaf MINPREALLOCATIONPERIOD {
  type uint8 {
   range "1..40";
  }
  mandatory false;
 }
 leaf MINSRIPERIOD {
  type enumeration {
   enum val-0;
   enum val-1;
   enum val-2;
   enum val-3;
   enum val-4;
  }
  mandatory false;
 }
 leaf MULTIRATSYMBOLSHUTDOWNSW {
  type boolean;
  mandatory false;
 }
 leaf STOPBUNDLINGDLTTIPRBTHLD {
  type uint16 {
   range "0..500";
  }
  mandatory false;
 }
 leaf SYMBOLSHUTDOWNENHANCEDSW {
  type string;
  mandatory false;
 }
 leaf TRIGBNDLSCHDLAVGPRBTHLD {
  type uint8 {
   range "0..70";
  }
  mandatory false;
 }
 leaf UEINACTIVITYTIMER {
  type uint16 {
   range "0..3600";
  }
  mandatory false;
 }
 }
 grouping TACOUNTERPARAMGRP-attributes {
 leaf TAENDVALUE {
  type uint8 {
   range "0..255";
  }
  mandatory false;
 }
 leaf OLD_TARANGEINDEX {
  type union {
   type int8 {
    range "-1..15";
   }
  }
  mandatory false;
 }
 leaf TARANGEINDEX {
  type union {
   type int8 {
    range "-1..15";
   }
  }
  mandatory false;
 }
 leaf TASTARTVALUE {
  type uint8 {
   range "0..254";
  }
  mandatory false;
 }
 }
 grouping TCEIPMAPPING-attributes {
 leaf IPMODE {
  type boolean;
  mandatory false;
 }
 leaf OLD_TCEID {
  type union {
   type int16 {
    range "-1..255";
   }
  }
  mandatory false;
 }
 leaf TCEID {
  type union {
   type int16 {
    range "-1..255";
   }
  }
  mandatory false;
 }
 leaf TCEIPV4ADDR {
  type inet:ipv4-address;
  mandatory false;
 }
 leaf TCEIPV6ADDR {
  type inet:ipv6-address;
  mandatory false;
 }
 }
 grouping TDDRESMODESWITCH-attributes {
 leaf BBRESEXCLUSIVESWITCH {
  type enumeration {
   enum val-0;
   enum val-1;
   enum val-2;
  }
  mandatory false;
 }
 leaf CLKRESEXCLUDESWITCH {
  type boolean;
  mandatory false;
 }
 leaf NOCLKCELLACTSWEXPIRYTIME {
  type hwat:yyyy_mm_dd_HH_MM_SS_Time;
  mandatory false;
 }
 }
 grouping TIMEALIGNMENTTIMER-attributes {
 leaf LOCALCELLNAME {
  type string;
  mandatory false;
 }
 leaf HIGHSPEEDTACMDSENDPERIOD {
  type enumeration {
   enum val-0;
   enum val-1;
   enum val-2;
   enum val-3;
   enum val-4;
   enum val-5;
   enum val-6;
  }
  mandatory false;
 }
 leaf LOCALCELLID {
  type union {
   type int16 {
    range "-1..255";
   }
  }
  mandatory false;
 }
 leaf PUCCHTIMEOFFSETCOMPVAL {
  type uint8 {
   range "0..15";
  }
  mandatory false;
 }
 leaf TACMDSENDPERIOD {
  type enumeration {
   enum val-0;
   enum val-218;
   enum val-343;
   enum val-608;
   enum val-928;
   enum val-1248;
   enum val-2528;
   enum val-5088;
  }
  mandatory false;
 }
 leaf TAADJMAXSTEP {
  type uint8 {
   range "2..8";
  }
  mandatory false;
 }
 leaf TAENHANCE {
  type string;
  mandatory false;
 }
 leaf TAMEASOPTSWITCH {
  type string;
  mandatory false;
 }
 leaf TIMEALIGNMENTTIMER {
  type enumeration {
   enum val-0;
   enum val-1;
   enum val-2;
   enum val-3;
   enum val-4;
   enum val-5;
   enum val-6;
   enum val-7;
  }
  mandatory false;
 }
 leaf TIMINGADVCMDOPTSWITCH {
  type boolean;
  mandatory false;
 }
 leaf TIMINGMEASMODE {
  type boolean;
  mandatory false;
 }
 leaf TIMINGRESOPTSWITCH {
  type boolean;
  mandatory false;
 }
 }
 grouping TM9DEDICATEDCARRIER-attributes {
 leaf CRSTRANSMISSIONSTRATEGY {
  type boolean;
  mandatory false;
 }
 leaf OLD_TM9CCDLEARFCN {
  type union {
   type int32 {
    range "-1..229575";
   }
  }
  mandatory false;
 }
 leaf TM9CCDLEARFCN {
  type union {
   type int32 {
    range "-1..229575";
   }
  }
  mandatory false;
 }
 leaf WORKMODE {
  type enumeration {
   enum val-0;
   enum val-1;
   enum val-2;
   enum val-3;
  }
  mandatory false;
 }
 }
 grouping TYPDRBBSR-attributes {
 leaf QCI {
  type enumeration {
   enum val--1;
   enum val-1;
   enum val-2;
   enum val-3;
   enum val-4;
   enum val-5;
   enum val-6;
   enum val-7;
   enum val-8;
   enum val-9;
   enum val-65;
   enum val-66;
   enum val-67;
   enum val-69;
   enum val-70;
   enum val-71;
   enum val-72;
   enum val-73;
   enum val-74;
   enum val-75;
   enum val-76;
   enum val-79;
  }
  mandatory false;
 }
 leaf RETXBSRTIMER {
  type enumeration {
   enum val-0;
   enum val-1;
   enum val-2;
   enum val-3;
   enum val-4;
   enum val-5;
  }
  mandatory false;
 }
 leaf TPERODICBSRTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 }
 grouping UECOMPAT-attributes {
 leaf BLACKLISTCONTROLEXTSWITCH1 {
  type string;
  mandatory false;
 }
 leaf BLACKLISTCONTROLEXTSWITCH2 {
  type string;
  mandatory false;
 }
 leaf BLKLSTCTRLSWITCH {
  type string;
  mandatory false;
 }
 leaf IMEISVSVN {
  type uint8 {
   range "0..99";
  }
  mandatory false;
 }
 leaf IMEISVTAC {
  type uint32 {
   range "0..99999999";
  }
  mandatory false;
 }
 leaf OLD_INDEX {
  type union {
   type int8 {
    range "-1..127";
   }
  }
  mandatory false;
 }
 leaf INDEX {
  type union {
   type int8 {
    range "-1..127";
   }
  }
  mandatory false;
 }
 leaf LNRFREQRELPBLACKLIST {
  type string;
  mandatory false;
 }
 leaf LNRFREQRELPWHITELIST {
  type string;
  mandatory false;
 }
 leaf LNRNOGAPFREQCOMBBLACKLIST {
  type string;
  mandatory false;
 }
 leaf NSABANDCOMBBLACKLIST1 {
  type string;
  mandatory false;
 }
 leaf NSABANDCOMBBLACKLIST2 {
  type string;
  mandatory false;
 }
 leaf NSADCMAXINTERFMEASOBJNUM {
  type union {
   type uint8 {
    range "0..32";
   }
  }
  mandatory false;
 }
 leaf NSANRULANTSELBLACKLIST1 {
  type string;
  mandatory false;
 }
 leaf NSANRULANTSELBLACKLIST2 {
  type string;
  mandatory false;
 }
 leaf NSAPERSISTB1MAXMEASOBJNUM {
  type uint8 {
   range "0..15";
  }
  mandatory false;
 }
 leaf SPEEDTURBOAGGATTR {
  type uint16 {
   range "0..65535";
  }
  mandatory false;
 }
 leaf TM9HYBRIDPRECODINGPOLICY {
  type enumeration {
   enum val-0;
   enum val-1;
   enum val-2;
   enum val-3;
  }
  mandatory false;
 }
 leaf UECAPINDEX {
  type uint8 {
   range "0..63";
  }
  mandatory false;
 }
 leaf UEDIFFDRXSWITCH {
  type boolean;
  mandatory false;
 }
 leaf UEINFOTYPE {
  type enumeration {
   enum val-0;
   enum val-1;
   enum val-2;
  }
  mandatory false;
 }
 leaf UESPECIFICCONFIGINDEX {
  type uint16 {
   range "0..256";
  }
  mandatory false;
 }
 leaf UESTATUSPROHIBITTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
   enum val-22;
   enum val-23;
   enum val-24;
   enum val-25;
   enum val-26;
   enum val-27;
   enum val-28;
   enum val-29;
   enum val-30;
   enum val-31;
   enum val-32;
   enum val-33;
   enum val-34;
   enum val-35;
   enum val-36;
   enum val-37;
   enum val-38;
   enum val-39;
   enum val-40;
   enum val-41;
   enum val-42;
   enum val-43;
   enum val-44;
   enum val-45;
   enum val-46;
   enum val-47;
   enum val-48;
   enum val-49;
   enum val-50;
   enum val-51;
   enum val-52;
   enum val-53;
   enum val-54;
   enum val-55;
   enum val-56;
   enum val-57;
   enum val-58;
   enum val-59;
   enum val-60;
   enum val-61;
   enum val-62;
  }
  mandatory false;
 }
 leaf UETYPEDESC {
  type string {
   length "0..80";
  }
  mandatory false;
 }
 leaf UL256QAMUECONFIGINDEX {
  type union {
   type uint8 {
    range "0..255";
   }
  }
  mandatory false;
 }
 leaf WHITELSTCACOMBSWITCH {
  type string;
  mandatory false;
 }
 leaf WHITELSTCTRLSWITCH {
  type string;
  mandatory false;
 }
 leaf WHITELISTCTRLEXTSWITCH1 {
  type string;
  mandatory false;
 }
 leaf WHITELISTCTRLEXTSWITCH2 {
  type string;
  mandatory false;
 }
 leaf WHITELISTGAPFREECOMBSWITCH {
  type string;
  mandatory false;
 }
 }
 grouping UECOOPERATIONPARA-attributes {
 leaf LOCALCELLNAME {
  type string;
  mandatory false;
 }
 leaf A2OFFSET {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf A3OFFSET {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf DSDSCOOPERATIONRPTSWITCH {
  type string;
  mandatory false;
 }
 leaf DSDSLCID {
  type uint8 {
   range "11..26";
  }
  mandatory false;
 }
 leaf INCRUEIDENTMODE {
  type boolean;
  mandatory false;
 }
 leaf INCRUEIDENTSINRTHLD {
  type int8 {
   range "-23..40";
  }
  mandatory false;
 }
 leaf INCRUEIDENTTRUSTTHLD {
  type uint8 {
   range "20..100";
  }
  mandatory false;
 }
 leaf LOCALCELLID {
  type union {
   type int16 {
    range "-1..255";
   }
  }
  mandatory false;
 }
 leaf MACCEMSGLCID {
  type uint8 {
   range "17..19";
  }
  mandatory false;
 }
 leaf SPECNBUSERMINPAGINGCYCLE {
  type enumeration {
   enum val-0;
   enum val-1;
   enum val-2;
   enum val-255;
  }
  mandatory false;
 }
 leaf SPECUSERCOOPERATIONSWITCH {
  type string;
  mandatory false;
 }
 leaf SPECUSERPRIVATEELCID {
  type uint8 {
   range "39..95";
  }
  mandatory false;
 }
 leaf SPECUSERSMARTDRXSWITCH {
  type boolean;
  mandatory false;
 }
 leaf UEAWAREPOWERSAVINGSWITCH {
  type boolean;
  mandatory false;
 }
 leaf UEFORBIDDENMSGTHD {
  type uint8 {
   range "2..50";
  }
  mandatory false;
 }
 leaf VOLTEPAGINGPRIORITY {
  type enumeration {
   enum val-0;
   enum val-1;
   enum val-2;
   enum val-3;
   enum val-4;
   enum val-5;
   enum val-6;
   enum val-7;
   enum val-255;
  }
  mandatory false;
 }
 }
 grouping UEDIFFCONFIG-attributes {
 leaf LOCALCELLNAME {
  type string;
  mandatory false;
 }
 leaf DRXPARAGROUPID {
  type union {
   type uint8 {
    range "0..255";
   }
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf OLD_QCI {
  type union {
   type int16 {
    range "-1..254";
   }
  }
  mandatory false;
 }
 leaf QCI {
  type union {
   type int16 {
    range "-1..254";
   }
  }
  mandatory false;
 }
 leaf OLD_UEINFOINDEX {
  type union {
   type int8 {
    range "-1..127";
   }
  }
  mandatory false;
 }
 leaf UEINFOINDEX {
  type union {
   type int8 {
    range "-1..127";
   }
  }
  mandatory false;
 }
 }
 grouping UEINFO-attributes {
 leaf ACCESSSTRATUMRELEASE {
  type uint8 {
   range "0..255";
  }
  mandatory false;
 }
 leaf DLUECATEGORY {
  type uint32 {
   range "0..4294967295";
  }
  mandatory false;
 }
 leaf EUTRANBANDLIST1 {
  type uint32 {
   range "0..4294967295";
  }
  mandatory false;
 }
 leaf EUTRANBANDLIST2 {
  type uint32 {
   range "0..4294967295";
  }
  mandatory false;
 }
 leaf FGI {
  type uint32 {
   range "0..4294967295";
  }
  mandatory false;
 }
 leaf FGIR10 {
  type uint32 {
   range "0..4294967295";
  }
  mandatory false;
 }
 leaf FGIR9 {
  type uint32 {
   range "0..4294967295";
  }
  mandatory false;
 }
 leaf FGIR9ADD {
  type uint32 {
   range "0..4294967295";
  }
  mandatory false;
 }
 leaf OLD_UECAPINDEX {
  type union {
   type int8 {
    range "-1..63";
   }
  }
  mandatory false;
 }
 leaf UECAPINDEX {
  type union {
   type int8 {
    range "-1..63";
   }
  }
  mandatory false;
 }
 leaf UECATEGORY {
  type uint16 {
   range "0..65535";
  }
  mandatory false;
 }
 leaf UEFEATUREVALUECONTENT {
  type string {
   length "0..64";
  }
  mandatory false;
 }
 leaf UEFEATUREVALUEMASK {
  type string {
   length "64";
  }
  mandatory false;
 }
 leaf UESPECIFICCAPABILITYINFO {
  type uint32 {
   range "0..4294967295";
  }
  mandatory false;
 }
 leaf ULUECATEGORY {
  type uint32 {
   range "0..4294967295";
  }
  mandatory false;
 }
 }
 grouping UESPECDRXPARAGROUP-attributes {
 leaf LOCALCELLNAME {
  type string;
  mandatory false;
 }
 leaf DRXINACTIVITYTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
   enum val-17;
   enum val-18;
   enum val-19;
   enum val-20;
   enum val-21;
  }
  mandatory false;
 }
 leaf OLD_DRXPARAGROUPINDEX {
  type union {
   type int16 {
    range "-1..252";
   }
  }
  mandatory false;
 }
 leaf DRXPARAGROUPINDEX {
  type union {
   type int16 {
    range "-1..252";
   }
  }
  mandatory false;
 }
 leaf DRXPARAGROUPSTAT {
  type boolean;
  mandatory false;
 }
 leaf DRXRETXTIMER {
  type enumeration {
   enum val-0;
   enum val-1;
   enum val-2;
   enum val-3;
   enum val-4;
   enum val-5;
   enum val-6;
   enum val-7;
  }
  mandatory false;
 }
 leaf DRXSHORTCYCLETIMER {
  type uint8 {
   range "1..16";
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf LONGDRXCYCLE {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
  }
  mandatory false;
 }
 leaf ONDURATIONTIMER {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf SHORTDRXCYCLE {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf SUPPORTSHORTDRX {
  type boolean;
  mandatory false;
 }
 }
 grouping UETIMERCONFIG-attributes {
 leaf MAXNUMUESYNCOROUTOFSYNCIND {
  type uint8 {
   range "0..200";
  }
  mandatory false;
 }
 leaf TIMERDURATION {
  type uint16 {
   range "1..3600";
  }
  mandatory false;
 }
 leaf TIMERDURATIONMILLISECOND {
  type union {
   type uint32 {
    range "0..4294967295";
   }
  }
  mandatory false;
 }
 leaf TIMERTYPE {
  type enumeration {
   enum val--1;
   enum val-0;
   enum val-1;
   enum val-2;
   enum val-3;
   enum val-4;
   enum val-5;
   enum val-6;
   enum val-7;
   enum val-8;
   enum val-9;
   enum val-10;
   enum val-11;
   enum val-12;
   enum val-13;
   enum val-14;
  }
  mandatory false;
 }
 }
 grouping UETIMERCONST-attributes {
 leaf LOCALCELLNAME {
  type string;
  mandatory false;
 }
 leaf LOCALCELLID {
  type union {
   type int16 {
    range "-1..255";
   }
  }
  mandatory false;
 }
 leaf N310 {
  type enumeration {
   enum val-0;
   enum val-1;
   enum val-2;
   enum val-3;
   enum val-4;
   enum val-5;
   enum val-6;
   enum val-7;
  }
  mandatory false;
 }
 leaf N311 {
  type enumeration {
   enum val-0;
   enum val-1;
   enum val-2;
   enum val-3;
   enum val-4;
   enum val-5;
   enum val-6;
   enum val-7;
  }
  mandatory false;
 }
 leaf N313 {
  type enumeration {
   enum val-0;
   enum val-1;
   enum val-2;
   enum val-3;
   enum val-4;
   enum val-5;
   enum val-6;
   enum val-7;
  }
  mandatory false;
 }
 leaf N314 {
  type enumeration {
   enum val-0;
   enum val-1;
   enum val-2;
   enum val-3;
   enum val-4;
   enum val-5;
   enum val-6;
   enum val-7;
  }
  mandatory false;
 }
 leaf T300 {
  type enumeration {
   enum val-0;
   enum val-1;
   enum val-2;
   enum val-3;
   enum val-4;
   enum val-5;
   enum val-6;
   enum val-7;
  }
  mandatory false;
 }
 leaf T300CE {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf T300FORNB {
  type enumeration {
   enum val-0;
   enum val-1;
   enum val-2;
   enum val-3;
   enum val-4;
   enum val-5;
   enum val-6;
   enum val-7;
  }
  mandatory false;
 }
 leaf T300FORNBEDT {
  type enumeration {
   enum val-0;
   enum val-1;
   enum val-2;
   enum val-3;
   enum val-4;
   enum val-5;
   enum val-6;
   enum val-7;
  }
  mandatory false;
 }
 leaf T301 {
  type enumeration {
   enum val-0;
   enum val-1;
   enum val-2;
   enum val-3;
   enum val-4;
   enum val-5;
   enum val-6;
   enum val-7;
  }
  mandatory false;
 }
 leaf T301CE {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
  }
  mandatory false;
 }
 leaf T301FORNB {
  type enumeration {
   enum val-0;
   enum val-1;
   enum val-2;
   enum val-3;
   enum val-4;
   enum val-5;
   enum val-6;
   enum val-7;
  }
  mandatory false;
 }
 leaf T307 {
  type enumeration {
   enum val-0;
   enum val-1;
   enum val-2;
   enum val-3;
   enum val-4;
   enum val-5;
   enum val-6;
  }
  mandatory false;
 }
 leaf T310 {
  type enumeration {
   enum val-0;
   enum val-1;
   enum val-2;
   enum val-3;
   enum val-4;
   enum val-5;
   enum val-6;
  }
  mandatory false;
 }
 leaf T310CE {
  type enumeration {
   enum val-0;
   enum val-1;
   enum val-2;
   enum val-3;
   enum val-4;
   enum val-5;
   enum val-6;
   enum val-7;
   enum val-8;
  }
  mandatory false;
 }
 leaf T310FORNB {
  type enumeration {
   enum val-0;
   enum val-1;
   enum val-2;
   enum val-3;
   enum val-4;
   enum val-5;
   enum val-6;
  }
  mandatory false;
 }
 leaf T311 {
  type enumeration {
   enum val-0;
   enum val-1;
   enum val-2;
   enum val-3;
   enum val-4;
   enum val-5;
   enum val-6;
  }
  mandatory false;
 }
 leaf T311CE {
  type enumeration {
   enum val-0;
   enum val-1;
   enum val-2;
   enum val-3;
   enum val-4;
   enum val-5;
   enum val-6;
  }
  mandatory false;
 }
 leaf T311FORNB {
  type enumeration {
   enum val-0;
   enum val-1;
   enum val-2;
   enum val-3;
   enum val-4;
   enum val-5;
   enum val-6;
   enum val-7;
   enum val-8;
   enum val-9;
   enum val-10;
  }
  mandatory false;
 }
 leaf T313 {
  type enumeration {
   enum val-0;
   enum val-1;
   enum val-2;
   enum val-3;
   enum val-4;
   enum val-5;
   enum val-6;
  }
  mandatory false;
 }
 leaf T322FORNB {
  type enumeration {
   enum val-0;
   enum val-1;
   enum val-2;
   enum val-3;
   enum val-4;
   enum val-5;
   enum val-6;
  }
  mandatory false;
 }
 leaf T325 {
  type enumeration {
   enum val-0;
   enum val-1;
   enum val-2;
   enum val-3;
  }
  mandatory false;
 }
 }
 grouping ULCSALGOPARA-attributes {
 leaf LOCALCELLNAME {
  type string;
  mandatory false;
 }
 leaf LOCALCELLID {
  type union {
   type int16 {
    range "-1..255";
   }
  }
  mandatory false;
 }
 leaf ULCOPCINTHD {
  type int8 {
   range "-115..-80";
  }
  mandatory false;
 }
 leaf ULCOPCRBKRSRPTHD {
  type int8 {
   range "-126..24";
  }
  mandatory false;
 }
 leaf ULCOPCUSERNUMTHD {
  type uint16 {
   range "30..10000";
  }
  mandatory false;
 }
 leaf ULCORESALLOCBANDMODE {
  type enumeration {
   enum val-0;
   enum val-1;
   enum val-2;
   enum val-255;
  }
  mandatory false;
 }
 leaf ULCORESALLOCRBLOADTHLD {
  type uint8 {
   range "40..100";
  }
  mandatory false;
 }
 leaf ULCOORDINTRFAWARESCHSW {
  type string;
  mandatory false;
 }
 leaf ULCRAINTHLD {
  type int8 {
   range "-115..80";
  }
  mandatory false;
 }
 leaf ULCRASUPPORTMOCNSWITCH {
  type boolean;
  mandatory false;
 }
 leaf ULCRAUSERNUMTHLD {
  type uint16 {
   range "1..300";
  }
  mandatory false;
 }
 leaf ULCSA3OFFSET {
  type int8 {
   range "-30..30";
  }
  mandatory false;
 }
 leaf ULCSSW {
  type string;
  mandatory false;
 }
 }
 grouping ULGUARDBANDCFG-attributes {
 leaf LOCALCELLNAME {
  type string;
  mandatory false;
 }
 leaf HIGHFREQGUARDBAND {
  type uint8 {
   range "0..47";
  }
  mandatory false;
 }
 leaf LOCALCELLID {
  type union {
   type int16 {
    range "-1..255";
   }
  }
  mandatory false;
 }
 leaf LOWFREQGUARDBAND {
  type uint8 {
   range "0..47";
  }
  mandatory false;
 }
 leaf NPRACHNPUSCHGUARDBAND {
  type uint8 {
   range "0..4";
  }
  mandatory false;
 }
 leaf PRBID {
  type union {
   type int16 {
    range "-1..255";
   }
  }
  mandatory false;
 }
 }
 grouping ULINTERFSUPPRESSCFG-attributes {
 leaf LOCALCELLNAME {
  type string;
  mandatory false;
 }
 leaf CELLPUSCHAVAILABLERBRATIO {
  type uint8 {
   range "0..100";
  }
  mandatory false;
 }
 leaf CHNCALOPTSWITCH {
  type enumeration {
   enum val-0;
   enum val-1;
   enum val-2;
  }
  mandatory false;
 }
 leaf CHNCALIBEVALUATEOPTSW {
  type boolean;
  mandatory false;
 }
 leaf CHNCALIBFAILUREPROPTHLD {
  type uint8 {
   range "0..100";
  }
  mandatory false;
 }
 leaf CHNCALIBINTRFTHLD {
  type int8 {
   range "-120..-60";
  }
  mandatory false;
 }
 leaf CHNCALIBPUCCHINTRFAVOIDPCT {
  type uint8 {
   range "0..150";
  }
  mandatory false;
 }
 leaf CHNCALIBSHIFTSYMCONFIG {
  type union {
   type uint8 {
    range "0..12";
   }
  }
  mandatory false;
 }
 leaf CHNCALIBTHLD {
  type union {
   type int8 {
    range "-5..127";
   }
  }
  mandatory false;
 }
 leaf DELTAMSG2OFFSET {
  type enumeration {
   enum val-0;
   enum val-1;
   enum val-2;
   enum val-3;
   enum val-4;
   enum val-5;
  }
  mandatory false;
 }
 leaf INTERFERENCERBRATIOTHLD {
  type uint8 {
   range "0..100";
  }
  mandatory false;
 }
 leaf LOCALCELLID {
  type union {
   type int16 {
    range "-1..255";
   }
  }
  mandatory false;
 }
 leaf P0UEPUCCHOFFSET {
  type uint8 {
   range "0..7";
  }
  mandatory false;
 }
 leaf P0UEPUSCHOFFSET {
  type uint8 {
   range "0..7";
  }
  mandatory false;
 }
 leaf PUSCHENHDELTASINRTHD {
  type int8 {
   range "-10..30";
  }
  mandatory false;
 }
 leaf PUSCHSYMCOSCHCELLNUM {
  type uint8 {
   range "1..10";
  }
  mandatory false;
 }
 leaf PUSCHSYMCOSCHSW {
  type enumeration {
   enum val-0;
   enum val-1;
   enum val-2;
  }
  mandatory false;
 }
 leaf RASIGNALMCSOFFSET {
  type uint8 {
   range "0..30";
  }
  mandatory false;
 }
 leaf RASIGNALPCSWITCH {
  type boolean;
  mandatory false;
 }
 leaf REMOTEINFULENHANCESW {
  type string;
  mandatory false;
 }
 leaf REMOTEINTRFDLENHSWITCH {
  type string;
  mandatory false;
 }
 leaf SRSSHIFTINTRFDIFFTHLD {
  type int8 {
   range "-10..30";
  }
  mandatory false;
 }
 leaf STRONGINFUSERTHDRATIO {
  type int16 {
   range "-100..1000";
  }
  mandatory false;
 }
 leaf ULINFSTATISTICPERIOD {
  type uint8 {
   range "1..10";
  }
  mandatory false;
 }
 leaf ULINFSTATISTICPERIODNUM {
  type uint8 {
   range "1..20";
  }
  mandatory false;
 }
 leaf ULHOMOLOGOUSINTRFPCTTHLD {
  type uint8 {
   range "0..100";
  }
  mandatory false;
 }
 leaf ULINTERPWRDIFFTHD {
  type int8 {
   range "-30..30";
  }
  mandatory false;
 }
 leaf ULINTERFSUPPRESSIONTHD {
  type int8 {
   range "-120..-80";
  }
  mandatory false;
 }
 leaf ULINTRFDETECTIONA3OFFSET {
  type int8 {
   range "-30..30";
  }
  mandatory false;
 }
 leaf ULINTRFDETECTIONTRIGTHLD {
  type union {
   type int8 {
    range "-120..127";
   }
  }
  mandatory false;
 }
 leaf ULINTRFPOSITIONINGCONFIG {
  type uint32 {
   range "0..4294967295";
  }
  mandatory false;
 }
 leaf ULINTRFSUPPRESSIONVALUE {
  type uint8 {
   range "0..21";
  }
  mandatory false;
 }
 leaf ULJOINTINTRFMANAGEMENTSW {
  type string;
  mandatory false;
 }
 leaf ULSINGLESIDEINTRFIMPMITSW {
  type enumeration {
   enum val-0;
   enum val-1;
   enum val-2;
   enum val-3;
  }
  mandatory false;
 }
 leaf ULSTRONGINTRFCORRCOEFFTHLD {
  type uint8 {
   range "0..100";
  }
  mandatory false;
 }
 leaf UPPTSINTERFERENCETHLD {
  type int16 {
   range "-140..-43";
  }
  mandatory false;
 }
 leaf VOLTEMCSOFFSET {
  type uint8 {
   range "0..30";
  }
  mandatory false;
 }
 leaf VOLTEPUCCHPCTARSINROFFSET {
  type uint8 {
   range "0..30";
  }
  mandatory false;
 }
 leaf VOLTEPUSCHPSDCTRLTARGET {
  type uint8 {
   range "1..96";
  }
  mandatory false;
 }
 }
 grouping ULSPECTRUMSHRCONFIG-attributes {
 leaf LTEPRBENDINDEX {
  type uint8 {
   range "0..99";
  }
  mandatory false;
 }
 leaf LTEPRBSTARTINDEX {
  type uint8 {
   range "0..99";
  }
  mandatory false;
 }
 leaf OLD_PRBRSVTYPE {
  type enumeration {
   enum val--1;
   enum val-0;
   enum val-1;
   enum val-2;
   enum val-3;
   enum val-4;
   enum val-5;
   enum val-6;
   enum val-7;
   enum val-8;
  }
  mandatory false;
 }
 leaf PRBRSVTYPE {
  type enumeration {
   enum val--1;
   enum val-0;
   enum val-1;
   enum val-2;
   enum val-3;
   enum val-4;
   enum val-5;
   enum val-6;
   enum val-7;
   enum val-8;
  }
  mandatory false;
 }
 leaf OLD_ULSPECTRUMSHARINGCONFIGID {
  type union {
   type int8 {
    range "-1..25";
   }
  }
  mandatory false;
 }
 leaf ULSPECTRUMSHARINGCONFIGID {
  type union {
   type int8 {
    range "-1..25";
   }
  }
  mandatory false;
 }
 }
 grouping ULZEROBUFFERZONE-attributes {
 leaf LOCALCELLNAME {
  type string;
  mandatory false;
 }
 leaf LOCALCELLID {
  type union {
   type int16 {
    range "-1..255";
   }
  }
  mandatory false;
 }
 leaf ULSHAREDFREQENDRB {
  type uint8 {
   range "0..99";
  }
  mandatory false;
 }
 leaf ULSHAREDFREQSTARTRB {
  type uint8 {
   range "0..99";
  }
  mandatory false;
 }
 leaf ULSPECTRUMSHARINGCONFIGID {
  type uint8 {
   range "0..25";
  }
  mandatory false;
 }
 leaf ULZEROBUFZOINTERRATB1TIMER {
  type uint16 {
   range "0..600";
  }
  mandatory false;
 }
 leaf ULZEROBUFZONEB1RMVOFFSET {
  type uint8 {
   range "0..20";
  }
  mandatory false;
 }
 leaf ULZEROBUFZONEPRBOFFSET {
  type uint8 {
   range "0..100";
  }
  mandatory false;
 }
 leaf ULZEROBUFZONEPRBTHD {
  type uint8 {
   range "0..100";
  }
  mandatory false;
 }
 leaf ULZEROBUFZONERSRPOFFSET {
  type uint8 {
   range "0..60";
  }
  mandatory false;
 }
 leaf ULZEROBUFZONERSRPTHD {
  type int16 {
   range "-140..-43";
  }
  mandatory false;
 }
 leaf ULZEROBUFZONEUTRANRSCPTHD {
  type int8 {
   range "-120..-25";
  }
  mandatory false;
 }
 leaf ZEROBUFZONESWITCH {
  type string;
  mandatory false;
 }
 }
 grouping USERPRBGROUPPARAM-attributes {
 leaf OLD_SPID {
  type union {
   type int16 {
    range "-1..256";
   }
  }
  mandatory false;
 }
 leaf SPID {
  type union {
   type int16 {
    range "-1..256";
   }
  }
  mandatory false;
 }
 leaf TRACKINGAREAID {
  type uint16 {
   range "0..65535";
  }
  mandatory false;
 }
 leaf OLD_USERPRBGROUPID {
  type union {
   type int16 {
    range "-1..215";
   }
  }
  mandatory false;
 }
 leaf USERPRBGROUPID {
  type union {
   type int16 {
    range "-1..215";
   }
  }
  mandatory false;
 }
 }
 grouping USERPRIORITY-attributes {
 leaf ARP10PRIORITY {
  type enumeration {
   enum val-1;
   enum val-2;
   enum val-3;
   enum val-4;
  }
  mandatory false;
 }
 leaf ARP11PRIORITY {
  type enumeration {
   enum val-1;
   enum val-2;
   enum val-3;
   enum val-4;
  }
  mandatory false;
 }
 leaf ARP12PRIORITY {
  type enumeration {
   enum val-1;
   enum val-2;
   enum val-3;
   enum val-4;
  }
  mandatory false;
 }
 leaf ARP13PRIORITY {
  type enumeration {
   enum val-1;
   enum val-2;
   enum val-3;
   enum val-4;
  }
  mandatory false;
 }
 leaf ARP14PRIORITY {
  type enumeration {
   enum val-1;
   enum val-2;
   enum val-3;
   enum val-4;
  }
  mandatory false;
 }
 leaf ARP15PRIORITY {
  type enumeration {
   enum val-1;
   enum val-2;
   enum val-3;
   enum val-4;
  }
  mandatory false;
 }
 leaf ARP1PRIORITY {
  type enumeration {
   enum val-1;
   enum val-2;
   enum val-3;
   enum val-4;
  }
  mandatory false;
 }
 leaf ARP2PRIORITY {
  type enumeration {
   enum val-1;
   enum val-2;
   enum val-3;
   enum val-4;
  }
  mandatory false;
 }
 leaf ARP3PRIORITY {
  type enumeration {
   enum val-1;
   enum val-2;
   enum val-3;
   enum val-4;
  }
  mandatory false;
 }
 leaf ARP4PRIORITY {
  type enumeration {
   enum val-1;
   enum val-2;
   enum val-3;
   enum val-4;
  }
  mandatory false;
 }
 leaf ARP5PRIORITY {
  type enumeration {
   enum val-1;
   enum val-2;
   enum val-3;
   enum val-4;
  }
  mandatory false;
 }
 leaf ARP6PRIORITY {
  type enumeration {
   enum val-1;
   enum val-2;
   enum val-3;
   enum val-4;
  }
  mandatory false;
 }
 leaf ARP7PRIORITY {
  type enumeration {
   enum val-1;
   enum val-2;
   enum val-3;
   enum val-4;
  }
  mandatory false;
 }
 leaf ARP8PRIORITY {
  type enumeration {
   enum val-1;
   enum val-2;
   enum val-3;
   enum val-4;
  }
  mandatory false;
 }
 leaf ARP9PRIORITY {
  type enumeration {
   enum val-1;
   enum val-2;
   enum val-3;
   enum val-4;
  }
  mandatory false;
 }
 leaf ARPSCHSWITCH {
  type string;
  mandatory false;
 }
 }
 grouping USERQCIPRIORITY-attributes {
 leaf BRONZEDLSCHPRIORITYFACTOR {
  type uint16 {
   range "1..1000";
  }
  mandatory false;
 }
 leaf BRONZEULSCHPRIORITYFACTOR {
  type uint16 {
   range "1..1000";
  }
  mandatory false;
 }
 leaf GOLDDLSCHPRIORITYFACTOR {
  type uint16 {
   range "1..1000";
  }
  mandatory false;
 }
 leaf GOLDULSCHPRIORITYFACTOR {
  type uint16 {
   range "1..1000";
  }
  mandatory false;
 }
 leaf IRONDLSCHPRIORITYFACTOR {
  type uint16 {
   range "1..1000";
  }
  mandatory false;
 }
 leaf IRONULSCHPRIORITYFACTOR {
  type uint16 {
   range "1..1000";
  }
  mandatory false;
 }
 leaf QCI {
  type enumeration {
   enum val--1;
   enum val-6;
   enum val-7;
   enum val-8;
   enum val-9;
  }
  mandatory false;
 }
 leaf SILVERDLSCHPRIORITYFACTOR {
  type uint16 {
   range "1..1000";
  }
  mandatory false;
 }
 leaf SILVERULSCHPRIORITYFACTOR {
  type uint16 {
   range "1..1000";
  }
  mandatory false;
 }
 }
 grouping USERVPFMPARA-attributes {
 leaf LOCALCELLNAME {
  type string;
  mandatory false;
 }
 leaf DLACCESSDELAYBADTHD {
  type uint16 {
   range "0..10000";
  }
  mandatory false;
 }
 leaf DLACCESSDELAYGOODTHD {
  type uint16 {
   range "0..10000";
  }
  mandatory false;
 }
 leaf DLUSERTHRUPUTTHD0 {
  type uint32 {
   range "0..1048576";
  }
  mandatory false;
 }
 leaf DLUSERTHRUPUTTHD1 {
  type uint32 {
   range "0..1048576";
  }
  mandatory false;
 }
 leaf DLUSERTHRUPUTTHD2 {
  type uint32 {
   range "0..1048576";
  }
  mandatory false;
 }
 leaf DLUSERTHRUPUTTHD3 {
  type uint32 {
   range "0..1048576";
  }
  mandatory false;
 }
 leaf DLUSERTHRUPUTTHD4 {
  type uint32 {
   range "0..1048576";
  }
  mandatory false;
 }
 leaf LOCALCELLID {
  type union {
   type int16 {
    range "-1..255";
   }
  }
  mandatory false;
 }
 leaf ULACCESSDELAYBADTHD {
  type uint16 {
   range "0..10000";
  }
  mandatory false;
 }
 leaf ULACCESSDELAYGOODTHD {
  type uint16 {
   range "0..10000";
  }
  mandatory false;
 }
 }
 grouping UTRANBLKNCELL-attributes {
 leaf LOCALCELLNAME {
  type string;
  mandatory false;
 }
 leaf AUTOCFGFLAG {
  type boolean;
  mandatory false;
 }
 leaf CELLID {
  type union {
   type int32 {
    range "-1..65535";
   }
  }
  mandatory false;
 }
 leaf CTRLMODE {
  type boolean;
  mandatory false;
 }
 leaf LOCALCELLID {
  type union {
   type int16 {
    range "-1..255";
   }
  }
  mandatory false;
 }
 leaf MCC {
  type string {
   length "3";
  }
  mandatory false;
 }
 leaf MNC {
  type string {
   length "2..3";
  }
  mandatory false;
 }
 leaf RNCID {
  type union {
   type int32 {
    range "-1..65535";
   }
  }
  mandatory false;
 }
 }
 grouping UTRANEXTERNALCELL-attributes {
 leaf ANRFLAG {
  type boolean;
  mandatory false;
 }
 leaf CELLID {
  type union {
   type int32 {
    range "-1..65535";
   }
  }
  mandatory false;
 }
 leaf CELLNAME {
  type string {
   length "0..99";
  }
  mandatory false;
 }
 leaf CSPSHOIND {
  type boolean;
  mandatory false;
 }
 leaf CTRLMODE {
  type boolean;
  mandatory false;
 }
 leaf LAC {
  type union {
   type uint16 {
    range "1..65535";
   }
  }
  mandatory false;
 }
 leaf MCC {
  type string {
   length "3";
  }
  mandatory false;
 }
 leaf MNC {
  type string {
   length "2..3";
  }
  mandatory false;
 }
 leaf PSCRAMBCODE {
  type uint16 {
   range "0..511";
  }
  mandatory false;
 }
 leaf RAC {
  type uint8 {
   range "0..255";
  }
  mandatory false;
 }
 leaf RACCFGIND {
  type boolean;
  mandatory false;
 }
 leaf RNCID {
  type union {
   type int32 {
    range "-1..65535";
   }
  }
  mandatory false;
 }
 leaf ROAMINGAREAHOIND {
  type boolean;
  mandatory false;
 }
 leaf UTRANDLARFCN {
  type uint16 {
   range "0..16383";
  }
  mandatory false;
 }
 leaf UTRANFDDTDDTYPE {
  type boolean;
  mandatory false;
 }
 leaf UTRANULARFCN {
  type uint16 {
   range "0..16383";
  }
  mandatory false;
 }
 leaf UTRANULARFCNCFGIND {
  type boolean;
  mandatory false;
 }
 }
 grouping UTRANEXTERNALCELLPLMN-attributes {
 leaf CELLNAME {
  type string;
  mandatory false;
 }
 leaf CELLID {
  type union {
   type int32 {
    range "-1..65535";
   }
  }
  mandatory false;
 }
 leaf MCC {
  type string {
   length "3";
  }
  mandatory false;
 }
 leaf MNC {
  type string {
   length "2..3";
  }
  mandatory false;
 }
 leaf RNCID {
  type union {
   type int32 {
    range "-1..65535";
   }
  }
  mandatory false;
 }
 leaf SHAREMCC {
  type string {
   length "3";
  }
  mandatory false;
 }
 leaf SHAREMNC {
  type string {
   length "2..3";
  }
  mandatory false;
 }
 }
 grouping UTRANEXTERNALCELL_MULTIBAND-attributes {
 leaf CELLNAME {
  type string;
  mandatory false;
 }
 leaf CELLID {
  type union {
   type int32 {
    range "-1..65535";
   }
  }
  mandatory false;
 }
 leaf FREQBAND {
  type union {
   type int16 {
    range "-1..256";
   }
  }
  mandatory false;
 }
 leaf MCC {
  type string {
   length "3";
  }
  mandatory false;
 }
 leaf MNC {
  type string {
   length "2..3";
  }
  mandatory false;
 }
 leaf RNCID {
  type union {
   type int32 {
    range "-1..65535";
   }
  }
  mandatory false;
 }
 }
 grouping UTRANNCELL-attributes {
 leaf ANRFLAG {
  type boolean;
  mandatory false;
 }
 leaf BLINDHOPRIORITY {
  type uint8 {
   range "0..32";
  }
  mandatory false;
 }
 leaf CELLID {
  type union {
   type int32 {
    range "-1..65535";
   }
  }
  mandatory false;
 }
 leaf CELLMEASPRIORITY {
  type boolean;
  mandatory false;
 }
 leaf CTRLMODE {
  type boolean;
  mandatory false;
 }
 leaf LOCALCELLID {
  type union {
   type int16 {
    range "-1..255";
   }
  }
  mandatory false;
 }
 leaf LOCALCELLNAME {
  type string {
   length "0..99";
  }
  mandatory false;
 }
 leaf MCC {
  type string {
   length "3";
  }
  mandatory false;
 }
 leaf MNC {
  type string {
   length "2..3";
  }
  mandatory false;
 }
 leaf NCELLMEASPRIORITY {
  type uint8 {
   range "0..128";
  }
  mandatory false;
 }
 leaf NEIGHBOURCELLNAME {
  type string {
   length "0..99";
  }
  mandatory false;
 }
 leaf NOHOFLAG {
  type boolean;
  mandatory false;
 }
 leaf NORMVFLAG {
  type boolean;
  mandatory false;
 }
 leaf OVERLAPIND {
  type boolean;
  mandatory false;
 }
 leaf RNCID {
  type union {
   type int32 {
    range "-1..65535";
   }
  }
  mandatory false;
 }
 }
 grouping UTRANNETWORKCAPCFG-attributes {
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf NETWORKCAPCFG {
  type string;
  mandatory false;
 }
 leaf OLD_RNCID {
  type union {
   type int64 {
    range "-1..4294967295";
   }
  }
  mandatory false;
 }
 leaf RNCID {
  type union {
   type int64 {
    range "-1..4294967295";
   }
  }
  mandatory false;
 }
 }
 grouping UTRANNFREQ-attributes {
 leaf LOCALCELLNAME {
  type string;
  mandatory false;
 }
 leaf ANRIND {
  type boolean;
  mandatory false;
 }
 leaf CELLRESELPRIORITY {
  type uint8 {
   range "0..7";
  }
  mandatory false;
 }
 leaf CELLRESELPRIORITYCFGIND {
  type boolean;
  mandatory false;
 }
 leaf CONNFREQPRIORITY {
  type uint8 {
   range "0..8";
  }
  mandatory false;
 }
 leaf CONTINUCOVERAGEINDICATION {
  type boolean;
  mandatory false;
 }
 leaf CSPRIORITY {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
  }
  mandatory false;
 }
 leaf CSPSMIXEDPRIORITY {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
  }
  mandatory false;
 }
 leaf LOCALCELLID {
  type union {
   type int16 {
    range "-1..255";
   }
  }
  mandatory false;
 }
 leaf MASTERBANDFLAG {
  type boolean;
  mandatory false;
 }
 leaf MLBFREQPRIORITY {
  type uint8 {
   range "0..7";
  }
  mandatory false;
 }
 leaf MLBTARGETIND {
  type boolean;
  mandatory false;
 }
 leaf OFFSETFREQ {
  type int8 {
   range "-15..15";
  }
  mandatory false;
 }
 leaf PMAXUTRAN {
  type int8 {
   range "-50..33";
  }
  mandatory false;
 }
 leaf PSPRIORITY {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
  }
  mandatory false;
 }
 leaf QRXLEVMIN {
  type int8 {
   range "-60..-13";
  }
  mandatory false;
 }
 leaf QQUALMIN {
  type int8 {
   range "-24..0";
  }
  mandatory false;
 }
 leaf SRVCCPRIORITY {
  type enumeration {
   enum val-0;
   enum val-1;
   enum val-2;
   enum val-3;
   enum val-4;
   enum val-5;
   enum val-6;
   enum val-7;
   enum val-8;
   enum val-9;
   enum val-10;
   enum val-11;
   enum val-12;
   enum val-13;
   enum val-14;
   enum val-15;
   enum val-16;
  }
  mandatory false;
 }
 leaf THRESHXHIGH {
  type uint8 {
   range "0..31";
  }
  mandatory false;
 }
 leaf THRESHXHIGHQ {
  type uint8 {
   range "0..31";
  }
  mandatory false;
 }
 leaf THRESHXLOW {
  type uint8 {
   range "0..31";
  }
  mandatory false;
 }
 leaf THRESHXLOWQ {
  type uint8 {
   range "0..31";
  }
  mandatory false;
 }
 leaf ULSHAREDFREQIND {
  type boolean;
  mandatory false;
 }
 leaf UTRANDLARFCN {
  type union {
   type int16 {
    range "-1..16383";
   }
  }
  mandatory false;
 }
 leaf UTRANFDDTDDTYPE {
  type boolean;
  mandatory false;
 }
 leaf UTRANFREQHIGHSPEEDFLAG {
  type enumeration {
   enum val-0;
   enum val-1;
   enum val-2;
  }
  mandatory false;
 }
 leaf UTRANRANSHARINGIND {
  type boolean;
  mandatory false;
 }
 leaf UTRANULARFCN {
  type uint16 {
   range "0..16383";
  }
  mandatory false;
 }
 leaf UTRANULARFCNCFGIND {
  type boolean;
  mandatory false;
 }
 leaf UTRANVERSION {
  type enumeration {
   enum val-0;
   enum val-1;
   enum val-2;
   enum val-3;
  }
  mandatory false;
 }
 }
 grouping UTRANNFREQSCELLOP-attributes {
 leaf LOCALCELLNAME {
  type string;
  mandatory false;
 }
 leaf CELLRESELDEDIPRI {
  type uint8 {
   range "0..7";
  }
  mandatory false;
 }
 leaf CELLRESELDEDIPRICFGIND {
  type boolean;
  mandatory false;
 }
 leaf CNOPERATORID {
  type union {
   type int8 {
    range "-1..5";
   }
  }
  mandatory false;
 }
 leaf LOCALCELLID {
  type union {
   type int16 {
    range "-1..255";
   }
  }
  mandatory false;
 }
 leaf UTRANDLARFCN {
  type union {
   type int16 {
    range "-1..16383";
   }
  }
  mandatory false;
 }
 }
 grouping UTRANRANSHARE-attributes {
 leaf LOCALCELLNAME {
  type string;
  mandatory false;
 }
 leaf CELLRESELPRIORITY {
  type uint8 {
   range "0..7";
  }
  mandatory false;
 }
 leaf CELLRESELPRIORITYCFGIND {
  type boolean;
  mandatory false;
 }
 leaf LOCALCELLID {
  type union {
   type int16 {
    range "-1..255";
   }
  }
  mandatory false;
 }
 leaf MCC {
  type string {
   length "3";
  }
  mandatory false;
 }
 leaf MNC {
  type string {
   length "2..3";
  }
  mandatory false;
 }
 leaf UTRANDLARFCN {
  type union {
   type int16 {
    range "-1..16383";
   }
  }
  mandatory false;
 }
 }
 grouping VOICEAMRCONTROL-attributes {
 leaf LOCALCELLNAME {
  type string;
  mandatory false;
 }
 leaf HIGHAMRCODINGMODE {
  type enumeration {
   enum val-0;
   enum val-1;
   enum val-2;
   enum val-3;
   enum val-4;
   enum val-5;
  }
  mandatory false;
 }
 leaf OLD_LOCALCELLID {
  type union {
   type int16 {
    range "-1..255";
   }
  }
  mandatory false;
 }
 leaf LOCALCELLID {
  type union {
   type int16 {
    range "-1..255";
   }
  }
  mandatory false;
 }
 leaf LOWAMRCODINGMODE {
  type enumeration {
   enum val-0;
   enum val-1;
   enum val-2;
   enum val-3;
   enum val-4;
   enum val-5;
  }
  mandatory false;
 }
 leaf PLRTHDFORDECREASINGAMR {
  type uint8 {
   range "1..100";
  }
  mandatory false;
 }
 leaf PLRTHDFORINCREASINGAMR {
  type uint8 {
   range "1..100";
  }
  mandatory false;
 }
 leaf RSNTHDFORDECREASINGAMR {
  type uint8 {
   range "0..40";
  }
  mandatory false;
 }
 leaf RSNTHDFORINCREASINGAMR {
  type uint8 {
   range "1..40";
  }
  mandatory false;
 }
 leaf OLD_VOICEAMRCTRLPARAGROUPID {
  type union {
   type int8 {
    range "-1..5";
   }
  }
  mandatory false;
 }
 leaf VOICEAMRCTRLPARAGROUPID {
  type union {
   type int8 {
    range "-1..5";
   }
  }
  mandatory false;
 }
 }
 grouping VOLTEALGOCONFIG-attributes {
 leaf LOCALCELLNAME {
  type string;
  mandatory false;
 }
 leaf ASDLHOSIGSPSPKTSIZE {
  type uint8 {
   range "0..255";
  }
  mandatory false;
 }
 leaf ASUEULHOADDLSCHDATAVOLUME {
  type uint16 {
   range "0..65535";
  }
  mandatory false;
 }
 leaf ASVOLTEAFTERACTSCHNUM {
  type union {
   type uint8 {
    range "0..255";
   }
  }
  mandatory false;
 }
 leaf ASVOLTEBEFOREACTSCHNUM {
  type union {
   type uint8 {
    range "0..255";
   }
  }
  mandatory false;
 }
 leaf ASVOLTEULDATAVOLUME {
  type uint16 {
   range "0..65535";
  }
  mandatory false;
 }
 leaf ASVOLTEULPOWEROFFSET {
  type uint8 {
   range "0..21";
  }
  mandatory false;
 }
 leaf ASVOLTEULSPSPERIOD {
  type enumeration {
   enum val-0;
   enum val-1;
   enum val-2;
   enum val-3;
  }
  mandatory false;
 }
 leaf ASVOLTEULSPSRBNUM {
  type uint8 {
   range "0..20";
  }
  mandatory false;
 }
 leaf CCELOADSPSEFFECTIVEMODE {
  type enumeration {
   enum val-0;
   enum val-1;
   enum val-2;
  }
  mandatory false;
 }
 leaf CCEUSAGEHIGHOFFSET {
  type uint8 {
   range "0..100";
  }
  mandatory false;
 }
 leaf CCEUSAGEHIGHTHLD {
  type uint8 {
   range "0..100";
  }
  mandatory false;
 }
 leaf DELAYBUDGETRPTPROHIBITTMR {
  type enumeration {
   enum val-0;
   enum val-1;
   enum val-2;
   enum val-3;
   enum val-4;
   enum val-5;
   enum val-6;
   enum val-7;
   enum val-255;
  }
  mandatory false;
 }
 leaf DLCOSCHPOORQLTYUEIDENTTHLD {
  type uint8 {
   range "0..50";
  }
  mandatory false;
 }
 leaf EPSFBULACTIVESCHDATAVOL {
  type uint16 {
   range "45..5000";
  }
  mandatory false;
 }
 leaf EPSFBULACTIVESCHMINPERIOD {
  type uint8 {
   range "1..40";
  }
  mandatory false;
 }
 leaf FASTMOVDLJITTERELIMDURTHLD {
  type uint8 {
   range "0..10";
  }
  mandatory false;
 }
 leaf FASTMOVEULMCSSELECTIONTHLD {
  type union {
   type int16 {
    range "-150..32767";
   }
  }
  mandatory false;
 }
 leaf FASTMOVINGUEDLSPSDEATHLD {
  type uint8 {
   range "3..5";
  }
  mandatory false;
 }
 leaf FASTMOVINGUEULLWSPSDATAVOL {
  type union {
   type uint8 {
    range "10..255";
   }
  }
  mandatory false;
 }
 leaf LINKQLTYBASEDDLSPSACTVTHLD {
  type union {
   type int8 {
    range "-10..127";
   }
  }
  mandatory false;
 }
 leaf LINKQLTYBASEDULSPSACTVTHLD {
  type union {
   type int8 {
    range "-10..127";
   }
  }
  mandatory false;
 }
 leaf LOCALCELLID {
  type union {
   type int16 {
    range "-1..255";
   }
  }
  mandatory false;
 }
 leaf MTVOICEIDENTDLSIPHIGHTHLD {
  type uint16 {
   range "0..5000";
  }
  mandatory false;
 }
 leaf MTVOICEIDENTDLSIPLOWTHLD {
  type uint16 {
   range "0..5000";
  }
  mandatory false;
 }
 leaf MTVOICEIDENTULSIPHIGHTHLD {
  type uint16 {
   range "0..5000";
  }
  mandatory false;
 }
 leaf MTVOICEIDENTULSIPLOWTHLD {
  type uint16 {
   range "0..5000";
  }
  mandatory false;
 }
 leaf MOVOICEIDENTDLSIPHIGHTHLD {
  type uint16 {
   range "0..5000";
  }
  mandatory false;
 }
 leaf MOVOICEIDENTDLSIPLOWTHLD {
  type uint16 {
   range "0..5000";
  }
  mandatory false;
 }
 leaf MOVOICEIDENTULSIPHIGHTHLD {
  type uint16 {
   range "0..5000";
  }
  mandatory false;
 }
 leaf MOVOICEIDENTULSIPLOWTHLD {
  type uint16 {
   range "0..5000";
  }
  mandatory false;
 }
 leaf NCELLSTOPSCHTIMERATIO {
  type uint8 {
   range "0..100";
  }
  mandatory false;
 }
 leaf NEIGHBORCELLSTOPSCHTIME {
  type uint16 {
   range "0..1000";
  }
  mandatory false;
 }
 leaf NEWCALLINGALGOSWITCH {
  type string;
  mandatory false;
 }
 leaf POORSIGQLTYUEIDENTRSRPTHLD {
  type int16 {
   range "-140..-43";
  }
  mandatory false;
 }
 leaf POORSIGQLTYUEIDENTRSRQTHLD {
  type int8 {
   range "-40..-6";
  }
  mandatory false;
 }
 leaf POORVOLTEPDCCHSINROFFSET {
  type uint8 {
   range "0..30";
  }
  mandatory false;
 }
 leaf SPSENTERCCETHLD {
  type union {
   type uint8 {
    range "0..255";
   }
  }
  mandatory false;
 }
 leaf SPSEXITCCETHLD {
  type union {
   type uint8 {
    range "0..255";
   }
  }
  mandatory false;
 }
 leaf SPSPDSCHPWRBOOSTSINRTHLD {
  type union {
   type int8 {
    range "-5..127";
   }
  }
  mandatory false;
 }
 leaf ULCOMPNSCHBASETIMEUPTTHLD {
  type uint8 {
   range "0..255";
  }
  mandatory false;
 }
 leaf ULSPSMCSDECREASEIBLERTHLD {
  type uint8 {
   range "1..99";
  }
  mandatory false;
 }
 leaf VOICEPKTDUPOPTDLPRBTHLD {
  type union {
   type uint8 {
    range "0..255";
   }
  }
  mandatory false;
 }
 leaf VOICERBRSVRSRPTHLD {
  type union {
   type int16 {
    range "-140..0";
   }
  }
  mandatory false;
 }
 leaf VOICEUERELEASEDELAYTIMER {
  type uint16 {
   range "0..3600";
  }
  mandatory false;
 }
 leaf VOLTEANBRDLSCHRBNUMTHLD {
  type uint8 {
   range "0..100";
  }
  mandatory false;
 }
 leaf VOLTEANBRQPROHIBITTIMER {
  type enumeration {
   enum val-0;
   enum val-1;
   enum val-2;
   enum val-3;
   enum val-4;
   enum val-5;
   enum val-6;
   enum val-7;
   enum val-255;
  }
  mandatory false;
 }
 leaf VOLTECCEALCFLRATHIGHOFFSET {
  type uint8 {
   range "0..100";
  }
  mandatory false;
 }
 leaf VOLTECCEALLCFILRATHIGHTHLD {
  type uint8 {
   range "0..100";
  }
  mandatory false;
 }
 leaf VOLTECCEALOCHIGHFLRATETHLD {
  type uint8 {
   range "0..100";
  }
  mandatory false;
 }
 leaf VOLTEDLINITTRANSMCSDEC {
  type uint8 {
   range "0..28";
  }
  mandatory false;
 }
 leaf VOLTEDLLOWQUALSINRTHLD {
  type int8 {
   range "-5..3";
  }
  mandatory false;
 }
 leaf VOLTEGUARANTEEARPBITVALUE {
  type uint16 {
   range "0..32767";
  }
  mandatory false;
 }
 leaf VOLTEOPTEXTSWITCH {
  type string;
  mandatory false;
 }
 leaf VOLTEOPTSWITCH {
  type string;
  mandatory false;
 }
 leaf VOLTEPRDCINTERFA2RSRQTHLD {
  type union {
   type int8 {
    range "-40..0";
   }
  }
  mandatory false;
 }
 leaf VOLTERANDELAYBUDGET {
  type enumeration {
   enum val-0;
   enum val-1;
   enum val-255;
  }
  mandatory false;
 }
 leaf VOLTERANULDELAYBUDGET {
  type enumeration {
   enum val-0;
   enum val-1;
   enum val-255;
  }
  mandatory false;
 }
 leaf VOLTESIPPKTPREALLOCATEPRD {
  type uint8 {
   range "1..20";
  }
  mandatory false;
 }
 leaf VOLTESIPPKTPREALLOCATESIZE {
  type uint16 {
   range "1..4000";
  }
  mandatory false;
 }
 leaf VOLTESIPPKTSIZETHLD {
  type uint16 {
   range "0..4000";
  }
  mandatory false;
 }
 leaf VOLTEUENUMHIGHLOADOFFSET {
  type uint16 {
   range "0..1200";
  }
  mandatory false;
 }
 leaf VOLTEUENUMHIGHLOADTHLD {
  type uint16 {
   range "1..1200";
  }
  mandatory false;
 }
 leaf VOLTEUESCCADDDELAYTIMER {
  type uint8 {
   range "0..10";
  }
  mandatory false;
 }
 leaf VOLTEUESCGADDDELAYTIMER {
  type uint8 {
   range "0..10";
  }
  mandatory false;
 }
 leaf VOLTEUEULCAMGMTSTRATEGY {
  type boolean;
  mandatory false;
 }
 leaf VOLTEULCCEALLCFILRATHHTHLD {
  type uint8 {
   range "0..100";
  }
  mandatory false;
 }
 leaf VOLTEULPRECSCHCCEUSAGETHLD {
  type uint8 {
   range "0..100";
  }
  mandatory false;
 }
 leaf VOLTEULSCHWAITTIMETHLD {
  type uint8 {
   range "21..99";
  }
  mandatory false;
 }
 }
 grouping VQMALGO-attributes {
 leaf AMRLOWQUALRELPERIODNUM {
  type uint8 {
   range "0..100";
  }
  mandatory false;
 }
 leaf AMRNBRADIOLOWQUALRELTHD {
  type uint8 {
   range "0..100";
  }
  mandatory false;
 }
 leaf AMRNBRCVLOWQUALRELTHD {
  type uint8 {
   range "0..100";
  }
  mandatory false;
 }
 leaf AMRNBSILENTTHD {
  type uint8 {
   range "0..100";
  }
  mandatory false;
 }
 leaf AMRSILENTPERIODNUM {
  type uint8 {
   range "0..100";
  }
  mandatory false;
 }
 leaf AMRWBRADIOLOWQUALRELTHD {
  type uint8 {
   range "0..100";
  }
  mandatory false;
 }
 leaf AMRWBRCVLOWQUALRELTHD {
  type uint8 {
   range "0..100";
  }
  mandatory false;
 }
 leaf AMRWBSILENTTHD {
  type uint8 {
   range "0..100";
  }
  mandatory false;
 }
 leaf ULDELAYJITTER {
  type uint8 {
   range "1..255";
  }
  mandatory false;
 }
 leaf VQMALGOPERIOD {
  type enumeration {
   enum val-0;
   enum val-1;
   enum val-2;
  }
  mandatory false;
 }
 leaf VOICECALLSETUPDELAYTHLD {
  type uint16 {
   range "0..30000";
  }
  mandatory false;
 }
 leaf VQIBADTHD {
  type uint16 {
   range "0..500";
  }
  mandatory false;
 }
 leaf VQIEXCELLENTTHD {
  type uint16 {
   range "0..500";
  }
  mandatory false;
 }
 leaf VQIGOODTHD {
  type uint16 {
   range "0..500";
  }
  mandatory false;
 }
 leaf VQIPOORTHD {
  type uint16 {
   range "0..500";
  }
  mandatory false;
 }
 }
 grouping WTCPPROXYALGO-attributes {
 leaf LOCALCELLNAME {
  type string;
  mandatory false;
 }
 leaf LOCALCELLID {
  type union {
   type int16 {
    range "-1..255";
   }
  }
  mandatory false;
 }
 leaf MAXPROXYPKTNUM {
  type uint16 {
   range "200..2000";
  }
  mandatory false;
 }
 leaf MAXRTTSTATISTICSTHD {
  type uint16 {
   range "100..30000";
  }
  mandatory false;
 }
 leaf RTOPROTECTIONBUFFERTHLD {
  type uint8 {
   range "0..20";
  }
  mandatory false;
 }
 leaf TCPSTATISTICSSWITCH {
  type boolean;
  mandatory false;
 }
 leaf TCPACCELERATIONSWITCH {
  type boolean;
  mandatory false;
 }
 leaf TCPACTIVEORDERINGTIMER {
  type uint8 {
   range "0..10";
  }
  mandatory false;
 }
 leaf TCPASSCHWEIGHTFACTOR {
  type uint16 {
   range "0..1000";
  }
  mandatory false;
 }
 leaf WTCPDLRTTTIMER {
  type uint8 {
   range "0..20";
  }
  mandatory false;
 }
 leaf WTCPENHANCEMENTSWITCH {
  type string;
  mandatory false;
 }
 }
 grouping X2-attributes {
 leaf CNOPSHARINGGROUPID {
  type union {
   type uint8 {
    range "0..255";
   }
  }
  mandatory false;
 }
 leaf CNOPERATORID {
  type uint8 {
   range "0..5";
  }
  mandatory false;
 }
 leaf CPEPGROUPID {
  type uint16 {
   range "0..65535";
  }
  mandatory false;
 }
 leaf EPGROUPCFGFLAG {
  type enumeration {
   enum val-0;
   enum val-1;
   enum val-2;
  }
  mandatory false;
 }
 leaf TARGETENODEBRELEASE {
  type enumeration {
   enum val-0;
   enum val-1;
   enum val-2;
   enum val-3;
   enum val-4;
   enum val-5;
   enum val-6;
   enum val-7;
   enum val-8;
   enum val-9;
  }
  mandatory false;
 }
 leaf UPEPGROUPID {
  type uint16 {
   range "0..65535";
  }
  mandatory false;
 }
 leaf USERLABEL {
  type string {
   length "0..256";
  }
  mandatory false;
 }
 leaf OLD_X2ID {
  type union {
   type int8 {
    range "-1..11";
   }
  }
  mandatory false;
 }
 leaf X2ID {
  type union {
   type int8 {
    range "-1..11";
   }
  }
  mandatory false;
 }
 }
 grouping X2AUTOSETUPOPERATOR-attributes {
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 }
 grouping X2BLACKWHITELIST-attributes {
 leaf OLD_ENODEBID {
  type union {
   type int32 {
    range "-1..1048575";
   }
  }
  mandatory false;
 }
 leaf ENODEBID {
  type union {
   type int32 {
    range "-1..1048575";
   }
  }
  mandatory false;
 }
 leaf OLD_MCC {
  type string {
   length "3";
  }
  mandatory false;
 }
 leaf MCC {
  type string {
   length "3";
  }
  mandatory false;
 }
 leaf OLD_MNC {
  type string {
   length "2..3";
  }
  mandatory false;
 }
 leaf MNC {
  type string {
   length "2..3";
  }
  mandatory false;
 }
 leaf X2LISTTYPE {
  type boolean;
  mandatory false;
 }
 }
 grouping X2INTERFACE-attributes {
 leaf AUTOCFGFLAG {
  type boolean;
  mandatory false;
 }
 leaf CNOPSHARINGGROUPID {
  type union {
   type uint8 {
    range "0..255";
   }
  }
  mandatory false;
 }
 leaf CNOPERATORID {
  type uint8 {
   range "0..5";
  }
  mandatory false;
 }
 leaf CTRLMODE {
  type boolean;
  mandatory false;
 }
 leaf NEIGHBORINGBASESTATIONTYPE {
  type boolean;
  mandatory false;
 }
 leaf TARGETENODEBRELEASE {
  type enumeration {
   enum val-0;
   enum val-1;
   enum val-2;
   enum val-3;
   enum val-4;
   enum val-5;
   enum val-6;
   enum val-7;
   enum val-8;
   enum val-9;
  }
  mandatory false;
 }
 leaf X2CPBEARERID {
  type union {
   type uint32 {
    range "0..79999";
   }
  }
  mandatory false;
 }
 leaf OLD_X2INTERFACEID {
  type union {
   type int32 {
    range "-1..65535";
   }
  }
  mandatory false;
 }
 leaf X2INTERFACEID {
  type union {
   type int32 {
    range "-1..65535";
   }
  }
  mandatory false;
 }
 }
 grouping XW-attributes {
 leaf CPEPGROUPID {
  type uint16 {
   range "0..65535";
  }
  mandatory false;
 }
 leaf EPGROUPCFGFLAG {
  type enumeration {
   enum val-2;
  }
  mandatory false;
 }
 leaf UPEPGROUPID {
  type uint16 {
   range "0..65535";
  }
  mandatory false;
 }
 leaf USERLABEL {
  type string {
   length "0..256";
  }
  mandatory false;
 }
 leaf OLD_XWID {
  type union {
   type int8 {
    range "-1..11";
   }
  }
  mandatory false;
 }
 leaf XWID {
  type union {
   type int8 {
    range "-1..11";
   }
  }
  mandatory false;
 }
 }
}
