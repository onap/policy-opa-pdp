module ericsson-adb-radio {
  yang-version 1.1;
  namespace "urn:com:ericsson:ecim:ReqAdb";
  prefix adbrdo;
  import ericsson-antenna-radio {
    prefix antrdo;
  }
  import ericsson-equip-radio {
    prefix equiprdo;
  }
  import ericsson-managed-element {
    prefix emael;
  }
  description "Auto-generated from Ericsson CPI MOM XML 15554-lza7016014_33-v1uenfk.xml\nThis MO represents ADB hardware unit installed in the antenna system that can be controlled and supervised by the system.";
  revision "2026-03-29" {
    description "Ericsson G3G4, version: CXP2020502/2-R32C08";
  }

  augment "/emael:ManagedElement/equiprdo:Equipment/antrdo:AntennaUnitGroup/antrdo:AntennaNearUnit" {
    list AdbSubUnit {
      description "Additional definitions from MOM:min/max-elements:0/1;root;systemCreated; Antenna database subunit stores data about antenna, contained arrays, installation and site mapping. MO created by system if parent MO is AISG 3.0. MO deleted by the system if parent MO changes AISG version from 3.0 to 2.0. The RDN of this MO is AdbSubUnit=1.";
      key "adbSubUnitId";
      leaf adbSubUnitId {
        type leafref {
          path "../attributes/adbSubUnitId";
        }
      }
      container attributes {
      uses AdbSubUnit-attributes;
      }
    }
  }
  typedef AvailStatus {
    description "The availability status is used to qualify the operational state. It indicates why the operational state has changed its value.";
    type enumeration {
      enum IN_TEST {
        description "The resource is undergoing a test procedure. If the administrative state is locked or shutting down, normal users are prevented from using the resource.";
      }
      enum FAILED {
        description "The resource has an internal fault that prevents it from operating.";
      }
      enum POWER_OFF {
        description "The resource requires power to be applied and is not powered on.";
      }
      enum OFF_LINE {
        description "The resource requires a routine operation to be performed. This routine operation is to place the resource online and make it available for use. The operation may be manual or automatic, or both. The operational state is disabled.";
      }
      enum OFF_DUTY {
        description "The resource has been made inactive by an internal control process.";
      }
      enum DEPENDENCY {
        description "The resource cannot operate because some other resource on which it depends is unavailable.";
      }
      enum DEGRADED {
        description "The service available from the resource is degraded in some respect.";
      }
      enum NOT_INSTALLED {
        description "The resource represented by the managed object is not present, or is incomplete.";
      }
      enum LOG_FULL {
        description "Indicates a log full condition. The semantics are defined in CCITT Rec. X.735 | ISO/IEC 10164-6.";
      }
      enum DEPENDENCY_LOCKED {
        description "The administrative state of a resource that this resource depends on is locked. Alternatively, the availability status of the other resource is dependency locked.";
      }
      enum DEPENDENCY_FAILED {
        description "The availability status of a resource that this resource depends on is failed or dependency failed.";
      }
      enum DEPENDENCY_SHUTTINGDOWN {
        description "The administrative state of a resource that this resource depends on is shutting down. Alternatively, the availability status of the other resource is dependency shutting down.";
      }
      enum DEPENDENCY_RECOVERY {
        description "Resource that this resource depends on is undergoing a recovery procedure.";
      }
      enum DEPENDENCY_HOLDING {
        description "Resource cannot operate because some other resource on which it depends is currently unavailable. The situation is expected to be resolved. Actions to facilitate dependency resolution may be ongoing.";
      }
    }
  }
  typedef GetArraysDataStatus {
    description "GetLogicalAntennaArraysData status.";
    type enumeration {
      enum IDLE {
        description "GetLogicalAntennaArraysData function is idle.";
      }
      enum STARTED {
        description "GetLogicalAntennaArraysData function started.";
      }
      enum FINISHED {
        description "GetLogicalAntennaArraysData function finished.";
      }
      enum FAILED {
        description "GetLogicalAntennaArraysData function failed.";
      }
    }
  }
  typedef OperState {
    description "Operational states of a resource.";
    type enumeration {
      enum DISABLED {
        description "The resource is totally inoperable.";
      }
      enum ENABLED {
        description "The resource is partially or fully operable.";
      }
    }
  }
  grouping AdbAisgVersion-struct {
    description "AISG version.";
    leaf majorVersion {
      type string;
    }
    leaf minorVersion {
      type string;
    }
    leaf releaseVersion {
      type string;
    }
  }
  grouping AdbSubUnit-attributes {
    leaf adbSubUnitId {
      description "The value component of the RDN..";
      type string;
      mandatory true;
    }
    leaf-list availabilityStatus {
      description "The availability status. It contains details about operationalState..";
      type AvailStatus;
      min-elements 0;
    }
    leaf operationalState {
      description "The operational state..";
      type enumeration {
        enum DISABLED;
        enum ENABLED;
      }
      config false;
    }
    leaf subunitNumber {
      description "Subunit identifier carried on L7 messages in which subunits are pointed with help of application level identifiers..";
      type int32;
      config false;
    }
    leaf userLabel {
      description "Label for free use.; length 1..128.";
      type string {
        length "1..128";
      }
    }
    leaf getArraysDataStatus {
      description "Status for getLogicalAntennaArraysData action..";
      type enumeration {
        enum IDLE;
        enum STARTED;
        enum FINISHED;
        enum FAILED;
      }
      config false;
    }
    list configuredAisgAdbVersion {
      config false;
      description "Version of AISG protocol that device runs on and expects commands from..";
      uses AdbAisgVersion-struct;
    }
    list supportedAisgAdbVersion {
      config false;
      min-elements 0;
      max-elements 75;
      uses AdbAisgVersion-struct;
    }
  }
}
