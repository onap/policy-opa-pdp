module ericsson-cc-link-radio {
  yang-version 1.1;
  namespace "urn:com:ericsson:ecim:ReqCcLink";
  prefix cclinkrdo;
  import ericsson-yang-types {
    prefix eytypes;
  }
  import ericsson-equip-radio {
    prefix equiprdo;
  }
  import ericsson-managed-element {
    prefix emael;
  }
  description "Auto-generated from Ericsson CPI MOM XML 15554-lza7016014_33-v1uenfk.xml\nThis MO represents the analog cross connect cable which is used to connect two radio units via their cross connect ports to enable antenna sharing.";
  revision "2026-03-29" {
    description "Ericsson G3G4, version: CXP2020502/2-R32C08";
  }

  augment "/emael:ManagedElement/equiprdo:Equipment" {
    list CcLink {
      description "Additional definitions from MOM:min/max-elements:0/24;root; This MO represents the analog cross connect cable which is used to connect two radio units via their cross connect ports to enable antenna sharing.";
      key "ccLinkId";
      leaf ccLinkId {
        type leafref {
          path "../attributes/ccLinkId";
        }
      }
      container attributes {
      uses CcLink-attributes;
      }
    }
  }
  typedef AdmState {
    description "Administrative state of a resource.";
    type enumeration {
      enum LOCKED {
        description "The resource is administratively prohibited from performing services for its users.";
      }
      enum UNLOCKED {
        description "The resource is administratively permitted to perform services for its users. This is independent of its inherent operability.";
      }
      enum SHUTTINGDOWN {
        description "Use of the resource is administratively permitted to existing instances of use only. While the system remains in the shutting down state the manager may at any time cause the managed object to revert to the locked state.";
      }
    }
  }
  typedef AvailStatus {
    description "The availability status is used to qualify the operational state. It indicates why the operational state has changed its value.";
    type enumeration {
      enum IN_TEST {
        description "The resource is undergoing a test procedure. If the administrative state is locked or shutting down, normal users are prevented from using the resource.";
      }
      enum FAILED {
        description "The resource has an internal fault that prevents it from operating.";
      }
      enum POWER_OFF {
        description "The resource requires power to be applied and is not powered on.";
      }
      enum OFF_LINE {
        description "The resource requires a routine operation to be performed. This routine operation is to place the resource online and make it available for use. The operation may be manual or automatic, or both. The operational state is disabled.";
      }
      enum OFF_DUTY {
        description "The resource has been made inactive by an internal control process.";
      }
      enum DEPENDENCY {
        description "The resource cannot operate because some other resource on which it depends is unavailable.";
      }
      enum DEGRADED {
        description "The service available from the resource is degraded in some respect.";
      }
      enum NOT_INSTALLED {
        description "The resource represented by the managed object is not present, or is incomplete.";
      }
      enum LOG_FULL {
        description "Indicates a log full condition. The semantics are defined in CCITT Rec. X.735 | ISO/IEC 10164-6.";
      }
      enum DEPENDENCY_LOCKED {
        description "The administrative state of a resource that this resource depends on is locked. Alternatively, the availability status of the other resource is dependency locked.";
      }
      enum DEPENDENCY_FAILED {
        description "The availability status of a resource that this resource depends on is failed or dependency failed.";
      }
      enum DEPENDENCY_SHUTTINGDOWN {
        description "The administrative state of a resource that this resource depends on is shutting down. Alternatively, the availability status of the other resource is dependency shutting down.";
      }
      enum DEPENDENCY_RECOVERY {
        description "Resource that this resource depends on is undergoing a recovery procedure.";
      }
      enum DEPENDENCY_HOLDING {
        description "Resource cannot operate because some other resource on which it depends is currently unavailable. The situation is expected to be resolved. Actions to facilitate dependency resolution may be ongoing.";
      }
    }
  }
  typedef OperState {
    description "Operational states of a resource.";
    type enumeration {
      enum DISABLED {
        description "The resource is totally inoperable.";
      }
      enum ENABLED {
        description "The resource is partially or fully operable.";
      }
    }
  }
  grouping CcLink-attributes {
    leaf ccLinkId {
      description "RDN value component..";
      type string;
      mandatory true;
    }
    leaf-list availabilityStatus {
      description "The availability status. It contains details about operationalState. Specification: ITU-T rec. X.731.";
      type AvailStatus;
      min-elements 0;
    }
    leaf operationalState {
      description "The operational state. Specification: ITU-T rec. X.731.";
      type enumeration {
        enum DISABLED;
        enum ENABLED;
      }
      config false;
    }
    leaf-list reservedBy {
      description "Contains a list of CcBranch MO instances that reserve this MO instance..";
      type string;
      min-elements 0;
    }
    leaf administrativeState {
      description "The administrative state. If set to SHUTTINGDOWN, the state will immediately be brought to LOCKED. Specification: ITU-T rec. X.731.";
      type enumeration {
        enum LOCKED;
        enum UNLOCKED;
        enum SHUTTINGDOWN;
      }
    }
    leaf rxInRfPortRef {
      description "Refers to the RfPort MO representing the physical cross connect port (RfPort=RXA_IO or RXB_IO) on the radio unit receiving the analogue uplink antenna stream from the cross connect cable..";
      type string;
      mandatory true;
    }
    leaf rxOutRfPortRef {
      description "Refers to the RfPort MO representing the physical cross connect port (RfPort=RXA_IO, RXA_OUT or RXB_IO) on the radio unit receiving the analogue uplink antenna stream from the antenna and sends it to the cross connect cable..";
      type string;
      mandatory true;
    }
    leaf-list ulAttenuation {
      description "Uplink attenuation of the cross-connect cable. The sequence contains 40 entries and each entry represents one 5-MHz interval. The first entry represents the attenuation value of the lowest frequency interval in the operating band, and so on. The number of intervals depends on the operating band. For information on the different operating bands, refer to 3GPP TS 36.104. The value range for each entry is -500 to -2, -1, 0-500 (-50 to 50 dB). Unused entries are set to -1.; Default values sequence: -1,-1,-1,-1,-1,-1,-1,-1,-1,-1,-1,-1,-1,-1,-1,-1,-1,-1,-1,-1,-1,-1,-1,-1,-1,-1,-1,-1,-1,-1,-1,-1,-1,-1,-1,-1,-1,-1,-1,-1.";
      type int32 {
        range "-500..500";
      }
      ordered-by user;
      min-elements 40;
      max-elements 40;
    }
    leaf-list ulTrafficDelay {
      description "Uplink delay of the cross-connect cable. The sequence contains 40 entries and each entry represents one 5-MHz interval. The first entry represents the delay value of the lowest frequency interval in the operating band, and so on. The number of intervals used depends on the operating band. For information on the different operating bands, refer to 3GPP TS 36.104. The value range for each entry is 0-800000 (0-800000 ns). Unused entries are set to -1. NOTE: The range supported by individual radio units may be smaller and must be considered when configuring the antenna system.; Default values sequence: -1,-1,-1,-1,-1,-1,-1,-1,-1,-1,-1,-1,-1,-1,-1,-1,-1,-1,-1,-1,-1,-1,-1,-1,-1,-1,-1,-1,-1,-1,-1,-1,-1,-1,-1,-1,-1,-1,-1,-1.";
      type eytypes:int32_range_-1-800000;
      ordered-by user;
      min-elements 40;
      max-elements 40;
    }
    leaf userLabel {
      description "Label for free use.; length 1..128.";
      type string {
        length "1..128";
      }
    }
  }
}
