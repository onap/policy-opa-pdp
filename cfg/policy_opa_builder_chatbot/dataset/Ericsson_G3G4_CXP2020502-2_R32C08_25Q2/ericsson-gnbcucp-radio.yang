module ericsson-gnbcucp-radio {
  yang-version 1.1;
  namespace "urn:com:ericsson:ecim:GNBCUCP";
  prefix gnbcucp;
  import ietf-inet-types {
    prefix ietfinet;
  }
  import ericsson-yang-types {
    prefix eytypes;
  }
  import ericsson-managed-element {
    prefix emael;
  }
  description "Auto-generated from Ericsson CPI MOM XML 15554-lza7016014_33-v1uenfk.xml\nNRAT Fragment for GNBCUCPFunction.";
  revision "2026-03-29" {
    description "Ericsson G3G4, version: CXP2020502/2-R32C08";
  }

  augment "/emael:ManagedElement" {
    list GNBCUCPFunction {
      description "Additional definitions from MOM:min/max-elements:0/unbounded;root; Represents the logical node gNodeB-CU-CP.";
      key "gNBCUCPFunctionId";
      leaf gNBCUCPFunctionId {
        type leafref {
          path "../attributes/gNBCUCPFunctionId";
        }
      }
      container attributes {
      uses GNBCUCPFunction-attributes;
      }
    }
  }

  augment "/emael:ManagedElement/gnbcucp:GNBCUCPFunction/gnbcucp:AdmissionControl" {
    list AdmissionLimit {
      description "Additional definitions from MOM:min/max-elements:0/unbounded; Configured capacity used by Priority-Based Admission Control. Applies to UEs that use the cell as PCell or PSCell. Attributes are used on cell level. Instance AdmissionLimit=Default is created automatically when parent MO instance is created, unless created manually in same transaction. NRCellCU::admissionLimitRef is automatically set to AdmissionLimit=Default instance, unless manually set to refer to another MO instance. Precondition: Instance AdmissionLimit=Default can only be created in same transaction as parent MO instance and cannot be deleted unless parent MO instance is deleted. Other instances can be created and deleted at any time.";
      key "admissionLimitId";
      leaf admissionLimitId {
        type leafref {
          path "../attributes/admissionLimitId";
        }
      }
      container attributes {
      uses AdmissionLimit-attributes;
      }
    }
  }

  augment "/emael:ManagedElement/gnbcucp:GNBCUCPFunction/gnbcucp:AdmissionControl" {
    list AdmissionPriority {
      description "Additional definitions from MOM:min/max-elements:0/unbounded; UE priorities definition used by Priority-Based Admission Control. Instance AdmissionPriority=Default is created automatically when parent MO instance is created, unless created manually in same transaction. NRCellCU::admissionPriorityRef is automatically set to AdmissionPriority=Default instance, unless manually set to refer to another MO instance. Precondition: Instance AdmissionPriority=Default can only be created in same transaction as parent MO instance and cannot be deleted unless parent MO instance is deleted. Other instances can be created and deleted at any time.";
      key "admissionPriorityId";
      leaf admissionPriorityId {
        type leafref {
          path "../attributes/admissionPriorityId";
        }
      }
      container attributes {
      uses AdmissionPriority-attributes;
      }
    }
  }

  augment "/emael:ManagedElement/gnbcucp:GNBCUCPFunction/gnbcucp:AdmissionControl" {
    list Uac {
      description "Additional definitions from MOM:min/max-elements:0/1; Container class for NR Unified Access Control. Container class with underlying classes that contain attributes for configuration of unified access control function. Instance Uac=1 is created automatically when parent MO instance is created, unless created manually in same transaction. The RDN of this MO must be Uac=1. Precondition: Instance Uac=1 can only be created in same transaction as parent MO instance and cannot be deleted unless parent MO instance is deleted.";
      key "uacId";
      leaf uacId {
        type leafref {
          path "../attributes/uacId";
        }
      }
      container attributes {
      uses Uac-attributes;
      }
    }
  }

  augment "/emael:ManagedElement/gnbcucp:GNBCUCPFunction/gnbcucp:AdmissionControl/gnbcucp:AdmissionPriority" {
    list AdmissionPriorityUeCfg {
      description "Additional definitions from MOM:min/max-elements:0/32; Admission Priority, UE configuration group. Applies to UEs that use cell as PCell or PSCell. Attributes are used on cell level. Instance AdmissionPriorityUeCfg=Base is created automatically when parent MO instance is created, unless created manually in same transaction. Attributes prefUeGroupList, ueGroupList and ueConfGroupList must be empty in instance AdmissionPriorityUeCfg=Base but cannot all be empty in any other instance of AdmissionPriorityUeCfg under same parent AdmissionPriority instance. Precondition: Instance AdmissionPriorityUeCfg=Base can only be created in same transaction as parent MO instance and cannot be deleted unless parent MO instance is deleted. Other instances can be created and deleted at any time. Maximum 31 AdmissionPriorityUeCfg instances, with RDN different from Base, can be created under parent MO instance.";
      key "admissionPriorityUeCfgId";
      leaf admissionPriorityUeCfgId {
        type leafref {
          path "../attributes/admissionPriorityUeCfgId";
        }
      }
      container attributes {
      uses AdmissionPriorityUeCfg-attributes;
      }
    }
  }

  augment "/emael:ManagedElement/gnbcucp:GNBCUCPFunction/gnbcucp:AnrFunction" {
    list AnrFunctionEUtran {
      description "Additional definitions from MOM:min/max-elements:0/1; E-UTRAN ANR functions. The RDN of this MO must be AnrFunctionEUtran=1.";
      key "anrFunctionEUtranId";
      leaf anrFunctionEUtranId {
        type leafref {
          path "../attributes/anrFunctionEUtranId";
        }
      }
      container attributes {
      uses AnrFunctionEUtran-attributes;
      }
    }
  }

  augment "/emael:ManagedElement/gnbcucp:GNBCUCPFunction/gnbcucp:AnrFunction" {
    list AnrFunctionNR {
      description "Additional definitions from MOM:min/max-elements:0/1; NR Automated Neighbor Relation (ANR) functions. The RDN of this MO must be AnrFunctionNR=1.";
      key "anrFunctionNRId";
      leaf anrFunctionNRId {
        type leafref {
          path "../attributes/anrFunctionNRId";
        }
      }
      container attributes {
      uses AnrFunctionNR-attributes;
      }
    }
  }

  augment "/emael:ManagedElement/gnbcucp:GNBCUCPFunction/gnbcucp:AnrFunction/gnbcucp:AnrFunctionEUtran" {
    list AnrFunctionEUtranUeCfg {
      description "Additional definitions from MOM:min/max-elements:0/1; UE configuration of E-UTRAN ANR functions. Instance AnrFunctionEUtranUeCfg=Base is created automatically when parent MO instance is created, unless created manually in same transaction. Precondition: Instance AnrFunctionEUtranUeCfg=Base can only be created in same transaction as parent MO instance and cannot be deleted unless parent MO instance is deleted.";
      key "anrFunctionEUtranUeCfgId";
      leaf anrFunctionEUtranUeCfgId {
        type leafref {
          path "../attributes/anrFunctionEUtranUeCfgId";
        }
      }
      container attributes {
      uses AnrFunctionEUtranUeCfg-attributes;
      }
    }
  }

  augment "/emael:ManagedElement/gnbcucp:GNBCUCPFunction/gnbcucp:AnrFunction/gnbcucp:AnrFunctionNR" {
    list AnrFunctionNRUeCfg {
      description "Additional definitions from MOM:min/max-elements:0/1; UE configuration of NR ANR functions. Instance AnrFunctionNRUeCfg=Base is created automatically when parent MO instance is created, unless created manually in same transaction. Precondition: Instance AnrFunctionNRUeCfg=Base can only be created in same transaction as parent MO instance and cannot be deleted unless parent MO instance is deleted.";
      key "anrFunctionNRUeCfgId";
      leaf anrFunctionNRUeCfgId {
        type leafref {
          path "../attributes/anrFunctionNRUeCfgId";
        }
      }
      container attributes {
      uses AnrFunctionNRUeCfg-attributes;
      }
    }
  }

  augment "/emael:ManagedElement/gnbcucp:GNBCUCPFunction/gnbcucp:AnrFunction/gnbcucp:AnrFunctionNR" {
    list AnrPLMNTable {
      description "Additional definitions from MOM:min/max-elements:0/11; A table of ANR support for gNBId length for each PLMN. Each AnrPLMNTable instance contains a gNBId length that is supported for a list of PLMNs. ANR supports the gNBId length for a PLMN when target gNodeB belongs to a PLMN that is listed for that gNBId length. If a PLMN is not configured within AnrPLMNTable instances, ANR uses GNBCUCPFunction::gNBIdLength of its own node as gNBId length for node of newly found cell.";
      key "anrPLMNTableId";
      leaf anrPLMNTableId {
        type leafref {
          path "../attributes/anrPLMNTableId";
        }
      }
      container attributes {
      uses AnrPLMNTable-attributes;
      }
    }
  }

  augment "/emael:ManagedElement/gnbcucp:GNBCUCPFunction/gnbcucp:CUCP5qiTable" {
    list CUCP5qi {
      description "Additional definitions from MOM:min/max-elements:1/29; QoS configuration for each 5QI profile. Each profile can be present once in each table.";
      key "cUCP5qiId";
      leaf cUCP5qiId {
        type leafref {
          path "../attributes/cUCP5qiId";
        }
      }
      container attributes {
      uses CUCP5qi-attributes;
      }
    }
  }

  augment "/emael:ManagedElement/gnbcucp:GNBCUCPFunction/gnbcucp:CarrierAggregation/gnbcucp:CaCellMeasProfile" {
    list CaCellMeasProfileUeCfg {
      description "Additional definitions from MOM:min/max-elements:0/32; Carrier Aggregation cell measurement configuration profile, UE configuration group. Applies to UEs that use cell as SpCell. Attributes are used on cell level. Instance CaCellMeasProfileUeCfg=Base is created automatically when parent MO instance is created, unless created manually in same transaction. Attributes prefUeGroupList, ueGroupList and ueConfGroupList must be empty in instance CaCellMeasProfileUeCfg=Base but cannot all be empty in other instances of CaCellMeasProfileUeCfg under same parent CaCellMeasProfile. Precondition: Instance CaCellMeasProfileUeCfg=Base can only be created in same transaction as parent MO instance and cannot be deleted unless parent MO instance is deleted. Other instances can be created and deleted at any time. Maximum 31 CaCellMeasProfileUeCfg instances, with RDN different from Base, can be created under parent MO instance.";
      key "caCellMeasProfileUeCfgId";
      leaf caCellMeasProfileUeCfgId {
        type leafref {
          path "../attributes/caCellMeasProfileUeCfgId";
        }
      }
      container attributes {
      uses CaCellMeasProfileUeCfg-attributes;
      }
    }
  }

  augment "/emael:ManagedElement/gnbcucp:GNBCUCPFunction/gnbcucp:CarrierAggregation/gnbcucp:CaCellProfile" {
    list CaCellProfileUeCfg {
      description "Additional definitions from MOM:min/max-elements:0/32; Carrier Aggregation cell configuration profile, UE configuration group. Applies to UEs that use cell as SpCell. Attributes are used on cell level. Instance CaCellProfileUeCfg=Base is created automatically when parent MO instance is created, unless created manually in same transaction. Attributes prefUeGroupList, ueGroupList and ueConfGroupList must be empty in instance CaCellProfileUeCfg=Base but cannot all be empty in any other instance of CaCellProfileUeCfg under same parent CaCellProfile instance. Precondition: Instance CaCellProfileUeCfg=Base can only be created in same transaction as parent MO instance and cannot be deleted unless parent MO instance is deleted. Other instances can be created and deleted at any time. To be able to create an instance, the total number of instances, including all auto created instances, must be less than the total allowed number of instances under a GNBCUCPFunction instance that is 32.";
      key "caCellProfileUeCfgId";
      leaf caCellProfileUeCfgId {
        type leafref {
          path "../attributes/caCellProfileUeCfgId";
        }
      }
      container attributes {
      uses CaCellProfileUeCfg-attributes;
      }
    }
  }

  augment "/emael:ManagedElement/gnbcucp:GNBCUCPFunction/gnbcucp:CarrierAggregation/gnbcucp:CaFreqRelMeasProfile" {
    list CaFreqRelMeasProfileUeCfg {
      description "Additional definitions from MOM:min/max-elements:0/32; Carrier Aggregation frequency measurement configuration profile, UE configuration group. Applies to UEs that use cell as SpCell. Attributes are used on NR frequency relation level. Instance CaFreqRelMeasProfileUeCfg=Base is created automatically when parent MO instance is created, unless created manually in same transaction. Attributes prefUeGroupList, ueGroupList and ueConfGroupList must be empty in instance CaFreqRelMeasProfileUeCfg=Base but cannot all be empty in other instances of CaFreqRelMeasProfileUeCfg under same parent CaFreqRelMeasProfile. Precondition: Instance CaFreqRelMeasProfileUeCfg=Base can only be created in same transaction as parent MO instance and cannot be deleted unless parent MO instance is deleted. Other instances can be created and deleted at any time. Maximum 31 CaFreqRelMeasProfileUeCfg instances, with RDN different from Base, can be created under parent MO instance.";
      key "caFreqRelMeasProfileUeCfgId";
      leaf caFreqRelMeasProfileUeCfgId {
        type leafref {
          path "../attributes/caFreqRelMeasProfileUeCfgId";
        }
      }
      container attributes {
      uses CaFreqRelMeasProfileUeCfg-attributes;
      }
    }
  }

  augment "/emael:ManagedElement/gnbcucp:GNBCUCPFunction/gnbcucp:UeCC/gnbcucp:CapabilityHandling" {
    list CapabilityHandlingUeCfg {
      description "Additional definitions from MOM:min/max-elements:0/8; Configuration of CapabilityHandling for UE groups. Instance CapabilityHandlingUeCfg=Base is created automatically when parent MO instance is created, unless created manually in same transaction. Attributes prefUeGroupList, ueGroupList and ueConfGroupList must be empty in instance CapabilityHandlingUeCfg=Base but cannot all be empty in any other instance of CapabilityHandlingUeCfg under same parent CapabilityHandling instance. Precondition: Instance CapabilityHandlingUeCfg=Base can only be created in same transaction as parent MO instance and cannot be deleted unless parent MO instance is deleted. Other instances can be created and deleted at any time. Maximum 7 CapabilityHandlingUeCfg instances, with RDN different from Base, can be created under parent MO instance.";
      key "capabilityHandlingUeCfgId";
      leaf capabilityHandlingUeCfgId {
        type leafref {
          path "../attributes/capabilityHandlingUeCfgId";
        }
      }
      container attributes {
      uses CapabilityHandlingUeCfg-attributes;
      }
    }
  }

  augment "/emael:ManagedElement/gnbcucp:GNBCUCPFunction/gnbcucp:CarrierAggregation" {
    list CaCellMeasProfile {
      description "Additional definitions from MOM:min/max-elements:0/unbounded; Carrier Aggregation cell measurement configuration profile. Applies to UEs that use cell as SpCell. Attributes are used on cell level. Instance CaCellMeasProfile=Default is created automatically when parent MO instance is created, unless created manually in same transaction. NRCellCU::caCellMeasProfileRef is automatically set to CaCellMeasProfile=Default instance, unless manually set to refer to another MO instance. Precondition: Instance CaCellMeasProfile=Default can only be created in same transaction as parent MO instance and cannot be deleted unless parent MO instance is deleted. Other instances can be created and deleted at any time.";
      key "caCellMeasProfileId";
      leaf caCellMeasProfileId {
        type leafref {
          path "../attributes/caCellMeasProfileId";
        }
      }
      container attributes {
      uses CaCellMeasProfile-attributes;
      }
    }
  }

  augment "/emael:ManagedElement/gnbcucp:GNBCUCPFunction/gnbcucp:CarrierAggregation" {
    list CaCellProfile {
      description "Additional definitions from MOM:min/max-elements:0/32; Carrier Aggregation cell configuration profile. Applies to UEs that use cell as SpCell. Attributes are used on cell level. Instance CaCellProfile=Default is created automatically when parent MO instance is created, unless created manually in same transaction. NRCellCU::caCellProfileRef is automatically set to CaCellProfile=Default instance, unless manually set to refer to another MO instance. Precondition: Instance CaCellProfile=Default can only be created in same transaction as parent MO instance and cannot be deleted unless parent MO instance is deleted. Other instances can be created and deleted at any time. Maximum 31 CaCellProfile instances, with RDN different from Default, can be created. When creating an instance there must be possible to create a child CaCellProfileUeCfg=Base among total allowed instances of that MO class that is 32.";
      key "caCellProfileId";
      leaf caCellProfileId {
        type leafref {
          path "../attributes/caCellProfileId";
        }
      }
      container attributes {
      uses CaCellProfile-attributes;
      }
    }
  }

  augment "/emael:ManagedElement/gnbcucp:GNBCUCPFunction/gnbcucp:CarrierAggregation" {
    list CaFreqRelMeasProfile {
      description "Additional definitions from MOM:min/max-elements:0/unbounded; Carrier Aggregation frequency measurement configuration profile. Applies to UEs that use cell as SpCell. Attributes are used on NR frequency relation level. Instance CaFreqRelMeasProfile=Default is created automatically when parent MO instance is created, unless created manually in same transaction. NRFreqRelation::caFreqRelMeasProfileRef is automatically set to CaFreqRelMeasProfile=Default instance, unless manually set to refer to another MO instance. Precondition: Instance CaFreqRelMeasProfile=Default can only be created in same transaction as parent MO instance and cannot be deleted unless parent MO instance is deleted. Other instances can be created and deleted at any time.";
      key "caFreqRelMeasProfileId";
      leaf caFreqRelMeasProfileId {
        type leafref {
          path "../attributes/caFreqRelMeasProfileId";
        }
      }
      container attributes {
      uses CaFreqRelMeasProfile-attributes;
      }
    }
  }

  augment "/emael:ManagedElement/gnbcucp:GNBCUCPFunction/gnbcucp:EUtraNetwork" {
    list EUtranFrequency {
      description "Additional definitions from MOM:min/max-elements:0/32; Container for information of a specific E-UTRAN frequency. The RDNs of these MOs are EUtranFrequency=<number>, for example EUtranFrequency=2586. RDN must match arfcnValueEUtranDl.";
      key "eUtranFrequencyId";
      leaf eUtranFrequencyId {
        type leafref {
          path "../attributes/eUtranFrequencyId";
        }
      }
      container attributes {
      uses EUtranFrequency-attributes;
      }
    }
  }

  augment "/emael:ManagedElement/gnbcucp:GNBCUCPFunction/gnbcucp:EUtraNetwork" {
    list ExternalENodeBFunction {
      description "Additional definitions from MOM:min/max-elements:0/256; Representation of an eNodeB. Created automatically when X2 interface is set up, unless it already exists. Deleted automatically. Can also be created and deleted manually. When created automatically, the RDN of this MO is ExternalENodeBFunction=auto<mcc>_<mnc>_<mncLength>_<eNodeBId>. Length of RDN value is up to 21 characters for automatically created instance. Instance can be created without a preceding user-initiated transaction.";
      key "externalENodeBFunctionId";
      leaf externalENodeBFunctionId {
        type leafref {
          path "../attributes/externalENodeBFunctionId";
        }
      }
      container attributes {
      uses ExternalENodeBFunction-attributes;
      }
    }
  }

  augment "/emael:ManagedElement/gnbcucp:GNBCUCPFunction/gnbcucp:EndpointResource" {
    list LocalDnsEndpoint {
      description "Additional definitions from MOM:min/max-elements:0/1; Local transport network endpoint for DNS interface. If no instance exists, DNS interface configured in the OAM network is used.";
      key "localDnsEndpointId";
      leaf localDnsEndpointId {
        type leafref {
          path "../attributes/localDnsEndpointId";
        }
      }
      container attributes {
      uses LocalDnsEndpoint-attributes;
      }
    }
  }

  augment "/emael:ManagedElement/gnbcucp:GNBCUCPFunction/gnbcucp:EndpointResource" {
    list LocalIpEndpoint {
      description "Additional definitions from MOM:min/max-elements:0/unbounded; Local transport network endpoint for user plane interface. E1 control plane uses TCP, hence this interface is also configured by this class.";
      key "localIpEndpointId";
      leaf localIpEndpointId {
        type leafref {
          path "../attributes/localIpEndpointId";
        }
      }
      container attributes {
      uses LocalIpEndpoint-attributes;
      }
    }
  }

  augment "/emael:ManagedElement/gnbcucp:GNBCUCPFunction/gnbcucp:EndpointResource" {
    list LocalSctpEndpoint {
      description "Additional definitions from MOM:min/max-elements:0/unbounded; Local transport network endpoint for control plane interface. E1 control plane uses TCP, hence this interface is configured in MO class LocalIpEndpoint.";
      key "localSctpEndpointId";
      leaf localSctpEndpointId {
        type leafref {
          path "../attributes/localSctpEndpointId";
        }
      }
      container attributes {
      uses LocalSctpEndpoint-attributes;
      }
    }
  }

  augment "/emael:ManagedElement/gnbcucp:GNBCUCPFunction/gnbcucp:EnergyPerformance" {
    list EpBoCS {
      description "Additional definitions from MOM:min/max-elements:0/1; Configuration and supervision support for Booster Carrier Sleep function. Instance EpBoCS=1 is created automatically when parent MO instance is created, unless created manually in same transaction. The RDN of this MO must be EpBoCS=1. Precondition: Instance EpBoCS=1 can only be created in same transaction as parent MO instance and cannot be deleted unless parent MO instance is deleted.";
      key "epBoCSId";
      leaf epBoCSId {
        type leafref {
          path "../attributes/epBoCSId";
        }
      }
      container attributes {
      uses EpBoCS-attributes;
      }
    }
  }

  augment "/emael:ManagedElement/gnbcucp:GNBCUCPFunction/gnbcucp:EnergyPerformance/gnbcucp:EpBoCS" {
    list EpBoosterAdvCfg {
      description "Additional definitions from MOM:min/max-elements:0/50; Booster Carrier Sleep advanced profile settings. Instance EpBoosterAdvCfg=Default is created automatically when parent MO instance is created, unless created manually in same transaction. EpBoosterCellProfile::epBoosterAdvCfgRef is automatically set to EpBoosterAdvCfg=Default instance, unless manually set to refer to another MO instance. Precondition: Instance EpBoosterAdvCfg=Default can only be created in same transaction as parent MO instance and cannot be deleted unless parent MO instance is deleted. Maximum 49 EpBoosterAdvCfg instances, with RDN different from Default, can be created under parent MO instance. Other instances can be created and deleted at any time.";
      key "epBoosterAdvCfgId";
      leaf epBoosterAdvCfgId {
        type leafref {
          path "../attributes/epBoosterAdvCfgId";
        }
      }
      container attributes {
      uses EpBoosterAdvCfg-attributes;
      }
    }
  }

  augment "/emael:ManagedElement/gnbcucp:GNBCUCPFunction/gnbcucp:EnergyPerformance/gnbcucp:EpBoCS" {
    list EpBoosterCellProfile {
      description "Additional definitions from MOM:min/max-elements:0/50; Booster Carrier Sleep profile. Instance EpBoosterCellProfile=Default is created automatically when parent MO instance is created, unless created manually in same transaction. Precondition: Instance EpBoosterCellProfile=Default can only be created in same transaction as parent MO instance and cannot be deleted unless parent MO instance is deleted. Maximum 49 EpBoosterCellProfile instances, with RDN different from Default, can be created under parent MO instance. Other instances can be created and deleted at any time.";
      key "epBoosterCellProfileId";
      leaf epBoosterCellProfileId {
        type leafref {
          path "../attributes/epBoosterCellProfileId";
        }
      }
      container attributes {
      uses EpBoosterCellProfile-attributes;
      }
    }
  }

  augment "/emael:ManagedElement/gnbcucp:GNBCUCPFunction/gnbcucp:EUtraNetwork/gnbcucp:ExternalENodeBFunction" {
    list ExternalEUtranCell {
      description "Additional definitions from MOM:min/max-elements:0/48; External E-UTRAN cell. Contains parameters that are specific for this cell. Can be created by action promoteLwEUtranCellRelation in NRCellCU instance. RDN is the same as for automatically created instance. When created automatically, the RDN of this MO is ExternalEUtranCell=auto<ECI>, where ECI = <eNBid>*256 + <cellLocalId>. Length of RDN value is up to 13 characters for automatically created instance. Instance can be created without a preceding user-initiated transaction.";
      key "externalEUtranCellId";
      leaf externalEUtranCellId {
        type leafref {
          path "../attributes/externalEUtranCellId";
        }
      }
      container attributes {
      uses ExternalEUtranCell-attributes;
      }
    }
  }

  augment "/emael:ManagedElement/gnbcucp:GNBCUCPFunction/gnbcucp:EUtraNetwork/gnbcucp:ExternalENodeBFunction" {
    list TermPointToENodeB {
      description "Additional definitions from MOM:min/max-elements:0/1; Local eNodeB termination point of X2 link between gNodeB and eNodeB. Created automatically when X2 interface is set up, unless it already exists. Deleted automatically. Can also be created and deleted manually. When created automatically, the RDN of this MO is TermPointToENodeB=auto1. Length of RDN value is 5 characters for automatically created instance. Instance can be created without a preceding user-initiated transaction.";
      key "termPointToENodeBId";
      leaf termPointToENodeBId {
        type leafref {
          path "../attributes/termPointToENodeBId";
        }
      }
      container attributes {
      uses TermPointToENodeB-attributes;
      }
    }
  }

  augment "/emael:ManagedElement/gnbcucp:GNBCUCPFunction/gnbcucp:NRNetwork/gnbcucp:ExternalGNBCUCPFunction" {
    list ExternalNRCellCU {
      description "Additional definitions from MOM:min/max-elements:0/256; Representation of an external NRCellCU. Created automatically when Xn message is received, unless it already exists. Deleted automatically. Can also be created and deleted manually. Can be created by action promoteLwNRCellRelation in NRCellCU instance. RDN is the same as for automatically created instance. When created automatically, the RDN of this MO is ExternalNRCellCU=auto<NCI>, where NCI = <gNBId>*2^(36-<gNBIdLength>) + <cellLocalId>. Length of RDN value is up to 15 characters for automatically created instance. Instance can be created without a preceding user-initiated transaction.";
      key "externalNRCellCUId";
      leaf externalNRCellCUId {
        type leafref {
          path "../attributes/externalNRCellCUId";
        }
      }
      container attributes {
      uses ExternalNRCellCU-attributes;
      }
    }
  }

  augment "/emael:ManagedElement/gnbcucp:GNBCUCPFunction/gnbcucp:NRNetwork/gnbcucp:ExternalGNBCUCPFunction" {
    list TermPointToGNodeB {
      description "Additional definitions from MOM:min/max-elements:0/1; Local gNodeB termination point of Xn link between gNodeB and neighbor gNodeB. Created automatically when Xn interface is set up, unless it already exists. Deleted automatically. Can also be created and deleted manually. When created automatically, the RDN of this MO is TermPointToGNodeB=auto1. Length of RDN value is 5 characters for automatically created instance. Instance can be created without a preceding user-initiated transaction. Precondition: Manual creation of TermPointToGNodeB instances, to gNodeBs listed in GNBCUCPFunction::blockedGNodeBList, is blocked.";
      key "termPointToGNodeBId";
      leaf termPointToGNodeBId {
        type leafref {
          path "../attributes/termPointToGNodeBId";
        }
      }
      container attributes {
      uses TermPointToGNodeB-attributes;
      }
    }
  }

  augment "/emael:ManagedElement/gnbcucp:GNBCUCPFunction/gnbcucp:NRNetwork/gnbcucp:ExternalGNBCUCPFunction/gnbcucp:ExternalNRCellCU" {
    list ExternalBroadcastPLMNInfo {
      description "Additional definitions from MOM:min/max-elements:0/12; PLMN-related information that is served by external NR cell. Created automatically when Xn message is received, unless it already exists. Deleted automatically. Can also be created and deleted manually. Can be created by action promoteLwNRCellRelation in NRCellCU instance. RDN is the same as for automatically created instance. When created automatically, the RDNs of these MOs are ExternalBroadcastPLMNInfo=1 to ExternalBroadcastPLMNInfo=12. RDN value is assigned based on order received over Xn. Length of RDN value is up to 2 characters for automatically created instance. Instance can be created without a preceding user-initiated transaction. Precondition: MO can be created and deleted manually, only if TermPointToGNodeB has administrativeState LOCKED.";
      key "externalBroadcastPLMNInfoId";
      leaf externalBroadcastPLMNInfoId {
        type leafref {
          path "../attributes/externalBroadcastPLMNInfoId";
        }
      }
      container attributes {
      uses ExternalBroadcastPLMNInfo-attributes;
      }
    }
  }

  augment "/emael:ManagedElement/gnbcucp:GNBCUCPFunction" {
    list AdmissionControl {
      description "Additional definitions from MOM:min/max-elements:0/1; Container class for admission limits, admission priority and unified access control. Instance AdmissionControl=1 is created automatically when parent MO instance is created, unless created manually in same transaction. The RDN of this MO must be AdmissionControl=1. Precondition: Instance AdmissionControl=1 can only be created in same transaction as parent MO instance and cannot be deleted unless parent MO instance is deleted.";
      key "admissionControlId";
      leaf admissionControlId {
        type leafref {
          path "../attributes/admissionControlId";
        }
      }
      container attributes {
      uses AdmissionControl-attributes;
      }
    }
  }

  augment "/emael:ManagedElement/gnbcucp:GNBCUCPFunction" {
    list AnrFunction {
      description "Additional definitions from MOM:min/max-elements:0/1; Parameters and constraints for ANR functions. The RDN of this MO must be AnrFunction=1.";
      key "anrFunctionId";
      leaf anrFunctionId {
        type leafref {
          path "../attributes/anrFunctionId";
        }
      }
      container attributes {
      uses AnrFunction-attributes;
      }
    }
  }

  augment "/emael:ManagedElement/gnbcucp:GNBCUCPFunction" {
    list BlockedGNodeB {
      description "Additional definitions from MOM:min/max-elements:0/512; Configuration of blocked neighbor gNodeBs. When gNodeB is blocked, Xn setup to it is blocked.";
      key "blockedGNodeBId";
      leaf blockedGNodeBId {
        type leafref {
          path "../attributes/blockedGNodeBId";
        }
      }
      container attributes {
      uses BlockedGNodeB-attributes;
      }
    }
  }

  augment "/emael:ManagedElement/gnbcucp:GNBCUCPFunction" {
    list CardinalityLimits {
      description "Additional definitions from MOM:min/max-elements:0/1; Cardinality limits for current deployment. Listed cardinality limits is maximum number of MO instances that can be created. Instance CardinalityLimits=1 is created automatically when parent MO instance is created, unless created manually in same transaction. The RDN of this MO must be CardinalityLimits=1. Precondition: Instance CardinalityLimits=1 can only be created in same transaction as parent MO instance and cannot be deleted unless parent MO instance is deleted.";
      key "cardinalityLimitsId";
      leaf cardinalityLimitsId {
        type leafref {
          path "../attributes/cardinalityLimitsId";
        }
      }
      container attributes {
      uses CardinalityLimits-attributes;
      }
    }
  }

  augment "/emael:ManagedElement/gnbcucp:GNBCUCPFunction" {
    list CarrierAggregation {
      description "Additional definitions from MOM:min/max-elements:0/1; Container class for Carrier Aggregation control attributes and profile classes. Instance CarrierAggregation=1 is created automatically when parent MO instance is created, unless created manually in same transaction. The RDN of this MO must be CarrierAggregation=1. Precondition: Instance CarrierAggregation=1 can only be created in same transaction as parent MO instance and cannot be deleted unless parent MO instance is deleted.";
      key "carrierAggregationId";
      leaf carrierAggregationId {
        type leafref {
          path "../attributes/carrierAggregationId";
        }
      }
      container attributes {
      uses CarrierAggregation-attributes;
      }
    }
  }

  augment "/emael:ManagedElement/gnbcucp:GNBCUCPFunction" {
    list CellGroupCategoryDefinition {
      description "Additional definitions from MOM:min/max-elements:0/8; Cell group category definition.";
      key "cellGroupCategoryDefinitionId";
      leaf cellGroupCategoryDefinitionId {
        type leafref {
          path "../attributes/cellGroupCategoryDefinitionId";
        }
      }
      container attributes {
      uses CellGroupCategoryDefinition-attributes;
      }
    }
  }

  augment "/emael:ManagedElement/gnbcucp:GNBCUCPFunction" {
    list CUCP5qiTable {
      description "Additional definitions from MOM:min/max-elements:0/36; Mapping from 5G QoS Identifier to parameters that have impact on QoS. At least one CUCP5qi instance must be created in same transaction when a CUCP5qiTable is created.";
      key "cUCP5qiTableId";
      leaf cUCP5qiTableId {
        type leafref {
          path "../attributes/cUCP5qiTableId";
        }
      }
      container attributes {
      uses CUCP5qiTable-attributes;
      }
    }
  }

  augment "/emael:ManagedElement/gnbcucp:GNBCUCPFunction" {
    list EmCall {
      description "Additional definitions from MOM:min/max-elements:0/12; Emergency call configuration for NRCellCU instances.";
      key "emCallId";
      leaf emCallId {
        type leafref {
          path "../attributes/emCallId";
        }
      }
      container attributes {
      uses EmCall-attributes;
      }
    }
  }

  augment "/emael:ManagedElement/gnbcucp:GNBCUCPFunction" {
    list EndpointResource {
      description "Additional definitions from MOM:min/max-elements:0/unbounded; Transport network endpoints for RAN interfaces. Configuration is valid for an entity that refers to an instance of this MO.";
      key "endpointResourceId";
      leaf endpointResourceId {
        type leafref {
          path "../attributes/endpointResourceId";
        }
      }
      container attributes {
      uses EndpointResource-attributes;
      }
    }
  }

  augment "/emael:ManagedElement/gnbcucp:GNBCUCPFunction" {
    list EnergyPerformance {
      description "Additional definitions from MOM:min/max-elements:0/1; Configuration and supervision support for functions related to energy performance. Instance EnergyPerformance=1 is created automatically when parent MO instance is created, unless created manually in same transaction. The RDN of this MO must be EnergyPerformance=1. Precondition: Instance EnergyPerformance=1 can only be created in same transaction as parent MO instance and cannot be deleted unless parent MO instance is deleted.";
      key "energyPerformanceId";
      leaf energyPerformanceId {
        type leafref {
          path "../attributes/energyPerformanceId";
        }
      }
      container attributes {
      uses EnergyPerformance-attributes;
      }
    }
  }

  augment "/emael:ManagedElement/gnbcucp:GNBCUCPFunction" {
    list EUtraNetwork {
      description "Additional definitions from MOM:min/max-elements:0/1; Container for MOs related to E-UTRA networks. Created automatically when X2 message is received, unless it already exists. Can also be created and deleted manually. When created automatically, the RDN of this MO is EUtraNetwork=1. Length of RDN value is 1 character for automatically created instance. Instance can be created without a preceding user-initiated transaction.";
      key "eUtraNetworkId";
      leaf eUtraNetworkId {
        type leafref {
          path "../attributes/eUtraNetworkId";
        }
      }
      container attributes {
      uses EUtraNetwork-attributes;
      }
    }
  }

  augment "/emael:ManagedElement/gnbcucp:GNBCUCPFunction" {
    list IntraFreqMC {
      description "Additional definitions from MOM:min/max-elements:0/1; This is a container for Intra-frequency mobility control profiles. Instance IntraFreqMC=1 is created automatically when parent MO instance is created, unless created manually in same transaction. The RDN of this MO must be IntraFreqMC=1. Precondition: Instance IntraFreqMC=1 can only be created in same transaction as parent MO instance and cannot be deleted unless parent MO instance is deleted.";
      key "intraFreqMCId";
      leaf intraFreqMCId {
        type leafref {
          path "../attributes/intraFreqMCId";
        }
      }
      container attributes {
      uses IntraFreqMC-attributes;
      }
    }
  }

  augment "/emael:ManagedElement/gnbcucp:GNBCUCPFunction" {
    list Mcfb {
      description "Additional definitions from MOM:min/max-elements:0/1; Container class for mobility control fallback attributes and profile classes. Instance Mcfb=1 is created automatically when parent MO instance is created, unless created manually in same transaction. The RDN of this MO is Mcfb=1. Precondition: Instance Mcfb=1 can only be created in same transaction as parent MO instance and cannot be deleted unless parent MO instance is deleted.";
      key "mcfbId";
      leaf mcfbId {
        type leafref {
          path "../attributes/mcfbId";
        }
      }
      container attributes {
      uses Mcfb-attributes;
      }
    }
  }

  augment "/emael:ManagedElement/gnbcucp:GNBCUCPFunction" {
    list Mcpc {
      description "Additional definitions from MOM:min/max-elements:0/1; Configuration of Mobility Control at Poor Coverage function and container for MCPC profiles. Instance Mcpc=1 is created automatically when parent MO instance is created, unless created manually in same transaction. The RDN of this MO must be Mcpc=1. Precondition: Instance Mcpc=1 can only be created in same transaction as parent MO instance and cannot be deleted unless parent MO instance is deleted.";
      key "mcpcId";
      leaf mcpcId {
        type leafref {
          path "../attributes/mcpcId";
        }
      }
      container attributes {
      uses Mcpc-attributes;
      }
    }
  }

  augment "/emael:ManagedElement/gnbcucp:GNBCUCPFunction" {
    list Mdt {
      description "Additional definitions from MOM:min/max-elements:0/1; Container class for MDT profile classes. Instance Mdt=1 is created automatically when parent MO instance is created, unless created manually in same transaction. The RDN of this MO must be Mdt=1. Precondition: Instance Mdt=1 can only be created in same transaction as parent MO instance and cannot be deleted unless parent MO instance is deleted.";
      key "mdtId";
      leaf mdtId {
        type leafref {
          path "../attributes/mdtId";
        }
      }
      container attributes {
      uses Mdt-attributes;
      }
    }
  }

  augment "/emael:ManagedElement/gnbcucp:GNBCUCPFunction" {
    list Nccm {
      description "Additional definitions from MOM:min/max-elements:0/1; Container class for neighbor cell coverage measurement configuration classes. Instance Nccm=1 is created automatically when parent MO instance is created, unless created manually in same transaction. Only applicable to Low-Band and Mid-Band cells. The RDN of this MO must be Nccm=1. Precondition: Instance Nccm=1 can only be created in same transaction as parent MO instance and cannot be deleted unless parent MO instance is deleted.";
      key "nccmId";
      leaf nccmId {
        type leafref {
          path "../attributes/nccmId";
        }
      }
      container attributes {
      uses Nccm-attributes;
      }
    }
  }

  augment "/emael:ManagedElement/gnbcucp:GNBCUCPFunction" {
    list NRCellCU {
      description "Additional definitions from MOM:min/max-elements:0/unbounded; Representation of an NR cell in gNodeB-CU. Manages inter-cell mobility and neighbor relations through NR Automated Neighbor Relations feature. Created automatically when a configuration message over F1 interface is received if no NRCellCU instance with same NCI already exists. Can also be created and deleted manually. When created automatically, RDN of this MO is NRCellCU=<NCI>, where NCI = <gNBId>*2^(36-<gNBIdLength>) + <cellLocalId>. Length of RDN value is up to 11 characters for automatically created instance. Instance can be created without a preceding user-initiated transaction. Precondition: Can be deleted only when NRCellDU instance with matching cellLocalId does not exist or has administrativeState LOCKED.";
      key "nRCellCUId";
      leaf nRCellCUId {
        type leafref {
          path "../attributes/nRCellCUId";
        }
      }
      container attributes {
      uses NRCellCU-attributes;
      }
    }
  }

  augment "/emael:ManagedElement/gnbcucp:GNBCUCPFunction" {
    list NrdcControl {
      description "Additional definitions from MOM:min/max-elements:0/1; Configuration of NR-NR Dual Connectivity in Master Node and container for NR-DC profiles. Instance NrdcControl=1 is created automatically when parent MO instance is created, unless created manually in same transaction. The RDN of this MO must be NrdcControl=1. Precondition: Instance NrdcControl=1 can only be created in same transaction as parent MO instance and cannot be deleted unless parent MO instance is deleted.";
      key "nrdcControlId";
      leaf nrdcControlId {
        type leafref {
          path "../attributes/nrdcControlId";
        }
      }
      container attributes {
      uses NrdcControl-attributes;
      }
    }
  }

  augment "/emael:ManagedElement/gnbcucp:GNBCUCPFunction" {
    list NrdcSnTermination {
      description "Additional definitions from MOM:min/max-elements:0/30; Profile for Secondary Node termination. Instance NrdcSnTermination=SnTerminationProhibited is created automatically when parent MO instance is created, unless created manually in same transaction. Attribute defaultNrdcSnTerm must be false in NrdcSnTermination=SnTerminationProhibited instance. Precondition: Instance NrdcSnTermination=SnTerminationProhibited can only be created in same transaction as parent MO instance and cannot be deleted unless parent MO instance is deleted. Other instances can be created and deleted at any time. Maximum 29 NrdcSnTermination instances, with RDN different from SnTerminationProhibited, can be created under parent MO instance.";
      key "nrdcSnTerminationId";
      leaf nrdcSnTerminationId {
        type leafref {
          path "../attributes/nrdcSnTerminationId";
        }
      }
      container attributes {
      uses NrdcSnTermination-attributes;
      }
    }
  }

  augment "/emael:ManagedElement/gnbcucp:GNBCUCPFunction" {
    list NRNetwork {
      description "Additional definitions from MOM:min/max-elements:0/1; Container for MOs related to NR networks. Created automatically when Xn message is received, unless it already exists. Can also be created and deleted manually. When created automatically, the RDN of this MO is NRNetwork=1. Length of RDN value is 1 character for automatically created instance. Instance can be created without a preceding user-initiated transaction.";
      key "nRNetworkId";
      leaf nRNetworkId {
        type leafref {
          path "../attributes/nRNetworkId";
        }
      }
      container attributes {
      uses NRNetwork-attributes;
      }
    }
  }

  augment "/emael:ManagedElement/gnbcucp:GNBCUCPFunction" {
    list PciHandling {
      description "Additional definitions from MOM:min/max-elements:0/1; Parameters and constraints for PCI handling functions. Instance PciHandling=1 is created automatically when parent MO instance is created, unless created manually in same transaction. The RDN of this MO must be PciHandling=1. Precondition: Instance PciHandling=1 can only be created in same transaction as parent MO instance and cannot be deleted unless parent MO instance is deleted.";
      key "pciHandlingId";
      leaf pciHandlingId {
        type leafref {
          path "../attributes/pciHandlingId";
        }
      }
      container attributes {
      uses PciHandling-attributes;
      }
    }
  }

  augment "/emael:ManagedElement/gnbcucp:GNBCUCPFunction" {
    list PeriodicUeMeas {
      description "Additional definitions from MOM:min/max-elements:0/1; Container class for periodic UE measurement profiles. Instance PeriodicUeMeas=1 is created automatically when parent MO instance is created, unless created manually in same transaction. The RDN of this MO must be PeriodicUeMeas=1. Precondition: Instance PeriodicUeMeas=1 can only be created in same transaction as parent MO instance and cannot be deleted unless parent MO instance is deleted.";
      key "periodicUeMeasId";
      leaf periodicUeMeasId {
        type leafref {
          path "../attributes/periodicUeMeasId";
        }
      }
      container attributes {
      uses PeriodicUeMeas-attributes;
      }
    }
  }

  augment "/emael:ManagedElement/gnbcucp:GNBCUCPFunction" {
    list PmUeMeas {
      description "Additional definitions from MOM:min/max-elements:0/1; Container class for PM UE measurement profile classes. Instance PmUeMeas=1 is created automatically when parent MO instance is created, unless created manually in same transaction. The RDN of this MO must be PmUeMeas=1. Precondition: Instance PmUeMeas=1 can only be created in same transaction as parent MO instance and cannot be deleted unless parent MO instance is deleted.";
      key "pmUeMeasId";
      leaf pmUeMeasId {
        type leafref {
          path "../attributes/pmUeMeasId";
        }
      }
      container attributes {
      uses PmUeMeas-attributes;
      }
    }
  }

  augment "/emael:ManagedElement/gnbcucp:GNBCUCPFunction" {
    list PriorityService {
      description "Additional definitions from MOM:min/max-elements:0/12; Priority service configuration for NRCellCU instances.";
      key "priorityServiceId";
      leaf priorityServiceId {
        type leafref {
          path "../attributes/priorityServiceId";
        }
      }
      container attributes {
      uses PriorityService-attributes;
      }
    }
  }

  augment "/emael:ManagedElement/gnbcucp:GNBCUCPFunction" {
    list QciProfileEndcConfigExt {
      description "Additional definitions from MOM:min/max-elements:1/1;systemCreated; Managing QoS-related parameters for Data Radio Bearers in EN-DC and NR-DC. The RDN of this MO is QciProfileEndcConfigExt=1.";
      key "qciProfileEndcConfigExtId";
      status deprecated;
      leaf qciProfileEndcConfigExtId {
        type leafref {
          path "../attributes/qciProfileEndcConfigExtId";
        }
        status deprecated;
      }
      container attributes {
      uses QciProfileEndcConfigExt-attributes;
      }
    }
  }

  augment "/emael:ManagedElement/gnbcucp:GNBCUCPFunction" {
    list RelaxedRrmMeas {
      description "Additional definitions from MOM:min/max-elements:0/1; Container class for relaxed RRM measurement cell profiles.";
      key "relaxedRrmMeasId";
      leaf relaxedRrmMeasId {
        type leafref {
          path "../attributes/relaxedRrmMeasId";
        }
      }
      container attributes {
      uses RelaxedRrmMeas-attributes;
      }
    }
  }

  augment "/emael:ManagedElement/gnbcucp:GNBCUCPFunction" {
    list ResourcePartitions {
      description "Additional definitions from MOM:min/max-elements:0/1; Set of resource partitions.";
      key "resourcePartitionsId";
      leaf resourcePartitionsId {
        type leafref {
          path "../attributes/resourcePartitionsId";
        }
      }
      container attributes {
      uses ResourcePartitions-attributes;
      }
    }
  }

  augment "/emael:ManagedElement/gnbcucp:GNBCUCPFunction" {
    list SecurityHandling {
      description "Additional definitions from MOM:min/max-elements:1/1;systemCreated; Manageable characteristics of security handling except during Xn handover and NG handover. The RDN of this MO is SecurityHandling=1.";
      key "securityHandlingId";
      leaf securityHandlingId {
        type leafref {
          path "../attributes/securityHandlingId";
        }
      }
      container attributes {
      uses SecurityHandling-attributes;
      }
    }
  }

  augment "/emael:ManagedElement/gnbcucp:GNBCUCPFunction" {
    list TermPointToAmf {
      description "Additional definitions from MOM:min/max-elements:0/64; Models an NG link AMF termination point. Created and deleted automatically by DNS lookup on 5GS TAI if GNBCUCPFunction::dnsLookupOn5GsTai is true. Can also be created and deleted manually. When created automatically, the RDNs of these MOs are TermPointToAmf=<MCC>-<MNC>-<AMF Region Id>-<AMF Set Id>-<AMF Pointer>. Length of RDN value is up to 19 characters for automatically created instance. Instance can be created without a preceding user-initiated transaction.";
      key "termPointToAmfId";
      leaf termPointToAmfId {
        type leafref {
          path "../attributes/termPointToAmfId";
        }
      }
      container attributes {
      uses TermPointToAmf-attributes;
      }
    }
  }

  augment "/emael:ManagedElement/gnbcucp:GNBCUCPFunction" {
    list TermPointToGNBCUUP {
      description "Additional definitions from MOM:min/max-elements:0/unbounded;systemCreated; Models an E1 link to a gNodeB-CU-UP. Created when E1 link is set up. Deleted at node restart. The RDN of this MO is TermPointToGNBCUUP=[Local Ip Address]_[Remote Ip Address]. Length of RDN value is up to 79 characters. Instance can be created without a preceding user-initiated transaction.";
      key "termPointToGNBCUUPId";
      leaf termPointToGNBCUUPId {
        type leafref {
          path "../attributes/termPointToGNBCUUPId";
        }
      }
      container attributes {
      uses TermPointToGNBCUUP-attributes;
      }
    }
  }

  augment "/emael:ManagedElement/gnbcucp:GNBCUCPFunction" {
    list TermPointToGNBDU {
      description "Additional definitions from MOM:min/max-elements:0/unbounded;systemCreated; Models an F1-C link to a gNodeB-DU. Created when F1-C link is set up. Deleted at node restart. The RDN of this MO is TermPointToGNBDU=[gNBDUId]. Length of RDN value is up to 11 characters. Instance can be created without a preceding user-initiated transaction.";
      key "termPointToGNBDUId";
      leaf termPointToGNBDUId {
        type leafref {
          path "../attributes/termPointToGNBDUId";
        }
      }
      container attributes {
      uses TermPointToGNBDU-attributes;
      }
    }
  }

  augment "/emael:ManagedElement/gnbcucp:GNBCUCPFunction" {
    list TimeSchedulingGroup {
      description "Additional definitions from MOM:min/max-elements:0/96; A collection of TimeSchedulingWindow.";
      key "timeSchedulingGroupId";
      leaf timeSchedulingGroupId {
        type leafref {
          path "../attributes/timeSchedulingGroupId";
        }
      }
      container attributes {
      uses TimeSchedulingGroup-attributes;
      }
    }
  }

  augment "/emael:ManagedElement/gnbcucp:GNBCUCPFunction" {
    list TrafficOffload {
      description "Additional definitions from MOM:min/max-elements:0/1; Container for traffic offload profiles. Instance TrafficOffload=1 is created automatically when parent MO instance is created, unless created manually in same transaction. The RDN of this MO must be TrafficOffload=1. Precondition: Instance TrafficOffload=1 can only be created in same transaction as parent MO instance and cannot be deleted unless parent MO instance is deleted.";
      key "trafficOffloadId";
      leaf trafficOffloadId {
        type leafref {
          path "../attributes/trafficOffloadId";
        }
      }
      container attributes {
      uses TrafficOffload-attributes;
      }
    }
  }

  augment "/emael:ManagedElement/gnbcucp:GNBCUCPFunction" {
    list TrafficSteering {
      description "Additional definitions from MOM:min/max-elements:0/1; Configuration of Traffic Steering (TrSt) and container for TrSt profiles. Instance TrafficSteering=1 is created automatically when parent MO instance is created, unless created manually in same transaction. The RDN of this MO must be TrafficSteering=1. Precondition: Instance TrafficSteering=1 can only be created in same transaction as parent MO instance and cannot be deleted unless parent MO instance is deleted.";
      key "trafficSteeringId";
      leaf trafficSteeringId {
        type leafref {
          path "../attributes/trafficSteeringId";
        }
      }
      container attributes {
      uses TrafficSteering-attributes;
      }
    }
  }

  augment "/emael:ManagedElement/gnbcucp:GNBCUCPFunction" {
    list UeCC {
      description "Additional definitions from MOM:min/max-elements:0/1; Container class for UE connection control attributes and profile classes. Instance UeCC=1 is created automatically when parent MO instance is created, unless created manually in same transaction. The RDN of this MO must be UeCC=1. Precondition: Instance UeCC=1 can only be created in same transaction as parent MO instance and cannot be deleted unless parent MO instance is deleted.";
      key "ueCCId";
      leaf ueCCId {
        type leafref {
          path "../attributes/ueCCId";
        }
      }
      container attributes {
      uses UeCC-attributes;
      }
    }
  }

  augment "/emael:ManagedElement/gnbcucp:GNBCUCPFunction" {
    list UeCovMeas {
      description "Additional definitions from MOM:min/max-elements:0/1; Container class for UE coverage measurement configuration classes. Instance UeCovMeas=1 is created automatically when parent MO instance is created, unless created manually in same transaction. The RDN of this MO must be UeCovMeas=1. Precondition: Instance UeCovMeas=1 can only be created in same transaction as parent MO instance and cannot be deleted unless parent MO instance is deleted.";
      key "ueCovMeasId";
      leaf ueCovMeasId {
        type leafref {
          path "../attributes/ueCovMeasId";
        }
      }
      container attributes {
      uses UeCovMeas-attributes;
      }
    }
  }

  augment "/emael:ManagedElement/gnbcucp:GNBCUCPFunction" {
    list UeGroupSelection {
      description "Additional definitions from MOM:min/max-elements:0/1; Container class for MO classes defining different UE group types. The RDN of this MO must be UeGroupSelection=1.";
      key "ueGroupSelectionId";
      leaf ueGroupSelectionId {
        type leafref {
          path "../attributes/ueGroupSelectionId";
        }
      }
      container attributes {
      uses UeGroupSelection-attributes;
      }
    }
  }

  augment "/emael:ManagedElement/gnbcucp:GNBCUCPFunction" {
    list UeMC {
      description "Additional definitions from MOM:min/max-elements:0/1; Container class for UE mobility control attributes and UeMC profile classes. Instance UeMC=1 is created automatically when parent MO instance is created, unless created manually in same transaction. The RDN of this MO must be UeMC=1. Precondition: Instance UeMC=1 can only be created in same transaction as parent MO instance and cannot be deleted unless parent MO instance is deleted.";
      key "ueMCId";
      leaf ueMCId {
        type leafref {
          path "../attributes/ueMCId";
        }
      }
      container attributes {
      uses UeMC-attributes;
      }
    }
  }

  augment "/emael:ManagedElement/gnbcucp:GNBCUCPFunction" {
    list UeNoDrb {
      description "Additional definitions from MOM:min/max-elements:0/1; Configuration of UE context without DRBs. Instance UeNoDrb=1 is created automatically when parent MO instance is created, unless created manually in same transaction. The RDN of this MO must be UeNoDrb=1. Precondition: Instance UeNoDrb=1 can only be created in same transaction as parent MO instance and cannot be deleted unless parent MO instance is deleted.";
      key "ueNoDrbId";
      leaf ueNoDrbId {
        type leafref {
          path "../attributes/ueNoDrbId";
        }
      }
      container attributes {
      uses UeNoDrb-attributes;
      }
    }
  }

  augment "/emael:ManagedElement/gnbcucp:GNBCUCPFunction" {
    list UeUlResMon {
      description "Additional definitions from MOM:min/max-elements:0/1; Container class for UE uplink resource monitoring attributes and configuration classes. Instance UeUlResMon=1 is created automatically when parent MO instance is created, unless created manually in same transaction. The RDN of this MO must be UeUlResMon=1. Precondition: Instance UeUlResMon=1 can only be created in same transaction as parent MO instance and cannot be deleted unless parent MO instance is deleted.";
      key "ueUlResMonId";
      leaf ueUlResMonId {
        type leafref {
          path "../attributes/ueUlResMonId";
        }
      }
      container attributes {
      uses UeUlResMon-attributes;
      }
    }
  }

  augment "/emael:ManagedElement/gnbcucp:GNBCUCPFunction/gnbcucp:UeGroupSelection/gnbcucp:ImeiSvGroups" {
    list ImeiSvGroup {
      description "Additional definitions from MOM:min/max-elements:0/512; A set of IMEISVs used to define a subset of all UEs.";
      key "imeiSvGroupId";
      leaf imeiSvGroupId {
        type leafref {
          path "../attributes/imeiSvGroupId";
        }
      }
      container attributes {
      uses ImeiSvGroup-attributes;
      }
    }
  }

  augment "/emael:ManagedElement/gnbcucp:GNBCUCPFunction/gnbcucp:UeCC/gnbcucp:InactivityProfile" {
    list InactivityProfileUeCfg {
      description "Additional definitions from MOM:min/max-elements:0/8; Configuration of inactivity timer profile for UE groups. Instance InactivityProfileUeCfg=Base is created automatically when parent MO instance is created, unless created manually in same transaction. Attributes prefUeGroupList, ueGroupList and ueConfGroupList must be empty in instance InactivityProfileUeCfg=Base but cannot all be empty in any other instance of InactivityProfileUeCfg under same parent InactivityProfile instance. Value 0 is no longer allowed and is planned to be removed from the valid range of prefUeGroupList and ueGroupList. Precondition: Instance InactivityProfileUeCfg=Base can only be created in same transaction as parent MO instance and cannot be deleted unless parent MO instance is deleted. Other instances can be created and deleted at any time. Maximum 7 InactivityProfileUeCfg instances, with RDN different from Base, can be created under parent MO instance.";
      key "inactivityProfileUeCfgId";
      leaf inactivityProfileUeCfgId {
        type leafref {
          path "../attributes/inactivityProfileUeCfgId";
        }
      }
      container attributes {
      uses InactivityProfileUeCfg-attributes;
      }
    }
  }

  augment "/emael:ManagedElement/gnbcucp:GNBCUCPFunction/gnbcucp:UeCC/gnbcucp:InitialCg" {
    list InitialCgUeCfg {
      description "Additional definitions from MOM:min/max-elements:0/8; Initial cell group UE configuration group. Instance InitialCgUeCfg=Base is created automatically when parent MO instance is created, unless created manually in same transaction. Each UE configuration group identifier can only be defined in one ueConfGroupList among InitialCgUeCfg instances contained under parent InitialCg instance. Any combination of one UE group identifier in ueGroupList and one preference UE group identifier in prefUeGroupList must be unique among InitialCgUeCfg instances contained under parent InitialCg instance. Attributes prefUeGroupList, ueGroupList and ueConfGroupList must be empty in instance InitialCgUeCfg=Base but cannot all be empty in any other instance of InitialCgUeCfg under same parent InitialCg instance. Precondition: Instance InitialCgUeCfg=Base can only be created in same transaction as parent MO instance and cannot be deleted unless parent MO instance is deleted. Other instances can be created and deleted at any time. Maximum 7 InitialCgUeCfg instances, with RDN different from Base, can be created under parent MO instance.";
      key "initialCgUeCfgId";
      leaf initialCgUeCfgId {
        type leafref {
          path "../attributes/initialCgUeCfgId";
        }
      }
      container attributes {
      uses InitialCgUeCfg-attributes;
      }
    }
  }

  augment "/emael:ManagedElement/gnbcucp:GNBCUCPFunction/gnbcucp:IntraFreqMC" {
    list IntraFreqMCCellProfile {
      description "Additional definitions from MOM:min/max-elements:0/unbounded; Intra-frequency mobility control, cell configuration profile. Applies to UEs that use cell as SpCell. Attributes are used on cell level. Instance IntraFreqMCCellProfile=Default is created automatically when parent MO instance is created, unless created manually in same transaction. NRCellCU::intraFreqMCCellProfileRef is automatically set to IntraFreqMCCellProfile=Default instance, unless manually set to refer to another MO instance. Precondition: Instance IntraFreqMCCellProfile=Default can only be created in same transaction as parent MO instance and cannot be deleted unless parent MO instance is deleted. Other instances can be created and deleted at any time.";
      key "intraFreqMCCellProfileId";
      leaf intraFreqMCCellProfileId {
        type leafref {
          path "../attributes/intraFreqMCCellProfileId";
        }
      }
      container attributes {
      uses IntraFreqMCCellProfile-attributes;
      }
    }
  }

  augment "/emael:ManagedElement/gnbcucp:GNBCUCPFunction/gnbcucp:IntraFreqMC" {
    list IntraFreqMCFreqRelProfile {
      description "Additional definitions from MOM:min/max-elements:0/unbounded; Intra-frequency mobility control cell configuration profile. Applies to UEs that use cell as SpCell. Attributes are used on NR frequency relation level. Instance IntraFreqMCFreqRelProfile=Default is created automatically when parent MO instance is created, unless created manually in same transaction. NRFreqRelation::intraFreqMCFreqRelProfileRef is automatically set to IntraFreqMCFreqRelProfile=Default instance, unless manually set to refer to another MO instance. Precondition: Instance IntraFreqMCFreqRelProfile=Default can only be created in same transaction as parent MO instance and cannot be deleted unless parent MO instance is deleted. Other instances can be created and deleted at any time.";
      key "intraFreqMCFreqRelProfileId";
      status deprecated;
      leaf intraFreqMCFreqRelProfileId {
        type leafref {
          path "../attributes/intraFreqMCFreqRelProfileId";
        }
        status deprecated;
      }
      container attributes {
      uses IntraFreqMCFreqRelProfile-attributes;
      }
    }
  }

  augment "/emael:ManagedElement/gnbcucp:GNBCUCPFunction/gnbcucp:IntraFreqMC/gnbcucp:IntraFreqMCCellProfile" {
    list IntraFreqMCCellProfileUeCfg {
      description "Additional definitions from MOM:min/max-elements:0/32; Intra-frequency mobility control cell configuration profile, UE configuration group. Applies to UEs that use cell as SpCell. Attributes are used on cell level. Instance IntraFreqMCCellProfileUeCfg=Base is created automatically when parent MO instance is created, unless created manually in same transaction. Attributes prefUeGroupList, ueGroupList and ueConfGroupList must be empty in instance IntraFreqMCCellProfileUeCfg=Base but cannot all be empty in any other instance of IntraFreqMCCellProfileUeCfg under same parent IntraFreqMCCellProfile instance. Precondition: Instance IntraFreqMCCellProfileUeCfg=Base can only be created in same transaction as parent MO instance and cannot be deleted unless parent MO instance is deleted. Other instances can be created and deleted at any time. Maximum 31 IntraFreqMCCellProfileUeCfg instances, with RDN different from Base, can be created under parent MO instance.";
      key "intraFreqMCCellProfileUeCfgId";
      leaf intraFreqMCCellProfileUeCfgId {
        type leafref {
          path "../attributes/intraFreqMCCellProfileUeCfgId";
        }
      }
      container attributes {
      uses IntraFreqMCCellProfileUeCfg-attributes;
      }
    }
  }

  augment "/emael:ManagedElement/gnbcucp:GNBCUCPFunction/gnbcucp:IntraFreqMC/gnbcucp:IntraFreqMCFreqRelProfile" {
    list IntraFreqMCFreqRelProfileUeCfg {
      description "Additional definitions from MOM:min/max-elements:0/32; Intra-frequency mobility control cell configuration profile for UE configuration group. Applies to UEs that use cell as SpCell. Attributes are used on NR frequency relation level. Instance IntraFreqMCFreqRelProfileUeCfg=Base is created automatically when parent MO instance is created, unless created manually in same transaction. Attributes prefUeGroupList, ueGroupList and ueConfGroupList must be empty in instance IntraFreqMCFreqRelProfileUeCfg=Base but cannot all be empty in any other instance of IntraFreqMCFreqRelProfileUeCfg under same parent IntraFreqMCFreqRelProfile instance. Precondition: Instance IntraFreqMCFreqRelProfileUeCfg=Base can only be created in same transaction as parent MO instance and cannot be deleted unless parent MO instance is deleted. Other instances can be created and deleted at any time. Maximum 31 IntraFreqMCFreqRelProfileUeCfg instances, with RDN different from Base, can be created under parent MO instance.";
      key "intraFreqMCFreqRelProfileUeCfgId";
      status deprecated;
      leaf intraFreqMCFreqRelProfileUeCfgId {
        type leafref {
          path "../attributes/intraFreqMCFreqRelProfileUeCfgId";
        }
        status deprecated;
      }
      container attributes {
      uses IntraFreqMCFreqRelProfileUeCfg-attributes;
      }
    }
  }

  augment "/emael:ManagedElement/gnbcucp:GNBCUCPFunction/gnbcucp:Mcfb" {
    list McfbCellProfile {
      description "Additional definitions from MOM:min/max-elements:0/unbounded; Profile of mobility control fallback for cell. Applies to UEs that use the cell as PCell. Attributes are used on cell level. Instance McfbCellProfile=Default is created automatically when parent MO instance is created, unless created manually in same transaction. NRCellCU::mcfbCellProfileRef is automatically set to McfbCellProfile=Default instance, unless manually set to refer to another MO instance. Precondition: Instance McfbCellProfile=Default can only be created in same transaction as parent MO instance and cannot be deleted unless parent MO instance is deleted.";
      key "mcfbCellProfileId";
      leaf mcfbCellProfileId {
        type leafref {
          path "../attributes/mcfbCellProfileId";
        }
      }
      container attributes {
      uses McfbCellProfile-attributes;
      }
    }
  }

  augment "/emael:ManagedElement/gnbcucp:GNBCUCPFunction/gnbcucp:Mcfb/gnbcucp:McfbCellProfile" {
    list McfbCellProfileUeCfg {
      description "Additional definitions from MOM:min/max-elements:0/32; Mobility Control Fallback Cell Profile, UE configuration group. Applies to UEs that use cell as PCell. Attributes are used on cell level. Instance McfbCellProfileUeCfg=Base is created automatically when parent MO instance is created, unless created manually in same transaction. Attributes prefUeGroupList, ueGroupList and ueConfGroupList must be empty in instance McfbCellProfileUeCfg=Base but cannot all be empty in any other instance of McfbCellProfileUeCfg under same parent McfbCellProfile instance. Precondition: Instance McfbCellProfileUeCfg=Base can only be created in same transaction as parent MO instance and cannot be deleted unless parent MO instance is deleted. Other instances can be created and deleted at any time. Maximum 31 McfbCellProfileUeCfg instances, with RDN different from Base, can be created under parent MO instance.";
      key "mcfbCellProfileUeCfgId";
      leaf mcfbCellProfileUeCfgId {
        type leafref {
          path "../attributes/mcfbCellProfileUeCfgId";
        }
      }
      container attributes {
      uses McfbCellProfileUeCfg-attributes;
      }
    }
  }

  augment "/emael:ManagedElement/gnbcucp:GNBCUCPFunction/gnbcucp:Mcpc" {
    list McpcNrdcPSCellProfile {
      description "Additional definitions from MOM:min/max-elements:0/unbounded; Mobility Control at Poor Coverage (MCPC) function for PSCell in NR-DC configuration. Applies to UEs that use cell as PSCell in NR-DC. Attributes are used on cell level. Instance McpcNrdcPSCellProfile=Default is created automatically when parent MO instance is created, unless created manually in same transaction. NRCellCU::mcpcNrdcPSCellProfileRef is automatically set to McpcNrdcPSCellProfile=Default instance, unless manually set to refer to another MO instance. Precondition: Instance McpcNrdcPSCellProfile=Default can only be created in same transaction as parent MO instance and cannot be deleted unless parent MO instance is deleted. Other instances can be created and deleted at any time.";
      key "mcpcNrdcPSCellProfileId";
      leaf mcpcNrdcPSCellProfileId {
        type leafref {
          path "../attributes/mcpcNrdcPSCellProfileId";
        }
      }
      container attributes {
      uses McpcNrdcPSCellProfile-attributes;
      }
    }
  }

  augment "/emael:ManagedElement/gnbcucp:GNBCUCPFunction/gnbcucp:Mcpc" {
    list McpcPCellEUtranFreqRelProfile {
      description "Additional definitions from MOM:min/max-elements:0/unbounded; Mobility Control at Poor Coverage (MCPC) for PCell. Applies to UEs that use the cell as PCell. Attributes are used on E-UTRAN frequency relation level. Instance McpcPCellEUtranFreqRelProfile=Default is created automatically when parent MO instance is created, unless created manually in same transaction. MCPC for PCell is enabled for each NRCellCU instance by setting NRCellCU::mcpcPCellEnabled. EUtranFreqRelation::mcpcPCellEUtranFreqRelProfileRef is automatically set to McpcPCellEUtranFreqRelProfile=Default instance, unless manually set to refer to another MO instance. Precondition: Instance McpcPCellEUtranFreqRelProfile=Default can only be created in same transaction as parent MO instance and cannot be deleted unless parent MO instance is deleted. Other instances can be created and deleted at any time.";
      key "mcpcPCellEUtranFreqRelProfileId";
      leaf mcpcPCellEUtranFreqRelProfileId {
        type leafref {
          path "../attributes/mcpcPCellEUtranFreqRelProfileId";
        }
      }
      container attributes {
      uses McpcPCellEUtranFreqRelProfile-attributes;
      }
    }
  }

  augment "/emael:ManagedElement/gnbcucp:GNBCUCPFunction/gnbcucp:Mcpc" {
    list McpcPCellNrFreqRelProfile {
      description "Additional definitions from MOM:min/max-elements:0/unbounded; Mobility Control at Poor Coverage (MCPC) for PCell. Applies to UEs that use the cell as PCell. Attributes are used on NR frequency relation level. Instance McpcPCellNrFreqRelProfile=Default is created automatically when parent MO instance is created, unless created manually in same transaction. MCPC for PCell is enabled per NRCellCU instance by setting NRCellCU::mcpcPCellEnabled. NRFreqRelation::mcpcPCellNrFreqRelProfileRef is automatically set to McpcPCellNrFreqRelProfile=Default instance, unless manually set to refer to another MO instance. Precondition: Instance McpcPCellNrFreqRelProfile=Default can only be created in same transaction as parent MO instance and cannot be deleted unless parent MO instance is deleted. Other instances can be created and deleted at any time.";
      key "mcpcPCellNrFreqRelProfileId";
      leaf mcpcPCellNrFreqRelProfileId {
        type leafref {
          path "../attributes/mcpcPCellNrFreqRelProfileId";
        }
      }
      container attributes {
      uses McpcPCellNrFreqRelProfile-attributes;
      }
    }
  }

  augment "/emael:ManagedElement/gnbcucp:GNBCUCPFunction/gnbcucp:Mcpc" {
    list McpcPCellProfile {
      description "Additional definitions from MOM:min/max-elements:0/unbounded; Mobility Control at Poor Coverage (MCPC) for PCell. Applies to UEs that use the cell as PCell. Attributes are used on cell level. Instance McpcPCellProfile=Default is created automatically when parent MO instance is created, unless created manually in same transaction. MCPC for PCell is enabled per NRCellCU instance by setting NRCellCU::mcpcPCellEnabled. NRCellCU::mcpcPCellProfileRef is automatically set to McpcPCellProfile=Default instance, unless manually set to refer to another MO instance. Precondition: Instance McpcPCellProfile=Default can only be created in same transaction as parent MO instance and cannot be deleted unless parent MO instance is deleted. Other instances can be created and deleted at any time.";
      key "mcpcPCellProfileId";
      leaf mcpcPCellProfileId {
        type leafref {
          path "../attributes/mcpcPCellProfileId";
        }
      }
      container attributes {
      uses McpcPCellProfile-attributes;
      }
    }
  }

  augment "/emael:ManagedElement/gnbcucp:GNBCUCPFunction/gnbcucp:Mcpc" {
    list McpcPSCellNrFreqRelProfile {
      description "Additional definitions from MOM:min/max-elements:0/unbounded; Mobility Control at Poor Coverage function for PSCell in EN-DC. Applies to UEs that use this cell as PSCell in EN-DC. Attributes are used on NR frequency relation level. This function for PSCell in EN-DC can be enabled for each NRCellCU instance with NRCellCU::mcpcPSCellEnabled. Instance McpcPSCellNrFreqRelProfile=Default is created automatically when parent MO instance is created, unless created manually in same transaction. NRFreqRelation::mcpcPSCellNrFreqRelProfileRef is automatically set to McpcPSCellNrFreqRelProfile=Default instance, unless manually set to refer to another MO instance. Precondition: Instance McpcPSCellNrFreqRelProfile=Default can only be created in same transaction as parent MO instance and cannot be deleted unless parent MO instance is deleted. Other instances can be created and deleted at any time.";
      key "mcpcPSCellNrFreqRelProfileId";
      leaf mcpcPSCellNrFreqRelProfileId {
        type leafref {
          path "../attributes/mcpcPSCellNrFreqRelProfileId";
        }
      }
      container attributes {
      uses McpcPSCellNrFreqRelProfile-attributes;
      }
    }
  }

  augment "/emael:ManagedElement/gnbcucp:GNBCUCPFunction/gnbcucp:Mcpc" {
    list McpcPSCellProfile {
      description "Additional definitions from MOM:min/max-elements:0/unbounded; Mobility Control at Poor Coverage function for PSCell in EN-DC. Applies to UEs that use this cell as PSCell in EN-DC. Attributes are used on cell level. This function for PSCell in EN-DC can be enabled for each NRCellCU instance with NRCellCU::mcpcPSCellEnabled. Instance McpcPSCellProfile=Default is created automatically when parent MO instance is created, unless created manually in same transaction. NRCellCU::mcpcPSCellProfileRef is automatically set to McpcPSCellProfile=Default instance, unless manually set to refer to another MO instance. Precondition: Instance McpcPSCellProfile=Default can only be created in same transaction as parent MO instance and cannot be deleted unless parent MO instance is deleted. Other instances can be created and deleted at any time.";
      key "mcpcPSCellProfileId";
      leaf mcpcPSCellProfileId {
        type leafref {
          path "../attributes/mcpcPSCellProfileId";
        }
      }
      container attributes {
      uses McpcPSCellProfile-attributes;
      }
    }
  }

  augment "/emael:ManagedElement/gnbcucp:GNBCUCPFunction/gnbcucp:Mcpc/gnbcucp:McpcNrdcPSCellProfile" {
    list McpcNrdcPSCellProfileUeCfg {
      description "Additional definitions from MOM:min/max-elements:0/32; Mobility Control at Poor Coverage function for PSCell in NR-DC, UE configuration group. Applies to UEs that use cell as PSCell in NR-DC. Attributes are used on cell level. Instance McpcNrdcPSCellProfileUeCfg=Base is created automatically when parent MO instance is created, unless created manually in same transaction. Attributes prefUeGroupList, ueGroupList and ueConfGroupList must be empty in instance McpcNrdcPSCellProfileUeCfg=Base but cannot all be empty in any other instance of McpcNrdcPSCellProfileUeCfg under same parent McpcNrdcPSCellProfile instance. Precondition: Instance McpcNrdcPSCellProfileUeCfg=Base can only be created in same transaction as parent MO instance and cannot be deleted unless parent MO instance is deleted. Other instances can be created and deleted at any time. Maximum 31 McpcNrdcPSCellProfileUeCfg instances, with RDN different from Base, can be created under parent MO instance.";
      key "mcpcNrdcPSCellProfileUeCfgId";
      leaf mcpcNrdcPSCellProfileUeCfgId {
        type leafref {
          path "../attributes/mcpcNrdcPSCellProfileUeCfgId";
        }
      }
      container attributes {
      uses McpcNrdcPSCellProfileUeCfg-attributes;
      }
    }
  }

  augment "/emael:ManagedElement/gnbcucp:GNBCUCPFunction/gnbcucp:Mcpc/gnbcucp:McpcPCellEUtranFreqRelProfile" {
    list McpcPCellEUtranFreqRelProfileUeCfg {
      description "Additional definitions from MOM:min/max-elements:0/32; Mobility Control at Poor Coverage (MCPC) for PCell, UE configuration group. Applies to UEs that use the cell as PCell. Attributes are used on E-UTRAN frequency relation level. Instance McpcPCellEUtranFreqRelProfileUeCfg=Base is created automatically when parent MO instance is created, unless created manually in same transaction. Attributes prefUeGroupList, ueGroupList and ueConfGroupList must be empty in instance McpcPCellEUtranFreqRelProfileUeCfg=Base but cannot all be empty in any other instance of McpcPCellEUtranFreqRelProfileUeCfg under same parent McpcPCellEUtranFreqRelProfile instance. Precondition: Instance McpcPCellEUtranFreqRelProfileUeCfg=Base can only be created in same transaction as parent MO instance and cannot be deleted unless parent MO instance is deleted. Other instances can be created and deleted at any time. Maximum 31 McpcPCellEUtranFreqRelProfileUeCfg instances, with RDN different from Base, can be created under parent MO instance.";
      key "mcpcPCellEUtranFreqRelProfileUeCfgId";
      leaf mcpcPCellEUtranFreqRelProfileUeCfgId {
        type leafref {
          path "../attributes/mcpcPCellEUtranFreqRelProfileUeCfgId";
        }
      }
      container attributes {
      uses McpcPCellEUtranFreqRelProfileUeCfg-attributes;
      }
    }
  }

  augment "/emael:ManagedElement/gnbcucp:GNBCUCPFunction/gnbcucp:Mcpc/gnbcucp:McpcPCellNrFreqRelProfile" {
    list McpcPCellNrFreqRelProfileUeCfg {
      description "Additional definitions from MOM:min/max-elements:0/32; Mobility Control at Poor Coverage (MCPC) for PCell, UE configuration group. Applies to UEs that use the cell as PCell. Attributes are used on NR frequency relation level. Instance McpcPCellNrFreqRelProfileUeCfg=Base is created automatically when parent MO instance is created, unless created manually in same transaction. Attributes prefUeGroupList, ueGroupList and ueConfGroupList must be empty in instance McpcPCellNrFreqRelProfileUeCfg=Base but cannot all be empty in any other instance of McpcPCellNrFreqRelProfileUeCfg under same parent McpcPCellNrFreqRelProfile instance. Precondition: Instance McpcPCellNrFreqRelProfileUeCfg=Base can only be created in same transaction as parent MO instance and cannot be deleted unless parent MO instance is deleted. Other instances can be created and deleted at any time. Maximum 31 McpcPCellNrFreqRelProfileUeCfg instances, with RDN different from Base, can be created under parent MO instance.";
      key "mcpcPCellNrFreqRelProfileUeCfgId";
      leaf mcpcPCellNrFreqRelProfileUeCfgId {
        type leafref {
          path "../attributes/mcpcPCellNrFreqRelProfileUeCfgId";
        }
      }
      container attributes {
      uses McpcPCellNrFreqRelProfileUeCfg-attributes;
      }
    }
  }

  augment "/emael:ManagedElement/gnbcucp:GNBCUCPFunction/gnbcucp:Mcpc/gnbcucp:McpcPCellProfile" {
    list McpcPCellProfileUeCfg {
      description "Additional definitions from MOM:min/max-elements:0/32; Mobility Control at Poor Coverage (MCPC) for PCell, UE configuration group. Applies to UEs that use cell as PCell. Attributes are used on cell level. Instance McpcPCellProfileUeCfg=Base is created automatically when parent MO instance is created, unless created manually in same transaction. Attributes prefUeGroupList, ueGroupList and ueConfGroupList must be empty in instance McpcPCellProfileUeCfg=Base but cannot all be empty in any other instance of McpcPCellProfileUeCfg under same parent McpcPCellProfile instance. Precondition: Instance McpcPCellProfileUeCfg=Base can only be created in same transaction as parent MO instance and cannot be deleted unless parent MO instance is deleted. Other instances can be created and deleted at any time. Maximum 31 McpcPCellProfileUeCfg instances, with RDN different from Base, can be created under parent MO instance.";
      key "mcpcPCellProfileUeCfgId";
      leaf mcpcPCellProfileUeCfgId {
        type leafref {
          path "../attributes/mcpcPCellProfileUeCfgId";
        }
      }
      container attributes {
      uses McpcPCellProfileUeCfg-attributes;
      }
    }
  }

  augment "/emael:ManagedElement/gnbcucp:GNBCUCPFunction/gnbcucp:Mcpc/gnbcucp:McpcPSCellNrFreqRelProfile" {
    list McpcPSCellNrFreqRelProfileUeCfg {
      description "Additional definitions from MOM:min/max-elements:0/32; Mobility Control at Poor Coverage function for PSCell in EN-DC, UE configuration group. Applies to UEs that use this cell as PSCell in EN-DC. Attributes are used on NR frequency relation level. Instance McpcPSCellNrFreqRelProfileUeCfg=Base is created automatically when parent MO instance is created, unless created manually in same transaction. Attributes prefUeGroupList, ueGroupList and ueConfGroupList must be empty in instance McpcPSCellNrFreqRelProfileUeCfg=Base but cannot all be empty in any other instance of McpcPSCellNrFreqRelProfileUeCfg under same parent McpcPSCellNrFreqRelProfile instance. Precondition: Instance McpcPSCellNrFreqRelProfileUeCfg=Base can only be created in same transaction as parent MO instance and cannot be deleted unless parent MO instance is deleted. Other instances can be created and deleted at any time. Maximum 31 McpcPSCellNrFreqRelProfileUeCfg instances, with RDN different from Base, can be created under parent MO instance.";
      key "mcpcPSCellNrFreqRelProfileUeCfgId";
      leaf mcpcPSCellNrFreqRelProfileUeCfgId {
        type leafref {
          path "../attributes/mcpcPSCellNrFreqRelProfileUeCfgId";
        }
      }
      container attributes {
      uses McpcPSCellNrFreqRelProfileUeCfg-attributes;
      }
    }
  }

  augment "/emael:ManagedElement/gnbcucp:GNBCUCPFunction/gnbcucp:Mcpc/gnbcucp:McpcPSCellProfile" {
    list McpcPSCellProfileUeCfg {
      description "Additional definitions from MOM:min/max-elements:0/32; Mobility Control at Poor Coverage function for PSCell in EN-DC, UE configuration group. Applies to UEs that use this cell as PSCell in EN-DC. Attributes are used on cell level. Instance McpcPSCellProfileUeCfg=Base is created automatically when parent MO instance is created, unless created manually in same transaction. Attributes prefUeGroupList, ueGroupList and ueConfGroupList must be empty in instance McpcPSCellProfileUeCfg=Base but cannot all be empty in any other instance of McpcPSCellProfileUeCfg under same parent McpcPSCellProfile instance. Precondition: Instance McpcPSCellProfileUeCfg=Base can only be created in same transaction as parent MO instance and cannot be deleted unless parent MO instance is deleted. Other instances can be created and deleted at any time. Maximum 31 McpcPSCellProfileUeCfg instances, with RDN different from Base, can be created under parent MO instance.";
      key "mcpcPSCellProfileUeCfgId";
      leaf mcpcPSCellProfileUeCfgId {
        type leafref {
          path "../attributes/mcpcPSCellProfileUeCfgId";
        }
      }
      container attributes {
      uses McpcPSCellProfileUeCfg-attributes;
      }
    }
  }

  augment "/emael:ManagedElement/gnbcucp:GNBCUCPFunction/gnbcucp:Mdt" {
    list MdtCellProfile {
      description "Additional definitions from MOM:min/max-elements:0/unbounded; MDT profile for cell level. Instance MdtCellProfile=Default is created automatically when parent MO instance is created, unless created manually in same transaction. NRCellCU::mdtCellProfileRef is automatically set to MdtCellProfile=Default instance, unless manually set to refer to another MO instance. Precondition: Instance MdtCellProfile=Default can only be created in same transaction as parent MO instance and cannot be deleted unless parent MO instance is deleted. Other instances can be created and deleted at any time.";
      key "mdtCellProfileId";
      leaf mdtCellProfileId {
        type leafref {
          path "../attributes/mdtCellProfileId";
        }
      }
      container attributes {
      uses MdtCellProfile-attributes;
      }
    }
  }

  augment "/emael:ManagedElement/gnbcucp:GNBCUCPFunction/gnbcucp:Mdt/gnbcucp:MdtCellProfile" {
    list MdtCellProfileUeCfg {
      description "Additional definitions from MOM:min/max-elements:0/32; MDT profile for UE configuration group. Applies to UEs configured for MDT. Instance MdtCellProfileUeCfg=Base is created automatically when parent MO instance is created, unless created manually in same transaction. Precondition: Instance MdtCellProfileUeCfg=Base can only be created in same transaction as parent MO instance and cannot be deleted unless parent MO instance is deleted. Other instances can be created and deleted at any time. Maximum 31 MdtCellProfileUeCfg instances, with RDN different from Base, can be created under parent MO instance.";
      key "mdtCellProfileUeCfgId";
      leaf mdtCellProfileUeCfgId {
        type leafref {
          path "../attributes/mdtCellProfileUeCfgId";
        }
      }
      container attributes {
      uses MdtCellProfileUeCfg-attributes;
      }
    }
  }

  augment "/emael:ManagedElement/gnbcucp:GNBCUCPFunction/gnbcucp:NRCellCU" {
    list AdditionalPLMNInfo {
      description "Additional definitions from MOM:min/max-elements:0/11;systemCreated; PLMN-related Information that can be additionally served by NR cell. Created when F1 interface is set up or configuration is updated by GNBDUFunction. Deleted when configuration is updated by GNBDUFunction. The RDNs of these MOs are AdditionalPLMNInfo=1 to AdditionalPLMNInfo=11. Length of RDN value is up to 2 characters. Instance can be created without a preceding user-initiated transaction.";
      key "additionalPLMNInfoId";
      leaf additionalPLMNInfoId {
        type leafref {
          path "../attributes/additionalPLMNInfoId";
        }
      }
      container attributes {
      uses AdditionalPLMNInfo-attributes;
      }
    }
  }

  augment "/emael:ManagedElement/gnbcucp:GNBCUCPFunction/gnbcucp:NRCellCU" {
    list DESManagementFunction {
      description "Additional definitions from MOM:min/max-elements:0/1; Distributed SON energy saving settings for cell. Instance DESManagementFunction=1 is created automatically when parent MO instance is created, unless created manually in same transaction. The RDN of this MO must be DESManagementFunction=1. Precondition: Instance DESManagementFunction=1 can only be created in same transaction as parent MO instance and cannot be deleted unless parent MO instance is deleted.";
      key "dESManagementFunctionId";
      leaf dESManagementFunctionId {
        type leafref {
          path "../attributes/dESManagementFunctionId";
        }
      }
      container attributes {
      uses DESManagementFunction-attributes;
      }
    }
  }

  augment "/emael:ManagedElement/gnbcucp:GNBCUCPFunction/gnbcucp:NRCellCU" {
    list EUtranCellRelation {
      description "Additional definitions from MOM:min/max-elements:0/128; Handover relationship between NR cell and a neighboring E-UTRAN cell. Can be created by action promoteLwEUtranCellRelation in NRCellCU instance. RDN is the same as for automatically created instance. When created automatically, the RDN of this MO is EUtranCellRelation=auto<ECI>, where ECI = <eNBid>*256 + <cellLocalId>. Length of RDN value is up to 13 characters for automatically created instance. Instance can be created without a preceding user-initiated transaction.";
      key "eUtranCellRelationId";
      leaf eUtranCellRelationId {
        type leafref {
          path "../attributes/eUtranCellRelationId";
        }
      }
      container attributes {
      uses EUtranCellRelation-attributes;
      }
    }
  }

  augment "/emael:ManagedElement/gnbcucp:GNBCUCPFunction/gnbcucp:NRCellCU" {
    list EUtranFreqRelation {
      description "Additional definitions from MOM:min/max-elements:0/16; Mobility relation between NR cell and an E-UTRAN frequency.";
      key "eUtranFreqRelationId";
      leaf eUtranFreqRelationId {
        type leafref {
          path "../attributes/eUtranFreqRelationId";
        }
      }
      container attributes {
      uses EUtranFreqRelation-attributes;
      }
    }
  }

  augment "/emael:ManagedElement/gnbcucp:GNBCUCPFunction/gnbcucp:NRCellCU" {
    list NRCellRelation {
      description "Additional definitions from MOM:min/max-elements:0/512; Handover relationship between NR cell and a neighboring NR cell. This MO is updated or deleted automatically when configuration message over F1, Xn or X2 interface is received, with changed frequency of neighbor cell. If matching NRFreqRelation instance exists, then nRFreqRelationRef is updated. Otherwise, NRCellRelation instance is deleted. See dependencies of nRFreqRelationRef. Can be created by action promoteLwNRCellRelation in NRCellCU instance. RDN is the same as for automatically created instance. When created automatically, the RDN of this MO is NRCellRelation=auto<NCI>, where NCI = <gNBId>*2^(36-<gNBIdLength>) + <cellLocalId>. Length of RDN value is up to 15 characters for automatically created instance. Instance can be created without a preceding user-initiated transaction.";
      key "nRCellRelationId";
      leaf nRCellRelationId {
        type leafref {
          path "../attributes/nRCellRelationId";
        }
      }
      container attributes {
      uses NRCellRelation-attributes;
      }
    }
  }

  augment "/emael:ManagedElement/gnbcucp:GNBCUCPFunction/gnbcucp:NRCellCU" {
    list NRFreqRelation {
      description "Additional definitions from MOM:min/max-elements:0/16; Mobility relation between NR cell and an NR frequency. Must use an NRFrequency on the Global Synchronization Channel Raster (indicated in NRFrequency::gscn) for Standalone operation. Frequency relation not on the GSCN are not included in SIB4, nor used for PCell mobility. Created automatically when F1 or Xn message is received and cell frequency is in frequency range defined in NRFreqRelationTemplate. Can also be created and deleted manually. When created automatically, the RDN of this MO is NRFreqRelation=auto<arfcn>_<scs>. Length of RDN value is up to 15 characters for automatically created instance. Instance can be created without a preceding user-initiated transaction.";
      key "nRFreqRelationId";
      leaf nRFreqRelationId {
        type leafref {
          path "../attributes/nRFreqRelationId";
        }
      }
      container attributes {
      uses NRFreqRelation-attributes;
      }
    }
  }

  augment "/emael:ManagedElement/gnbcucp:GNBCUCPFunction/gnbcucp:NRCellCU" {
    list NRFreqRelationTemplate {
      description "Additional definitions from MOM:min/max-elements:0/4; Frequency range of automatically created or deleted NRFreqRelation instances. Can be used, for example, for CBRS. Contains reference to default NRFreqRelation instance used as template for automatically created NRFreqRelation instances within this range. Note: Only NRFreqRelation instances within this range are automatically deleted. Changing the range or deleting an NRFreqRelationTemplate instance may require manual deletion of NRFreqRelation instances. NRFreqRelationTemplate instances cannot have overlapping nRFrequencyRange values under same NRCellCU instance.";
      key "nRFreqRelationTemplateId";
      leaf nRFreqRelationTemplateId {
        type leafref {
          path "../attributes/nRFreqRelationTemplateId";
        }
      }
      container attributes {
      uses NRFreqRelationTemplate-attributes;
      }
    }
  }

  augment "/emael:ManagedElement/gnbcucp:GNBCUCPFunction/gnbcucp:NRCellCU" {
    list RibTmRelation {
      description "Additional definitions from MOM:min/max-elements:0/unbounded; Radio interface-based time monitoring relation between a monitoring and an assisting NR cell. Created automatically when GNBCUCPFunction::ribTmAutoMax is higher than 0, a suitable NRCellRelation instance exists and there is enough capacity. Runs periodically every 5 minutes. Deleted automatically when GNBCUCPFunction::ribTmAutoMax is set to 0 or number of automatically created RibTmRelation instances exceeded GNBCUCPFunction::ribTmAutoMax limit (after setting new GNBCUCPFunction::ribTmAutoMax). Runs periodically every 5 minutes. Can also be created and deleted manually. When created automatically, the RDN of this MO is RibTmRelation=auto<NCI>, where remote NCI = <gNBId>*2^(36-<gNBIdLength>) + <cellLocalId>. Length of RDN value is up to 15 characters for automatically created instance. Instance can be created without a preceding user-initiated transaction.";
      key "ribTmRelationId";
      leaf ribTmRelationId {
        type leafref {
          path "../attributes/ribTmRelationId";
        }
      }
      container attributes {
      uses RibTmRelation-attributes;
      }
    }
  }

  augment "/emael:ManagedElement/gnbcucp:GNBCUCPFunction/gnbcucp:NRNetwork/gnbcucp:NRFrequency" {
    list NRFrequencyUeCfg {
      description "Additional definitions from MOM:min/max-elements:0/32; NRFrequency parameters for UE groups. Instance NRFrequencyUeCfg=Base is created automatically when parent MO instance is created, unless created manually in same transaction. Attributes prefUeGroupList, ueGroupList and ueConfGroupList must be empty in instance NRFrequencyUeCfg=Base but cannot all be empty in any other instance of NRFrequencyUeCfg under same parent NRFrequency instance. Precondition: Instance NRFrequencyUeCfg=Base can only be created in same transaction as parent MO instance and cannot be deleted unless parent MO instance is deleted. Other instances can be created and deleted at any time. Maximum 31 NRFrequencyUeCfg instances, with RDN different from Base, can be created under parent MO instance.";
      key "nRFrequencyUeCfgId";
      leaf nRFrequencyUeCfgId {
        type leafref {
          path "../attributes/nRFrequencyUeCfgId";
        }
      }
      container attributes {
      uses NRFrequencyUeCfg-attributes;
      }
    }
  }

  augment "/emael:ManagedElement/gnbcucp:GNBCUCPFunction/gnbcucp:NRNetwork" {
    list ExternalGNBCUCPFunction {
      description "Additional definitions from MOM:min/max-elements:0/512; Representation of external gNodeB-CU-CP function. Created automatically when Xn interface is set up, unless it already exists. Deleted automatically. Can also be created and deleted manually. When created automatically, the RDN of this MO is ExternalGNBCUCPFunction=auto<mcc>_<mnc>_<mncLength>_<gNodeBId>. Length of RDN value is up to 24 characters for automatically created instance. Instance can be created without a preceding user-initiated transaction.";
      key "externalGNBCUCPFunctionId";
      leaf externalGNBCUCPFunctionId {
        type leafref {
          path "../attributes/externalGNBCUCPFunctionId";
        }
      }
      container attributes {
      uses ExternalGNBCUCPFunction-attributes;
      }
    }
  }

  augment "/emael:ManagedElement/gnbcucp:GNBCUCPFunction/gnbcucp:NRNetwork" {
    list NRFrequency {
      description "Additional definitions from MOM:min/max-elements:0/64; NRFrequency and related measurement parameters. Created automatically when X2, Xn, or F1 message is received, unless it already exists. Can also be created and deleted manually. The RDN of this MO must be NRFrequency=<arfcnValueNRDl>-<smtcScs>. Length of RDN value is up to 11 characters. Instance can be created without a preceding user-initiated transaction. Example: NRFrequency=630000-30";
      key "nRFrequencyId";
      leaf nRFrequencyId {
        type leafref {
          path "../attributes/nRFrequencyId";
        }
      }
      container attributes {
      uses NRFrequency-attributes;
      }
    }
  }

  augment "/emael:ManagedElement/gnbcucp:GNBCUCPFunction/gnbcucp:Nccm" {
    list NccmUeCfg {
      description "Additional definitions from MOM:min/max-elements:0/32; Neighbor Cell Coverage Measurement UE configuration group. Instance NccmUeCfg=Base is created automatically when parent MO instance is created, unless created manually in same transaction. Each UE configuration group identifier can only be defined in one ueConfGroupList among NccmUeCfg instances under parent Nccm instance. Any combination of one UE group identifier in ueGroupList and one preference UE group identifier in prefUeGroupList must be unique among NccmUeCfg instances under parent Nccm instance. Attributes prefUeGroupList, ueGroupList, and ueConfGroupList must be empty in instance NccmUeCfg=Base but cannot all be empty in any other instance of NccmUeCfg. Only applicable to inter-frequency periodic measurements. Precondition: Instance NccmUeCfg=Base can only be created in same transaction as parent MO instance and cannot be deleted unless parent MO instance is deleted. Other instances can be created and deleted at any time. Maximum 31 NccmUeCfg instances, with RDN different from Base, can be created under parent MO instance.";
      key "nccmUeCfgId";
      leaf nccmUeCfgId {
        type leafref {
          path "../attributes/nccmUeCfgId";
        }
      }
      container attributes {
      uses NccmUeCfg-attributes;
      }
    }
  }

  augment "/emael:ManagedElement/gnbcucp:GNBCUCPFunction/gnbcucp:NrdcControl" {
    list NrdcMnCellProfile {
      description "Additional definitions from MOM:min/max-elements:0/unbounded; NR-NR Dual Connectivity control for PCell in Master Node. Applies to UEs that use the cell as PCell in Master Node. Attributes are used on cell level. Instance NrdcMnCellProfile=Default is created automatically when parent MO instance is created, unless created manually in same transaction. NRCellCU::nrdcMnCellProfileRef is automatically set to NrdcMnCellProfile=Default instance, unless manually set to refer to another MO instance. Precondition: Instance NrdcMnCellProfile=Default can only be created in same transaction as parent MO instance and cannot be deleted unless parent MO instance is deleted. Other instances can be created and deleted at any time.";
      key "nrdcMnCellProfileId";
      leaf nrdcMnCellProfileId {
        type leafref {
          path "../attributes/nrdcMnCellProfileId";
        }
      }
      container attributes {
      uses NrdcMnCellProfile-attributes;
      }
    }
  }

  augment "/emael:ManagedElement/gnbcucp:GNBCUCPFunction/gnbcucp:NrdcControl/gnbcucp:NrdcMnCellProfile" {
    list NrdcMnCellProfileUeCfg {
      description "Additional definitions from MOM:min/max-elements:0/8; NR-NR Dual Connectivity control for PCell in Master Node, UE configuration group. Applies to UEs that use the cell as PCell in Master Node. Attributes are used on cell level. Instance NrdcMnCellProfileUeCfg=Base is created automatically when parent MO instance is created, unless created manually in same transaction. Attributes prefUeGroupList, ueGroupList, and ueConfGroupList must be empty in instance NrdcMnCellProfileUeCfg=Base but cannot all be empty in any other instance of NrdcMnCellProfileUeCfg under same parent NrdcMnCellProfile instance. Only applicable to Low-Band and Mid-Band cells. Precondition: Instance NrdcMnCellProfileUeCfg=Base can only be created in same transaction as parent MO instance and cannot be deleted unless parent MO instance is deleted. Other instances can be created and deleted at any time. Maximum 7 NrdcMnCellProfileUeCfg instances, with RDN different from Base, can be created under parent MO instance.";
      key "nrdcMnCellProfileUeCfgId";
      leaf nrdcMnCellProfileUeCfgId {
        type leafref {
          path "../attributes/nrdcMnCellProfileUeCfgId";
        }
      }
      container attributes {
      uses NrdcMnCellProfileUeCfg-attributes;
      }
    }
  }

  augment "/emael:ManagedElement/gnbcucp:GNBCUCPFunction/gnbcucp:NrdcSnTermination" {
    list NrdcSnTerminationUeCfg {
      description "Additional definitions from MOM:min/max-elements:0/32; UE configuration of Secondary Node termination for NR-DC. Instance NrdcSnTerminationUeCfg=Base is created automatically when parent MO instance is created, unless created manually in same transaction. Attributes prefUeGroupList, ueGroupList and ueConfGroupList must be empty in instance NrdcSnTerminationUeCfg=Base but cannot all be empty in any other instance of NrdcSnTerminationUeCfg under same parent NrdcSnTermination instance. Precondition: Instance NrdcSnTerminationUeCfg=Base can only be created in same transaction as parent MO instance and cannot be deleted unless parent MO instance is deleted. Other instances can be created and deleted at any time. Maximum 31 NrdcSnTerminationUeCfg instances, with RDN different from Base, can be created under parent MO instance.";
      key "nrdcSnTerminationUeCfgId";
      leaf nrdcSnTerminationUeCfgId {
        type leafref {
          path "../attributes/nrdcSnTerminationUeCfgId";
        }
      }
      container attributes {
      uses NrdcSnTerminationUeCfg-attributes;
      }
    }
  }

  augment "/emael:ManagedElement/gnbcucp:GNBCUCPFunction/gnbcucp:TrafficOffload/gnbcucp:OffloadCellProfile" {
    list OffloadCellProfileUeCfg {
      description "Additional definitions from MOM:min/max-elements:0/32; Traffic offload profile, UE configuration group. Attributes are used on cell level. Instance OffloadCellProfileUeCfg=Base is created automatically when parent MO instance is created, unless created manually in same transaction. Attributes prefUeGroupList, ueGroupList and ueConfGroupList must be empty in instance OffloadCellProfileUeCfg=Base but cannot all be empty in any other instance of OffloadCellProfileUeCfg under same parent OffloadCellProfile instance. Precondition: Instance OffloadCellProfileUeCfg=Base can only be created in same transaction as parent MO instance and cannot be deleted unless parent MO instance is deleted. Other instances can be created and deleted at any time. Maximum 31 OffloadCellProfileUeCfg instances, with RDN different from Base, can be created under parent MO instance.";
      key "offloadCellProfileUeCfgId";
      leaf offloadCellProfileUeCfgId {
        type leafref {
          path "../attributes/offloadCellProfileUeCfgId";
        }
      }
      container attributes {
      uses OffloadCellProfileUeCfg-attributes;
      }
    }
  }

  augment "/emael:ManagedElement/gnbcucp:GNBCUCPFunction/gnbcucp:TrafficOffload/gnbcucp:OffloadEUtranFreqRelProfile" {
    list OffloadEUtranFreqRelProfileUeCfg {
      description "Additional definitions from MOM:min/max-elements:0/32; Traffic offload profile, UE configuration group. Attributes are used on NR frequency relation level. Instance OffloadEUtranFreqRelProfileUeCfg=Base is created automatically when parent MO instance is created, unless created manually in same transaction. Attributes prefUeGroupList, ueGroupList and ueConfGroupList must be empty in instance OffloadEUtranFreqRelProfileUeCfg=Base but cannot all be empty in any other instance of OffloadEUtranFreqRelProfileUeCfg under same parent OffloadEUtranFreqRelProfile instance. Precondition: Instance OffloadEUtranFreqRelProfileUeCfg=Base can only be created in same transaction as parent MO instance and cannot be deleted unless parent MO instance is deleted. Other instances can be created and deleted at any time. Maximum 31 OffloadEUtranFreqRelProfileUeCfg instances, with RDN different from Base, can be created under parent MO instance.";
      key "offloadEUtranFreqRelProfileUeCfgId";
      leaf offloadEUtranFreqRelProfileUeCfgId {
        type leafref {
          path "../attributes/offloadEUtranFreqRelProfileUeCfgId";
        }
      }
      container attributes {
      uses OffloadEUtranFreqRelProfileUeCfg-attributes;
      }
    }
  }

  augment "/emael:ManagedElement/gnbcucp:GNBCUCPFunction/gnbcucp:TrafficOffload/gnbcucp:OffloadNrFreqRelProfile" {
    list OffloadNrFreqRelProfileUeCfg {
      description "Additional definitions from MOM:min/max-elements:0/32; Traffic offload profile, UE configuration group. Attributes are used on NR frequency relation level. Instance OffloadNrFreqRelProfileUeCfg=Base is created automatically when parent MO instance is created, unless created manually in same transaction. Attributes prefUeGroupList, ueGroupList and ueConfGroupList must be empty in instance OffloadNrFreqRelProfileUeCfg=Base but cannot all be empty in any other instance of OffloadNrFreqRelProfileUeCfg under same parent OffloadNrFreqRelProfile instance. Precondition: Instance OffloadNrFreqRelProfileUeCfg=Base can only be created in same transaction as parent MO instance and cannot be deleted unless parent MO instance is deleted. Other instances can be created and deleted at any time. Maximum 31 OffloadNrFreqRelProfileUeCfg instances, with RDN different from Base, can be created under parent MO instance.";
      key "offloadNrFreqRelProfileUeCfgId";
      leaf offloadNrFreqRelProfileUeCfgId {
        type leafref {
          path "../attributes/offloadNrFreqRelProfileUeCfgId";
        }
      }
      container attributes {
      uses OffloadNrFreqRelProfileUeCfg-attributes;
      }
    }
  }

  augment "/emael:ManagedElement/gnbcucp:GNBCUCPFunction/gnbcucp:PciHandling/gnbcucp:PciConflictEUtran" {
    list PciConflictEUtranUeCfg {
      description "Additional definitions from MOM:min/max-elements:0/32; UE configuration of E-UTRAN PCI conflict handling functions. Instance PciConflictEUtranUeCfg=Base is created automatically when parent MO instance is created, unless created manually in same transaction. Attributes prefUeGroupList, ueGroupList and ueConfGroupList must be empty in instance PciConflictEUtranUeCfg=Base but cannot all be empty in any other instance of PciConflictEUtranUeCfg under same parent PciConflictEUtran instance. Precondition: Instance PciConflictEUtranUeCfg=Base can only be created in same transaction as parent MO instance and cannot be deleted unless parent MO instance is deleted. Other instances can be created and deleted at any time. Maximum 31 PciConflictEUtranUeCfg instances, with RDN different from Base, can be created under parent MO instance.";
      key "pciConflictEUtranUeCfgId";
      leaf pciConflictEUtranUeCfgId {
        type leafref {
          path "../attributes/pciConflictEUtranUeCfgId";
        }
      }
      container attributes {
      uses PciConflictEUtranUeCfg-attributes;
      }
    }
  }

  augment "/emael:ManagedElement/gnbcucp:GNBCUCPFunction/gnbcucp:PciHandling/gnbcucp:PciConflictNR" {
    list PciConflictNRUeCfg {
      description "Additional definitions from MOM:min/max-elements:0/32; UE configuration of NR PCI conflict handling functions. Instance PciConflictNRUeCfg=Base is created automatically when parent MO instance is created, unless created manually in same transaction. Attributes prefUeGroupList, ueGroupList and ueConfGroupList must be empty in instance PciConflictNRUeCfg=Base but cannot all be empty in any other instance of PciConflictNRUeCfg under same parent PciConflictNR instance. Precondition: Instance PciConflictNRUeCfg=Base can only be created in same transaction as parent MO instance and cannot be deleted unless parent MO instance is deleted. Other instances can be created and deleted at any time. Maximum 31 PciConflictNRUeCfg instances, with RDN different from Base, can be created under parent MO instance.";
      key "pciConflictNRUeCfgId";
      leaf pciConflictNRUeCfgId {
        type leafref {
          path "../attributes/pciConflictNRUeCfgId";
        }
      }
      container attributes {
      uses PciConflictNRUeCfg-attributes;
      }
    }
  }

  augment "/emael:ManagedElement/gnbcucp:GNBCUCPFunction/gnbcucp:PciHandling" {
    list PciConflictEUtran {
      description "Additional definitions from MOM:min/max-elements:0/1; Configuration for finding cells suspicious of PCI conflict and creation of cell relation object. Instance PciConflictEUtran=1 is created automatically when parent MO instance is created, unless created manually in same transaction. The RDN of this MO must be PciConflictEUtran=1. Precondition: Instance PciConflictEUtran=1 can only be created in same transaction as parent MO instance and cannot be deleted unless parent MO instance is deleted.";
      key "pciConflictEUtranId";
      leaf pciConflictEUtranId {
        type leafref {
          path "../attributes/pciConflictEUtranId";
        }
      }
      container attributes {
      uses PciConflictEUtran-attributes;
      }
    }
  }

  augment "/emael:ManagedElement/gnbcucp:GNBCUCPFunction/gnbcucp:PciHandling" {
    list PciConflictNR {
      description "Additional definitions from MOM:min/max-elements:0/1; Configuration for finding cells suspicious of PCI conflict and creation of cell relation object. Instance PciConflictNR=1 is created automatically when parent MO instance is created, unless created manually in same transaction. The RDN of this MO must be PciConflictNR=1. Precondition: Instance PciConflictNR=1 can only be created in same transaction as parent MO instance and cannot be deleted unless parent MO instance is deleted.";
      key "pciConflictNRId";
      leaf pciConflictNRId {
        type leafref {
          path "../attributes/pciConflictNRId";
        }
      }
      container attributes {
      uses PciConflictNR-attributes;
      }
    }
  }

  augment "/emael:ManagedElement/gnbcucp:GNBCUCPFunction/gnbcucp:PeriodicUeMeas" {
    list PuemCellProfile {
      description "Additional definitions from MOM:min/max-elements:0/unbounded; Periodic UE measurement profile for cell level. Instance PuemCellProfile=Default is created automatically when parent MO instance is created, unless created manually in same transaction. NRCellCU::puemCellProfileRef is automatically set to PuemCellProfile=Default instance, unless manually set to refer to another MO instance. Precondition: Instance PuemCellProfile=Default can only be created in same transaction as parent MO instance and cannot be deleted unless parent MO instance is deleted. Other instances can be created and deleted at any time.";
      key "puemCellProfileId";
      leaf puemCellProfileId {
        type leafref {
          path "../attributes/puemCellProfileId";
        }
      }
      container attributes {
      uses PuemCellProfile-attributes;
      }
    }
  }

  augment "/emael:ManagedElement/gnbcucp:GNBCUCPFunction/gnbcucp:PmUeMeas" {
    list PmUeIntraFreqCellProfile {
      description "Additional definitions from MOM:min/max-elements:0/11; Profile for PM intra-frequency UE measurements. Instance PmUeIntraFreqCellProfile=Default is created automatically when parent MO instance is created, unless created manually in same transaction. NRCellCU::pmUeIntraFreqCellProfileRef is automatically set to PmUeIntraFreqCellProfile=Default instance, unless manually set to refer to another MO instance. Precondition: Instance PmUeIntraFreqCellProfile=Default can only be created in same transaction as parent MO instance and cannot be deleted unless parent MO instance is deleted. Other instances can be created and deleted at any time. Maximum 10 PmUeIntraFreqCellProfile instances, with RDN different from Default, can be created under parent MO instance.";
      key "pmUeIntraFreqCellProfileId";
      leaf pmUeIntraFreqCellProfileId {
        type leafref {
          path "../attributes/pmUeIntraFreqCellProfileId";
        }
      }
      container attributes {
      uses PmUeIntraFreqCellProfile-attributes;
      }
    }
  }

  augment "/emael:ManagedElement/gnbcucp:GNBCUCPFunction/gnbcucp:PeriodicUeMeas/gnbcucp:PuemCellProfile" {
    list PuemCellProfileUeCfg {
      description "Additional definitions from MOM:min/max-elements:0/32; Periodic UE measurement profile for UE configuration group. Applies to UEs configured for periodic UE measurement. Instance PuemCellProfileUeCfg=Base is created automatically when parent MO instance is created, unless created manually in same transaction. Attributes prefUeGroupList, ueGroupList and ueConfGroupList must be empty in instance PuemCellProfileUeCfg=Base but cannot all be empty in any other instance of PuemCellProfileUeCfg under same parent PuemCellProfile instance. Precondition: Instance PuemCellProfileUeCfg=Base can only be created in same transaction as parent MO instance and cannot be deleted unless parent MO instance is deleted. Other instances can be created and deleted at any time. Maximum 31 PuemCellProfileUeCfg instances, with RDN different from Base, can be created under parent MO instance.";
      key "puemCellProfileUeCfgId";
      leaf puemCellProfileUeCfgId {
        type leafref {
          path "../attributes/puemCellProfileUeCfgId";
        }
      }
      container attributes {
      uses PuemCellProfileUeCfg-attributes;
      }
    }
  }

  augment "/emael:ManagedElement/gnbcucp:GNBCUCPFunction/gnbcucp:RelaxedRrmMeas" {
    list RelaxedRrmMeasCellProfile {
      description "Additional definitions from MOM:min/max-elements:0/unbounded; Profile for configuration of relaxed RRM measurements.";
      key "relaxedRrmMeasCellProfileId";
      leaf relaxedRrmMeasCellProfileId {
        type leafref {
          path "../attributes/relaxedRrmMeasCellProfileId";
        }
      }
      container attributes {
      uses RelaxedRrmMeasCellProfile-attributes;
      }
    }
  }

  augment "/emael:ManagedElement/gnbcucp:GNBCUCPFunction/gnbcucp:ResourcePartitions/gnbcucp:ResourcePartition" {
    list ResourcePartitionMember {
      description "Additional definitions from MOM:min/max-elements:0/36; Set of member information of resource partition.";
      key "resourcePartitionMemberId";
      leaf resourcePartitionMemberId {
        type leafref {
          path "../attributes/resourcePartitionMemberId";
        }
      }
      container attributes {
      uses ResourcePartitionMember-attributes;
      }
    }
  }

  augment "/emael:ManagedElement/gnbcucp:GNBCUCPFunction/gnbcucp:ResourcePartitions" {
    list ResourcePartition {
      description "Additional definitions from MOM:min/max-elements:0/36; Combination of attributes specifying in which resource partition a UE is included.";
      key "resourcePartitionId";
      leaf resourcePartitionId {
        type leafref {
          path "../attributes/resourcePartitionId";
        }
      }
      container attributes {
      uses ResourcePartition-attributes;
      }
    }
  }

  augment "/emael:ManagedElement/gnbcucp:GNBCUCPFunction/gnbcucp:UeCC/gnbcucp:Rohc" {
    list RohcUeCfg {
      description "Additional definitions from MOM:min/max-elements:0/8; Configuration of Robust Header Compression feature for UE groups. Instance RohcUeCfg=Base is created automatically when parent MO instance is created, unless created manually in same transaction. Each UE configuration group identifier can only be defined in one ueConfGroupList among RohcUeCfg instances contained under parent Rohc instance. Any combination of one UE group identifier in ueGroupList and one preference UE group identifier in prefUeGroupList must be unique among RohcUeCfg instances contained under parent Rohc instance. Attributes prefUeGroupList, ueGroupList, and ueConfGroupList must be empty in instance RohcUeCfg=Base but cannot all be empty in any other instance of RohcUeCfg. Precondition: Instance RohcUeCfg=Base can only be created in same transaction as parent MO instance and cannot be deleted unless parent MO instance is deleted. Other instances can be created and deleted at any time. Maximum 7 RohcUeCfg instances, with RDN different from Base, can be created under parent MO instance.";
      key "rohcUeCfgId";
      leaf rohcUeCfgId {
        type leafref {
          path "../attributes/rohcUeCfgId";
        }
      }
      container attributes {
      uses RohcUeCfg-attributes;
      }
    }
  }

  augment "/emael:ManagedElement/gnbcucp:GNBCUCPFunction/gnbcucp:UeCC/gnbcucp:Rrc" {
    list RrcUeCfg {
      description "Additional definitions from MOM:min/max-elements:0/8; Configuration of RRC UE groups. Instance RrcUeCfg=Base is created automatically when parent MO instance is created, unless created manually in same transaction. Attributes prefUeGroupList, ueGroupList and ueConfGroupList must be empty in instance RrcUeCfg=Base but cannot all be empty in any other instance of RrcUeCfg under same parent RrcInactiveProfile instance. Precondition: Instance RrcUeCfg=Base can only be created in same transaction as parent MO instance and cannot be deleted unless parent MO instance is deleted. Other instances can be created and deleted at any time. Maximum 7 RrcUeCfg instances, with RDN different from Base, can be created under parent MO instance.";
      key "rrcUeCfgId";
      leaf rrcUeCfgId {
        type leafref {
          path "../attributes/rrcUeCfgId";
        }
      }
      container attributes {
      uses RrcUeCfg-attributes;
      }
    }
  }

  augment "/emael:ManagedElement/gnbcucp:GNBCUCPFunction/gnbcucp:UeCC/gnbcucp:RrcInactiveProfile" {
    list RrcInactiveProfileUeCfg {
      description "Additional definitions from MOM:min/max-elements:0/8; Configuration of RRC inactive profile for UE groups. Instance RrcInactiveProfileUeCfg=Base is created automatically when parent MO instance is created, unless created manually in same transaction. Attributes prefUeGroupList, ueGroupList and ueConfGroupList must be empty in instance RrcInactiveProfileUeCfg=Base but cannot all be empty in any other instance of RrcInactiveProfileUeCfg under same parent RrcInactiveProfile instance. Precondition: Instance RrcInactiveProfileUeCfg=Base can only be created in same transaction as parent MO instance and cannot be deleted unless parent MO instance is deleted. Other instances can be created and deleted at any time. Maximum 7 RrcInactiveProfileUeCfg instances, with RDN different from Base, can be created under parent MO instance.";
      key "rrcInactiveProfileUeCfgId";
      leaf rrcInactiveProfileUeCfgId {
        type leafref {
          path "../attributes/rrcInactiveProfileUeCfgId";
        }
      }
      container attributes {
      uses RrcInactiveProfileUeCfg-attributes;
      }
    }
  }

  augment "/emael:ManagedElement/gnbcucp:GNBCUCPFunction/gnbcucp:TermPointToAmf" {
    list TnlAssociation {
      description "Additional definitions from MOM:min/max-elements:0/32;systemCreated; Transport Network Layer association between gNodeB and AMF. Created when new SCTP association is successfully established between gNodeB and AMF. Deleted when SCTP association removal is ordered by AMF or when NG-C connection between gNodeB and AMF is released. The RDN of this MO is TnlAssociation=[Remote Port]_[Remote IP]. Example: TnlAssociation=38412_2001:0db8:85a3:0000:0000:8a2e:0370:7334. Length of RDN value is up to 45 characters. Instance can be created without a preceding user-initiated transaction.";
      key "tnlAssociationId";
      leaf tnlAssociationId {
        type leafref {
          path "../attributes/tnlAssociationId";
        }
      }
      container attributes {
      uses TnlAssociation-attributes;
      }
    }
  }

  augment "/emael:ManagedElement/gnbcucp:GNBCUCPFunction/gnbcucp:TimeSchedulingGroup" {
    list TimeSchedulingWindow {
      description "Additional definitions from MOM:min/max-elements:0/30; Configuration of time scheduling window. In addition to time scheduling configuration, it also includes a reference to EpBoosterCellProfile instance for cell sleep configuration.";
      key "timeSchedulingWindowId";
      leaf timeSchedulingWindowId {
        type leafref {
          path "../attributes/timeSchedulingWindowId";
        }
      }
      container attributes {
      uses TimeSchedulingWindow-attributes;
      }
    }
  }

  augment "/emael:ManagedElement/gnbcucp:GNBCUCPFunction/gnbcucp:TrafficSteering/gnbcucp:TrStPSCellNrFreqRelProfile" {
    list TrStPSCellNrFreqRelProfileUeCfg {
      description "Additional definitions from MOM:min/max-elements:0/32; Traffic steering function for PSCell in NR EN-DC, UE configuration group. Applicable to UEs that use this cell as PSCell in NR EN-DC. Attributes are used on NR frequency relation level. Instance TrStPSCellNrFreqRelProfileUeCfg=Base is created automatically when parent MO instance is created, unless created manually in same transaction. Attributes prefUeGroupList, ueGroupList and ueConfGroupList must be empty in instance TrStPSCellNrFreqRelProfileUeCfg=Base but cannot all be empty in any other instance of TrStPSCellNrFreqRelProfileUeCfg under same parent TrStPSCellNrFreqRelProfile instance. Precondition: Instance TrStPSCellNrFreqRelProfileUeCfg=Base can only be created in same transaction as parent MO instance and cannot be deleted unless parent MO instance is deleted. Other instances can be created and deleted at any time. Maximum 31 TrStPSCellNrFreqRelProfileUeCfg instances, with RDN different from Base, can be created under parent MO instance.";
      key "trStPSCellNrFreqRelProfileUeCfgId";
      leaf trStPSCellNrFreqRelProfileUeCfgId {
        type leafref {
          path "../attributes/trStPSCellNrFreqRelProfileUeCfgId";
        }
      }
      container attributes {
      uses TrStPSCellNrFreqRelProfileUeCfg-attributes;
      }
    }
  }

  augment "/emael:ManagedElement/gnbcucp:GNBCUCPFunction/gnbcucp:TrafficSteering/gnbcucp:TrStPSCellProfile" {
    list TrStPSCellProfileUeCfg {
      description "Additional definitions from MOM:min/max-elements:0/32; Traffic steering function for PSCell in EN-DC, UE configuration group. Applies to UEs that use this cell as PSCell in EN-DC. Attributes are used on cell level. Instance TrStPSCellProfileUeCfg=Base is created automatically when parent MO instance is created, unless created manually in same transaction. Attributes prefUeGroupList, ueGroupList and ueConfGroupList must be empty in instance TrStPSCellProfileUeCfg=Base but cannot all be empty in any other instance of TrStPSCellProfileUeCfg under same parent TrStPSCellProfile instance. Precondition: Instance TrStPSCellProfileUeCfg=Base can only be created in same transaction as parent MO instance and cannot be deleted unless parent MO instance is deleted. Other instances can be created and deleted at any time. Maximum 31 TrStPSCellProfileUeCfg instances, with RDN different from Base, can be created under parent MO instance.";
      key "trStPSCellProfileUeCfgId";
      leaf trStPSCellProfileUeCfgId {
        type leafref {
          path "../attributes/trStPSCellProfileUeCfgId";
        }
      }
      container attributes {
      uses TrStPSCellProfileUeCfg-attributes;
      }
    }
  }

  augment "/emael:ManagedElement/gnbcucp:GNBCUCPFunction/gnbcucp:TrafficSteering/gnbcucp:TrStSaCellProfile" {
    list TrStSaCellProfileUeCfg {
      description "Additional definitions from MOM:min/max-elements:0/32; Traffic steering function for PCell and SCells in NR Standalone, UE configuration group. Applicable to UEs that use this cell as PCell in NR Standalone. Attributes are used on cell level. Instance TrStSaCellProfileUeCfg=Base is created automatically when parent MO instance is created, unless created manually in same transaction. Attributes prefUeGroupList, ueGroupList and ueConfGroupList must be empty in instance TrStSaCellProfileUeCfg=Base but cannot all be empty in any other instance of TrStSaCellProfileUeCfg under same parent TrStSaCellProfile instance. Precondition: Instance TrStSaCellProfileUeCfg=Base can only be created in same transaction as parent MO instance and cannot be deleted unless parent MO instance is deleted. Other instances can be created and deleted at any time. Maximum 31 TrStSaCellProfileUeCfg instances, with RDN different from Base, can be created under parent MO instance.";
      key "trStSaCellProfileUeCfgId";
      leaf trStSaCellProfileUeCfgId {
        type leafref {
          path "../attributes/trStSaCellProfileUeCfgId";
        }
      }
      container attributes {
      uses TrStSaCellProfileUeCfg-attributes;
      }
    }
  }

  augment "/emael:ManagedElement/gnbcucp:GNBCUCPFunction/gnbcucp:TrafficSteering/gnbcucp:TrStSaEUtranFreqRelProfile" {
    list TrStSaEUtranFreqRelProfileUeCfg {
      description "Additional definitions from MOM:min/max-elements:0/32; Traffic steering function for PCell NR Standalone, UE configuration group. Applicable to UEs that use this cell as PCell in NR Standalone. Attributes are used on E-UTRAN frequency relation level. Instance TrStSaEUtranFreqRelProfileUeCfg=Base is created automatically when parent MO instance is created, unless created manually in same transaction. Attributes prefUeGroupList, ueGroupList and ueConfGroupList must be empty in instance TrStSaEUtranFreqRelProfileUeCfg=Base but cannot all be empty in any other instance of TrStSaEUtranFreqRelProfileUeCfg under same parent TrStSaEUtranFreqRelProfile instance. Precondition: Instance TrStSaEUtranFreqRelProfileUeCfg=Base can only be created in same transaction as parent MO instance and cannot be deleted unless parent MO instance is deleted. Other instances can be created and deleted at any time. Maximum 31 TrStSaEUtranFreqRelProfileUeCfg instances, with RDN different from Base, can be created under parent MO instance.";
      key "trStSaEUtranFreqRelProfileUeCfgId";
      leaf trStSaEUtranFreqRelProfileUeCfgId {
        type leafref {
          path "../attributes/trStSaEUtranFreqRelProfileUeCfgId";
        }
      }
      container attributes {
      uses TrStSaEUtranFreqRelProfileUeCfg-attributes;
      }
    }
  }

  augment "/emael:ManagedElement/gnbcucp:GNBCUCPFunction/gnbcucp:TrafficSteering/gnbcucp:TrStSaNrFreqRelProfile" {
    list TrStSaNrFreqRelProfileUeCfg {
      description "Additional definitions from MOM:min/max-elements:0/32; Traffic steering function for PCell and SCells in NR Standalone, UE configuration group. Applicable to UEs that use this cell as PCell in NR Standalone. Attributes are used on NR frequency relation level. Instance TrStSaNrFreqRelProfileUeCfg=Base is created automatically when parent MO instance is created, unless created manually in same transaction. Attributes prefUeGroupList, ueGroupList and ueConfGroupList must be empty in instance TrStSaNrFreqRelProfileUeCfg=Base but cannot all be empty in any other instance of TrStSaNrFreqRelProfileUeCfg under same parent TrStSaNrFreqRelProfile instance. Precondition: Instance TrStSaNrFreqRelProfileUeCfg=Base can only be created in same transaction as parent MO instance and cannot be deleted unless parent MO instance is deleted. Other instances can be created and deleted at any time. Maximum 31 TrStSaNrFreqRelProfileUeCfg instances, with RDN different from Base, can be created under parent MO instance.";
      key "trStSaNrFreqRelProfileUeCfgId";
      leaf trStSaNrFreqRelProfileUeCfgId {
        type leafref {
          path "../attributes/trStSaNrFreqRelProfileUeCfgId";
        }
      }
      container attributes {
      uses TrStSaNrFreqRelProfileUeCfg-attributes;
      }
    }
  }

  augment "/emael:ManagedElement/gnbcucp:GNBCUCPFunction/gnbcucp:TrafficOffload" {
    list OffloadCellProfile {
      description "Additional definitions from MOM:min/max-elements:0/unbounded; Traffic offload profile. Attributes are used on cell level. Instance OffloadCellProfile=Default is created automatically when parent MO instance is created, unless created manually in same transaction. NRCellCU::offloadCellProfileRef is automatically set to OffloadCellProfile=Default instance, unless manually set to refer to another MO instance. Precondition: Instance OffloadCellProfile=Default can only be created in same transaction as parent MO instance and cannot be deleted unless parent MO instance is deleted. Other instances can be created and deleted at any time.";
      key "offloadCellProfileId";
      leaf offloadCellProfileId {
        type leafref {
          path "../attributes/offloadCellProfileId";
        }
      }
      container attributes {
      uses OffloadCellProfile-attributes;
      }
    }
  }

  augment "/emael:ManagedElement/gnbcucp:GNBCUCPFunction/gnbcucp:TrafficOffload" {
    list OffloadEUtranFreqRelProfile {
      description "Additional definitions from MOM:min/max-elements:0/unbounded; Traffic offload profile. Attributes are used on EUtran frequency relation level. Instance OffloadEUtranFreqRelProfile=Default is created automatically when parent MO instance is created, unless created manually in same transaction. EUtranFreqRelation::offloadEUtranFreqRelProfileRef is automatically set to OffloadEUtranFreqRelProfile=Default instance, unless manually set to refer to another MO instance. Precondition: Instance OffloadEUtranFreqRelProfile=Default can only be created in same transaction as parent MO instance and cannot be deleted unless parent MO instance is deleted. Other instances can be created and deleted at any time.";
      key "offloadEUtranFreqRelProfileId";
      leaf offloadEUtranFreqRelProfileId {
        type leafref {
          path "../attributes/offloadEUtranFreqRelProfileId";
        }
      }
      container attributes {
      uses OffloadEUtranFreqRelProfile-attributes;
      }
    }
  }

  augment "/emael:ManagedElement/gnbcucp:GNBCUCPFunction/gnbcucp:TrafficOffload" {
    list OffloadNrFreqRelProfile {
      description "Additional definitions from MOM:min/max-elements:0/unbounded; Traffic offload profile. Attributes are used on NR frequency relation level. Instance OffloadNrFreqRelProfile=Default is created automatically when parent MO instance is created, unless created manually in same transaction. NRFreqRelation::offloadNrFreqRelProfileRef is automatically set to OffloadNrFreqRelProfile=Default instance, unless manually set to refer to another MO instance. Precondition: Instance OffloadNrFreqRelProfile=Default can only be created in same transaction as parent MO instance and cannot be deleted unless parent MO instance is deleted. Other instances can be created and deleted at any time.";
      key "offloadNrFreqRelProfileId";
      leaf offloadNrFreqRelProfileId {
        type leafref {
          path "../attributes/offloadNrFreqRelProfileId";
        }
      }
      container attributes {
      uses OffloadNrFreqRelProfile-attributes;
      }
    }
  }

  augment "/emael:ManagedElement/gnbcucp:GNBCUCPFunction/gnbcucp:TrafficSteering" {
    list TrStPSCellNrFreqRelProfile {
      description "Additional definitions from MOM:min/max-elements:0/unbounded; Traffic steering function for PSCell in NR EN-DC. Applicable to UEs that use this cell as PSCell in NR EN-DC. Attributes are used on NR frequency relation level. Instance TrStPSCellNrFreqRelProfile=Default is created automatically when parent MO instance is created, unless created manually in same transaction. NRFreqRelation::trStPSCellNrFreqRelProfileRef is automatically set to TrStPSCellNrFreqRelProfile=Default instance, unless manually set to refer to another MO instance. Precondition: Instance TrStPSCellNrFreqRelProfile=Default can only be created in same transaction as parent MO instance and cannot be deleted unless parent MO instance is deleted. Other instances can be created and deleted at any time.";
      key "trStPSCellNrFreqRelProfileId";
      leaf trStPSCellNrFreqRelProfileId {
        type leafref {
          path "../attributes/trStPSCellNrFreqRelProfileId";
        }
      }
      container attributes {
      uses TrStPSCellNrFreqRelProfile-attributes;
      }
    }
  }

  augment "/emael:ManagedElement/gnbcucp:GNBCUCPFunction/gnbcucp:TrafficSteering" {
    list TrStPSCellProfile {
      description "Additional definitions from MOM:min/max-elements:0/unbounded; Traffic steering function for PSCell in EN-DC. Applies to UEs that use this cell as PSCell in EN-DC. Attributes are used on cell level. Instance TrStPSCellProfile=Default is created automatically when parent MO instance is created, unless created manually in same transaction. NRCellCU::trStPSCellProfileRef is automatically set to TrStPSCellProfile=Default instance, unless manually set to refer to another MO instance. Precondition: Instance TrStPSCellProfile=Default can only be created in same transaction as parent MO instance and cannot be deleted unless parent MO instance is deleted. Other instances can be created and deleted at any time.";
      key "trStPSCellProfileId";
      leaf trStPSCellProfileId {
        type leafref {
          path "../attributes/trStPSCellProfileId";
        }
      }
      container attributes {
      uses TrStPSCellProfile-attributes;
      }
    }
  }

  augment "/emael:ManagedElement/gnbcucp:GNBCUCPFunction/gnbcucp:TrafficSteering" {
    list TrStSaCellProfile {
      description "Additional definitions from MOM:min/max-elements:0/unbounded; Traffic steering function for PCell and SCells in NR Standalone. Applicable to UEs that use this cell as PCell in NR Standalone. Attributes are used on cell level. Instance TrStSaCellProfile=Default is created automatically when parent MO instance is created, unless created manually in same transaction. NRCellCU::trStSaCellProfileRef is automatically set to TrStSaCellProfile=Default instance, unless manually set to refer to another MO instance. Precondition: Instance TrStSaCellProfile=Default can only be created in same transaction as parent MO instance and cannot be deleted unless parent MO instance is deleted. Other instances can be created and deleted at any time.";
      key "trStSaCellProfileId";
      leaf trStSaCellProfileId {
        type leafref {
          path "../attributes/trStSaCellProfileId";
        }
      }
      container attributes {
      uses TrStSaCellProfile-attributes;
      }
    }
  }

  augment "/emael:ManagedElement/gnbcucp:GNBCUCPFunction/gnbcucp:TrafficSteering" {
    list TrStSaEUtranFreqRelProfile {
      description "Additional definitions from MOM:min/max-elements:0/unbounded; Traffic steering function for PCell in NR Standalone. Applicable to UEs that use this cell as PCell in NR Standalone. Attributes are used on E-UTRAN frequency relation level. Instance TrStSaEUtranFreqRelProfile=Default is created automatically when parent MO instance is created, unless created manually in same transaction. EUtranFreqRelation::trStSaEUtranFreqRelProfileRef is automatically set to TrStSaEUtranFreqRelProfile=Default instance, unless manually set to refer to another MO instance. Precondition: Instance TrStSaEUtranFreqRelProfile=Default can only be created in same transaction as parent MO instance and cannot be deleted unless parent MO instance is deleted. Other instances can be created and deleted at any time.";
      key "trStSaEUtranFreqRelProfileId";
      leaf trStSaEUtranFreqRelProfileId {
        type leafref {
          path "../attributes/trStSaEUtranFreqRelProfileId";
        }
      }
      container attributes {
      uses TrStSaEUtranFreqRelProfile-attributes;
      }
    }
  }

  augment "/emael:ManagedElement/gnbcucp:GNBCUCPFunction/gnbcucp:TrafficSteering" {
    list TrStSaNrFreqRelProfile {
      description "Additional definitions from MOM:min/max-elements:0/unbounded; Traffic steering function for PCell and SCells in NR Standalone. Applicable to UEs that use this cell as PCell in NR Standalone. Attributes are used on NR frequency relation level. Instance TrStSaNrFreqRelProfile=Default is created automatically when parent MO instance is created, unless created manually in same transaction. NRFreqRelation::trStSaNrFreqRelProfileRef is automatically set to TrStSaNrFreqRelProfile=Default instance, unless manually set to refer to another MO instance. Precondition: Instance TrStSaNrFreqRelProfile=Default can only be created in same transaction as parent MO instance and cannot be deleted unless parent MO instance is deleted. Other instances can be created and deleted at any time.";
      key "trStSaNrFreqRelProfileId";
      leaf trStSaNrFreqRelProfileId {
        type leafref {
          path "../attributes/trStSaNrFreqRelProfileId";
        }
      }
      container attributes {
      uses TrStSaNrFreqRelProfile-attributes;
      }
    }
  }

  augment "/emael:ManagedElement/gnbcucp:GNBCUCPFunction/gnbcucp:AdmissionControl/gnbcucp:Uac" {
    list UacProfile {
      description "Additional definitions from MOM:min/max-elements:0/12; Configuration profile for NR Unified Access Control. Instance UacProfile=Default is created automatically when parent MO instance is created, unless created manually in same transaction. NRCellCU::uacProfileRef is automatically set to UacProfile=Default instance, unless manually set to refer to another MO instance. Precondition: Instance UacProfile=Default can only be created in same transaction as parent MO instance and cannot be deleted unless parent MO instance is deleted. Other instances can be created and deleted at any time. Maximum 11 UacProfile instances, with RDN different from Default, can be created under parent MO instance.";
      key "uacProfileId";
      leaf uacProfileId {
        type leafref {
          path "../attributes/uacProfileId";
        }
      }
      container attributes {
      uses UacProfile-attributes;
      }
    }
  }

  augment "/emael:ManagedElement/gnbcucp:GNBCUCPFunction/gnbcucp:AdmissionControl/gnbcucp:Uac/gnbcucp:UacProfile" {
    list BarringGroup {
      description "Additional definitions from MOM:min/max-elements:0/8; Thresholds and parameters for barring group used by NR Unified Access Control. Default values for attributes in this MO are set so that barring triggered by unified access is not sent out in SIB1. Instance BarringGroup=Default is created automatically when parent MO instance is created, unless created manually in same transaction. Precondition: Instance BarringGroup=Default can only be created in same transaction as parent MO instance and cannot be deleted unless parent MO instance is deleted. Other instances can be created and deleted at any time. Maximum 7 BarringGroup instances, with RDN different from Default, can be created under parent MO instance.";
      key "barringGroupId";
      leaf barringGroupId {
        type leafref {
          path "../attributes/barringGroupId";
        }
      }
      container attributes {
      uses BarringGroup-attributes;
      }
    }
  }

  augment "/emael:ManagedElement/gnbcucp:GNBCUCPFunction/gnbcucp:UeCC/gnbcucp:UaiProfile" {
    list UaiProfileUeCfg {
      description "Additional definitions from MOM:min/max-elements:0/8; Configuration of UE Assistance Information profile for UE groups. Instance UaiProfileUeCfg=Base is created automatically when parent MO instance is created, unless created manually in same transaction. Attributes prefUeGroupList, ueGroupList and ueConfGroupList must be empty in instance UaiProfileUeCfg=Base but cannot all be empty in any other instance of UaiProfileUeCfg. Precondition: Instance UaiProfileUeCfg=Base can only be created in same transaction as parent MO instance and cannot be deleted unless parent MO instance is deleted. Other instances can be created and deleted at any time. Maximum 7 UaiProfileUeCfg instances, with RDN different from Base, can be created under parent MO instance.";
      key "uaiProfileUeCfgId";
      leaf uaiProfileUeCfgId {
        type leafref {
          path "../attributes/uaiProfileUeCfgId";
        }
      }
      container attributes {
      uses UaiProfileUeCfg-attributes;
      }
    }
  }

  augment "/emael:ManagedElement/gnbcucp:GNBCUCPFunction/gnbcucp:UeCovMeas/gnbcucp:UcmCellProfile" {
    list UcmCellProfileUeCfg {
      description "Additional definitions from MOM:min/max-elements:0/32; UE coverage measurement configuration group. Instance UcmCellProfileUeCfg=Base is created automatically when parent MO instance is created, unless created manually in same transaction. Each UE configuration group identifier can only be defined in one ueConfGroupList among UcmCellProfileUeCfg instances under parent UcmCellProfile instance. Any combination of one UE group identifier in ueGroupList attribute and one preference UE group identifier in prefUeGroupList must be unique among UcmCellProfileUeCfg instances under parent UcmCellProfile instance. Attributes prefUeGroupList, ueGroupList, and ueConfGroupList must be empty in instance UcmCellProfileUeCfg=Base but cannot all be empty in any other instance of UcmCellProfileUeCfg under same parent UcmCellProfile instance. NRCellCU::ucmCellProfileRef is automatically set to UcmCellProfile=Default instance, unless manually set to refer to another MO instance. Precondition: Instance UcmCellProfileUeCfg=Base can only be created in same transaction as parent MO instance and cannot be deleted unless parent MO instance is deleted. Other instances can be created and deleted at any time. Maximum 31 UcmCellProfileUeCfg instances, with RDN different from Base, can be created under parent MO instance.";
      key "ucmCellProfileUeCfgId";
      leaf ucmCellProfileUeCfgId {
        type leafref {
          path "../attributes/ucmCellProfileUeCfgId";
        }
      }
      container attributes {
      uses UcmCellProfileUeCfg-attributes;
      }
    }
  }

  augment "/emael:ManagedElement/gnbcucp:GNBCUCPFunction/gnbcucp:UeCC" {
    list CapabilityHandling {
      description "Additional definitions from MOM:min/max-elements:0/1; This is a container for Capability Handling UE Configurations. Instance CapabilityHandling=1 is created automatically when parent MO instance is created, unless created manually in same transaction. The RDN of this MO must be CapabilityHandling=1. Precondition: Instance CapabilityHandling=1 can only be created in same transaction as parent MO instance and cannot be deleted unless parent MO instance is deleted.";
      key "capabilityHandlingId";
      leaf capabilityHandlingId {
        type leafref {
          path "../attributes/capabilityHandlingId";
        }
      }
      container attributes {
      uses CapabilityHandling-attributes;
      }
    }
  }

  augment "/emael:ManagedElement/gnbcucp:GNBCUCPFunction/gnbcucp:UeCC" {
    list InactivityProfile {
      description "Additional definitions from MOM:min/max-elements:0/1; Inactivity profile used for current UE. Instance InactivityProfile=Default is created automatically when parent MO instance is created, unless created manually in same transaction. Precondition: Instance InactivityProfile=Default can only be created in same transaction as parent MO instance and cannot be deleted unless parent MO instance is deleted.";
      key "inactivityProfileId";
      leaf inactivityProfileId {
        type leafref {
          path "../attributes/inactivityProfileId";
        }
      }
      container attributes {
      uses InactivityProfile-attributes;
      }
    }
  }

  augment "/emael:ManagedElement/gnbcucp:GNBCUCPFunction/gnbcucp:UeCC" {
    list InitialCg {
      description "Additional definitions from MOM:min/max-elements:0/8; Initial cell group profile. Instance InitialCg=Default is created automatically when parent MO instance is created, unless created manually in same transaction. NRCellCU::endcInitialCgRef and NRCellCU::nrdcInitialCgRef are automatically set to InitialCg=Default instance, unless manually set to refer to another MO instance. Precondition: Instance InitialCg=Default can only be created in same transaction as parent MO instance and cannot be deleted unless parent MO instance is deleted. Other instances can be created and deleted at any time. Maximum 7 InitialCg instance, with RDN different from Default, can be created under parent MO instance.";
      key "initialCgId";
      leaf initialCgId {
        type leafref {
          path "../attributes/initialCgId";
        }
      }
      container attributes {
      uses InitialCg-attributes;
      }
    }
  }

  augment "/emael:ManagedElement/gnbcucp:GNBCUCPFunction/gnbcucp:UeCC" {
    list Rohc {
      description "Additional definitions from MOM:min/max-elements:0/1; Container class for ROHC configuration classes. Instance Rohc=1 is created automatically when parent MO instance is created, unless created manually in same transaction. The RDN of this MO must be Rohc=1. Precondition: Instance Rohc=1 can only be created in same transaction as parent MO instance and cannot be deleted unless parent MO instance is deleted.";
      key "rohcId";
      leaf rohcId {
        type leafref {
          path "../attributes/rohcId";
        }
      }
      container attributes {
      uses Rohc-attributes;
      }
    }
  }

  augment "/emael:ManagedElement/gnbcucp:GNBCUCPFunction/gnbcucp:UeCC" {
    list Rrc {
      description "Additional definitions from MOM:min/max-elements:0/1; Container class for RRC UE configuration classes. Instance Rrc=1 is created automatically when parent MO instance is created, unless created manually in same transaction. The RDN of this MO must be Rrc=1. Precondition: Instance Rrc=1 can only be created in same transaction as parent MO instance and cannot be deleted unless parent MO instance is deleted.";
      key "rrcId";
      leaf rrcId {
        type leafref {
          path "../attributes/rrcId";
        }
      }
      container attributes {
      uses Rrc-attributes;
      }
    }
  }

  augment "/emael:ManagedElement/gnbcucp:GNBCUCPFunction/gnbcucp:UeCC" {
    list RrcInactiveProfile {
      description "Additional definitions from MOM:min/max-elements:0/1; RRC inactive profile used for current UE. Instance RrcInactiveProfile=Default is created automatically when parent MO instance is created, unless created manually in same transaction. The RDN of this MO must be RrcInactiveProfile=Default. Precondition: Instance RrcInactiveProfile=Default can only be created in same transaction as parent MO instance and cannot be deleted unless parent MO instance is deleted.";
      key "rrcInactiveProfileId";
      leaf rrcInactiveProfileId {
        type leafref {
          path "../attributes/rrcInactiveProfileId";
        }
      }
      container attributes {
      uses RrcInactiveProfile-attributes;
      }
    }
  }

  augment "/emael:ManagedElement/gnbcucp:GNBCUCPFunction/gnbcucp:UeCC" {
    list UaiProfile {
      description "Additional definitions from MOM:min/max-elements:0/1; UE Assistance Information profile for current UE. Instance UaiProfile=Default is created automatically when parent MO instance is created, unless created manually in same transaction. The RDN of this MO must be UaiProfile=Default. Precondition: Instance UaiProfile=Default can only be created in same transaction as parent MO instance and cannot be deleted unless parent MO instance is deleted.";
      key "uaiProfileId";
      leaf uaiProfileId {
        type leafref {
          path "../attributes/uaiProfileId";
        }
      }
      container attributes {
      uses UaiProfile-attributes;
      }
    }
  }

  augment "/emael:ManagedElement/gnbcucp:GNBCUCPFunction/gnbcucp:UeCC" {
    list UlDataSplit {
      description "Additional definitions from MOM:min/max-elements:0/8; Uplink PDCP data split profile. Instances UlDataSplit=Default_endc and UlDataSplit=Default_nrdc are created automatically when parent MO instance is created, unless created manually in same transaction. CUCP5qi::endcUlDataSplitRef is automatically set to UlDataSplit=Default_endc instance, unless manually set to refer to another MO instance. CUCP5qi::nrdcUlDataSplitRef is automatically set to UlDataSplit=Default_nrdc instance, unless manually set to refer to another MO instance. UlDataSplit=Default_endc and UlDataSplit=Default_nrdc instances are used for DRBs when CUCP5qi instance with matching profile5qi does not exist or feature Service-Adaptive Uplink User Plane Profile is deactivated. Precondition: Instances UlDataSplit=Default_endc and UlDataSplit=Default_nrdc can only be created in same transaction as parent MO instance and cannot be deleted unless parent MO instance is deleted. Other instances can be created and deleted at any time. Maximum 6 UlDataSplit instances, with RDN different from Default_endc and Default_nrdc, can be created under parent MO instance.";
      key "ulDataSplitId";
      leaf ulDataSplitId {
        type leafref {
          path "../attributes/ulDataSplitId";
        }
      }
      container attributes {
      uses UlDataSplit-attributes;
      }
    }
  }

  augment "/emael:ManagedElement/gnbcucp:GNBCUCPFunction/gnbcucp:UeCovMeas" {
    list UcmCellProfile {
      description "Additional definitions from MOM:min/max-elements:0/unbounded; UE coverage measurement profile for cell level. Instance UcmCellProfile=Default is created automatically when parent MO instance is created, unless created manually in same transaction. Precondition: Instance UcmCellProfile=Default can only be created in same transaction as parent MO instance and cannot be deleted unless parent MO instance is deleted. Other instances can be created and deleted at any time.";
      key "ucmCellProfileId";
      leaf ucmCellProfileId {
        type leafref {
          path "../attributes/ucmCellProfileId";
        }
      }
      container attributes {
      uses UcmCellProfile-attributes;
      }
    }
  }

  augment "/emael:ManagedElement/gnbcucp:GNBCUCPFunction/gnbcucp:UeCovMeas" {
    list UcmEUtranFreqRelProfile {
      description "Additional definitions from MOM:min/max-elements:0/unbounded; UE coverage measurement attributes used on frequency relation level. Instance UcmEUtranFreqRelProfile=Default is created automatically when parent MO instance is created, unless created manually in same transaction. EUtranFreqRelation::ucmEUtranFreqRelProfileRef is automatically set to UcmEUtranFreqRelProfile=Default instance, unless manually set to refer to another MO instance. Precondition: Instance UcmEUtranFreqRelProfile=Default can only be created in same transaction as parent MO instance and cannot be deleted unless parent MO instance is deleted. Other instances can be created and deleted at any time.";
      key "ucmEUtranFreqRelProfileId";
      leaf ucmEUtranFreqRelProfileId {
        type leafref {
          path "../attributes/ucmEUtranFreqRelProfileId";
        }
      }
      container attributes {
      uses UcmEUtranFreqRelProfile-attributes;
      }
    }
  }

  augment "/emael:ManagedElement/gnbcucp:GNBCUCPFunction/gnbcucp:UeCovMeas" {
    list UcmNrFreqRelProfile {
      description "Additional definitions from MOM:min/max-elements:0/unbounded; UE coverage measurement attributes used on frequency relation level. Instance UcmNrFreqRelProfile=Default is created automatically when parent MO instance is created, unless created manually in same transaction. NRFreqRelation::ucmNrFreqRelProfileRef is automatically set to UcmNrFreqRelProfile=Default instance, unless manually set to refer to another MO instance. Precondition: Instance UcmNrFreqRelProfile=Default can only be created in same transaction as parent MO instance and cannot be deleted unless parent MO instance is deleted. Other instances can be created and deleted at any time.";
      key "ucmNrFreqRelProfileId";
      leaf ucmNrFreqRelProfileId {
        type leafref {
          path "../attributes/ucmNrFreqRelProfileId";
        }
      }
      container attributes {
      uses UcmNrFreqRelProfile-attributes;
      }
    }
  }

  augment "/emael:ManagedElement/gnbcucp:GNBCUCPFunction/gnbcucp:UeGroupSelection" {
    list Chipsets {
      description "Additional definitions from MOM:min/max-elements:0/22; A set of chipset identifiers used to define a subset of all UEs.";
      key "chipsetsId";
      leaf chipsetsId {
        type leafref {
          path "../attributes/chipsetsId";
        }
      }
      container attributes {
      uses Chipsets-attributes;
      }
    }
  }

  augment "/emael:ManagedElement/gnbcucp:GNBCUCPFunction/gnbcucp:UeGroupSelection" {
    list ImeiSvGroups {
      description "Additional definitions from MOM:min/max-elements:0/1; Container class for MO classes defining different IMEISV groups. Instance ImeiSvGroups=1 is created automatically when parent MO instance is created, unless created manually in same transaction. The RDN of this MO must be ImeiSvGroups=1. Precondition: Instance ImeiSvGroups=1 can only be created in same transaction as parent MO instance and cannot be deleted unless parent MO instance is deleted.";
      key "imeiSvGroupsId";
      leaf imeiSvGroupsId {
        type leafref {
          path "../attributes/imeiSvGroupsId";
        }
      }
      container attributes {
      uses ImeiSvGroups-attributes;
      }
    }
  }

  augment "/emael:ManagedElement/gnbcucp:GNBCUCPFunction/gnbcucp:UeGroupSelection" {
    list ImeiSvs {
      description "Additional definitions from MOM:min/max-elements:0/22; A set of IMEISV groups used to define a subset of all UEs.";
      key "imeiSvsId";
      leaf imeiSvsId {
        type leafref {
          path "../attributes/imeiSvsId";
        }
      }
      container attributes {
      uses ImeiSvs-attributes;
      }
    }
  }

  augment "/emael:ManagedElement/gnbcucp:GNBCUCPFunction/gnbcucp:UeGroupSelection" {
    list PrefUeGroupSelectionProfile {
      description "Additional definitions from MOM:min/max-elements:0/32; A set of preference UE group selection criteria used to define a subset of all UEs.";
      key "prefUeGroupSelectionProfileId";
      leaf prefUeGroupSelectionProfileId {
        type leafref {
          path "../attributes/prefUeGroupSelectionProfileId";
        }
      }
      container attributes {
      uses PrefUeGroupSelectionProfile-attributes;
      }
    }
  }

  augment "/emael:ManagedElement/gnbcucp:GNBCUCPFunction/gnbcucp:UeGroupSelection" {
    list UeAdmissionGroupDefinition {
      description "Additional definitions from MOM:min/max-elements:0/32; UE admission group definition.";
      key "ueAdmissionGroupDefinitionId";
      leaf ueAdmissionGroupDefinitionId {
        type leafref {
          path "../attributes/ueAdmissionGroupDefinitionId";
        }
      }
      container attributes {
      uses UeAdmissionGroupDefinition-attributes;
      }
    }
  }

  augment "/emael:ManagedElement/gnbcucp:GNBCUCPFunction/gnbcucp:UeGroupSelection" {
    list UeGroupSelectionProfile {
      description "Additional definitions from MOM:min/max-elements:0/32; A set of UE group selection criteria used to define a subset of all UEs.";
      key "ueGroupSelectionProfileId";
      leaf ueGroupSelectionProfileId {
        type leafref {
          path "../attributes/ueGroupSelectionProfileId";
        }
      }
      container attributes {
      uses UeGroupSelectionProfile-attributes;
      }
    }
  }

  augment "/emael:ManagedElement/gnbcucp:GNBCUCPFunction/gnbcucp:UeGroupSelection" {
    list UeMobilityGroupDefinition {
      description "Additional definitions from MOM:min/max-elements:0/32; UE mobility group definition.";
      key "ueMobilityGroupDefinitionId";
      leaf ueMobilityGroupDefinitionId {
        type leafref {
          path "../attributes/ueMobilityGroupDefinitionId";
        }
      }
      container attributes {
      uses UeMobilityGroupDefinition-attributes;
      }
    }
  }

  augment "/emael:ManagedElement/gnbcucp:GNBCUCPFunction/gnbcucp:UeGroupSelection" {
    list UeServiceGroupDefinition {
      description "Additional definitions from MOM:min/max-elements:0/32; UE service group definition.";
      key "ueServiceGroupDefinitionId";
      leaf ueServiceGroupDefinitionId {
        type leafref {
          path "../attributes/ueServiceGroupDefinitionId";
        }
      }
      container attributes {
      uses UeServiceGroupDefinition-attributes;
      }
    }
  }

  augment "/emael:ManagedElement/gnbcucp:GNBCUCPFunction/gnbcucp:UeMC" {
    list UeMCCellProfile {
      description "Additional definitions from MOM:min/max-elements:0/unbounded; UE mobility control attributes. The attributes are used on cell level. Instance UeMCCellProfile=Default is created automatically when parent MO instance is created, unless created manually in same transaction. NRCellCU::ueMCCellProfileRef is automatically set to UeMCCellProfile=Default instance, unless manually set to refer to another MO instance. Precondition: Instance UeMCCellProfile=Default can only be created in same transaction as parent MO instance and cannot be deleted unless parent MO instance is deleted. Other instances can be created and deleted at any time.";
      key "ueMCCellProfileId";
      leaf ueMCCellProfileId {
        type leafref {
          path "../attributes/ueMCCellProfileId";
        }
      }
      container attributes {
      uses UeMCCellProfile-attributes;
      }
    }
  }

  augment "/emael:ManagedElement/gnbcucp:GNBCUCPFunction/gnbcucp:UeMC" {
    list UeMCEUtranFreqRelProfile {
      description "Additional definitions from MOM:min/max-elements:0/unbounded; UE mobility control attributes used on E-UTRAN frequency relation level. Instance UeMCEUtranFreqRelProfile=Default is created automatically when parent MO instance is created, unless created manually in same transaction. EUtranFreqRelation::ueMCEUtranFreqRelProfileRef is automatically set to UeMCEUtranFreqRelProfile=Default instance, unless manually set to refer to another MO instance. Precondition: Instance UeMCEUtranFreqRelProfile=Default can only be created in same transaction as parent MO instance and cannot be deleted unless parent MO instance is deleted. Other instances can be created and deleted at any time.";
      key "ueMCEUtranFreqRelProfileId";
      leaf ueMCEUtranFreqRelProfileId {
        type leafref {
          path "../attributes/ueMCEUtranFreqRelProfileId";
        }
      }
      container attributes {
      uses UeMCEUtranFreqRelProfile-attributes;
      }
    }
  }

  augment "/emael:ManagedElement/gnbcucp:GNBCUCPFunction/gnbcucp:UeMC" {
    list UeMCNrFreqRelProfile {
      description "Additional definitions from MOM:min/max-elements:0/unbounded; UE mobility control attributes. Attributes are used on NR frequency relation level. Instance UeMCNrFreqRelProfile=Default is created automatically when parent MO instance is created, unless created manually in same transaction. NRFreqRelation::ueMCNrFreqRelProfileRef is automatically set to UeMCNrFreqRelProfile=Default instance, unless manually set to refer to another MO instance. Precondition: Instance UeMCNrFreqRelProfile=Default can only be created in same transaction as parent MO instance and cannot be deleted unless parent MO instance is deleted. Other instances can be created and deleted at any time.";
      key "ueMCNrFreqRelProfileId";
      leaf ueMCNrFreqRelProfileId {
        type leafref {
          path "../attributes/ueMCNrFreqRelProfileId";
        }
      }
      container attributes {
      uses UeMCNrFreqRelProfile-attributes;
      }
    }
  }

  augment "/emael:ManagedElement/gnbcucp:GNBCUCPFunction/gnbcucp:UeMC" {
    list UeMCUeCfg {
      description "Additional definitions from MOM:min/max-elements:0/32; Mobility control for UE configuration group. Attributes are used on gNodeB level. Instance UeMCUeCfg=Base is created automatically when parent MO instance is created, unless created manually in same transaction. Attributes prefUeGroupList, ueGroupList and ueConfGroupList must be empty in instance UeMCUeCfg=Base but cannot all be empty in any other instance of UeMCUeCfg under same parent MO instance. Precondition: Instance UeMCUeCfg=Base can only be created in same transaction as parent MO instance and cannot be deleted unless parent MO instance is deleted. Other instances can be created and deleted at any time. Maximum 31 UeMCUeCfg instances, with RDN different from Base, can be created under parent MO instance.";
      key "ueMCUeCfgId";
      leaf ueMCUeCfgId {
        type leafref {
          path "../attributes/ueMCUeCfgId";
        }
      }
      container attributes {
      uses UeMCUeCfg-attributes;
      }
    }
  }

  augment "/emael:ManagedElement/gnbcucp:GNBCUCPFunction/gnbcucp:UeMC/gnbcucp:UeMCCellProfile" {
    list UeMCCellProfileUeCfg {
      description "Additional definitions from MOM:min/max-elements:0/32; UE mobility control for UE groups. Instance UeMCCellProfileUeCfg=Base is created automatically when parent MO instance is created, unless created manually in same transaction. Each UE configuration group identifier can only be defined in one ueConfGroupList among UeMCCellProfileUeCfg instances contained under parent UeMCCellProfile instance. Any combination of one UE group identifier in ueGroupList and one preference UE group identifier in prefUeGroupList must be unique among UeMCCellProfileUeCfg instances contained under parent UeMCCellProfile instance. Attributes prefUeGroupList, ueGroupList, and ueConfGroupList must be empty in instance UeMCCellProfileUeCfg=Base but cannot all be empty in any other instance of UeMCCellProfileUeCfg. Precondition: Instance UeMCCellProfileUeCfg=Base can only be created in same transaction as parent MO instance and cannot be deleted unless parent MO instance is deleted. Other instances can be created and deleted at any time. Maximum 31 UeMCCellProfileUeCfg instances, with RDN different from Base, can be created under parent MO instance.";
      key "ueMCCellProfileUeCfgId";
      leaf ueMCCellProfileUeCfgId {
        type leafref {
          path "../attributes/ueMCCellProfileUeCfgId";
        }
      }
      container attributes {
      uses UeMCCellProfileUeCfg-attributes;
      }
    }
  }

  augment "/emael:ManagedElement/gnbcucp:GNBCUCPFunction/gnbcucp:UeMC/gnbcucp:UeMCEUtranFreqRelProfile" {
    list UeMCEUtranFreqRelProfileUeCfg {
      description "Additional definitions from MOM:min/max-elements:0/32; Mobility control for UE configuration group. The attributes are used on E-UTRAN frequency relation level. Instance UeMCEUtranFreqRelProfileUeCfg=Base is created automatically when parent MO instance is created, unless created manually in same transaction. Attributes prefUeGroupList, ueGroupList and ueConfGroupList must be empty in instance UeMCEUtranFreqRelProfileUeCfg=Base but cannot all be empty in any other instance of UeMCEUtranFreqRelProfileUeCfg under same parent UeMCEUtranFreqRelProfile instance. Precondition: Instance UeMCEUtranFreqRelProfileUeCfg=Base can only be created in same transaction as parent MO instance and cannot be deleted unless parent MO instance is deleted. Other instances can be created and deleted at any time. Maximum 31 UeMCEUtranFreqRelProfileUeCfg instances, with RDN different from Base, can be created under parent MO instance.";
      key "ueMCEUtranFreqRelProfileUeCfgId";
      leaf ueMCEUtranFreqRelProfileUeCfgId {
        type leafref {
          path "../attributes/ueMCEUtranFreqRelProfileUeCfgId";
        }
      }
      container attributes {
      uses UeMCEUtranFreqRelProfileUeCfg-attributes;
      }
    }
  }

  augment "/emael:ManagedElement/gnbcucp:GNBCUCPFunction/gnbcucp:UeMC/gnbcucp:UeMCNrFreqRelProfile" {
    list UeMCNrFreqRelProfileUeCfg {
      description "Additional definitions from MOM:min/max-elements:0/32; Mobility control for UE configuration group. Attributes are used on NR frequency relation level. Instance UeMCNrFreqRelProfileUeCfg=Base is created automatically when parent MO instance is created, unless created manually in same transaction. Attributes prefUeGroupList, ueGroupList and ueConfGroupList must be empty in instance UeMCNrFreqRelProfileUeCfg=Base but cannot all be empty in any other instance of UeMCNrFreqRelProfileUeCfg under same parent UeMCNrFreqRelProfile instance. Precondition: Instance UeMCNrFreqRelProfileUeCfg=Base can only be created in same transaction as parent MO instance and cannot be deleted unless parent MO instance is deleted. Other instances can be created and deleted at any time. Maximum 31 UeMCNrFreqRelProfileUeCfg instances, with RDN different from Base, can be created under parent MO instance.";
      key "ueMCNrFreqRelProfileUeCfgId";
      leaf ueMCNrFreqRelProfileUeCfgId {
        type leafref {
          path "../attributes/ueMCNrFreqRelProfileUeCfgId";
        }
      }
      container attributes {
      uses UeMCNrFreqRelProfileUeCfg-attributes;
      }
    }
  }

  augment "/emael:ManagedElement/gnbcucp:GNBCUCPFunction/gnbcucp:UeNoDrb" {
    list UeNoDrbPCellProfile {
      description "Additional definitions from MOM:min/max-elements:0/unbounded; UE context without DRBs for PCell. Applies to UEs that use the cell as PCell. Attributes are used on cell level. Instance UeNoDrbPCellProfile=Default is created automatically when parent MO instance is created, unless created manually in same transaction. NRCellCU::ueNoDrbPCellProfileRef is automatically set to UeNoDrbPCellProfile=Default instance, unless manually set to refer to another MO instance. Precondition: Instance UeNoDrbPCellProfile=Default can only be created in same transaction as parent MO instance and cannot be deleted unless parent MO instance is deleted. Other instances can be created and deleted at any time.";
      key "ueNoDrbPCellProfileId";
      leaf ueNoDrbPCellProfileId {
        type leafref {
          path "../attributes/ueNoDrbPCellProfileId";
        }
      }
      container attributes {
      uses UeNoDrbPCellProfile-attributes;
      }
    }
  }

  augment "/emael:ManagedElement/gnbcucp:GNBCUCPFunction/gnbcucp:UeNoDrb/gnbcucp:UeNoDrbPCellProfile" {
    list UeNoDrbPCellProfileUeCfg {
      description "Additional definitions from MOM:min/max-elements:0/8; UE context without DRBs for PCell, UE configuration group. Applies to UEs that use cell as PCell. Attributes are used on cell level. Instance UeNoDrbPCellProfileUeCfg=Base is created automatically when parent MO instance is created, unless created manually in same transaction. Attributes ueGroupList and ueConfGroupList must be empty in instance UeNoDrbPCellProfileUeCfg=Base but cannot all be empty in any other instance of UeNoDrbPCellProfileUeCfg under same parent UeNoDrbPCellProfile instance. Precondition: Instance UeNoDrbPCellProfileUeCfg=Base can only be created in same transaction as parent MO instance and cannot be deleted unless parent MO instance is deleted. Other instances can be created and deleted at any time. Maximum 7 UeNoDrbPCellProfileUeCfg instances, with RDN different from Base, can be created under parent MO instance.";
      key "ueNoDrbPCellProfileUeCfgId";
      leaf ueNoDrbPCellProfileUeCfgId {
        type leafref {
          path "../attributes/ueNoDrbPCellProfileUeCfgId";
        }
      }
      container attributes {
      uses UeNoDrbPCellProfileUeCfg-attributes;
      }
    }
  }

  augment "/emael:ManagedElement/gnbcucp:GNBCUCPFunction/gnbcucp:UeUlResMon" {
    list UlBufferMonCfg {
      description "Additional definitions from MOM:min/max-elements:0/16; Uplink buffer monitoring configurations. Instance UlBufferMonCfg=Default is created automatically when parent MO instance is created, unless created manually in same transaction. NrdcMnCellProfileUeCfg::nrdcSetupUlBufferMonCfgRef is automatically set to UlBufferMonCfg=Default instance, unless manually set to refer to another MO instance. Precondition: Instance UlBufferMonCfg=Default can only be created in same transaction as parent MO instance and cannot be deleted unless parent MO instance is deleted. Other instances can be created and deleted at any time. Maximum 15 UlBufferMonCfg instances, with RDN different from Default, can be created under parent MO instance.";
      key "ulBufferMonCfgId";
      leaf ulBufferMonCfgId {
        type leafref {
          path "../attributes/ulBufferMonCfgId";
        }
      }
      container attributes {
      uses UlBufferMonCfg-attributes;
      }
    }
  }

  augment "/emael:ManagedElement/gnbcucp:GNBCUCPFunction/gnbcucp:UeUlResMon" {
    list UlQualMcpcMeasCfg {
      description "Additional definitions from MOM:min/max-elements:0/8; Uplink quality measurement configuration for Mobility Control at Poor Coverage (MCPC). Instance UlQualMcpcMeasCfg=Default is created automatically when parent MO instance is created, unless created manually in same transaction. McpcPCellProfileUeCfg::ulQualMcpcMeasCfgRef is automatically set to UlQualMcpcMeasCfg=Default instance, unless manually set to refer to another MO instance. Precondition: Instance UlQualMcpcMeasCfg=Default can only be created in same transaction as parent MO instance and cannot be deleted unless parent MO instance is deleted. Other instances can be created and deleted at any time. Maximum 7 UlQualMcpcMeasCfg instances, with RDN different from Default, can be created under parent MO instance.";
      key "ulQualMcpcMeasCfgId";
      leaf ulQualMcpcMeasCfgId {
        type leafref {
          path "../attributes/ulQualMcpcMeasCfgId";
        }
      }
      container attributes {
      uses UlQualMcpcMeasCfg-attributes;
      }
    }
  }

  augment "/emael:ManagedElement/gnbcucp:GNBCUCPFunction/gnbcucp:UeCC/gnbcucp:UlDataSplit" {
    list UlDataSplitUeCfg {
      description "Additional definitions from MOM:min/max-elements:0/8; Uplink PDCP data split UE configuration group. Instance UlDataSplitUeCfg=Base is created automatically when parent MO instance is created, unless created manually in same transaction. Each UE configuration group identifier can only be defined in one ueConfGroupList among UlDataSplitUeCfg instances contained under parent UlDataSplit instance. Any combination of one UE group identifier in ueGroupList and one preference UE group identifier in prefUeGroupList must be unique among UlDataSplitUeCfg instances contained under parent UlDataSplit instance. Attributes prefUeGroupList, ueGroupList and ueConfGroupList must be empty in instance UlDataSplitUeCfg=Base but cannot all be empty in any other instance of UlDataSplitUeCfg under same parent UlDataSplit instance. Precondition: Instance UlDataSplitUeCfg=Base can only be created in same transaction as parent MO instance and cannot be deleted unless parent MO instance is deleted. Other instances can be created and deleted at any time. Maximum 7 UlDataSplitUeCfg instances, with RDN different from Base, can be created under parent MO instance.";
      key "ulDataSplitUeCfgId";
      leaf ulDataSplitUeCfgId {
        type leafref {
          path "../attributes/ulDataSplitUeCfgId";
        }
      }
      container attributes {
      uses UlDataSplitUeCfg-attributes;
      }
    }
  }
  typedef AcaOperationMode {
    description "Operational mode of Automated Carrier Aggregation.";
    type enumeration {
      enum AUTO {
        description "NRCellRelation::sCellCandidate is operated by Automated Carrier Aggregation. NRCellRelation::sCellCandidate can be configured for both uplink and downlink CA.";
      }
      enum MANUAL {
        description "NRCellRelation::sCellCandidate is managed manually by operator.";
      }
    }
  }
  typedef ActionAtRelease {
    description "Traffic steering action at UE release.";
    type enumeration {
      enum DISABLED {
        description "Traffic steering at release is disabled.";
      }
      enum CA_CONF {
        description "Cell reselection steering based on current carrier aggregation configuration. Cell reselection steering affects UEs both in RRC IDLE state and RRC INACTIVE state. Cell reselection priorities are included in 38.331 RRCRelease message if UE is configured with carrier aggregation at release occasion and if TrStSaCellProfileUeCfg::mlcEnabled is true. Cell reselection priorities are set in RRCRelease message as follows: - Priority for current PCell frequency is set to 7.8. - Priorities for current SCell frequencies are set to 6.8, 6.6, 6.4, 6.2 or 6 in order of decreasing ARFCN. - Priorities for remaining NR cell frequencies are set to 5.8, 5.6, 5.4, 5.2 or 5 in order of decreasing ARFCN. - Priorities for E-UTRAN frequencies are set between 4.8 and 0 in such a way that the priority order between E-UTRAN frequencies, as defined by EUtranFreqRelation::cellReselectionPriority and EUtranFreqRelation::cellReselectionSubPriority settings, is preserved.";
      }
      enum PRIORITY_LIST {
        description "Cell reselection steering based on frequency priority lists. Cell reselection steering affects UEs both in RRC IDLE state and RRC INACTIVE state. Cell reselection priorities are included in 38.331 RRCRelease message according to freqPrioListNR and freqPrioListEUtran.";
      }
      enum CRP_MLC_CONDITIONAL {
        description "Cell reselection steering conditional on multi-layer coordination evaluation. Cell reselection steering affects UEs both in RRC IDLE state and RRC INACTIVE state. Cell reselection priorities are included in 38.331 RRC release message if a multi-layer coordination evaluation has been performed at least once for UE. Cell reselection priorities are set in RRCRelease message as follows: - Priority for current PCell frequency is set to 7.8. - Priorities for current SCell frequencies are set to 6.8, 6.6, 6.4, 6.2 or 6 in order of decreasing ARFCN. - Priorities for remaining NR cell frequencies are set to 5.8, 5.6, 5.4, 5.2 or 5 in order of decreasing ARFCN. - Priorities for E-UTRAN frequencies are set between 4.8 and 0 in such a way that the priority order between E-UTRAN frequencies, as defined by EUtranFreqRelation::cellReselectionPriority and EUtranFreqRelation::cellReselectionSubPriority settings, is preserved.";
      }
      enum RANDOM_REDIRECT {
        description "Randomized redirection steering. Randomized redirection steering affects UEs in RRC IDLE state. Redirected carrier info is included in 38.331 RRCRelease message according to randomly selected frequency among allowed PCells frequencies.";
      }
    }
  }
  typedef AdmState {
    description "Administrative state of a resource.";
    type enumeration {
      enum LOCKED {
        description "The resource is administratively prohibited from performing services for its users.";
      }
      enum UNLOCKED {
        description "The resource is administratively permitted to perform services for its users. This is independent of its inherent operability.";
      }
      enum SHUTTINGDOWN {
        description "Use of the resource is administratively permitted to existing instances of use only. While the system remains in the shutting down state the manager may at any time cause the managed object to revert to the locked state.";
      }
    }
  }
  typedef AdvancedUePositioningMode {
    description "Positioning report mode for NR Advanced UE Location Support feature.";
    type enumeration {
      enum NONE {
        description "NR Advanced UE Location Support feature is disabled.";
      }
      enum ALL {
        description "Operation takes Timing Advance and Angle of Arrival into consideration.";
      }
      enum TA_ONLY {
        description "Operation takes Timing Advance into consideration.";
      }
    }
  }
  typedef AggressorNodeType {
    description "Node type of aggressor.";
    type enumeration {
      enum __UNDEFINED__ {
      }
    }
  }
  typedef AnrCgiMeasInterFreqMode {
    description "ANR with CGI measurement operation for RBS.";
    type enumeration {
      enum DISABLED {
        description "ANR with CGI measurement for inter-frequency is disabled for RBS.";
      }
      enum FR1 {
        description "ANR with CGI measurement for inter-frequency is enabled for RBS on FR1.";
      }
    }
  }
  typedef AvailStatus {
    description "The availability status is used to qualify the operational state. It indicates why the operational state has changed its value.";
    type enumeration {
      enum IN_TEST {
        description "The resource is undergoing a test procedure. If the administrative state is locked or shutting down, normal users are prevented from using the resource.";
      }
      enum FAILED {
        description "The resource has an internal fault that prevents it from operating.";
      }
      enum POWER_OFF {
        description "The resource requires power to be applied and is not powered on.";
      }
      enum OFF_LINE {
        description "The resource requires a routine operation to be performed. This routine operation is to place the resource online and make it available for use. The operation may be manual or automatic, or both. The operational state is disabled.";
      }
      enum OFF_DUTY {
        description "The resource has been made inactive by an internal control process.";
      }
      enum DEPENDENCY {
        description "The resource cannot operate because some other resource on which it depends is unavailable.";
      }
      enum DEGRADED {
        description "The service available from the resource is degraded in some respect.";
      }
      enum NOT_INSTALLED {
        description "The resource represented by the managed object is not present, or is incomplete.";
      }
      enum LOG_FULL {
        description "Indicates a log full condition. The semantics are defined in CCITT Rec. X.735 | ISO/IEC 10164-6.";
      }
      enum DEPENDENCY_LOCKED {
        description "The administrative state of a resource that this resource depends on is locked. Alternatively, the availability status of the other resource is dependency locked.";
      }
      enum DEPENDENCY_FAILED {
        description "The availability status of a resource that this resource depends on is failed or dependency failed.";
      }
      enum DEPENDENCY_SHUTTINGDOWN {
        description "The administrative state of a resource that this resource depends on is shutting down. Alternatively, the availability status of the other resource is dependency shutting down.";
      }
      enum DEPENDENCY_RECOVERY {
        description "Resource that this resource depends on is undergoing a recovery procedure.";
      }
      enum DEPENDENCY_HOLDING {
        description "Resource cannot operate because some other resource on which it depends is currently unavailable. The situation is expected to be resolved. Actions to facilitate dependency resolution may be ongoing.";
      }
    }
  }
  typedef CaStatusCause {
    description "Additional information on status of carrier aggregation.";
    type enumeration {
      enum E5_TUNNEL_CAP {
        description "E5 tunnel capacity is reached. E5 setup between partners failed and caStatusActive is false for this NRCellRelation instance.";
      }
      enum E5_TUNNEL_CAP_REMOTE {
        description "E5 tunnel capacity is reached on remote host. E5 setup between partners failed and caStatusActive is false for this NRCellRelation instance.";
      }
      enum E5_CELL_ALLOC_CAP {
        description "E5 cell allocation capacity is reached. E5 setup between partners failed and caStatusActive is false for this NRCellRelation instance.";
      }
      enum E5_CELL_ALLOC_CAP_REMOTE {
        description "E5 cell allocation capacity is reached on remote host. E5 setup between partners failed and caStatusActive is false for this NRCellRelation instance.";
      }
      enum E5_SW_VERSION_MISMATCH {
        description "Software version mismatch detected towards external gNodeB-DU partner during E5 setup. E5 setup between partners failed and caStatusActive is false for this NRCellRelation instance.";
      }
      enum E5_MAND_CAP_MISMATCH {
        description "E5 mandatory capability mismatch detected towards external gNodeB-DU partner during E5 setup. E5 setup between partners failed and caStatusActive is false for this NRCellRelation instance.";
      }
      enum E5_DLCA_CAP_ONLY {
        description "E5 uplink CA capability mismatch detected towards external gNodeB-DU partner during E5 setup. E5 is set up between partners and caStatusActive is true for this NRCellRelation instance with downlink carrier aggregation function.";
      }
      enum INTRA_BAND_CA_BLOCKED {
        description "Unused value.";
      }
      enum ESS_ULCA_BLOCKED {
        description "Uplink CA is blocked between non-colocated ESS FDD carriers. SCell referenced by nRCellRef is non-colocated and caStatusActive is true for this NRCellRelation instance with downlink carrier aggregation function.";
      }
    }
  }
  typedef CellRelationOutput {
    description "Format of action output.";
    type enumeration {
      enum UNFORMATTED_TEXT {
        description "Output is unformatted text, suitable for on-screen reading.";
      }
      enum FORMATTED_TEXT {
        description "Output is formatted text, suitable for automated interpretation.";
      }
    }
  }
  typedef CipheringAlgorithmID {
    description "Ciphering algorithms enum.";
    type enumeration {
      enum NEA0 {
        description "No ciphering is applied.";
      }
      enum NEA1 {
        description "128-NEA1 (based on SNOW 3G).";
      }
      enum NEA2 {
        description "128-NEA2 (based on AES).";
      }
      enum NEA3 {
        description "128-NEA3 (based on ZUC).";
      }
    }
  }
  typedef Colocation {
    description "Colocation information.";
    type enumeration {
      enum UNKNOWN {
        description "Colocation between cells is unknown.";
      }
      enum COLOCATED {
        description "Related cell is colocated with current cell.";
      }
      enum NON_COLOCATED {
        description "Related cell is not colocated with current cell.";
      }
    }
  }
  typedef CoordinationType {
    description "Type of inter-cell coordination.";
    type enumeration {
      enum INTRA_CM {
        description "Intra-capacity module coordination. NR Cells reside in the same capacity module in the same gNodeB-DU.";
      }
      enum INTER_CM {
        description "Inter-capacity module coordination. NR Cells reside in different capacity modules in the same gNodeB-DU.";
      }
      enum EXT_CM {
        description "External capacity module coordination. NR Cells reside in different capacity modules in different gNodeB-DUs.";
      }
    }
  }
  typedef DayOfWeekOnly {
    description "The day of the week.";
    type enumeration {
      enum MON {
        description "Monday.";
      }
      enum TUE {
        description "Tuesday.";
      }
      enum WED {
        description "Wednesday.";
      }
      enum THU {
        description "Thursday.";
      }
      enum FRI {
        description "Friday.";
      }
      enum SAT {
        description "Saturday.";
      }
      enum SUN {
        description "Sunday.";
      }
    }
  }
  typedef DrxInactivityTimer {
    description "Inactivity timer value for DRX.";
    type enumeration {
      enum INACTIVITYTIMER_0MS {
        description "Inactivity timer value 0.";
      }
      enum INACTIVITYTIMER_1MS {
        description "Inactivity timer value 1 ms.";
      }
      enum INACTIVITYTIMER_2MS {
        description "Inactivity timer value 2 ms.";
      }
      enum INACTIVITYTIMER_3MS {
        description "Inactivity timer value 3 ms.";
      }
      enum INACTIVITYTIMER_4MS {
        description "Inactivity timer value 4 ms.";
      }
      enum INACTIVITYTIMER_5MS {
        description "Inactivity timer value 5 ms.";
      }
      enum INACTIVITYTIMER_6MS {
        description "Inactivity timer value 6 ms.";
      }
      enum INACTIVITYTIMER_8MS {
        description "Inactivity timer value 8 ms.";
      }
      enum INACTIVITYTIMER_10MS {
        description "Inactivity timer value 10 ms.";
      }
      enum INACTIVITYTIMER_20MS {
        description "Inactivity timer value 20 ms.";
      }
      enum INACTIVITYTIMER_30MS {
        description "Inactivity timer value 30 ms.";
      }
      enum INACTIVITYTIMER_40MS {
        description "Inactivity timer value 40 ms.";
      }
      enum INACTIVITYTIMER_50MS {
        description "Inactivity timer value 50 ms.";
      }
      enum INACTIVITYTIMER_60MS {
        description "Inactivity timer value 60 ms.";
      }
      enum INACTIVITYTIMER_80MS {
        description "Inactivity timer value 80 ms.";
      }
      enum INACTIVITYTIMER_100MS {
        description "Inactivity timer value 100 ms.";
      }
      enum INACTIVITYTIMER_200MS {
        description "Inactivity timer value 200 ms.";
      }
      enum INACTIVITYTIMER_300MS {
        description "Inactivity timer value 300 ms.";
      }
      enum INACTIVITYTIMER_500MS {
        description "Inactivity timer value 500 ms.";
      }
      enum INACTIVITYTIMER_750MS {
        description "Inactivity timer value 750 ms.";
      }
      enum INACTIVITYTIMER_1280MS {
        description "Inactivity timer value 1280 ms.";
      }
      enum INACTIVITYTIMER_1920MS {
        description "Inactivity timer value 1920 ms.";
      }
      enum INACTIVITYTIMER_2560MS {
        description "Inactivity timer value 2560 ms.";
      }
    }
  }
  typedef DrxLongCycle {
    description "Long Cycle value for DRX.";
    type enumeration {
      enum LONGCYCLE_10MS {
        description "Long cycle value 10 ms.";
      }
      enum LONGCYCLE_20MS {
        description "Long cycle value 20 ms.";
      }
      enum LONGCYCLE_32MS {
        description "Long cycle value 32 ms.";
      }
      enum LONGCYCLE_40MS {
        description "Long cycle value 40 ms.";
      }
      enum LONGCYCLE_60MS {
        description "Long cycle value 60 ms.";
      }
      enum LONGCYCLE_64MS {
        description "Long cycle value 64 ms.";
      }
      enum LONGCYCLE_70MS {
        description "Long cycle value 70 ms.";
      }
      enum LONGCYCLE_80MS {
        description "Long cycle value 80 ms.";
      }
      enum LONGCYCLE_128MS {
        description "Long cycle value 128 ms.";
      }
      enum LONGCYCLE_160MS {
        description "Long cycle value 160 ms.";
      }
      enum LONGCYCLE_256MS {
        description "Long cycle value 256 ms.";
      }
      enum LONGCYCLE_320MS {
        description "Long cycle value 320 ms.";
      }
      enum LONGCYCLE_512MS {
        description "Long cycle value 512 ms.";
      }
      enum LONGCYCLE_640MS {
        description "Long cycle value 640 ms.";
      }
      enum LONGCYCLE_1024MS {
        description "Long cycle value 1024 ms.";
      }
      enum LONGCYCLE_1280MS {
        description "Long cycle value 1280 ms.";
      }
      enum LONGCYCLE_2048MS {
        description "Long cycle value 2048 ms.";
      }
      enum LONGCYCLE_2560MS {
        description "Long cycle value 2560 ms.";
      }
      enum LONGCYCLE_5120MS {
        description "Long cycle value 5120 ms.";
      }
      enum LONGCYCLE_10240MS {
        description "Long cycle value 10240 ms.";
      }
    }
  }
  typedef DrxOnDurationTimer {
    description "On-duration timer value for DRX.";
    type enumeration {
      enum ONDURATIONTIMER_1SUBMS {
        description "On-duration value 1/32 ms.";
      }
      enum ONDURATIONTIMER_2SUBMS {
        description "On-duration value 2/32 ms.";
      }
      enum ONDURATIONTIMER_3SUBMS {
        description "On-duration value 3/32 ms.";
      }
      enum ONDURATIONTIMER_4SUBMS {
        description "On-duration value 4/32 ms.";
      }
      enum ONDURATIONTIMER_5SUBMS {
        description "On-duration value 5/32 ms.";
      }
      enum ONDURATIONTIMER_6SUBMS {
        description "On-duration value 6/32 ms.";
      }
      enum ONDURATIONTIMER_7SUBMS {
        description "On-duration value 7/32 ms.";
      }
      enum ONDURATIONTIMER_8SUBMS {
        description "On-duration value 8/32 ms.";
      }
      enum ONDURATIONTIMER_9SUBMS {
        description "On-duration value 9/32 ms.";
      }
      enum ONDURATIONTIMER_10SUBMS {
        description "On-duration value 10/32 ms.";
      }
      enum ONDURATIONTIMER_11SUBMS {
        description "On-duration value 11/32 ms.";
      }
      enum ONDURATIONTIMER_12SUBMS {
        description "On-duration value 12/32 ms.";
      }
      enum ONDURATIONTIMER_13SUBMS {
        description "On-duration value 13/32 ms.";
      }
      enum ONDURATIONTIMER_14SUBMS {
        description "On-duration value 14/32 ms.";
      }
      enum ONDURATIONTIMER_15SUBMS {
        description "On-duration value 15/32 ms.";
      }
      enum ONDURATIONTIMER_16SUBMS {
        description "On-duration value 16/32 ms.";
      }
      enum ONDURATIONTIMER_17SUBMS {
        description "On-duration value 17/32 ms.";
      }
      enum ONDURATIONTIMER_18SUBMS {
        description "On-duration value 18/32 ms.";
      }
      enum ONDURATIONTIMER_19SUBMS {
        description "On-duration value 19/32 ms.";
      }
      enum ONDURATIONTIMER_20SUBMS {
        description "On-duration value 20/32 ms.";
      }
      enum ONDURATIONTIMER_21SUBMS {
        description "On-duration value 21/32 ms.";
      }
      enum ONDURATIONTIMER_22SUBMS {
        description "On-duration value 22/32 ms.";
      }
      enum ONDURATIONTIMER_23SUBMS {
        description "On-duration value 23/32 ms.";
      }
      enum ONDURATIONTIMER_24SUBMS {
        description "On-duration value 24/32 ms.";
      }
      enum ONDURATIONTIMER_25SUBMS {
        description "On-duration value 25/32 ms.";
      }
      enum ONDURATIONTIMER_26SUBMS {
        description "On-duration value 26/32 ms.";
      }
      enum ONDURATIONTIMER_27SUBMS {
        description "On-duration value 27/32 ms.";
      }
      enum ONDURATIONTIMER_28SUBMS {
        description "On-duration value 28/32 ms.";
      }
      enum ONDURATIONTIMER_29SUBMS {
        description "On-duration value 29/32 ms.";
      }
      enum ONDURATIONTIMER_30SUBMS {
        description "On-duration value 30/32 ms.";
      }
      enum ONDURATIONTIMER_31SUBMS {
        description "On-duration value 31/32 ms.";
      }
      enum ONDURATIONTIMER_1MS {
        description "On-duration value 1 ms.";
      }
      enum ONDURATIONTIMER_2MS {
        description "On-duration value 2 ms.";
      }
      enum ONDURATIONTIMER_3MS {
        description "On-duration value 3 ms.";
      }
      enum ONDURATIONTIMER_4MS {
        description "On-duration value 4 ms.";
      }
      enum ONDURATIONTIMER_5MS {
        description "On-duration value 5 ms.";
      }
      enum ONDURATIONTIMER_6MS {
        description "On-duration value 6 ms.";
      }
      enum ONDURATIONTIMER_8MS {
        description "On-duration value 8 ms.";
      }
      enum ONDURATIONTIMER_10MS {
        description "On-duration value 10 ms.";
      }
      enum ONDURATIONTIMER_20MS {
        description "On-duration value 20 ms.";
      }
      enum ONDURATIONTIMER_30MS {
        description "On-duration value 30 ms.";
      }
      enum ONDURATIONTIMER_40MS {
        description "On-duration value 40 ms.";
      }
      enum ONDURATIONTIMER_50MS {
        description "On-duration value 50 ms.";
      }
      enum ONDURATIONTIMER_60MS {
        description "On-duration value 60 ms.";
      }
      enum ONDURATIONTIMER_80MS {
        description "On-duration value 80 ms.";
      }
      enum ONDURATIONTIMER_100MS {
        description "On-duration value 100 ms.";
      }
      enum ONDURATIONTIMER_200MS {
        description "On-duration value 200 ms.";
      }
      enum ONDURATIONTIMER_300MS {
        description "On-duration value 300 ms.";
      }
      enum ONDURATIONTIMER_400MS {
        description "On-duration value 400 ms.";
      }
      enum ONDURATIONTIMER_500MS {
        description "On-duration value 500 ms.";
      }
      enum ONDURATIONTIMER_600MS {
        description "On-duration value 600 ms.";
      }
      enum ONDURATIONTIMER_800MS {
        description "On-duration value 800 ms.";
      }
      enum ONDURATIONTIMER_1000MS {
        description "On-duration value 1000 ms.";
      }
      enum ONDURATIONTIMER_1200MS {
        description "On-duration value 1200 ms.";
      }
      enum ONDURATIONTIMER_1600MS {
        description "On-duration value 1600 ms.";
      }
    }
  }
  typedef EndcMobilityAction {
    description "Intra-frequency handover evaluation fails to select a target NR cell or SN change procedure fails.";
    type enumeration {
      enum RELEASE {
        description "SN initiated SN Release is triggered.";
      }
      enum IGNORE {
        description "No action is taken.";
      }
    }
  }
  typedef EnergySavingState {
    description "Energy saving states.";
    type enumeration {
      enum NOT_ENERGYSAVING {
        description "Cell is not in energy saving state.";
      }
      enum ENERGYSAVING {
        description "Cell is in energy saving state.";
      }
    }
  }
  typedef EnergyState {
    description "Energy saving states.";
    type enumeration {
      enum IS_NOT_ENERGYSAVING {
        description "Cell is not in energy saving state.";
      }
      enum IS_ENERGYSAVING {
        description "Cell is in energy saving state.";
      }
    }
  }
  typedef EpBoCSMode {
    description "Mode of operation for Booster Carrier Sleep.";
    type enumeration {
      enum DISABLED {
        description "Feature is disabled.";
      }
      enum TIME {
        description "Feature is enabled. Wake-up is based on time, and sleep is based on own load of cell.";
      }
      enum MULTI_LAYER_TRAFFIC {
        description "Feature is enabled. Wake-up is based on traffic, and sleep is based on both own load of cell and load of energy performance-related cells.";
      }
    }
  }
  typedef EpsFallbackOperationType {
    description "EPS fallback operation.";
    type enumeration {
      enum INACTIVE {
        description "Always use Voice over NR (VoNR).";
      }
      enum ACTIVE {
        description "Use Release with Redirection EPS fallback without measurement. Applied for UE not supporting Voice over NR (VoNR).";
      }
      enum FORCED {
        description "Use EPS fallback with Release with Redirection without measurement.";
      }
      enum ACTIVE_MEAS_RWR {
        description "Use measurement-based Release with Redirection EPS fallback. Applied for UE not supporting Voice over NR (VoNR).";
      }
      enum ACTIVE_MEAS_IRAT_HO {
        description "Use measurement-based Inter-RAT handover EPS fallback. Applied for UE not supporting Voice over NR (VoNR).";
      }
      enum FORCED_MEAS_RWR {
        description "Use measurement-based Release with Redirection EPS fallback.";
      }
      enum FORCED_MEAS_IRAT_HO {
        description "Use Measurement-based Inter-RAT handover EPS fallback.";
      }
    }
  }
  typedef EpsFbAtSessionSetupType {
    description "EPS fallback operation can be done at session setup.";
    type enumeration {
      enum INACTIVE {
        description "Always use Voice over NR (VoNR).";
      }
      enum ACTIVE {
        description "For voice call at session setup, policy defined by epsFallbackOperation is used. For emergency call at session setup, policy defined by epsFallbackOperationEm is used. For EPS fallback, entire IMS PDU Session establishment is rejected.";
      }
    }
  }
  typedef EpsFbOperationTypeEm {
    description "EPS fallback operation for emergency calls.";
    type enumeration {
      enum ACTIVE {
        description "Use Release with Redirection EPS fallback without measurement for emergency call. Applied for UE and RAN not supporting emergency call over NR.";
      }
      enum FORCED {
        description "Use Release with Redirection EPS fallback without measurement for emergency call.";
      }
      enum ACTIVE_MEAS_RWR {
        description "Use measurement-based Release with Redirection EPS fallback for emergency call. Applied for UE and RAN not supporting emergency call over NR.";
      }
      enum ACTIVE_MEAS_IRAT_HO {
        description "Use measurement-based Inter-RAT handover EPS fallback for emergency call. Applied for UE and RAN not supporting emergency call over NR.";
      }
      enum FORCED_MEAS_RWR {
        description "Use measurement-based Release with Redirection EPS fallback for emergency call.";
      }
      enum FORCED_MEAS_IRAT_HO {
        description "Use Measurement-based Inter-RAT handover EPS fallback for emergency call.";
      }
    }
  }
  typedef EpsFbPrioritizationType {
    description "EPS fallback prioritization over an ongoing procedure.";
    type enumeration {
      enum PRIO_OVER_XN_HO {
        description "EPS fallback is prioritized over Xn-based handover.";
      }
    }
  }
  typedef FeatCtrlState {
    description "Whether a feature is on or off.";
    type enumeration {
      enum OFF {
        description "Feature is OFF.";
      }
      enum ON {
        description "Feature is ON.";
      }
    }
  }
  typedef InitialUlPrimaryPathMode {
    description "Uplink path mode used at dual connectivity setup.";
    type enumeration {
      enum MCG {
        description "MCG is used as uplink primary path at initial state.";
      }
      enum COVERAGE_BASED {
        description "SCG is preferred as uplink primary path at initial state. SCG is used as uplink primary path in high PSCell uplink quality or RSRP at initial state. Otherwise, MCG is used as uplink primary path at initial state.";
      }
      enum SCG {
        description "SCG is kept as uplink primary path at initial state. Used as uplink primary path in high RSRP and in low RSRP at initial state.";
      }
    }
  }
  typedef InitialUplinkConf {
    description "Initial uplink configurations enum.";
    type enumeration {
      enum MCG {
        description "PDCP uplink data PDU to the configured RLC entity in MCG at initial state.";
      }
      enum SCG {
        description "PDCP uplink data PDU to the configured RLC entity in SCG at initial state.";
      }
    }
  }
  typedef IntegProtLowRateHandling {
    description "How a low rate request for user plane integrity protection is handled.";
    type enumeration {
      enum REJECT {
        description "Reject incoming low rate Integrity Protection requests.";
      }
      enum NO_INTEGRITY_PROTECTION {
        description "No Integrity Protection on incoming low rate Integrity Protection requests.";
      }
    }
  }
  typedef IntegrityAlgorithmID {
    description "Integrity algorithms enum.";
    type enumeration {
      enum NIA1 {
        description "128-NIA1 SNOW 3G based algorithm.";
      }
      enum NIA2 {
        description "128-NIA2 AES based algorithm.";
      }
      enum NIA3 {
        description "128-NIA3 ZUC based algorithm.";
      }
    }
  }
  typedef InterfaceName {
    description "RAN interfaces.";
    type enumeration {
      enum C5 {
        description "C5 for user plane.";
      }
      enum E1 {
        description "E1 for control and user plane.";
      }
      enum E6 {
        description "E6 for control plane.";
      }
      enum F1 {
        description "F1 for control and user plane.";
      }
      enum NG {
        description "NG for control and user plane.";
      }
      enum S1 {
        description "S1 for user plane.";
      }
      enum XN {
        description "Xn for control and user plane.";
      }
      enum X2 {
        description "X2 for control and user plane.";
      }
    }
  }
  typedef InterfaceSupervision {
    description "Interfaces considered when setting cellState.";
    type enumeration {
      enum ALL_LINKS {
        description "NRCellCU::cellState is based on overall X2, NG and Xn availability. If any X2, NG or Xn links are available, NRCellCU::cellState is always ACTIVE.";
      }
      enum NO_SUPERVISION {
        description "No interfaces are considered and NRCellCU::cellState is always ACTIVE.";
      }
      enum NG_ONLY {
        description "NRCellCU::cellState is based on NG availability. If any NG links are available, NRCellCU::cellState is always ACTIVE.";
      }
      enum X2_ONLY {
        description "NRCellCU::cellState is based on X2 availability. If any X2 links are available, NRCellCU::cellState is always ACTIVE.";
      }
      enum XN_ONLY {
        description "NRCellCU::cellState is based on Xn availability. If any Xn links are available, NRCellCU::cellState is always ACTIVE.";
      }
      enum NG_X2_COEXISTENCE {
        description "NRCellCU::cellState is based on overall X2 and NG availability. If any NG or X2 links are available, NRCellCU::cellState is always ACTIVE.";
      }
      enum NG_XN_COEXISTENCE {
        description "NRCellCU::cellState is based on overall NG and Xn availability. If any NG or Xn links are available, NRCellCU::cellState is always ACTIVE.";
      }
      enum X2_XN_COEXISTENCE {
        description "NRCellCU::cellState is based on overall X2 and Xn availability. If any X2 or Xn links are available, NRCellCU::cellState is always ACTIVE.";
      }
    }
  }
  typedef LowPrioSpCellCandHandling {
    description "Handling of low priority special cell candidate. Defines how a reported low priority PCell or PSCell candidate is treated when received during MCPC priority period.";
    type enumeration {
      enum STORE_LATEST_RECEIVED {
        description "Latest received special cell candidate is stored. Latest received low priority PCell or PSCell candidate is unconditional stored. If a stored low priority PCell or PSCell candidate already exists, it is replaced with latest received low priority candidate.";
      }
      enum STORE_HIGHEST_PRIO {
        description "Received special cell candidate with highest priority is stored. A received low priority PCell or PSCell candidate is stored unless a low priority candidate with higher priority is already stored.";
      }
    }
  }
  typedef McpcNrdcQuantity {
    description "Combination of measurement quantities applicable to Mobility Control at Poor Coverage feature.";
    type enumeration {
      enum NONE {
        description "Measurement disabled.";
      }
      enum RSRP {
        description "RSRP measurement quantity.";
      }
      enum RSRQ {
        description "RSRQ measurement quantity.";
      }
      enum SINR_FALLBACK_RSRP {
        description "SINR measurement quantity with fallback to RSRP if SINR is not supported.";
      }
      enum SINR_FALLBACK_RSRQ {
        description "SINR measurement quantity with fallback to RSRQ if SINR is not supported.";
      }
      enum RSRP_AND_RSRQ {
        description "RSRP and RSRQ measurement quantities.";
      }
      enum RSRP_AND_SINR_FALLBACK_RSRQ {
        description "RSRP and SINR measurement quantities with fallback to RSRQ if SINR is not supported.";
      }
      enum RSRP_AND_SINR_NO_FALLBACK {
        description "RSRP and SINR measurement quantities without fallback if SINR is not supported.";
      }
    }
  }
  typedef McpcQuantity {
    description "Measurement quantities applicable to MCPC function.";
    type enumeration {
      enum RSRP {
        description "Reference signal received power.";
      }
      enum RSRQ {
        description "Reference signal received quality.";
      }
      enum SINR_NO_FALLBACK {
        description "Signal to Interference Noise Ratio, no fallback. If UE does not support SINR measurement, no fallback to instead use RSRP or RSRQ.";
      }
      enum SINR_FALLBACK_RSRQ {
        description "Signal to Interference Noise Ratio, fallback RSRQ. If UE does not support SINR measurement, fallback to instead use RSRQ as trigger quantity.";
      }
      enum SINR_FALLBACK_RSRP {
        description "Signal to Interference Noise Ratio, fallback RSRP. If UE does not support SINR measurement, fallback to instead use RSRP as trigger quantity.";
      }
      enum UL_SINR {
        description "Uplink signal to interference and noise ratio.";
      }
    }
  }
  typedef MdtMeasurementName {
    description "MDT measurement names.";
    type enumeration {
      enum __UNDEFINED__ {
      }
    }
  }
  typedef MdtReportIntervalNR {
    description "MDT report interval for NR.";
    type enumeration {
      enum MS_1024 {
        description "1024 ms.";
      }
      enum MS_2048 {
        description "2048 ms.";
      }
      enum MS_5120 {
        description "5120 ms.";
      }
      enum MS_10240 {
        description "10240 ms.";
      }
      enum MS_20480 {
        description "20480 ms.";
      }
      enum MS_40960 {
        description "40960 ms.";
      }
      enum MIN_1 {
        description "1 minute.";
      }
    }
  }
  typedef MdtReportQuantityNR {
    description "MDT report quantity for NR.";
    type enumeration {
      enum RSRP {
        description "Reference Signal Received Power.";
      }
      enum RSRQ {
        description "Reference Signal Received Quality.";
      }
      enum SINR {
        description "Signal to Interference and Noise Ratio.";
      }
      enum RSRP_RSRQ {
        description "Reference Signal Received Power and Reference Signal Received Quality.";
      }
      enum RSRP_SINR {
        description "Reference Signal Received Power and Signal to Interference and Noise Ratio.";
      }
      enum RSRQ_SINR {
        description "Reference Signal Received Quality and Signal to Interference and Noise Ratio.";
      }
      enum RSRP_RSRQ_SINR {
        description "RSRP, RSRQ and SINR.";
      }
    }
  }
  typedef MdtReportingTrigger {
    description "MDT reporting trigger.";
    type enumeration {
      enum PERIODIC {
        description "Periodic MDT measurement reporting.";
      }
      enum A2EVENT_TRIGGERED {
        description "A2 event-triggered measurement reporting.";
      }
      enum A2EVENT_TRIGGERED_PERIODIC {
        description "A2 event-triggered periodic measurement reporting.";
      }
    }
  }
  typedef MdtTriggerQuantityNR {
    description "MDT trigger quantity for NR.";
    type enumeration {
      enum RSRP {
        description "Reference Signal Received Power.";
      }
      enum RSRQ {
        description "Reference Signal Received Quality.";
      }
      enum SINR {
        description "Signal to Interference and Noise Ratio.";
      }
    }
  }
  typedef MlcCellSetChangeAction {
    description "Cell set change action(s) for multi-layer coordination. Handover is a cell set change that always changes PCell. SCell reselection is a cell set change that keeps current PCell but changes SCell configuration.";
    type enumeration {
      enum HANDOVER {
        description "Handover. Handover is a cell set change that always changes PCell.";
      }
      enum SCELL_RESELECTION {
        description "SCell reselection. SCell reselection is a cell set change that keeps current PCell but changes SCell configuration.";
      }
      enum HO_AND_SCELL_RESELECTION {
        description "Handover and SCell reselection.";
      }
    }
  }
  typedef NRCellServiceState {
    description "Cell service state.";
    type enumeration {
      enum OUT_OF_SERVICE {
        description "Cell is not operational and cannot serve UE instances. The gNodeB Distributed Unit (gNodeB-DU) is trying to make cell operational.";
      }
      enum IN_SERVICE {
        description "Cell is operational and Master Information Block is broadcast. UE instances can be served when active external connections are present.";
      }
    }
  }
  typedef NRCellState {
    description "Cell states.";
    type enumeration {
      enum IDLE {
        description "The resource is not currently in use.";
      }
      enum INACTIVE {
        description "The cell is known by both the gNodeB-DU and the gNodeB-CU-CP. The cell shall not serve UEs.";
      }
      enum ACTIVE {
        description "The cell is known by both the gNodeB-DU and the gNodeB-CU-CP. The cell should try to provide service to the UEs.";
      }
    }
  }
  typedef NrdcQuantity {
    description "Measurement quantity that triggers a measurement event and additional quantity evaluation.";
    type enumeration {
      enum __UNDEFINED__ {
      }
    }
  }
  typedef OperState {
    description "Operational states of a resource.";
    type enumeration {
      enum DISABLED {
        description "The resource is totally inoperable.";
      }
      enum ENABLED {
        description "The resource is partially or fully operable.";
      }
    }
  }
  typedef PWSRestartHandling {
    description "Whether PWS restart handling is supported.";
    type enumeration {
      enum DISABLED {
        description "PWS restart and failure messages cannot be sent to AMF.";
      }
      enum ENABLED {
        description "PWS restart and failure messages can be sent to AMF.";
      }
    }
  }
  typedef PciConflictDetectionEcgiMeas {
    description "ECGI measurement to UE for PCI conflict suspicious cell allowed state.";
    type enumeration {
      enum DISABLED {
        description "ECGI measurement for PCI conflict suspicious cell is disabled.";
      }
      enum ENABLED {
        description "ECGI measurement for PCI conflict suspicious cell is enabled.";
      }
    }
  }
  typedef PciConflictDetectionNcgiMeas {
    description "NCGI measurement to UE for PCI conflict suspicious cell allowed state.";
    type enumeration {
      enum DISABLED {
        description "NCGI measurement for PCI conflict suspicious cell is disabled.";
      }
      enum FR1 {
        description "NCGI measurement for PCI conflict suspicious cell is enabled for FR1.";
      }
    }
  }
  typedef PciConflictMobilityEcgiMeas {
    description "ECGI measurement-based IRAT mobility allowed state.";
    type enumeration {
      enum DISABLED {
        description "ECGI measurement-based IRAT mobility is disabled.";
      }
      enum ENABLED {
        description "ECGI measurement-based IRAT mobility is enabled.";
      }
    }
  }
  typedef PciConflictMobilityNcgiMeas {
    description "NCGI measurement-based intra-NR mobility allowed range.";
    type enumeration {
      enum DISABLED {
        description "NCGI measurement-based intra-NR mobility is disabled.";
      }
      enum FR1 {
        description "NCGI measurement-based intra-NR mobility is enabled for FR1.";
      }
    }
  }
  typedef PciConflictTargetSelectMode {
    description "Method of selecting target cell in PCI conflict.";
    type enumeration {
      enum DISABLED {
        description "First found cell relation is selected cell for mobility in PCI configuration.";
      }
      enum HITRATE_BASED {
        description "Target cell with higher CGI hit-rate is selected for mobility in PCI conflict configuration.";
      }
      enum MANUAL_BASED {
        description "Target cell that is manually selected for mobility in PCI conflict configuration. Preferred target cell is selected by setting NRCellRelation::preferredCellManual or EUtranCellRelation::preferredCellManual to true.";
      }
      enum HITRATE_MANUAL_BASED {
        description "Primary method of target cell selection is HITRATE_BASED, secondary is MANUAL_BASED.";
      }
      enum MANUAL_HITRATE_BASED {
        description "Primary method of target cell selection is MANUAL_BASED, secondary is HITRATE_BASED.";
      }
    }
  }
  typedef PciConflicted {
    description "States whether PCI conflict exists.";
    type enumeration {
      enum NO {
        description "PCI conflict with another cell that is resolved.";
      }
      enum YES {
        description "PCI conflict with another cell that is listed in pciConflictedCell.";
      }
    }
  }
  typedef PimDetectionRole {
    description "Role for PIM detection.";
    type enumeration {
      enum AGGRESSOR {
        description "Only aggressor role is selected for PIM detection.";
      }
      enum VICTIM {
        description "Only victim role is selected for PIM detection.";
      }
      enum VICTIM_AND_AGGRESSOR {
        description "Victim and aggressor roles are selected for PIM detection.";
      }
    }
  }
  typedef PimDetectionStatus {
    description "Status of PIM detection as a PIM victim.";
    type enumeration {
      enum NOT_APPLICABLE {
        description "Not applicable to PIM detection as a PIM victim.";
      }
      enum NO_PIM_DETECTED {
        description "PIM is not detected by PIM detection.";
      }
      enum PIM_DETECTED {
        description "PIM is detected by PIM detection, so it can be identified as PIM victim.";
      }
    }
  }
  typedef PimType {
    description "PIM detection type.";
    type enumeration {
      enum __UNDEFINED__ {
      }
    }
  }
  typedef PmUeReportType {
    description "Report type selected for PM purpose.";
    type enumeration {
      enum PERIODICAL {
        description "Periodical measurement report.";
      }
      enum EVENT_A2 {
        description "Event A2 measurement report.";
      }
      enum EVENT_A3 {
        description "Event A3 measurement report.";
      }
    }
  }
  typedef PowerClass {
    description "UE power class.";
    type enumeration {
      enum PC_1 {
        description "Power Class 1.";
      }
      enum PC_1_5 {
        description "Power Class 1_5.";
      }
      enum PC_2 {
        description "Power Class 2.";
      }
    }
  }
  typedef PredUeCapConfig {
    description "Configuration of predefined UE capability usage.";
    type enumeration {
      enum __UNDEFINED__ {
      }
    }
  }
  typedef PrefInterGnbHoType {
    description "Preferred inter-gNodeB handover type. Xn based or NG based handover can be supported.";
    type enumeration {
      enum XN_HO {
        description "Possibility to use Xn based handover is evaluated.";
      }
      enum NG_HO {
        description "NG based handover is used.";
      }
    }
  }
  typedef ProhibitCellTriggerConfig {
    description "Configuration of measurements for prohibited cell triggered mobility.";
    type enumeration {
      enum DISABLED {
        description "Prohibited cell triggered mobility is disabled.";
      }
      enum ENABLED_EUTRAN_ONLY {
        description "Prohibited cell triggered mobility is enabled, only E-UTRAN frequencies are configured.";
      }
      enum ENABLED_ALL {
        description "Prohibited cell triggered mobility is enabled, both NR and E-UTRAN frequencies are configured.";
      }
    }
  }
  typedef PuemReportQuantity {
    description "Periodical UE measurement report quantity.";
    type enumeration {
      enum RSRP {
        description "Reference Signal Received Power.";
      }
      enum RSRQ {
        description "Reference Signal Received Quality.";
      }
      enum SINR {
        description "Signal to Interference and Noise Ratio.";
      }
      enum RSRP_RSRQ {
        description "RSRP and RSRQ.";
      }
      enum RSRP_SINR {
        description "RSRP and SINR.";
      }
      enum RSRQ_SINR {
        description "RSRQ and SINR.";
      }
      enum RSRP_RSRQ_SINR {
        description "RSRP, RSRQ and SINR.";
      }
      enum NO_QUANTITY {
        description "No quantity.";
      }
    }
  }
  typedef RelPrefProhibitTimerLength {
    description "Length of release preference prohibit timer.";
    type enumeration {
      enum S0 {
        description "Prohibit timer is set to 0 seconds.";
      }
      enum S0DOT5 {
        description "Prohibit timer is set to half a second.";
      }
      enum S1 {
        description "Prohibit timer is set to 1 second.";
      }
      enum S2 {
        description "Prohibit timer is set to 2 seconds.";
      }
      enum S3 {
        description "Prohibit timer is set to 3 seconds.";
      }
      enum S4 {
        description "Prohibit timer is set to 4 seconds.";
      }
      enum S5 {
        description "Prohibit timer is set to 5 seconds.";
      }
      enum S6 {
        description "Prohibit timer is set to 6 seconds.";
      }
      enum S7 {
        description "Prohibit timer is set to 7 seconds.";
      }
      enum S8 {
        description "Prohibit timer is set to 8 seconds.";
      }
      enum S9 {
        description "Prohibit timer is set to 9 seconds.";
      }
      enum S10 {
        description "Prohibit timer is set to 10 seconds.";
      }
      enum S20 {
        description "Prohibit timer is set to 20 seconds.";
      }
      enum S30 {
        description "Prohibit timer is set to 30 seconds.";
      }
      enum INFINITY {
        description "Release preference can only be sent once.";
      }
    }
  }
  typedef ReleasePrefOverride {
    description "RRC state to be preferred by gNodeB for UE when UEAssistanceInformation message is received.";
    type enumeration {
      enum IDLE {
        description "UE release preference is overridden with RRC idle state.";
      }
      enum INACTIVE {
        description "UE release preference is overridden with RRC inactive state.";
      }
      enum NO_PREFERENCE {
        description "UE release preference is not overridden.";
      }
    }
  }
  typedef ReportAmount {
    description "Number of periodical or event-triggered measurement reports.";
    type enumeration {
      enum R1 {
        description "One report.";
      }
      enum R2 {
        description "Two reports.";
      }
      enum R4 {
        description "Four reports.";
      }
      enum R8 {
        description "Eight reports.";
      }
      enum R16 {
        description "16 reports.";
      }
      enum R32 {
        description "32 reports.";
      }
      enum R64 {
        description "64 reports.";
      }
      enum INFINITY {
        description "Infinite number of reports.";
      }
    }
  }
  typedef ReportConfigA6Mode {
    description "Configuration mode for A6 measurement report. Cell referring to parent of this class is used as a PCell or PSCell for UE.";
    type enumeration {
      enum ALWAYS {
        description "A6 measurement reports are always configured for all SCell frequencies.";
      }
      enum CONDITIONAL {
        description "A6 measurement reports are conditionally configured. A6 is configured if there is more than one SCell candidate in the same frequency.";
      }
    }
  }
  typedef ReportInterval {
    description "Interval between periodical reports.";
    type enumeration {
      enum MS_120 {
        description "120 ms interval.";
      }
      enum MS_240 {
        description "240 ms interval.";
      }
      enum MS_480 {
        description "480 ms interval.";
      }
      enum MS_640 {
        description "640 ms interval.";
      }
      enum MS_1024 {
        description "1024 ms interval.";
      }
      enum MS_2048 {
        description "2048 ms interval.";
      }
      enum MS_5120 {
        description "5120 ms interval.";
      }
      enum MS_10240 {
        description "10240 ms interval.";
      }
      enum MS_20480 {
        description "20480 ms interval.";
      }
      enum MS_40960 {
        description "40960 ms interval.";
      }
      enum MIN_1 {
        description "1 minute.";
      }
      enum MIN_6 {
        description "6 minutes.";
      }
      enum MIN_12 {
        description "12 minutes.";
      }
      enum MIN_30 {
        description "30 minutes.";
      }
    }
  }
  typedef RibTmAdditionalInfo {
    description "Information about any Radio-Interface Based Time Monitoring error.";
    type enumeration {
      enum FEATURE_DEACTIVATED {
        description "Radio Interface-Based Time Monitoring feature deactivated on monitoring node.";
      }
      enum PEER_FEATURE_DEACTIVATED {
        description "Radio Interface-Based Time Monitoring feature deactivated on assisting node.";
      }
      enum UNSUPP_HW_CONF {
        description "Unsupported hardware configuration on monitoring node.";
      }
      enum PEER_UNSUPP_HW_CONF {
        description "Unsupported hardware configuration on assisting node.";
      }
      enum MAX_PAIRS {
        description "Maximum number of measurement pairs on monitoring node exceeded.";
      }
      enum PEER_MAX_PAIRS {
        description "Maximum number of measurement pairs on assisting node exceeded.";
      }
      enum NO_RESP_FROM_PEER {
        description "No response from assisting node.";
      }
      enum PCI_CONFLICT {
        description "PCI conflict.";
      }
      enum INCOMPATIBLE_CELLS {
        description "Incompatible cell settings.";
      }
      enum CELL_DISABLED {
        description "Monitoring cell disabled.";
      }
      enum PEER_CELL_DISABLED {
        description "Assisting cell disabled.";
      }
    }
  }
  typedef RibTmMeasurementQuality {
    description "Information about quality of Radio Interface-Based Time Monitoring measurements.";
    type enumeration {
      enum NO_MEASUREMENTS {
        description "No Radio Interface-Based Time Monitoring measurements available.";
      }
      enum UNKNOWN {
        description "Radio Interface-BasedTime Monitoring quality is not yet possible to evaluate.";
      }
      enum RELIABLE {
        description "Radio Interface-Based Time Monitoring measurements are reliable.";
      }
      enum UNRELIABLE {
        description "Radio Interface-Based Time Monitoring measurements are unreliable.";
      }
    }
  }
  typedef RimOffloadType {
    description "RIM triggered offload action type.";
    type enumeration {
      enum NOT_ALLOWED {
        description "RIM triggered offload is not applicable.";
      }
      enum BLIND_RWR {
        description "Blind release with redirect is used for RIM triggered offload.";
      }
    }
  }
  typedef RlcMode {
    description "RLC mode.";
    type enumeration {
      enum AM {
        description "RLC mode is AM.";
      }
      enum UM {
        description "RLC mode is UM Bidirectional.";
      }
    }
  }
  typedef RobustUeCapEnquiryUseCase {
    description "Mode of robust UE capability enquiry.";
    type enumeration {
      enum COMBINED_THEN_SPLIT {
        description "UE capability enquiry sent for NR and EUTRA together and if failure possibly send them separately.";
      }
      enum SPLIT_ONLY {
        description "UE capability enquiry is sent for NR and EUTRA separately.";
      }
      enum COMBINED_ONLY {
        description "UE capability enquiry is sent for NR and EUTRA together.";
      }
    }
  }
  typedef RreSupportType {
    description "Support type of RRC Re-establishment.";
    type enumeration {
      enum NO_RRE_SUPPORT {
        description "No RRE support.";
      }
      enum INTRA_GNB_RRE {
        description "Support is only for intra-gNodeB RRE.";
      }
      enum INTRA_INTER_GNB_RRE {
        description "Support is for intra- and inter-gNodeB RREs.";
      }
    }
  }
  typedef RsrpAddQuantityEval {
    description "Additional radio quantity evaluation. Valid for measurement events with trigger quantity RSRP.";
    type enumeration {
      enum NONE {
        description "No additional evaluation.";
      }
      enum RSRQ {
        description "Additional evaluation is made on reported RSRQ value.";
      }
      enum SINR_FALLBACK_RSRQ {
        description "Additional evaluation is made on reported SINR value for UEs supporting SINR measurement. For UEs not supporting SINR measurement additional evaluation is instead made on reported RSRQ value.";
      }
      enum SINR_NO_FALLBACK_RSRQ {
        description "Additional evaluation is made on reported SINR value for UEs supporting SINR measurement. For UEs not supporting SINR measurement additional evaluation is not made on reported RSRQ value.";
      }
    }
  }
  typedef RsrqAddQuantityEval {
    description "Additional radio quantity evaluation. Valid for measurement events with trigger quantity RSRQ.";
    type enumeration {
      enum NONE {
        description "No additional evaluation.";
      }
      enum RSRP {
        description "Additional evaluation is made on reported RSRP value.";
      }
    }
  }
  typedef SCellCandidate {
    description "SCell candidate status.";
    type enumeration {
      enum NOT_ALLOWED {
        description "Not allowed as SCell candidate.";
      }
      enum ALLOWED {
        description "Allowed as SCell candidate for both uplink and downlink CA.";
      }
      enum ONLY_ALLOWED_FOR_DL {
        description "Allowed as SCell candidate for only downlink CA.";
      }
    }
  }
  typedef ServingCellSelectionPolicy {
    description "Criteria for selecting serving cell set for a UE connection.";
    type enumeration {
      enum PRIORITIZE_DL_THP {
        description "Prioritize downlink throughput in serving cell set selection.";
      }
      enum PRIORITIZE_UL_THP {
        description "Prioritize uplink throughput in serving cell set selection.";
      }
      enum PRIO_DL_THP_THEN_PCELL_UL_THP {
        description "Prioritize downlink throughput in serving cell set selection. In case of cell sets with equal estimated downlink throughput weight, cell set with best estimated uplink throughput weight for the PCell is selected.";
      }
    }
  }
  typedef SinrAddQuantityEval {
    description "Additional radio quantity evaluation. Valid for measurement events with trigger quantity SINR.";
    type enumeration {
      enum NONE {
        description "No additional evaluation.";
      }
      enum RSRP {
        description "Additional evaluation is made on reported RSRP value.";
      }
      enum RSRQ {
        description "Additional evaluation is made on reported RSRQ value.";
      }
      enum RSRP_AND_RSRQ {
        description "Additional evaluation is made on reported RSRP and RSRQ values.";
      }
    }
  }
  typedef SnssaiValidationMode {
    description "Validation mode of gNodeB regarding unconfigured S-NSSAI.";
    type enumeration {
      enum __UNDEFINED__ {
      }
    }
  }
  typedef SupportedCoverage {
    description "Coverage relation.";
    type enumeration {
      enum NONE {
        description "No coverage relation between cells.";
      }
      enum COVERS {
        description "Related cell covers current cell.";
      }
      enum OVERLAP {
        description "Related cell and current cell has approximately the same coverage area.";
      }
      enum CONTAINED_IN {
        description "Related cell is contained in current cell.";
      }
    }
  }
  typedef TnlAssocUsage {
    description "Usage of TNL association.";
    type enumeration {
      enum BOTH {
        description "Both UE-associated and non-UE associated signaling.";
      }
      enum UE {
        description "UE-associated signaling only.";
      }
      enum NON_UE {
        description "Non-UE associated signaling only.";
      }
    }
  }
  typedef TriggerQuantity {
    description "The measurement quantity that triggers a measurement event.";
    type enumeration {
      enum RSRP {
        description "RSRP (Reference Signal Received Power) is used.";
      }
      enum RSRQ {
        description "RSRQ (Reference Signal Received Quality) is used.";
      }
    }
  }
  typedef TriggerQuantity2 {
    description "Measurement quantity that triggers a measurement event.";
    type enumeration {
      enum RSRP {
        description "RSRP is used.";
      }
      enum RSRQ {
        description "RSRQ is used.";
      }
      enum SINR_FALLBACK_RSRP {
        description "SINR is used. For UEs not supporting SINR measurement on NR frequencies RSRP is used instead.";
      }
      enum SINR_FALLBACK_RSRQ {
        description "SINR is used. For UEs not supporting SINR measurement on NR frequencies RSRQ is used instead.";
      }
    }
  }
  typedef UcmReportQuantity {
    description "UE coverage measurement report quantity.";
    type enumeration {
      enum RSRP {
        description "Reference Signal Received Power.";
      }
      enum RSRQ {
        description "Reference Signal Received Quality.";
      }
      enum SINR {
        description "Signal to Interference and Noise Ratio.";
      }
      enum RSRP_RSRQ {
        description "RSRP and RSRQ.";
      }
      enum RSRP_SINR {
        description "RSRP and SINR.";
      }
      enum RSRQ_SINR {
        description "RSRQ and SINR.";
      }
      enum RSRP_RSRQ_SINR {
        description "RSRP, RSRQ and SINR.";
      }
    }
  }
  typedef UeConfGroupType {
    description "UE configuration group type.";
    type enumeration {
      enum UE_MOBILITY_GROUP {
        description "UE mobility group. Defined by UeMobilityGroupDefinition MO class.";
      }
      enum UE_SERVICE_GROUP {
        description "UE service group. Defined by UeServiceGroupDefinition MO class.";
      }
      enum UE_ADMISSION_GROUP {
        description "UE admission group. Defined by UeAdmissionGroupDefinition MO class.";
      }
    }
  }
  typedef UePositioningPeriodicityMode {
    description "Periodicity mode for NR Advanced UE Location Support feature.";
    type enumeration {
      enum COMB_PERIODICITY {
        description "Measurement Periodicity NR-AoA is used when having same value as Measurement Periodicity. E-CID MEASUREMENT INITIATION REQUEST is accepted if Information Element Measurement Periodicity NR-AoA (NR Angle of Arrival) has same value as Information Element Measurement Periodicity.";
      }
      enum AOA_PERIODICITY {
        description "Measurement Periodicity NR-AoA used. Information Element Measurement Periodicity NR-AoA (NR Angle of Arrival) in E-CID MEASUREMENT INITIATION REQUEST is used in case measurement quantity NR-AoA is requested.";
      }
    }
  }
  typedef UlCaConfigurationMode {
    description "Configuration mode for uplink aspect of SCell.";
    type enumeration {
      enum IMMEDIATE {
        description "Uplink aspect of SCell is configured in first NR RRC Reconfiguration. Uplink SCell configuration does not use PCell coverage measurement report from UE.";
      }
      enum DELAYED_ALWAYS {
        description "Uplink aspect of SCell is configured in subsequent NR RRC Reconfiguration. First NR RRC Reconfiguration configures downlink aspect of SCell and PCell coverage measurement report in UE. Upon reception of PCell coverage measurement report from UE, uplink aspect of SCell is configured in subsequent NR RRC Reconfiguration.";
      }
      enum DELAYED_CONDITIONAL {
        description "Uplink aspect of SCell is configured in subsequent NR RRC Reconfiguration. When UE-configured maximum output power for uplink carrier aggregation is less than UE-configured maximum output power for PCell, configuration of uplink aspect of SCell is delayed. See 3GPP TS 38.101-1, section 6.2.4 and section 6.2A.4. First NR RRC Reconfiguration configures downlink aspect of SCell and PCell coverage measurement report in UE. Upon reception of PCell coverage measurement report from UE, uplink aspect of SCell is configured in subsequent NR RRC Reconfiguration.";
      }
    }
  }
  typedef UlCompCellCandidate {
    description "Uplink coordinated multi-point reception cell partner status.";
    type enumeration {
      enum __UNDEFINED__ {
      }
    }
  }
  typedef UlCompStatusCause {
    description "Additional information on status of uplink coordinated multi-point reception.";
    type enumeration {
      enum __UNDEFINED__ {
      }
    }
  }
  typedef UlSuMimoFr1Prevention {
    description "Cell types where use of Uplink Single-User MIMO is prevented.";
    type enumeration {
      enum NONE {
        description "No prevention applied.";
      }
      enum TDD {
        description "Prevention applied to TDD cells.";
      }
      enum FDD {
        description "Prevention applied to FDD cells.";
      }
      enum TDD_AND_FDD {
        description "Prevention applied to both FDD and TDD cells.";
      }
    }
  }
  typedef UpdateAmfConnectionOption {
    description "Options on how to handle update of AMFs connections.";
    type enumeration {
      enum RETAIN_EXISTING {
        description "Retains all AMFs and connections that are included in DNS response. AMFs and connections that are not included in the response are removed. For AMFs domain names and IP addresses that are unknown for gNodeB, gNodeB establishes connections to those AMFs.";
      }
      enum RENEW_ALL {
        description "gNodeB releases all connections and AMFs. New DNS lookups are made and AMF termpoints and connections are created for AMFs that are included in DNS response. Traffic may be disturbed by this option.";
      }
    }
  }
  grouping Arp5qiPair-struct {
    description "ARP and 5QI pairs.";
    leaf arp {
      description "range 0..15; Default value: 0.";
      type eytypes:int32_range_0-15;
      default "0";
    }
    leaf profile5qi {
      description "range 0..255; Default value: 0.";
      type eytypes:int32_range_0-255;
      default "0";
    }
  }
  grouping BlockedGNodeBInfo-struct {
    description "Configuration of blocked neighbor gNodeB. When gNodeB is blocked, Xn connection to it is blocked.";
    leaf directPacketForwarding {
      description "Default value: true.";
      type boolean;
      default "true";
    }
    leaf gNBId {
      description "range -1..4294967295; Default value: 0.";
      type int64 {
        range "-1..4294967295";
      }
      default "0";
    }
    leaf gNBIdLength {
      description "range 22..32; Default value: 22.";
      type eytypes:int32_range_22-32;
      default "22";
    }
    leaf mcc {
      description "range 0..999; Default value: 1.";
      type int32 {
        range "0..999";
      }
      default "1";
    }
    leaf mnc {
      description "range 0..999; Default value: 1.";
      type int32 {
        range "0..999";
      }
      default "1";
    }
    leaf mncLength {
      description "range 2..3; Default value: 2.";
      type int32 {
        range "2..3";
      }
      default "2";
    }
  }
  grouping Chipset-struct {
    description "UE chipset identifier.";
    leaf maxVer {
      description "range 0..99999; Default value: 99999.";
      type int32 {
        range "0..99999";
      }
      default "99999";
    }
    leaf minVer {
      description "range 0..128; Default value: 0.";
      type int32 {
        range "0..128";
      }
      default "0";
    }
    leaf variant {
      description "range 0..64; Default value: 0.";
      type int32 {
        range "0..64";
      }
      default "0";
    }
    leaf vendor {
      description "range 0..16; Default value: 0.";
      type eytypes:int32_range_0-16;
      default "0";
    }
  }
  grouping EssCellScPair-struct {
    description "The eNodeB-gNodeB Sector Carrier pair used for ESS operation.";
    leaf eNBessLocalScId {
      description "range 0..99999; Default value: 0.";
      type int32 {
        range "0..99999";
      }
      default "0";
    }
    leaf essScPairId {
      description "range 0..9223372036854775807; Default value: 0.";
      type int64 {
        range "0..9223372036854775807";
      }
      default "0";
    }
    leaf gNBessLocalScId {
      description "range 0..99999; Default value: 0.";
      type int32 {
        range "0..99999";
      }
      default "0";
    }
  }
  grouping EUtraCgi-struct {
    description "EUtran Cell Global Identity.";
    leaf cellLocalId {
      description "range 0..255; Default value: 0.";
      type eytypes:int32_range_0-255;
      default "0";
    }
    leaf eNodeBId {
      description "range 0..1048575; Default value: 0.";
      type eytypes:int32_range_0-1048575;
      default "0";
    }
    leaf mcc {
      description "range 0..999; Default value: 1.";
      type int32 {
        range "0..999";
      }
      default "1";
    }
    leaf mnc {
      description "range 0..999; Default value: 1.";
      type int32 {
        range "0..999";
      }
      default "1";
    }
    leaf mncLength {
      description "range 2..3; Default value: 2.";
      type int32 {
        range "2..3";
      }
      default "2";
    }
  }
  grouping EUtranFreqPrio-struct {
    description "Element of E-UTRAN frequency priority list. Used in Cell Reselection Priorities IE in RRCRelease message.";
    leaf cellReselectionPriority {
      description "range 0..7; Default value: 7.";
      type eytypes:int32_range_0-7;
      default "7";
    }
    leaf cellReselectionSubPriority {
      description "Default value: 0.";
      type int32 {
        range "0 | 2 | 4 | 6 | 8";
      }
      default "0";
    }
    leaf eUtranArfcn {
      type int32 {
        range "0..17999 | 36000..262143";
      }
    }
  }
  grouping GlobalUniqueAmfId-struct {
    description "Globally Unique AMF Identifier (GUAMI).";
    leaf amfPointer {
      description "range 0..63; Default value: 0.";
      type eytypes:int32_range_0-63;
      default "0";
    }
    leaf amfRegionId {
      description "range 0..255; Default value: 0.";
      type eytypes:int32_range_0-255;
      default "0";
    }
    leaf amfSetId {
      description "range 0..1023; Default value: 0.";
      type eytypes:int32_range_0-1023-21;
      default "0";
    }
    leaf mcc {
      description "length 3..3; Default value: 001.";
      type string {
        length "3";
        pattern "[02345679][0-9][0-9]";
      }
      default "001";
    }
    leaf mnc {
      description "length 2..3; Default value: 01.";
      type string {
        length "2..3";
        pattern "(([0-9][0-9][0-9])|([0-9][0-9]))";
      }
      default "01";
    }
  }
  grouping GlobalUniqueAmfRegionId-struct {
    description "AMF regions to which the external gNodeB belongs.";
    leaf amfRegionId {
      description "range 0..255; Default value: 0.";
      type eytypes:int32_range_0-255;
      default "0";
    }
    leaf mcc {
      description "length 3..3; Default value: 001.";
      type string {
        length "3";
        pattern "[02345679][0-9][0-9]";
      }
      default "001";
    }
    leaf mnc {
      description "length 2..3; Default value: 01.";
      type string {
        length "2..3";
        pattern "(([0-9][0-9][0-9])|([0-9][0-9]))";
      }
      default "01";
    }
  }
  grouping ImeiTacSvSn-struct {
    description "Represents IMEISV type allocation code, software version range, and serial number range.";
    leaf maxSn {
      description "range 0..999999; Default value: 999999.";
      type int32 {
        range "0..999999";
      }
      default "999999";
    }
    leaf maxSvn {
      description "range 0..99; Default value: 99.";
      type eytypes:int32_range_0-99;
      default "99";
    }
    leaf minSn {
      description "range 0..999999; Default value: 0.";
      type int32 {
        range "0..999999";
      }
      default "0";
    }
    leaf minSvn {
      description "range 0..99; Default value: 0.";
      type eytypes:int32_range_0-99;
      default "0";
    }
    leaf tac {
      description "range 0..99999999; Default value: 0.";
      type int32 {
        range "0..99999999";
      }
      default "0";
    }
  }
  grouping LoadParameters-struct {
    description "Parameters used for traffic load and time duration definitions.";
    leaf threshold {
      description "range 0..100; Default value: 10.";
      type eytypes:int32_range_0-100;
      default "10";
      units "percent";
    }
    leaf timeDuration {
      description "range 60..86400; Default value: 900.";
      type int32 {
        range "60..86400";
      }
      default "900";
      units "s";
    }
  }
  grouping LwNeighborRelEUtranInfo-struct {
    description "Lightweight representation of an E-UTRAN neighbor relation.";
    leaf cellLocalId {
      description "range 0..255.";
      type eytypes:int32_range_0-255;
    }
    leaf eNBId {
      description "range 0..1048575.";
      type eytypes:int32_range_0-1048575;
    }
    leaf eUtranPCI {
      description "range 0..503.";
      type eytypes:int32_range_0-503;
    }
    leaf mcc {
      description "length 3..3.";
      type string {
        length "3";
      }
    }
    leaf mnc {
      description "length 2..3.";
      type string {
        length "2..3";
      }
    }
  }
  grouping LwNeighborRelInfo-struct {
    description "Lightweight representation of an NR neighbor relation.";
    leaf cellLocalId {
      description "range 0..16383.";
      type eytypes:int32_range_0-16383;
    }
    leaf gNBId {
      description "range 0..4294967295.";
      type eytypes:int64_range_0-4294967295;
    }
    leaf gNBIdLength {
      description "range 22..32.";
      type eytypes:int32_range_22-32;
    }
    leaf mcc {
      description "length 3..3.";
      type string {
        length "3";
      }
    }
    leaf mnc {
      description "length 2..3.";
      type string {
        length "2..3";
      }
    }
    leaf nRPCI {
      description "range 0..1007.";
      type int32 {
        range "0..1007";
      }
    }
  }
  grouping Ncgi-struct {
    description "NR Cell Global Identity.";
    leaf cellLocalId {
      description "range 0..16383; Default value: 0.";
      type eytypes:int32_range_0-16383;
      default "0";
    }
    leaf gNBId {
      description "range 0..4294967295; Default value: 0.";
      type eytypes:int64_range_0-4294967295;
      default "0";
    }
    leaf gNBIdLength {
      description "range 22..32; Default value: 22.";
      type eytypes:int32_range_22-32;
      default "22";
    }
    leaf mcc {
      description "range 0..999; Default value: 1.";
      type int32 {
        range "0..999";
      }
      default "1";
    }
    leaf mnc {
      description "range 0..999; Default value: 1.";
      type int32 {
        range "0..999";
      }
      default "1";
    }
    leaf mncLength {
      description "range 2..3; Default value: 2.";
      type int32 {
        range "2..3";
      }
      default "2";
    }
  }
  grouping NRFreqPrio-struct {
    description "Element of NR frequency priority list. Used in Cell Reselection Priorities IE in RRCRelease message.";
    leaf cellReselectionPriority {
      description "range 0..7; Default value: 7.";
      type eytypes:int32_range_0-7;
      default "7";
    }
    leaf cellReselectionSubPriority {
      description "Default value: 0.";
      type int32 {
        range "0 | 2 | 4 | 6 | 8";
      }
      default "0";
    }
    leaf nrArfcn {
      description "range 0..3279165.";
      type eytypes:int32_range_0-3279165;
    }
  }
  grouping PimDetectionAggressorSetInfo-struct {
    description "Information about set of aggressors in Passive Intermodulation (PIM) detection.";
  }
  grouping PLMNId-struct {
    description "PLMN Identity consisting of Mobile Country Code (MCC) and Mobile Network Code (MNC).";
    leaf mcc {
      description "length 3..3.";
      type string {
        length "3";
        pattern "[02345679][0-9][0-9]";
      }
    }
    leaf mnc {
      description "length 2..3.";
      type string {
        length "2..3";
        pattern "(([0-9][0-9][0-9])|([0-9][0-9]))";
      }
    }
  }
  grouping PuemReportConfigPeriodical-struct {
    description "Periodical report configuration for UE measurement.";
    leaf includeBeamMeas {
      description "Default value: true.";
      type boolean;
      default "true";
    }
    leaf maxNoOfRsIndexesToReport {
      description "range 0..32; Default value: 1.";
      type eytypes:int32_range_0-32;
      default "1";
    }
    leaf maxReportCells {
      description "range 1..8; Default value: 8.";
      type eytypes:int32_range_1-8;
      default "8";
    }
    leaf reportAddNeighMeas {
      description "Default value: true.";
      type boolean;
      default "true";
    }
    leaf reportAmount {
      type enumeration {
        enum R1;
        enum R2;
        enum R4;
        enum R8;
        enum R16;
        enum R32;
        enum R64;
        enum INFINITY;
      }
    }
    leaf reportInterval {
      type enumeration {
        enum MS_120;
        enum MS_240;
        enum MS_480;
        enum MS_640;
        enum MS_1024;
        enum MS_2048;
        enum MS_5120;
        enum MS_10240;
        enum MS_20480;
        enum MS_40960;
        enum MIN_1;
        enum MIN_6;
        enum MIN_12;
        enum MIN_30;
      }
    }
    leaf reportQuantityCell {
      type enumeration {
        enum RSRP;
        enum RSRQ;
        enum SINR;
        enum RSRP_RSRQ;
        enum RSRP_SINR;
        enum RSRQ_SINR;
        enum RSRP_RSRQ_SINR;
        enum NO_QUANTITY;
      }
    }
    leaf reportQuantityRsIndex {
      type enumeration {
        enum RSRP;
        enum RSRQ;
        enum SINR;
        enum RSRP_RSRQ;
        enum RSRP_SINR;
        enum RSRQ_SINR;
        enum RSRP_RSRQ_SINR;
        enum NO_QUANTITY;
      }
    }
  }
  grouping ReportConfigA1A2Rsrp-struct {
    description "Report configuration settings for UE DL A1, A2, or both measurements with trigger quantity RSRP.";
    leaf hysteresis {
      description "range 0..150; Default value: 10.";
      type eytypes:int32_range_0-150;
      default "10";
      units "dB";
    }
    leaf threshold {
      description "range -156..-29; Default value: -156.";
      type eytypes:int32_range_-156--29;
      default "-156";
      units "dBm";
    }
    leaf timeToTrigger {
      description "Default value: 160.";
      type int32 {
        range "0 | 40 | 64 | 80 | 100 | 128 | 160 | 256 | 320 | 480 | 512 | 640 | 1024 | 1280 | 2560 | 5120";
      }
      default "160";
      units "ms";
    }
    leaf timeToTriggerA1 {
      description "Default value: -1.";
      type int32 {
        range "-1..0 | 40 | 64 | 80 | 100 | 128 | 160 | 256 | 320 | 480 | 512 | 640 | 1024 | 1280 | 2560 | 5120";
      }
      default "-1";
      units "ms";
    }
  }
  grouping ReportConfigA1A2RsrpPcOffset-struct {
    description "Threshold offsets for high power UE for report configuration for A1, A2, or both measurements. Applied when trigger quantity is RSRP.";
    leaf powerClass {
      type enumeration {
        enum PC_1;
        enum PC_1_5;
        enum PC_2;
      }
    }
    leaf thresholdOffset {
      description "range -100..100; Default value: 0.";
      type eytypes:int32_range_-100-100;
      default "0";
      units "dB";
    }
  }
  grouping ReportConfigA1A2Rsrq-struct {
    description "Report configuration settings for A1 and A2 measurements when trigger quantity is RSRQ.";
    leaf hysteresis {
      description "range 0..150; Default value: 10.";
      type eytypes:int32_range_0-150;
      default "10";
      units "dB";
    }
    leaf threshold {
      description "range -435..200; Default value: -435.";
      type eytypes:int32_range_-435-200;
      default "-435";
      units "dB";
    }
    leaf timeToTrigger {
      description "Default value: 160.";
      type int32 {
        range "0 | 40 | 64 | 80 | 100 | 128 | 160 | 256 | 320 | 480 | 512 | 640 | 1024 | 1280 | 2560 | 5120";
      }
      default "160";
      units "ms";
    }
    leaf timeToTriggerA1 {
      description "Default value: -1.";
      type int32 {
        range "-1..0 | 40 | 64 | 80 | 100 | 128 | 160 | 256 | 320 | 480 | 512 | 640 | 1024 | 1280 | 2560 | 5120";
      }
      default "-1";
      units "ms";
    }
  }
  grouping ReportConfigA1A2Sinr-struct {
    description "Report configuration settings for A1 and A2 measurements when trigger quantity is SINR.";
    leaf hysteresis {
      description "range 0..150; Default value: 10.";
      type eytypes:int32_range_0-150;
      default "10";
      units "dB";
    }
    leaf threshold {
      description "range -230..405; Default value: -230.";
      type int32 {
        range "-230..405";
      }
      default "-230";
      units "dB";
    }
    leaf timeToTrigger {
      description "Default value: 640.";
      type int32 {
        range "0 | 40 | 64 | 80 | 100 | 128 | 160 | 256 | 320 | 480 | 512 | 640 | 1024 | 1280 | 2560 | 5120";
      }
      default "640";
      units "ms";
    }
    leaf timeToTriggerA1 {
      description "Default value: -1.";
      type int32 {
        range "-1..0 | 40 | 64 | 80 | 100 | 128 | 160 | 256 | 320 | 480 | 512 | 640 | 1024 | 1280 | 2560 | 5120";
      }
      default "-1";
      units "ms";
    }
  }
  grouping ReportConfigA2Rsrp-struct {
    description "Report configuration settings for A2 measurement event when trigger quantity is RSRP.";
    leaf hysteresis {
      description "range 0..150; Default value: 10.";
      type eytypes:int32_range_0-150;
      default "10";
      units "dB";
    }
    leaf threshold {
      description "range -156..-29; Default value: -156.";
      type eytypes:int32_range_-156--29;
      default "-156";
      units "dBm";
    }
    leaf timeToTrigger {
      description "Default value: 160.";
      type int32 {
        range "0 | 40 | 64 | 80 | 100 | 128 | 160 | 256 | 320 | 480 | 512 | 640 | 1024 | 1280 | 2560 | 5120";
      }
      default "160";
      units "ms";
    }
  }
  grouping ReportConfigA2Rsrq-struct {
    description "Report configuration settings for A2 measurement event when trigger quantity is RSRQ.";
    leaf hysteresis {
      description "range 0..150; Default value: 10.";
      type eytypes:int32_range_0-150;
      default "10";
      units "dB";
    }
    leaf threshold {
      description "range -435..200; Default value: -435.";
      type eytypes:int32_range_-435-200;
      default "-435";
      units "dB";
    }
    leaf timeToTrigger {
      description "Default value: 160.";
      type int32 {
        range "0 | 40 | 64 | 80 | 100 | 128 | 160 | 256 | 320 | 480 | 512 | 640 | 1024 | 1280 | 2560 | 5120";
      }
      default "160";
      units "ms";
    }
  }
  grouping ReportConfigA2Sinr-struct {
    description "Report configuration settings for A2 measurement event when trigger quantity is SINR.";
    leaf hysteresis {
      description "range 0..150; Default value: 10.";
      type eytypes:int32_range_0-150;
      default "10";
      units "dB";
    }
    leaf threshold {
      description "range -230..405; Default value: -230.";
      type int32 {
        range "-230..405";
      }
      default "-230";
      units "dB";
    }
    leaf timeToTrigger {
      description "Default value: 160.";
      type int32 {
        range "0 | 40 | 64 | 80 | 100 | 128 | 160 | 256 | 320 | 480 | 512 | 640 | 1024 | 1280 | 2560 | 5120";
      }
      default "160";
      units "ms";
    }
  }
  grouping ReportConfigA3Rsrp-struct {
    description "Report configuration settings for A3 measurement events when trigger quantity is RSRP.";
    leaf hysteresis {
      description "range 0..150; Default value: 10.";
      type eytypes:int32_range_0-150;
      default "10";
      units "dB";
    }
    leaf offset {
      description "range -150..150; Default value: 30.";
      type eytypes:int32_range_-150-150;
      default "30";
      units "dB";
    }
    leaf timeToTrigger {
      description "Default value: 640.";
      type int32 {
        range "0 | 40 | 64 | 80 | 100 | 128 | 160 | 256 | 320 | 480 | 512 | 640 | 1024 | 1280 | 2560 | 5120";
      }
      default "640";
      units "ms";
    }
  }
  grouping ReportConfigA3Rsrq-struct {
    description "Report configuration settings for A3 measurement events when trigger quantity is RSRQ.";
    leaf hysteresis {
      description "range 0..150; Default value: 10.";
      type eytypes:int32_range_0-150;
      default "10";
      units "dB";
    }
    leaf offset {
      description "range -150..150; Default value: 30.";
      type eytypes:int32_range_-150-150;
      default "30";
      units "dB";
    }
    leaf timeToTrigger {
      description "Default value: 640.";
      type int32 {
        range "0 | 40 | 64 | 80 | 100 | 128 | 160 | 256 | 320 | 480 | 512 | 640 | 1024 | 1280 | 2560 | 5120";
      }
      default "640";
      units "ms";
    }
  }
  grouping ReportConfigA3Sinr-struct {
    description "Report configuration settings for A3 measurement events when trigger quantity is SINR.";
    leaf hysteresis {
      description "range 0..150; Default value: 10.";
      type eytypes:int32_range_0-150;
      default "10";
      units "dB";
    }
    leaf offset {
      description "range -150..150; Default value: 30.";
      type eytypes:int32_range_-150-150;
      default "30";
      units "dB";
    }
    leaf timeToTrigger {
      description "Default value: 640.";
      type int32 {
        range "0 | 40 | 64 | 80 | 100 | 128 | 160 | 256 | 320 | 480 | 512 | 640 | 1024 | 1280 | 2560 | 5120";
      }
      default "640";
      units "ms";
    }
  }
  grouping ReportConfigA4Rsrp-struct {
    description "Report configuration settings for A4 measurement event when trigger quantity is RSRP.";
    leaf hysteresis {
      description "range 0..150; Default value: 10.";
      type eytypes:int32_range_0-150;
      default "10";
      units "dB";
    }
    leaf threshold {
      description "range -156..-29; Default value: -156.";
      type eytypes:int32_range_-156--29;
      default "-156";
      units "dBm";
    }
    leaf timeToTrigger {
      description "Default value: 0.";
      type int32 {
        range "0 | 40 | 64 | 80 | 100 | 128 | 160 | 256 | 320 | 480 | 512 | 640 | 1024 | 1280 | 2560 | 5120";
      }
      default "0";
      units "ms";
    }
  }
  grouping ReportConfigA4Rsrq-struct {
    description "Report configuration settings for A4 measurement event when trigger quantity is RSRQ.";
  }
  grouping ReportConfigA4Sinr-struct {
    description "Report configuration settings for A4 measurement event when trigger quantity is SINR.";
  }
  grouping ReportConfigA5NoThr1Rsrp-struct {
    description "Report configuration settings for A5 measurement event when trigger quantity is RSRP. Report configuration settings for A5 measurement event when trigger quantity is RSRP and where threshold1 is not used.";
    leaf hysteresis {
      description "range 0..150; Default value: 10.";
      type eytypes:int32_range_0-150;
      default "10";
      units "dB";
    }
    leaf threshold2 {
      description "range -156..-29; Default value: -156.";
      type eytypes:int32_range_-156--29;
      default "-156";
      units "dBm";
    }
    leaf timeToTrigger {
      description "Default value: 640.";
      type int32 {
        range "0 | 40 | 64 | 80 | 100 | 128 | 160 | 256 | 320 | 480 | 512 | 640 | 1024 | 1280 | 2560 | 5120";
      }
      default "640";
      units "ms";
    }
  }
  grouping ReportConfigA5NoThr1RsrpPcOffset-struct {
    description "Threshold2 offsets for high power UE for report configuration for A5 measurement. Applied when trigger quantity is RSRP.";
    leaf powerClass {
      type enumeration {
        enum PC_1;
        enum PC_1_5;
        enum PC_2;
      }
    }
    leaf threshold2Offset {
      description "range -100..100; Default value: 0.";
      type eytypes:int32_range_-100-100;
      default "0";
      units "dB";
    }
  }
  grouping ReportConfigA5NoThr1Rsrq-struct {
    description "Report configuration settings for A5 measurement event when trigger quantity is RSRQ. Report configuration settings for A5 measurement event when trigger quantity is RSRQ and where threshold1 is not used.";
    leaf hysteresis {
      description "range 0..150; Default value: 10.";
      type eytypes:int32_range_0-150;
      default "10";
      units "dB";
    }
    leaf threshold2 {
      description "range -435..200; Default value: -435.";
      type eytypes:int32_range_-435-200;
      default "-435";
      units "dB";
    }
    leaf timeToTrigger {
      description "Default value: 640.";
      type int32 {
        range "0 | 40 | 64 | 80 | 100 | 128 | 160 | 256 | 320 | 480 | 512 | 640 | 1024 | 1280 | 2560 | 5120";
      }
      default "640";
      units "ms";
    }
  }
  grouping ReportConfigA5NoThr1Sinr-struct {
    description "Report configuration settings for A5 measurement event when trigger quantity is SINR. Report configuration settings for A5 measurement event when trigger quantity is SINR and where threshold1 is not used.";
    leaf hysteresis {
      description "range 0..150; Default value: 10.";
      type eytypes:int32_range_0-150;
      default "10";
      units "dB";
    }
    leaf threshold2 {
      description "range -230..405; Default value: -230.";
      type int32 {
        range "-230..405";
      }
      default "-230";
      units "dB";
    }
    leaf timeToTrigger {
      description "Default value: 640.";
      type int32 {
        range "0 | 40 | 64 | 80 | 100 | 128 | 160 | 256 | 320 | 480 | 512 | 640 | 1024 | 1280 | 2560 | 5120";
      }
      default "640";
      units "ms";
    }
  }
  grouping ReportConfigA5Rsrp-struct {
    description "Report configuration settings for A5 measurement event when trigger quantity is RSRP.";
    leaf hysteresis {
      description "range 0..150; Default value: 10.";
      type eytypes:int32_range_0-150;
      default "10";
      units "dB";
    }
    leaf threshold1 {
      description "range -156..-29; Default value: -156.";
      type eytypes:int32_range_-156--29;
      default "-156";
      units "dBm";
    }
    leaf threshold2 {
      description "range -156..-29; Default value: -156.";
      type eytypes:int32_range_-156--29;
      default "-156";
      units "dBm";
    }
    leaf timeToTrigger {
      description "Default value: 640.";
      type int32 {
        range "0 | 40 | 64 | 80 | 100 | 128 | 160 | 256 | 320 | 480 | 512 | 640 | 1024 | 1280 | 2560 | 5120";
      }
      default "640";
      units "ms";
    }
  }
  grouping ReportConfigA5RsrpOffsets-struct {
    description "Threshold offsets for report configuration setting for A5 measurement event. Applied when trigger quantity is RSRP.";
    leaf threshold1Offset {
      description "range -100..100; Default value: 0.";
      type eytypes:int32_range_-100-100;
      default "0";
      units "dB";
    }
    leaf threshold2Offset {
      description "range -100..100; Default value: 0.";
      type eytypes:int32_range_-100-100;
      default "0";
      units "dB";
    }
  }
  grouping ReportConfigA5RsrpPcOffset-struct {
    description "Threshold offsets for high power UE for report configuration for A5 measurement. Applied when trigger quantity is RSRP.";
    leaf powerClass {
      type enumeration {
        enum PC_1;
        enum PC_1_5;
        enum PC_2;
      }
    }
    leaf threshold1Offset {
      description "range -100..100; Default value: 0.";
      type eytypes:int32_range_-100-100;
      default "0";
      units "dB";
    }
    leaf threshold2Offset {
      description "range -100..100; Default value: 0.";
      type eytypes:int32_range_-100-100;
      default "0";
      units "dB";
    }
  }
  grouping ReportConfigA5Rsrq-struct {
    description "Report configuration settings for A5 measurement event when trigger quantity is RSRQ.";
    leaf hysteresis {
      description "range 0..150; Default value: 10.";
      type eytypes:int32_range_0-150;
      default "10";
      units "dB";
    }
    leaf threshold1 {
      description "range -435..200; Default value: -435.";
      type eytypes:int32_range_-435-200;
      default "-435";
      units "dB";
    }
    leaf threshold2 {
      description "range -435..200; Default value: -435.";
      type eytypes:int32_range_-435-200;
      default "-435";
      units "dB";
    }
    leaf timeToTrigger {
      description "Default value: 640.";
      type int32 {
        range "0 | 40 | 64 | 80 | 100 | 128 | 160 | 256 | 320 | 480 | 512 | 640 | 1024 | 1280 | 2560 | 5120";
      }
      default "640";
      units "ms";
    }
  }
  grouping ReportConfigA5RsrqOffsets-struct {
    description "Threshold offsets for report configuration setting for A5 measurement event. Applied when trigger quantity is RSRQ.";
    leaf threshold1Offset {
      description "range -100..100; Default value: 0.";
      type eytypes:int32_range_-100-100;
      default "0";
      units "dB";
    }
    leaf threshold2Offset {
      description "range -100..100; Default value: 0.";
      type eytypes:int32_range_-100-100;
      default "0";
      units "dB";
    }
  }
  grouping ReportConfigA5Sinr-struct {
    description "Report configuration settings for A5 measurement event when trigger quantity is SINR.";
    leaf hysteresis {
      description "range 0..150; Default value: 10.";
      type eytypes:int32_range_0-150;
      default "10";
      units "dB";
    }
    leaf threshold1 {
      description "range -230..405; Default value: -230.";
      type int32 {
        range "-230..405";
      }
      default "-230";
      units "dB";
    }
    leaf threshold2 {
      description "range -230..405; Default value: -230.";
      type int32 {
        range "-230..405";
      }
      default "-230";
      units "dB";
    }
    leaf timeToTrigger {
      description "Default value: 640.";
      type int32 {
        range "0 | 40 | 64 | 80 | 100 | 128 | 160 | 256 | 320 | 480 | 512 | 640 | 1024 | 1280 | 2560 | 5120";
      }
      default "640";
      units "ms";
    }
  }
  grouping ReportConfigA5SinrOffsets-struct {
    description "Threshold offsets for report configuration setting for A5 measurement event. Applied when trigger quantity is SINR.";
    leaf threshold1Offset {
      description "range -100..100; Default value: 0.";
      type eytypes:int32_range_-100-100;
      default "0";
      units "dB";
    }
    leaf threshold2Offset {
      description "range -100..100; Default value: 0.";
      type eytypes:int32_range_-100-100;
      default "0";
      units "dB";
    }
  }
  grouping ReportConfigA6Rsrp-struct {
    description "Report configuration settings for A6 measurement event when trigger quantity is RSRP.";
    leaf hysteresis {
      description "range 0..150; Default value: 10.";
      type eytypes:int32_range_0-150;
      default "10";
      units "dB";
    }
    leaf offset {
      description "range -150..150; Default value: 30.";
      type eytypes:int32_range_-150-150;
      default "30";
      units "dB";
    }
    leaf timeToTrigger {
      description "Default value: 160.";
      type int32 {
        range "0 | 40 | 64 | 80 | 100 | 128 | 160 | 256 | 320 | 480 | 512 | 640 | 1024 | 1280 | 2560 | 5120";
      }
      default "160";
      units "ms";
    }
  }
  grouping ReportConfigA6Rsrq-struct {
    description "Report configuration settings for A6 measurement event when trigger quantity is RSRQ.";
    leaf hysteresis {
      description "range 0..150; Default value: 10.";
      type eytypes:int32_range_0-150;
      default "10";
      units "dB";
    }
    leaf offset {
      description "range -150..150; Default value: 30.";
      type eytypes:int32_range_-150-150;
      default "30";
      units "dB";
    }
    leaf timeToTrigger {
      description "Default value: 160.";
      type int32 {
        range "0 | 40 | 64 | 80 | 100 | 128 | 160 | 256 | 320 | 480 | 512 | 640 | 1024 | 1280 | 2560 | 5120";
      }
      default "160";
      units "ms";
    }
  }
  grouping ReportConfigA6Sinr-struct {
    description "Report configuration settings for A6 measurement event when trigger quantity is SINR.";
    leaf hysteresis {
      description "range 0..150; Default value: 10.";
      type eytypes:int32_range_0-150;
      default "10";
      units "dB";
    }
    leaf offset {
      description "range -150..150; Default value: 30.";
      type eytypes:int32_range_-150-150;
      default "30";
      units "dB";
    }
    leaf timeToTrigger {
      description "Default value: 160.";
      type int32 {
        range "0 | 40 | 64 | 80 | 100 | 128 | 160 | 256 | 320 | 480 | 512 | 640 | 1024 | 1280 | 2560 | 5120";
      }
      default "160";
      units "ms";
    }
  }
  grouping ReportConfigB1Rsrp-struct {
    description "Report configuration settings for E-UTRA B1 measurement event when trigger quantity is RSRP.";
    leaf hysteresis {
      description "range 0..150; Default value: 10.";
      type eytypes:int32_range_0-150;
      default "10";
      units "dB";
    }
    leaf threshold {
      description "range -140..-44; Default value: -140.";
      type eytypes:int32_range_-140--44;
      default "-140";
      units "dBm";
    }
    leaf timeToTrigger {
      description "Default value: 40.";
      type int32 {
        range "0 | 40 | 64 | 80 | 100 | 128 | 160 | 256 | 320 | 480 | 512 | 640 | 1024 | 1280 | 2560 | 5120";
      }
      default "40";
      units "ms";
    }
  }
  grouping ReportConfigB1Rsrq-struct {
    description "Report configuration settings for E-UTRA B1 measurement event when trigger quantity is RSRQ.";
    leaf hysteresis {
      description "range 0..150; Default value: 10.";
      type eytypes:int32_range_0-150;
      default "10";
      units "dB";
    }
    leaf threshold {
      description "range -195..-30; Default value: -195.";
      type eytypes:int32_range_-195--30;
      default "-195";
      units "dB";
    }
    leaf timeToTrigger {
      description "Default value: 40.";
      type int32 {
        range "0 | 40 | 64 | 80 | 100 | 128 | 160 | 256 | 320 | 480 | 512 | 640 | 1024 | 1280 | 2560 | 5120";
      }
      default "40";
      units "ms";
    }
  }
  grouping ReportConfigB1Sinr-struct {
    description "Report configuration settings for E-UTRA B1 measurement event when trigger quantity is SINR.";
    leaf hysteresis {
      description "range 0..150; Default value: 10.";
      type eytypes:int32_range_0-150;
      default "10";
      units "dB";
    }
    leaf threshold {
      description "range -230..405; Default value: -230.";
      type int32 {
        range "-230..405";
      }
      default "-230";
      units "dB";
    }
    leaf timeToTrigger {
      description "Default value: 40.";
      type int32 {
        range "0 | 40 | 64 | 80 | 100 | 128 | 160 | 256 | 320 | 480 | 512 | 640 | 1024 | 1280 | 2560 | 5120";
      }
      default "40";
      units "ms";
    }
  }
  grouping ReportConfigB2NoThr2RsrpPcOffset-struct {
    description "Threshold1 offsets for high power UE for report configuration for B2 measurement. Applied when trigger quantity is RSRP.";
    leaf powerClass {
      type enumeration {
        enum PC_1;
        enum PC_1_5;
        enum PC_2;
      }
    }
    leaf threshold1Offset {
      description "range -100..100; Default value: 0.";
      type eytypes:int32_range_-100-100;
      default "0";
      units "dB";
    }
  }
  grouping ReportConfigB2Rsrp-struct {
    description "Report configuration settings for B2 measurement event when trigger quantity is RSRP.";
    leaf hysteresis {
      description "range 0..150; Default value: 10.";
      type eytypes:int32_range_0-150;
      default "10";
      units "dB";
    }
    leaf threshold1 {
      description "range -156..-29; Default value: -156.";
      type eytypes:int32_range_-156--29;
      default "-156";
      units "dBm";
    }
    leaf threshold2EUtra {
      description "range -140..-44; Default value: -140.";
      type eytypes:int32_range_-140--44;
      default "-140";
      units "dBm";
    }
    leaf timeToTrigger {
      description "Default value: 640.";
      type int32 {
        range "0 | 40 | 64 | 80 | 100 | 128 | 160 | 256 | 320 | 480 | 512 | 640 | 1024 | 1280 | 2560 | 5120";
      }
      default "640";
      units "ms";
    }
  }
  grouping ReportConfigB2RsrpOffsets-struct {
    description "Threshold offsets for report configuration setting for B2 measurement event. Applied when trigger quantity is RSRP.";
    leaf threshold1Offset {
      description "range -100..100; Default value: 0.";
      type eytypes:int32_range_-100-100;
      default "0";
      units "dB";
    }
    leaf threshold2EUtraOffset {
      description "range -100..100; Default value: 0.";
      type eytypes:int32_range_-100-100;
      default "0";
      units "dB";
    }
  }
  grouping ReportConfigB2Rsrq-struct {
    description "Report configuration settings for B2 measurement event when trigger quantity is RSRQ.";
    leaf hysteresis {
      description "range 0..150; Default value: 10.";
      type eytypes:int32_range_0-150;
      default "10";
      units "dB";
    }
    leaf threshold1 {
      description "range -435..200; Default value: -435.";
      type eytypes:int32_range_-435-200;
      default "-435";
      units "dB";
    }
    leaf threshold2EUtra {
      description "range -195..-30; Default value: -195.";
      type eytypes:int32_range_-195--30;
      default "-195";
      units "dB";
    }
    leaf timeToTrigger {
      description "Default value: 640.";
      type int32 {
        range "0 | 40 | 64 | 80 | 100 | 128 | 160 | 256 | 320 | 480 | 512 | 640 | 1024 | 1280 | 2560 | 5120";
      }
      default "640";
      units "ms";
    }
  }
  grouping ReportConfigB2RsrqOffsets-struct {
    description "Threshold offsets for report configuration setting for B2 measurement event. Applied when trigger quantity is RSRQ.";
    leaf threshold1Offset {
      description "range -100..100; Default value: 0.";
      type eytypes:int32_range_-100-100;
      default "0";
      units "dB";
    }
    leaf threshold2EUtraOffset {
      description "range -100..100; Default value: 0.";
      type eytypes:int32_range_-100-100;
      default "0";
      units "dB";
    }
  }
  grouping ReportConfigB2Sinr-struct {
    description "Report configuration settings for B2 measurement event when trigger quantity is SINR.";
    leaf hysteresis {
      description "range 0..150; Default value: 10.";
      type eytypes:int32_range_0-150;
      default "10";
      units "dB";
    }
    leaf threshold1 {
      description "range -230..405; Default value: -230.";
      type int32 {
        range "-230..405";
      }
      default "-230";
      units "dB";
    }
    leaf threshold2EUtra {
      description "range -230..405; Default value: -230.";
      type int32 {
        range "-230..405";
      }
      default "-230";
      units "dB";
    }
    leaf timeToTrigger {
      description "Default value: 640.";
      type int32 {
        range "0 | 40 | 64 | 80 | 100 | 128 | 160 | 256 | 320 | 480 | 512 | 640 | 1024 | 1280 | 2560 | 5120";
      }
      default "640";
      units "ms";
    }
  }
  grouping ReportConfigB2SinrOffsets-struct {
    description "Threshold offsets for report configuration setting for B2 measurement event. Applied when trigger quantity is SINR.";
    leaf threshold1Offset {
      description "range -100..100; Default value: 0.";
      type eytypes:int32_range_-100-100;
      default "0";
      units "dB";
    }
    leaf threshold2EUtraOffset {
      description "range -100..100; Default value: 0.";
      type eytypes:int32_range_-100-100;
      default "0";
      units "dB";
    }
  }
  grouping ReportConfigLtmA3Rsrp-struct {
    description "Report configuration settings for LTM A3 measurement events when trigger quantity is RSRP. LTM stands for L1/L2 Triggered Mobility.";
  }
  grouping ReportConfigPeriodical-struct {
    description "Report configuration for UE coverage measurement.";
    leaf includeBeamMeas {
      description "Default value: false.";
      type boolean;
      default "false";
    }
    leaf maxNoOfRsIndexesToReport {
      description "range 1..32; Default value: 1.";
      type eytypes:int32_range_1-32;
      default "1";
    }
    leaf maxReportCells {
      description "range 1..8; Default value: 8.";
      type eytypes:int32_range_1-8;
      default "8";
    }
    leaf reportAddNeighMeas {
      description "Default value: true.";
      type boolean;
      default "true";
    }
    leaf reportAmount {
      type enumeration {
        enum R1;
        enum R2;
        enum R4;
        enum R8;
        enum R16;
        enum R32;
        enum R64;
        enum INFINITY;
      }
    }
    leaf reportInterval {
      type enumeration {
        enum MS_120;
        enum MS_240;
        enum MS_480;
        enum MS_640;
        enum MS_1024;
        enum MS_2048;
        enum MS_5120;
        enum MS_10240;
        enum MS_20480;
        enum MS_40960;
        enum MIN_1;
        enum MIN_6;
        enum MIN_12;
        enum MIN_30;
      }
    }
    leaf reportQuantityCell {
      type enumeration {
        enum RSRP;
        enum RSRQ;
        enum SINR;
        enum RSRP_RSRQ;
        enum RSRP_SINR;
        enum RSRQ_SINR;
        enum RSRP_RSRQ_SINR;
      }
    }
    leaf reportQuantityRsIndex {
      type enumeration {
        enum RSRP;
        enum RSRQ;
        enum SINR;
        enum RSRP_RSRQ;
        enum RSRP_SINR;
        enum RSRQ_SINR;
        enum RSRP_RSRQ_SINR;
      }
    }
  }
  grouping ReportConfigPeriodicalEUtran-struct {
    description "Report configuration for periodical UE coverage measurement.";
    leaf maxReportCells {
      description "range 1..8; Default value: 8.";
      type eytypes:int32_range_1-8;
      default "8";
    }
    leaf reportAmount {
      type enumeration {
        enum R1;
        enum R2;
        enum R4;
        enum R8;
        enum R16;
        enum R32;
        enum R64;
        enum INFINITY;
      }
    }
    leaf reportInterval {
      type enumeration {
        enum MS_120;
        enum MS_240;
        enum MS_480;
        enum MS_640;
        enum MS_1024;
        enum MS_2048;
        enum MS_5120;
        enum MS_10240;
        enum MS_20480;
        enum MS_40960;
        enum MIN_1;
        enum MIN_6;
        enum MIN_12;
        enum MIN_30;
      }
    }
    leaf reportQuantity {
      type enumeration {
        enum RSRP;
        enum RSRQ;
        enum SINR;
        enum RSRP_RSRQ;
        enum RSRP_SINR;
        enum RSRQ_SINR;
        enum RSRP_RSRQ_SINR;
      }
    }
  }
  grouping ReportQuantityCell-struct {
    description "Cell measurement quantities to be included in measurement report.";
    leaf rsrp {
      description "Default value: true.";
      type boolean;
      default "true";
    }
    leaf rsrq {
      description "Default value: true.";
      type boolean;
      default "true";
    }
    leaf sinr {
      description "Default value: false.";
      type boolean;
      default "false";
    }
  }
  grouping RfspSpidPair-struct {
    description "RAT Frequency Selection Priority (RFSP) and its mapped Subscriber Profile ID (SPID) value.";
    leaf rfsp {
      description "range 1..256.";
      type eytypes:int32_range_1-256;
    }
    leaf spid {
      description "range 1..256.";
      type eytypes:int32_range_1-256;
    }
  }
  grouping SliceSelectionAssistInfo-struct {
    description "Single Network Slice Selection Assistance Information (S-NSSAI).";
    leaf sd {
      description "range 0..16777215.";
      type eytypes:int32_range_0-16777215;
    }
    leaf sst {
      description "range 0..255.";
      type eytypes:int32_range_0-255;
    }
  }
  grouping SsRssiMeasurement-struct {
    description "Set of slots and symbols, within SMTC measurement duration, used for SS-RSSI measurement.";
    leaf endSymbol {
      type int32 {
        range "1 | 5 | 7 | 11";
      }
    }
    leaf measurementSlots {
      description "length 1..80.";
      type string {
        length "1..80";
        pattern "[0]*1[01]*";
      }
    }
  }
  grouping TimePeriod-struct {
    description "Time period for start and end time of week days which is not allowed for energy saving.";
    leaf endTime {
      description "length 5..5; Default value: 22:00.";
      type string {
        length "5";
        pattern "([0-1][0-9]|2[0-3]):([0-5][0-9])";
      }
      default "22:00";
    }
    leaf fri {
      description "Default value: true.";
      type boolean;
      default "true";
    }
    leaf mon {
      description "Default value: true.";
      type boolean;
      default "true";
    }
    leaf sat {
      description "Default value: true.";
      type boolean;
      default "true";
    }
    leaf startTime {
      description "length 5..5; Default value: 06:00.";
      type string {
        length "5";
        pattern "([0-1][0-9]|2[0-3]):([0-5][0-9])";
      }
      default "06:00";
    }
    leaf sun {
      description "Default value: true.";
      type boolean;
      default "true";
    }
    leaf thu {
      description "Default value: true.";
      type boolean;
      default "true";
    }
    leaf tue {
      description "Default value: true.";
      type boolean;
      default "true";
    }
    leaf wed {
      description "Default value: true.";
      type boolean;
      default "true";
    }
  }
  grouping UeTraceReference-struct {
    description "Contains PLMN ID (MCC and MNC) and trace ID.";
  }
  grouping UlQualMcpcCritical-struct {
    description "Critical uplink radio quality measurement configuration used for MCPC.";
    leaf hysteresis {
      description "range 0..150; Default value: 0.";
      type eytypes:int32_range_0-150;
      default "0";
      units "dB";
    }
    leaf threshold {
      description "range -150..500; Default value: -50.";
      type int32 {
        range "-150..500";
      }
      default "-50";
      units "dB";
    }
    leaf timeToTrigger {
      description "Default value: 160.";
      type int32 {
        range "0 | 40 | 64 | 80 | 100 | 128 | 160 | 256 | 320 | 480 | 512 | 640 | 1024 | 1280 | 2560 | 5120";
      }
      default "160";
      units "ms";
    }
  }
  grouping UlQualMcpcSearchZone-struct {
    description "Search zone uplink radio quality monitoring configuration used for MCPC.";
    leaf hysteresis {
      description "range 0..150; Default value: 40.";
      type eytypes:int32_range_0-150;
      default "40";
      units "dB";
    }
    leaf threshold {
      description "range -150..500; Default value: 70.";
      type int32 {
        range "-150..500";
      }
      default "70";
      units "dB";
    }
    leaf timeToTrigger {
      description "Default value: 160.";
      type int32 {
        range "0 | 40 | 64 | 80 | 100 | 128 | 160 | 256 | 320 | 480 | 512 | 640 | 1024 | 1280 | 2560 | 5120";
      }
      default "160";
      units "ms";
    }
    leaf timeToTriggerA1 {
      description "Default value: -1.";
      type int32 {
        range "-1..0 | 40 | 64 | 80 | 100 | 128 | 160 | 256 | 320 | 480 | 512 | 640 | 1024 | 1280 | 2560 | 5120";
      }
      default "-1";
      units "ms";
    }
  }
  grouping AdditionalPLMNInfo-attributes {
    leaf additionalPLMNInfoId {
      description "The value component of the RDN..";
      type string;
      mandatory true;
    }
    leaf nRTAC {
      description "NR Tracking Area Code (TAC). If empty, NR standalone is not supported for PLMN IDs in pLMNIdList..";
      type int32;
      config false;
    }
    list pLMNIdList {
      config false;
      min-elements 1;
      max-elements 12;
      uses PLMNId-struct;
    }
  }
  grouping AdmissionControl-attributes {
    leaf admissionControlId {
      description "The value component of the RDN..";
      type string;
      mandatory true;
    }
  }
  grouping AdmissionLimit-attributes {
    leaf admissionLimitId {
      description "The value component of the RDN..";
      type string;
      mandatory true;
    }
    leaf maxConnectedUe {
      description "Upper limit for connected users. When number of connected users exceeds this limit, admission and preemption mechanisms of Priority-Based Admission Control affect accessibility and retainability of traffic based on priority of configured users. Limit is also used in NR Unified Access Control to calculate cell load. If 0, UE admission and preemption mechanisms of Priority-Based Admission Control are disabled. Load measure based on number of UEs in NR Unified Access Control is also disabled.; range 0..10000; Default value: 0.";
      type int32 {
        range "0..10000";
      }
      default "0";
    }
    leaf maxConnectedUeOffloadISHo {
      description "Maximum number of connected UEs for offload-triggered inter-system handover. Used together with OffloadCellProfileUeCfg::ueOffloadISHoRatio.; range 0..10000; Default value: 10000.";
      type int32 {
        range "0..10000";
      }
      default "10000";
    }
    leaf preemptionRate {
      description "Intensity of UE preemption. Defines how intensively the preemption mechanisms of Priority-Based Admission Control are triggered to ensure that number of connected users does not exceed configured capacity. If 0, UE preemption mechanisms of Priority-Based Admission Control are disabled.; range 0..100; Default value: 80.";
      type eytypes:int32_range_0-100;
      default "80";
      units "percent";
    }
    leaf-list reservedBy {
      description "Contains a list of MO instances that reserve this MO instance..";
      type string;
      min-elements 0;
    }
  }
  grouping AdmissionPriority-attributes {
    leaf admissionPriorityId {
      description "The value component of the RDN..";
      type string;
      mandatory true;
    }
    leaf-list reservedBy {
      description "Contains a list of MO instances that reserve this MO instance..";
      type string;
      min-elements 0;
    }
    leaf ueConfGroupType {
      description "UE configuration group type. UE configuration group type that is applied in contained AdmissionPriorityUeCfg instances..";
      type enumeration {
        enum UE_MOBILITY_GROUP;
        enum UE_SERVICE_GROUP;
        enum UE_ADMISSION_GROUP;
      }
    }
  }
  grouping AdmissionPriorityUeCfg-attributes {
    leaf admissionPriorityUeCfgId {
      description "The value component of the RDN..";
      type string;
      mandatory true;
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 16;
    }
    leaf-list ueGroupList {
      description "UE group list. List of UE group identifiers. If empty, MO instance matches all UE group identifiers..";
      type eytypes:int32_range_1-255;
      ordered-by user;
      min-elements 0;
      max-elements 16;
    }
    leaf uePriority {
      description "Priority of UE. Used by the admission and preemption mechanisms of Priority-Based Admission Control to prioritize and then admit or preempt users when AdmissionLimit::maxConnectedUe is reached or exceeded. Lower value means higher UE priority.; range 1..255; Default value: 255.";
      type eytypes:int32_range_1-255;
      default "255";
    }
  }
  grouping AnrFunction-attributes {
    leaf anrFunctionId {
      description "The value component of the RDN..";
      type string;
      mandatory true;
    }
    leaf demoteCellRelMobAttThresh {
      description "ANR criteria for cell relation MO instance to be demoted to lightweight cell relation object. A neighbor cell relation MO instance is periodically evaluated and demoted when average mobility attempts number per day is less than or equal to this attribute. Neighbor cell relation MO instance having mobility attempts collected during at least 7 days is considered for demotion based on this attribute. If empty, threshold based automatic demotion is disabled.; range 1..1000.";
      type eytypes:int32_range_1-1000-6;
    }
    leaf lwCellRelationRatio {
      description "Number of lightweight cell relations in proportion of maximum number.; range 0..100.";
      type eytypes:int32_range_0-100;
      config false;
      units "percent";
    }
    leaf promoteCellRelMobAttThresh {
      description "ANR criteria for lightweight neighbor object to be promoted to visible MO instance. A lightweight neighbor object is internally evaluated before it is created as MO instance if number of average mobility attempts per day is higher than or equal to this attribute. If empty, automatic promotion and saturation handling are not enabled.; range 1..1000.";
      type eytypes:int32_range_1-1000-6;
    }
    leaf removeEnbTime {
      description "Time while neighbor eNodeB can be disconnected from gNodeB before being considered for removal. Value 1000 means no automatic removal is performed.; range 1..1000; Default value: 7.";
      type eytypes:int32_range_1-1000;
      default "7";
      units "day";
    }
    leaf removeEUtranFreqRelTime {
      description "Time before removing EUtranFreqRelation instance that refers to a frequency without external cell. If EUtranFreqRelation instance that refers to an EUtranFrequency instance that is configured for LTE CBRS band and unreferenced by any other ExternalEUtranCell instance during this period, it can be removed. If EUtranFrequency instance is configured for LTE CBRS band and unreferenced by ExternalEUtranCell instance and EUtranFreqRelation instance, it can be removed. If 10000, automatic removal is not performed.; range 10..10000; Default value: 10000.";
      type int32 {
        range "10..10000";
      }
      default "10000";
      units "minute";
    }
    leaf removeFreqRelTime {
      description "Maximum time an NRFreqRelation instance can be unreferenced before being considered for removal. If 10000, no automatic removal is performed.; range 10..10000; Default value: 15.";
      type int32 {
        range "10..10000";
      }
      default "15";
      units "minute";
    }
    leaf removeGnbTime {
      description "Time a neighbor gNodeB can be without a relation to this gNodeB before being considered for removal. 1000 means no automatic removal is performed.; range 1..1000; Default value: 7.";
      type eytypes:int32_range_1-1000;
      default "7";
      units "day";
    }
    leaf removeNrelTime {
      description "Maximum time while unused NR cell or E-UTRAN cell remains in RBS. Value 1000 means no automatic removal is performed.; range 1..1000; Default value: 7.";
      type eytypes:int32_range_1-1000;
      default "7";
      units "day";
    }
  }
  grouping AnrFunctionEUtran-attributes {
    leaf anrCgiMeasEUtranEnabled {
      description "Whether ANR with CGI measurement for E-UTRAN is enabled.; Default value: false.";
      type boolean;
      default "false";
    }
    leaf anrFunctionEUtranId {
      description "The value component of the RDN..";
      type string;
      mandatory true;
    }
  }
  grouping AnrFunctionEUtranUeCfg-attributes {
    leaf anrFunctionEUtranUeCfgId {
      description "The value component of the RDN..";
      type string;
      mandatory true;
    }
    leaf ecgiDuringEpsFbEnabled {
      description "Whether ECGI measurement during EPS fallback is enabled. ECGI measurement is triggered when B1 measurement report is received and E-UTRAN cell PCI is not known. Only applicable to EPS fallback of non-emergency voice call.; Default value: true.";
      type boolean;
      default "true";
    }
  }
  grouping AnrFunctionNR-attributes {
    leaf anrAutoCreateXnForEndc {
      description "Whether NR Automated Neighbor Relations feature can create Xn for NR neighbor relation for EN-DC. If true, Xn is created automatically for lightweight NR neighbor relations created by NR Automated Neighbor Relations feature for EN-DC over X2.; Default value: false.";
      type boolean;
      default "false";
    }
    leaf anrCgiMeasInterFreqMode {
      description "ANR with CGI measurement for inter-frequency for RBS..";
      type enumeration {
        enum DISABLED;
        enum FR1;
      }
    }
    leaf anrCgiMeasIntraFreqEnabled {
      description "Whether ANR with CGI measurement for intra frequency is enabled for RBS.; Default value: false.";
      type boolean;
      default "false";
    }
    leaf anrEndcX2Enabled {
      description "Whether ANR for EN-DC over X2 is enabled for NR for one RBS. Only takes effect when ANR feature is enabled.; Default value: false.";
      type boolean;
      default "false";
    }
    leaf anrFunctionNRId {
      description "The value component of the RDN..";
      type string;
      mandatory true;
    }
  }
  grouping AnrFunctionNRUeCfg-attributes {
    leaf adjustedAnrRsrpThreshold {
      description "Adjusted ANR-specific threshold RSRP value. If non-empty, system has reset lightweight cell relations and applied offsetAdjustAnrRsrpThreshold to anrRsrpThreshold. If empty, system has not applied offsetAdjustAnrRsrpThreshold.; range -156..-29.";
      type eytypes:int32_range_-156--29;
      config false;
      units "dBm";
    }
    leaf anrFunctionNRUeCfgId {
      description "The value component of the RDN..";
      type string;
      mandatory true;
    }
    leaf anrRsrpThreshold {
      description "ANR-specific threshold RSRP value for the received Measurement Report Event A3. If received Measurement Report A3 trigger quantity is RSRP and neighbor RSRP value is higher than or equal to this threshold value, ANR action is triggered.; range -156..-29; Default value: -156.";
      type eytypes:int32_range_-156--29;
      default "-156";
      units "dBm";
    }
    leaf anrRsrqThreshold {
      description "ANR-specific threshold RSRQ value for the received Measurement Report Event A3. If received Measurement Report A3 trigger quantity is RSRQ and neighbor RSRQ value is higher than or equal to this threshold value, ANR action is triggered.; range -435..200; Default value: -435.";
      type eytypes:int32_range_-435-200;
      default "-435";
      units "dB";
    }
    leaf anrSinrThreshold {
      description "ANR-specific threshold SINR value for the received event A3 measurement report. If received A3 measurement report trigger quantity is SINR, and neighbor SINR value is higher than or equal to this threshold value, ANR action is triggered.; range -230..405; Default value: -230.";
      type int32 {
        range "-230..405";
      }
      default "-230";
      units "dB";
    }
    leaf offsetAdjustAnrRsrpThreshold {
      description "Offset to adjust ANR-specific RSRP value. If not 0, when maximum number of lightweight cell relations is reached, system resets lightweight cell relations and adds this offset to anrRsrpThreshold. Attribute adjustedAnrRsrpThreshold shows adjusted value. If 0, no adjustment is applied, and lightweight cell relations are not reset.; range 0..127; Default value: 10.";
      type int32 {
        range "0..127";
      }
      default "10";
      units "dB";
    }
  }
  grouping AnrPLMNTable-attributes {
    leaf anrPLMNTableId {
      description "The value component of the RDN..";
      type string;
      mandatory true;
    }
    leaf gNBIdLength {
      description "Length of gNBId bit string representation when ANR extracts gNBId from NCGI. Value is used by ANR when node containing newly found cell belongs to a PLMN that is listed in pLMNIdList in same AnrPLMNTable instance.; range 22..32.";
      type eytypes:int32_range_22-32;
      mandatory true;
    }
    list pLMNIdList {
      key "id";
      leaf id {
        type uint32;
        description "Synthetic key for struct sequence entry.";
      }
      min-elements 1;
      max-elements 11;
      uses PLMNId-struct;
    }
  }
  grouping BarringGroup-attributes {
    leaf-list accessCategoryList {
      description "List of access categories. Access category defines which type of access a UE is attempting to perform. If empty, barring does not occur, regardless if load or rejection conditions are met for sending out barring info. Under each UacProfile instance, one specific access category is only allowed to be specified in one BarringGroup instance if it affects the same PLMN. Note: Explicitly defined access categories in one BarringGroup instance, take precedence over empty access categories defined in other BarringGroup instances if it affects the same PLMN..";
      type eytypes:int32_range_1-10;
      ordered-by user;
      min-elements 0;
      max-elements 10;
    }
    leaf barringGroupId {
      description "The value component of the RDN..";
      type string;
      mandatory true;
    }
    leaf barringTime {
      description "Time during which UE refrains from re-evaluating the possibility of an access attempt.; Default value: 16.";
      type int32 {
        range "4 | 8 | 16 | 32 | 64 | 128 | 256 | 512";
      }
      default "16";
      units "s";
    }
    leaf bgCounterId {
      description "Counter identity. Identity of counter representing this barring group. Set automatically during MO creation.; range 1..8.";
      type eytypes:int32_range_1-8;
      config false;
    }
    leaf cellUsageBarringMax {
      description "Threshold at which maximum probability that a UE is barred occurs. The amount of UEs that are barred is given by maxBarringProbability. If cell usage is above this threshold, maxBarringProbability is broadcast in SIB1. Cell usage is defined as number RRC connected UEs to a cell divided by AdmissionLimit::maxConnectedUe. If AdmissionLimit::maxConnectedUe is 0, this means that cell usage, based on number RRC connected UEs, is not used in unified access control calculations.; range 0..100; Default value: 100.";
      type eytypes:int32_range_0-100;
      default "100";
      units "percent";
    }
    leaf cellUsageBarringStart {
      description "Threshold at which 5 % of UEs are barred. If cell usage is above this threshold, barring information is broadcast in SIB1. Cell usage is defined as number of RRC-connected UEs in a cell divided by AdmissionLimit::maxConnectedUe. If AdmissionLimit::maxConnectedUe is 0, cell usage, based on number RRC connected UEs, is not used in unified access control calculations. Note: If equal to cellUsageBarringMax, amount of barred UEs is defined by maxBarringProbability.; range 0..100; Default value: 100.";
      type eytypes:int32_range_0-100;
      default "100";
      units "percent";
    }
    leaf maxBarringProbability {
      description "Maximum barring probability due to high cell usage. If cell usage is greater than or equal to value specified in cellUsageBarringMax, maximum barring probability is broadcast in SIB1. Cell usage is defined as number RRC connected UEs to a cell, divided by AdmissionLimit::maxConnectedUe. If AdmissionLimit::maxConnectedUe is set to zero, this means that cell usage, based on number RRC connected UEs, is not used in unified access control calculations.; Default value: 0.";
      type int32 {
        range "0 | 5 | 10 | 15 | 20 | 25 | 30 | 40 | 50 | 60 | 70 | 75 | 80 | 85 | 90 | 95 | 100";
      }
      default "0";
      units "percent";
    }
    list pLMNIdList {
      key "id";
      leaf id {
        type uint32;
        description "Synthetic key for struct sequence entry.";
      }
      min-elements 0;
      max-elements 12;
      uses PLMNId-struct;
    }
    leaf rejRatioBarringMax {
      description "Rejection ratio at which 100 % of UEs are barred. Rejection ratio is defined as the number of rejected UEs divided by total number of access attempts.; range 0..100; Default value: 100.";
      type eytypes:int32_range_0-100;
      default "100";
      units "percent";
    }
    leaf rejRatioBarringStart {
      description "Rejection ratio at which 5 % of UEs are barred. This is the lowest rejection ratio at which barring information is broadcast in SIB1. Rejection ratio is defined as number of rejected UEs divided by total number of access attempts.; range 0..100; Default value: 100.";
      type eytypes:int32_range_0-100;
      default "100";
      units "percent";
    }
    leaf startBarringAi1 {
      description "Threshold at which UEs of access identity 1 can be barred. If barring probability is greater than or equal to threshold, UEs of access identity 1 are barred to the same degree as UEs of access identity 0. If 100, barring never occurs. Barring probability is the outcome from calculations made by unified access control. It is defined by settings of following attributes: - cellUsageBarringStart - cellUsageBarringMax - maxBarringProbability - rejRatioBarringStart - rejRatioBarringMax Access identity 1 corresponds to UEs running multimedia priority service traffic.; Default value: 100.";
      type int32 {
        range "0 | 5 | 10 | 15 | 20 | 25 | 30 | 40 | 50 | 60 | 70 | 75 | 80 | 85 | 90 | 95 | 100";
      }
      default "100";
      units "percent";
    }
    leaf startBarringAi11 {
      description "Threshold at which UEs of access identity 11 can be barred. If barring probability is greater than or equal to threshold, UEs of access identity 11 are barred to the same degree as UEs of access identity 0. If 100, barring never occurs. Barring probability is the outcome from calculations made by unified access control. It is defined by settings of following attributes: - cellUsageBarringStart - cellUsageBarringMax - maxBarringProbability - rejRatioBarringStart - rejRatioBarringMax Access identity 11 correspond to LTE Access Classes 11.; Default value: 100.";
      type int32 {
        range "0 | 5 | 10 | 15 | 20 | 25 | 30 | 40 | 50 | 60 | 70 | 75 | 80 | 85 | 90 | 95 | 100";
      }
      default "100";
      units "percent";
    }
    leaf startBarringAi12 {
      description "Threshold at which UEs of access identity 12 can be barred. If barring probability is greater than or equal to threshold, UEs of access identity 12 are barred to the same degree as UEs of access identity 0. If 100, barring never occurs. Barring probability is the outcome from calculations made by unified access control. It is defined by settings of following attributes: - cellUsageBarringStart - cellUsageBarringMax - maxBarringProbability - rejRatioBarringStart - rejRatioBarringMax Access identity 12 correspond to LTE Access Classes 12.; Default value: 100.";
      type int32 {
        range "0 | 5 | 10 | 15 | 20 | 25 | 30 | 40 | 50 | 60 | 70 | 75 | 80 | 85 | 90 | 95 | 100";
      }
      default "100";
      units "percent";
    }
    leaf startBarringAi13 {
      description "Threshold at which UEs of access identity 13 can be barred. If barring probability is greater than or equal to threshold, UEs of access identity 13 are barred to the same degree as UEs of access identity 0. If 100, barring never occurs. Barring probability is the outcome from calculations made by unified access control. It is defined by settings of following attributes: - cellUsageBarringStart - cellUsageBarringMax - maxBarringProbability - rejRatioBarringStart - rejRatioBarringMax Access identity 13 correspond to LTE Access Classes 13; Default value: 100.";
      type int32 {
        range "0 | 5 | 10 | 15 | 20 | 25 | 30 | 40 | 50 | 60 | 70 | 75 | 80 | 85 | 90 | 95 | 100";
      }
      default "100";
      units "percent";
    }
    leaf startBarringAi14 {
      description "Threshold at which UEs of access identity 14 can be barred. If barring probability is greater than or equal to threshold, UEs of access identity 14 are barred to the same degree as UEs of access identity 0. If 100, barring never occurs. Barring probability is the outcome from calculations made by unified access control. It is defined by settings of following attributes: - cellUsageBarringStart - cellUsageBarringMax - maxBarringProbability - rejRatioBarringStart - rejRatioBarringMax Access identity 14 correspond to LTE Access Classes 14.; Default value: 100.";
      type int32 {
        range "0 | 5 | 10 | 15 | 20 | 25 | 30 | 40 | 50 | 60 | 70 | 75 | 80 | 85 | 90 | 95 | 100";
      }
      default "100";
      units "percent";
    }
    leaf startBarringAi15 {
      description "Threshold at which UEs of access identity 15 can be barred. If barring probability is greater than or equal to threshold, UEs of access identity 15 are barred to the same degree as UEs of access identity 0. If 100, barring never occurs. Barring probability is the outcome from calculations made by unified access control. It is defined by settings of following attributes: - cellUsageBarringStart - cellUsageBarringMax - maxBarringProbability - rejRatioBarringStart - rejRatioBarringMax Access identity 15 correspond to LTE Access Classes 15.; Default value: 100.";
      type int32 {
        range "0 | 5 | 10 | 15 | 20 | 25 | 30 | 40 | 50 | 60 | 70 | 75 | 80 | 85 | 90 | 95 | 100";
      }
      default "100";
      units "percent";
    }
    leaf startBarringAi2 {
      description "Threshold at which UEs of access identity 2 can be barred. If barring probability is greater than or equal to threshold, UEs of access identity 2 are barred to the same degree as UEs of access identity 0. If 100, barring never occurs. Barring probability is the outcome from calculations made by unified access control. It is defined by settings of following attributes: - cellUsageBarringStart - cellUsageBarringMax - maxBarringProbability - rejRatioBarringStart - rejRatioBarringMax Access identity 2 corresponds to UEs running mission critical traffic. Only applicable if license for NR Unified Access Control for Mission-Critical Services is present and feature is active.; Default value: 100.";
      type int32 {
        range "0 | 5 | 10 | 15 | 20 | 25 | 30 | 40 | 50 | 60 | 70 | 75 | 80 | 85 | 90 | 95 | 100";
      }
      default "100";
      units "percent";
    }
  }
  grouping BlockedGNodeB-attributes {
    leaf blockedGNodeBId {
      description "The value component of the RDN..";
      type string;
      mandatory true;
    }
    leaf directPacketForwarding {
      description "Whether direct packet forwarding is enabled. Direct packet forwarding is part of NR Mobility feature..";
      type boolean;
    }
    leaf gNBId {
      description "Identity of gNodeB. If -1, all gNBs with specified PLMN are blocked.; range -1..4294967295.";
      type int64 {
        range "-1..4294967295";
      }
    }
    leaf mcc {
      description "Mobile Country Code (MCC) identifies uniquely domicile country of mobile subscriber. If -1, all gNBs with specified gNBId regardless of PLMN are blocked.; range -1..999.";
      type int32 {
        range "-1..999";
      }
    }
    leaf mnc {
      description "Mobile Network Code (MNC) identifies home PLMN of mobile subscription.; range 0..999.";
      type int32 {
        range "0..999";
      }
    }
    leaf mncLength {
      description "Length of Mobile Network Code (MNC).; range 2..3.";
      type int32 {
        range "2..3";
      }
    }
  }
  grouping CaCellMeasProfile-attributes {
    leaf caCellMeasProfileId {
      description "The value component of the RDN..";
      type string;
      mandatory true;
    }
    leaf-list reservedBy {
      description "Contains a list of MO instances that reserve this MO instance..";
      type string;
      min-elements 0;
    }
    leaf ueConfGroupType {
      description "UE configuration group type. UE configuration group type that is applied in contained CaCellMeasProfileUeCfg instances..";
      type enumeration {
        enum UE_MOBILITY_GROUP;
        enum UE_SERVICE_GROUP;
        enum UE_ADMISSION_GROUP;
      }
    }
    leaf userLabel {
      description "Label for free use..";
      type string;
    }
  }
  grouping CaCellMeasProfileUeCfg-attributes {
    leaf betterSCellReportConfigMode {
      description "Condition for better SCell A6 measurement report. Cell referring to parent of this MO instance is used as a PCell or PSCell for UE. Not applicable to High-Band cells..";
      type enumeration {
        enum ALWAYS;
        enum CONDITIONAL;
      }
    }
    leaf betterSCellTriggerQuantity {
      description "Measurement trigger quantity used when detecting neighboring SCells with better downlink coverage. Only applicable to Low-Band and Mid-Band cells..";
      type enumeration {
        enum RSRP;
        enum RSRQ;
        enum SINR_FALLBACK_RSRP;
        enum SINR_FALLBACK_RSRQ;
      }
    }
    leaf caCellMeasProfileUeCfgId {
      description "The value component of the RDN..";
      type string;
      mandatory true;
    }
    leaf maxReportCells {
      description "Maximum number of non-serving cells included in measurement report. Only applicable to event A6.; range 1..8; Default value: 1.";
      type eytypes:int32_range_1-8;
      default "1";
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    list rsrpBetterSCell {
      key "id";
      leaf id {
        type uint32;
        description "Synthetic key for struct attribute.";
      }
      description "RSRP measurement report criteria to detect neighboring SCells with better downlink coverage. Used when betterSCellTriggerQuantity is RSRP. Only applicable to Low-Band and Mid-Band cells..";
      uses ReportConfigA6Rsrp-struct;
    }
    list rsrpSCellCoverage {
      key "id";
      leaf id {
        type uint32;
        description "Synthetic key for struct attribute.";
      }
      description "RSRP measurement report criteria to detect poor or good downlink coverage in SCell. Used when sCellCoverageTriggerQuantity is RSRP. Only applicable to Low-Band and Mid-Band cells..";
      uses ReportConfigA1A2Rsrp-struct;
    }
    list rsrqBetterSCell {
      key "id";
      leaf id {
        type uint32;
        description "Synthetic key for struct attribute.";
      }
      description "RSRQ measurement report criteria to detect neighboring SCells with better downlink coverage. Used when betterSCellTriggerQuantity is RSRQ. Only applicable to Low-Band and Mid-Band cells..";
      uses ReportConfigA6Rsrq-struct;
    }
    list rsrqSCellCoverage {
      key "id";
      leaf id {
        type uint32;
        description "Synthetic key for struct attribute.";
      }
      description "RSRQ measurement report criteria to detect poor or good downlink coverage in SCell. Used when sCellCoverageTriggerQuantity is RSRQ. Only applicable to Low-Band and Mid-Band cells..";
      uses ReportConfigA1A2Rsrq-struct;
    }
    leaf sCellCoverageTriggerQuantity {
      description "Measurement trigger quantity used for SCell downlink coverage measurements. Only applicable to Low-Band and Mid-Band cells..";
      type enumeration {
        enum RSRP;
        enum RSRQ;
        enum SINR_FALLBACK_RSRP;
        enum SINR_FALLBACK_RSRQ;
      }
    }
    list sinrBetterSCell {
      key "id";
      leaf id {
        type uint32;
        description "Synthetic key for struct attribute.";
      }
      description "SINR measurement report criteria to detect neighboring SCells with better downlink coverage. Used when betterSCellTriggerQuantity is SINR. Applicable for UE that support SS-SINR (Synchronization Signal Signal-To-Noise and interference Ratio) measurements. Only applicable to Low-Band and Mid-Band cells..";
      uses ReportConfigA6Sinr-struct;
    }
    list sinrSCellCoverage {
      key "id";
      leaf id {
        type uint32;
        description "Synthetic key for struct attribute.";
      }
      description "SINR measurement report criteria to detect poor or good downlink coverage in SCell. Used when sCellCoverageTriggerQuantity is SINR. Applicable for UE that support SS-SINR (Synchronization Signal Signal-To-Noise and interference Ratio) measurements. Only applicable to Low-Band and Mid-Band cells..";
      uses ReportConfigA1A2Sinr-struct;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 16;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping CaCellProfile-attributes {
    leaf caCellProfileId {
      description "The value component of the RDN..";
      type string;
      mandatory true;
    }
    leaf-list reservedBy {
      description "Contains a list of MO instances that reserve this MO instance..";
      type string;
      min-elements 0;
    }
    leaf ueConfGroupType {
      description "UE configuration group type. UE configuration group type that is applied in contained CaCellProfileUeCfg instances..";
      type enumeration {
        enum UE_MOBILITY_GROUP;
        enum UE_SERVICE_GROUP;
        enum UE_ADMISSION_GROUP;
      }
    }
    leaf userLabel {
      description "Label for free use..";
      type string;
    }
  }
  grouping CaCellProfileUeCfg-attributes {
    leaf-list blockedSCellFreqList {
      description "List of arfcnValueNRDl values that are not allowed as SCells for Carrier Aggregation..";
      type eytypes:int32_range_0-3279165;
      ordered-by user;
      min-elements 0;
      max-elements 32;
    }
    leaf caCellProfileUeCfgId {
      description "The value component of the RDN..";
      type string;
      mandatory true;
    }
    leaf effectiveBwImpactUl2Layer {
      description "Expected uplink throughput gain of having two layers compared with one. Only applicable to Low-Band and Mid-Band cells.; range 0..200; Default value: 180.";
      type int32 {
        range "0..200";
      }
      default "180";
    }
    leaf maxDlCcAllowed {
      description "Maximum number of downlink component carriers allowed.; range 1..32; Default value: 32.";
      type eytypes:int32_range_1-32;
      default "32";
    }
    leaf maxUlCcAllowed {
      description "Maximum number of uplink component carriers allowed.; range 1..32; Default value: 32.";
      type eytypes:int32_range_1-32;
      default "32";
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf servingCellSelectionPolicy {
      description "Criteria for selecting serving cell set for UE connection. Used to prioritize between downlink and uplink throughput in serving cell selection algorithm. Value PRIO_DL_THP_THEN_PCELL_UL_THP is only applicable if license for Uplink-Aware Advanced Multi-Layer Coordination is present and feature is active, otherwise handled as default. Only applicable to Low-Band and Mid-Band cells..";
      type enumeration {
        enum PRIORITIZE_DL_THP;
        enum PRIORITIZE_UL_THP;
        enum PRIO_DL_THP_THEN_PCELL_UL_THP;
      }
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 16;
    }
    leaf-list ueGroupList {
      description "UE group list. List of UE group identifiers. If empty, MO instance matches all UE group identifiers..";
      type eytypes:int32_range_1-255;
      ordered-by user;
      min-elements 0;
      max-elements 16;
    }
    leaf ulCaConfigurationMode {
      description "Configuration mode for uplink aspect of SCell. In immediate configuration, uplink aspect of SCell is configured in first NR RRC Reconfiguration message. In delayed configuration, uplink aspect of SCell is configured in subsequent NR RRC Reconfiguration message after reception of PCell coverage measurement report from UE. Only applicable to Low-Band and Mid-Band cells..";
      type enumeration {
        enum IMMEDIATE;
        enum DELAYED_ALWAYS;
        enum DELAYED_CONDITIONAL;
      }
    }
    leaf ulSuMimoFr1Prevention {
      description "Type of cells for which Uplink Single-User MIMO is prevented for this MO instance. Only applicable to Low-Band and Mid-Band cells..";
      type enumeration {
        enum NONE;
        enum TDD;
        enum FDD;
        enum TDD_AND_FDD;
      }
    }
    leaf ulTxSwitchingAllowed {
      description "Whether uplink TX switching configuration is allowed for CaCellProfileUeCfg instance. Only applicable to Mid-Band cells.; Default value: false.";
      type boolean;
      default "false";
    }
    leaf userLabel {
      description "Label for free use..";
      type string;
    }
  }
  grouping CaFreqRelMeasProfile-attributes {
    leaf caFreqRelMeasProfileId {
      description "The value component of the RDN..";
      type string;
      mandatory true;
    }
    leaf-list reservedBy {
      description "Contains a list of MO instances that reserve this MO instance..";
      type string;
      min-elements 0;
    }
    leaf ueConfGroupType {
      description "UE configuration group type. UE configuration group type that is applied in contained CaFreqRelMeasProfileUeCfg instances..";
      type enumeration {
        enum UE_MOBILITY_GROUP;
        enum UE_SERVICE_GROUP;
        enum UE_ADMISSION_GROUP;
      }
    }
    leaf userLabel {
      description "Label for free use..";
      type string;
    }
  }
  grouping CaFreqRelMeasProfileUeCfg-attributes {
    leaf caFreqRelMeasProfileUeCfgId {
      description "The value component of the RDN..";
      type string;
      mandatory true;
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf rsrpSCellCoverageThrOffset {
      description "RSRP A1 and A2 measurement event threshold offset for SCell coverage measurements. Used in combination with CaCellMeasProfileUeCfg::rsrpSCellCoverage. Only applicable to Low-Band and Mid-Band cells.; range -30..30; Default value: 0.";
      type eytypes:int32_range_-30-30;
      default "0";
      units "dB";
    }
    leaf rsrqSCellCoverageThrOffset {
      description "RSRQ A1 and A2 measurement event threshold offset for SCell coverage measurements. Used in combination with CaCellMeasProfileUeCfg::rsrqSCellCoverage. Only applicable to Low-Band and Mid-Band cells.; range -300..300; Default value: 0.";
      type int32 {
        range "-300..300";
      }
      default "0";
      units "dB";
    }
    leaf sinrSCellCoverageThrOffset {
      description "SINR A1 and A2 measurement event threshold offset for SCell coverage measurements. Used in combination with CaCellMeasProfileUeCfg::sinrSCellCoverage. Only applicable to Low-Band and Mid-Band cells.; range -100..100; Default value: 0.";
      type eytypes:int32_range_-100-100;
      default "0";
      units "dB";
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 16;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
    leaf waitForBetterSCellRep {
      description "Controls time gNodeB waits after reception of an A2 measurement report until SCell is deconfigured. If SCell A1 or A6 measurement report is received before timer expires, no SCell deconfiguration is attempted. Value -1 means waiting forever. Not applicable to High-Band cells.; range -1..32000; Default value: -1.";
      type eytypes:int32_range_-1-32000;
      default "-1";
      units "ms";
    }
  }
  grouping CapabilityHandling-attributes {
    leaf capabilityHandlingId {
      description "The value component of the RDN..";
      type string;
      mandatory true;
    }
    leaf ueConfGroupType {
      description "UE configuration group type. UE configuration group type that is applied in contained CapabilityHandlingUeCfg instances..";
      type enumeration {
        enum UE_MOBILITY_GROUP;
        enum UE_SERVICE_GROUP;
        enum UE_ADMISSION_GROUP;
      }
    }
  }
  grouping CapabilityHandlingUeCfg-attributes {
    leaf capabilityHandlingUeCfgId {
      description "The value component of the RDN..";
      type string;
      mandatory true;
    }
    leaf gaplessFr2InterFreqMeasSupp {
      description "Whether UE is assumed to support gapless FR2 inter-frequency measurements. Only applicable to High-Band cells.; Default value: false.";
      type boolean;
      default "false";
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf ulRrcSegAllowedForUeCapInfo {
      description "Indicator of allowing UE to send RRC ULDedicatedMessageSegment message. Only applicable to segmented RRC UECapabilityInformation message transfer. Only applicable to CapabilityHandlingUeCfg=Base instance. Value in Base instance is applied in all UE groups.; Default value: true; Takes effect: New connection; Status info: Since 23.Q4. Planned to be removed..";
      type boolean;
      status deprecated;
      default "true";
      reference "Takes effect: New connection.";
    }
    leaf userLabel {
      description "Label for free use..";
      type string;
    }
  }
  grouping CardinalityLimits-attributes {
    leaf cardinalityLimitsId {
      description "The value component of the RDN..";
      type string;
      mandatory true;
    }
    leaf maxNRCellCU {
      description "Maximum number of NRCellCU instances that can be created in current deployment..";
      type int32;
      config false;
    }
  }
  grouping CarrierAggregation-attributes {
    leaf carrierAggregationId {
      description "The value component of the RDN..";
      type string;
      mandatory true;
    }
  }
  grouping CellGroupCategoryDefinition-attributes {
    leaf categoryCriteria {
      description "Cell group category criteria. <CategoryCriteria> ::= <ExpressionList> | \"\" <ExpressionList> ::= <ExpressionList> <AndOr> <ExpressionList> | <Not>? \"(\" <ExpressionList> \")\" | <Not>? <VariableExpression> <VariableExpression> ::= <Variable> <RelationalOperator> <Value> | <Variable> \"==\" \"{\" <ValueList> \"}\" <ValueList> ::= <Value> \",\" <ValueList> | <Value> <Variable> ::= \"PCellDlFreq\" | \"PCellUlFreq\" | \"PSCellDlFreq\" | \"PSCellUlFreq\" <AndOr> ::= \"&&\" | \"||\" <Not> ::= \"!\" <RelationalOperator> ::= \"==\" | \"!=\" | \"<\" | \"<=\" | \">=\" | \">\" A list of possible values can be specified in the form <Variable> == {<value1>, <value2>, ... , <valueN>}. This statement is equivalent to writing (<Variable> == <value1> || <Variable> == <value2> || ... || <Variable> == <valueN>). Whitespaces are allowed between every token in the syntax above. Question mark (?) means zero or one occurrence. For example, <Not>? makes <Not> optional. Syntax is case sensitive. Semantic: ======== Category criteria evaluation is defined by the following semantic rules. If empty or set to empty string \"\", selection criteria always evaluates to True. Operator Precedence Order: ======================= The logical and relation operators are evaluated according to the precedence order listed below. --------------------------------------------- 1 (highest precedence) < Less than <= Less than or equal > Greater than >= Greater than or equal == Equal != Not equal ------------------------------------------- 2 ! (Not) --------------------------------------------- 3 && (And) --------------------------------------------- 4 (lowest precedence) || (Or) --------------------------------------------- The NOT operator \"!\" negates the following <VariableExpression> or an <ExpressionList> encapsulated in parenthesis. Therefore, the expression !a==b && c==d is equivalent to (!(a==b) && (c==d)) and different from !(a==b && c==d). Expression !a==b and !(a==b) are equivalent. Since the AND operator \"&&\" has higher precedence than the OR operator \"||\", a<b || a<c && c<d is equivalent to (a<b || (a<c && c<d)). To change the order of operations, surround the expression with parentheses (...) as (a<b || a<c) && c<d to force the NOT operator \"||\" to be evaluated first. As an example, this attribute can be used like: Category criteria = PCellDlFreq> 2.5e9 && PCellDlFreq < 2.8e9 to check whether PCell downlink frequency is between 2.5 GHz and 2.8 GHz.; length 0..1000.";
      type string {
        length "0..1000";
      }
    }
    leaf cellGroupCategoryDefinitionId {
      description "The value component of the RDN..";
      type string;
      mandatory true;
    }
    leaf cgCategoryId {
      description "Cell group category identifier.; range 0..255.";
      type eytypes:int32_range_0-255;
      mandatory true;
    }
    leaf userLabel {
      description "Label for free use..";
      type string;
    }
  }
  grouping Chipsets-attributes {
    list chipsetList {
      key "id";
      leaf id {
        type uint32;
        description "Synthetic key for struct sequence entry.";
      }
      min-elements 0;
      max-elements 128;
      uses Chipset-struct;
    }
    leaf chipsetsId {
      description "The value component of the RDN..";
      type string;
      mandatory true;
    }
    leaf-list reservedBy {
      description "Contains a list of MO instances that reserve this MO instance..";
      type string;
      min-elements 0;
    }
    leaf userLabel {
      description "Label for free use..";
      type string;
    }
  }
  grouping CUCP5qi-attributes {
    leaf cUCP5qiId {
      description "The value component of the RDN..";
      type string;
      mandatory true;
    }
    leaf endcUlDataSplitRef {
      description "Reference to an instance of UlDataSplit MO. Automatically set to UlDataSplit=Default_endc instance, unless manually set to refer to another MO instance. Applicable to EN-DC if Service-Adaptive Uplink User Plane Profile feature is activated. UlDataSplit=Default_endc instance is applied if Service-Adaptive Uplink User Plane Profile feature is deactivated..";
      type string;
    }
    leaf nrdcSnTerminationRef {
      description "Reference to an instance of NrdcSnTermination MO. For 5QIs 1,5,65,66 and 69, if empty then SnTerminationProhibited instance of NrdcSnTermination is used. For all other 5QI, if empty then instance of NrdcSnTermination is used where defaultNrdcSnTerm is true. If empty, and no such MO exists, SN termination is not allowed for this 5QI..";
      type string;
    }
    leaf nrdcUlDataSplitRef {
      description "Reference to an instance of UlDataSplit MO. Automatically set to UlDataSplit=Default_nrdc instance, unless manually set to refer to another MO instance. Applicable to NR-DC if Service-Adaptive Uplink User Plane Profile feature is activated. UlDataSplit=Default_nrdc instance is applied if Service-Adaptive Uplink User Plane Profile feature is deactivated..";
      type string;
    }
    leaf pdcpSnSize {
      description "PDCP sequence number length. Following values are recommended: * 12 if profile5qi is 1, 2, 3, 4, 5, 6, 7, 65, 66, 67, 69, 70, 79, 80, 82, 83, 84 or 85. * 18 if profile5qi is 8 or 9.; Default value: 18.";
      type int32 {
        range "12 | 18";
      }
      default "18";
    }
    leaf profile5qi {
      description "5G QoS Identifier, unique within a table.; range 0..255.";
      type eytypes:int32_range_0-255;
      mandatory true;
    }
    leaf rlcMode {
      description "RLC mode for DRB. Recommended values for non-restricted 5QIs: UM if profile5qi is 2. AM if profile5qi is 6, 7, 8, 9 or 70..";
      type enumeration {
        enum AM;
        enum UM;
      }
    }
    leaf tPdcpDiscard {
      description "UL PDCP discard timer used in UE. Following values are recommended: * 150 if profile5qi is 1, 2, 65, 66 or 67. * 1500 if profile5qi is 8 or 9. * 2147483646 (infinity) if profile5qi is 5 or 69.; Default value: 1500.";
      type int32 {
        range "10 | 20 | 30 | 40 | 50 | 60 | 75 | 100 | 150 | 200 | 250 | 300 | 500 | 750 | 1500..2147483646";
      }
      default "1500";
      units "ms";
    }
    leaf tReorderingDl {
      description "Reordering downlink timer used by the receiving-end PDCP entity in the UE. Following values are recommended: * 40 if profile5qi is 1, 2, 65, 66 or 67. * 200 if profile5qi is 5, 8, 9 or 69.; Default value: 200.";
      type int32 {
        range "0..2 | 4..5 | 8 | 10 | 15 | 20 | 30 | 40 | 50 | 60 | 80 | 100 | 120 | 140 | 160 | 180 | 200 | 220 | 240 | 260 | 280 | 300 | 500 | 750 | 1000 | 1250 | 1500 | 1750 | 2000 | 2250 | 2500 | 2750 | 3000";
      }
      default "200";
      units "ms";
    }
    leaf tReorderingUl {
      description "Reordering uplink timer used by the receiving-end PDCP entity in the gNodeB. Following values are recommended: * 20 if profile5qi is 1, 2, 65, 66 or 67. * 50 is profile5qi is 8 or 9. * 200 if profile5qi is 5 or 69.; Default value: 20.";
      type int32 {
        range "0..2 | 4..5 | 8 | 10 | 15 | 20 | 30 | 40 | 50 | 60 | 80 | 100 | 120 | 140 | 160 | 180 | 200 | 220 | 240 | 260 | 280 | 300 | 500 | 750 | 1000 | 1250 | 1500 | 1750 | 2000 | 2250 | 2500 | 2750 | 3000";
      }
      default "20";
      units "ms";
    }
    leaf userLabel {
      description "Label for free use..";
      type string;
    }
  }
  grouping CUCP5qiTable-attributes {
    leaf cUCP5qiTableId {
      description "The value component of the RDN..";
      type string;
      mandatory true;
    }
    leaf default5qiTable {
      description "Indicates that CUCP5qiTable instance is a default 5QI table. The default 5QI table is used when no CUCP5qiTable has been configured for a resource partition.; Default value: false.";
      type boolean;
      default "false";
    }
    leaf-list reservedBy {
      description "Contains a list of MO instances that reserve this MO instance..";
      type string;
      min-elements 0;
    }
  }
  grouping DESManagementFunction-attributes {
    leaf dESManagementFunctionId {
      description "The value component of the RDN..";
      type string;
      mandatory true;
    }
    leaf desSwitch {
      description "Whether energy saving for cell is enabled.; Default value: false.";
      type boolean;
      default "false";
    }
    leaf energySavingState {
      description "Energy saving state for cell..";
      type enumeration {
        enum IS_NOT_ENERGYSAVING;
        enum IS_ENERGYSAVING;
      }
      config false;
    }
    list esNotAllowedTimePeriod {
      key "id";
      leaf id {
        type uint32;
        description "Synthetic key for struct sequence entry.";
      }
      min-elements 0;
      uses TimePeriod-struct;
    }
    list intraRatEsActivationOriginalCellLoadParameters {
      key "id";
      leaf id {
        type uint32;
        description "Synthetic key for struct attribute.";
      }
      description "Enables energy saving in cell. If conditions in parameter set are met, cell initiates transition to energy saving state by using NR Booster Carrier Sleep feature..";
      uses LoadParameters-struct;
    }
    leaf periodicEsDuration {
      description "Duration for cell to periodic transition from IS_ENERGYSAVING back to IS_NOT_ENERGYSAVING state. Duration is only valid during time period when energy saving is allowed. When timer is expired: - If cell energySavingState is IS_ENERGYSAVING, transition to IS_NOT_ENERGYSAVING happens. - If cell is BARRED with value of NRCellDU::cellBarredReason equal to BOOSTER_CARRIER_SLEEP, transition to NOT_BARRED happens. If 0, energy saving has no periodic transition.; Default value: 120.";
      type int32 {
        range "0 | 5..1440";
      }
      default "120";
      units "minute";
    }
    leaf requiredWakeUpTime {
      description "Time for cell transition from OUT_OF_SERVICE to IN_SERVICE.; range 15..600; Default value: 180.";
      type int32 {
        range "15..600";
      }
      default "180";
      units "s";
    }
  }
  grouping EmCall-attributes {
    leaf-list arpPrioEm5qi1List {
      description "ARP level values used for emergency calls in QoS flow with 5qi = 1. If empty, no Allocation and Retention Priority (ARP) level is interpreted as emergency call..";
      type eytypes:int32_range_1-15-7;
      ordered-by user;
      min-elements 0;
      max-elements 15;
    }
    leaf-list arpPrioEm5qi5List {
      description "ARP level values used for emergency calls in QoS flow with 5qi = 5. If empty, no Allocation and Retention Priority (ARP) level is interpreted as emergency call..";
      type eytypes:int32_range_1-15-7;
      ordered-by user;
      min-elements 0;
      max-elements 15;
    }
    leaf emCallId {
      description "The value component of the RDN..";
      type string;
      mandatory true;
    }
    leaf mobilityRestrictionsApplied {
      description "Whether UE Mobility Restriction List is applied for emergency calls.; Default value: true.";
      type boolean;
      default "true";
    }
    list pLMNIdList {
      key "id";
      leaf id {
        type uint32;
        description "Synthetic key for struct sequence entry.";
      }
      min-elements 0;
      max-elements 12;
      uses PLMNId-struct;
    }
    leaf userLabel {
      description "Label for free use..";
      type string;
    }
  }
  grouping EndpointResource-attributes {
    leaf endpointResourceId {
      description "The value component of the RDN..";
      type string;
      mandatory true;
    }
    leaf-list reservedBy {
      description "Contains a list of MO instances that reserve this MO instance..";
      type string;
      min-elements 0;
    }
    leaf userLabel {
      description "Label for free use..";
      type string;
    }
  }
  grouping EnergyPerformance-attributes {
    leaf energyPerformanceId {
      description "The value component of the RDN..";
      type string;
      mandatory true;
    }
  }
  grouping EpBoCS-attributes {
    leaf epBoCSId {
      description "The value component of the RDN..";
      type string;
      mandatory true;
    }
  }
  grouping EpBoosterAdvCfg-attributes {
    leaf epBoosterAdvCfgId {
      description "The value component of the RDN..";
      type string;
      mandatory true;
    }
    leaf-list reservedBy {
      description "Contains a list of MO instances that reserve this MO instance..";
      type string;
      min-elements 0;
    }
    leaf sleepEvaluateTimeWindow {
      description "Time window for checking sleep condition before cell enters sleep mode. Window moves with time, stretching over the last n seconds configured through this attribute.; range 60..3600; Default value: 600.";
      type int32 {
        range "60..3600";
      }
      default "600";
      units "s";
    }
    leaf sleepFilterTimePercentage {
      description "Minimum percentage of time window for UCF must remain below sleep threshold. Used Capacity Factor (UCF) must be below EpBoosterCellProfile::sleepUcfThreshBooster for this percentage of time of sleepEvaluateTimeWindow to fulfill the sleep criterion for a cell.; range 0..100; Default value: 90.";
      type eytypes:int32_range_0-100;
      default "90";
      units "percent";
    }
    leaf sleepRelBoosterFilterTimePerc {
      description "Minimum percentage of time window for UCF in related cells is below sleep threshold. Used Capacity Factor (UCF) must be below EpBoosterCellProfile::sleepUcfThreshBooster for this percentage of time of sleepEvaluateTimeWindow to fulfill sleep criterion for a cell. Energy performance-related cells are cells which have cell relations with NRCellRelation::epLoadMonitoringEnabled set to true.; range 0..100; Default value: 90.";
      type eytypes:int32_range_0-100;
      default "90";
      units "percent";
    }
    leaf sleepUcfWakeupThreshFactor {
      description "Calculate offset to EpBoosterCellProfile::wakeupUcfThresh of related cells during sleep evaluation. Applied to check if energy performance-related cells can carry traffic when booster cell enters sleep. Energy performance-related cells are cells which have cell relations with NRCellRelation::epLoadMonitoringEnabled set to true.; range 0..100; Default value: 25.";
      type eytypes:int32_range_0-100;
      default "25";
      units "percent";
    }
    leaf userLabel {
      description "Label for free use..";
      type string;
    }
    leaf wakeupEvaluateTimeWindow {
      description "Time window for checking wake-up condition before waking up cell. Window moves with time, stretching over the last n seconds configured through this attribute.; range 60..3600; Default value: 360.";
      type int32 {
        range "60..3600";
      }
      default "360";
      units "s";
    }
    leaf wakeupFilterTimePercentage {
      description "Minimum percentage of time window for UCF must remain above wake-up threshold. Used Capacity Factor (UCF) must be above EpBoosterCellProfile::wakeupUcfThresh for this percentage of time of wakeupEvaluateTimeWindow to fulfill the wake-up criterion for a cell.; range 0..100; Default value: 80.";
      type eytypes:int32_range_0-100;
      default "80";
      units "percent";
    }
    leaf wakeupMissingSampleTime {
      description "Time duration without receiving Used Capacity Factor samples from energy performance-related cell. If at least one of the energy performance-related cells has successive missing Used Capacity Factor samples for this time duration or longer, wake-up of booster cell is triggered if other wake-up conditions are fulfilled. Energy performance-related cells are cells which have cell relations with NRCellRelation::epLoadMonitoringEnabled set to true.; range 5..300; Default value: 300.";
      type eytypes:int32_range_5-300;
      default "300";
      units "s";
    }
    leaf wakeupPeriodicEsDuration {
      description "Periodic wake-up from sleep, regardless of traffic conditions. Evaluated only if epBoCSMode is TIME.; Default value: 0.";
      type int32 {
        range "0 | 5..1440";
      }
      default "0";
      units "minute";
    }
  }
  grouping EpBoosterCellProfile-attributes {
    leaf epBoosterAdvCfgRef {
      description "Reference to an instance of EpBoosterAdvCfg MO. Automatically set to EpBoosterAdvCfg=Default instance, unless manually set to refer to another MO instance..";
      type string;
    }
    leaf epBoosterCellProfileId {
      description "The value component of the RDN..";
      type string;
      mandatory true;
    }
    leaf-list reservedBy {
      description "Contains a list of MO instances that reserve this MO instance..";
      type string;
      min-elements 0;
    }
    leaf sleepUcfThreshBooster {
      description "Sleep threshold for this booster cell expressed in percentage of Used Capacity Factor.; range 0..10000; Default value: 500.";
      type int32 {
        range "0..10000";
      }
      default "500";
      units "percent";
    }
    leaf userLabel {
      description "Label for free use..";
      type string;
    }
    leaf wakeupRequiredTime {
      description "Maximum time allowed to transition from OUT_OF_SERVICE to IN_SERVICE when waking up cell. Sleep function determines how many resources are put to sleep based on this attribute. If more resources are put to sleep, it might take longer to wake up cells.; range 2..600; Default value: 180.";
      type int32 {
        range "2..600";
      }
      default "180";
      units "s";
    }
    leaf wakeupUcfThresh {
      description "Used Capacity Factor wake up threshold for Energy Performance-related cells. Energy Performance-related cells are considered to have cell relations with NRCellRelation::epLoadMonitoringEnabled set to true.; range 0..10000; Default value: 2000.";
      type int32 {
        range "0..10000";
      }
      default "2000";
      units "percent";
    }
  }
  grouping EUtranCellRelation-attributes {
    leaf cellIndividualOffset {
      description "Offset value for neighbor E-UTRAN cell. Used when UE is in connected mode.; Default value: 0.";
      type int32 {
        range "-24 | -22 | -20 | -18 | -16 | -14 | -12 | -10 | -8 | -6..6 | 8 | 10 | 12 | 14 | 16 | 18 | 20 | 22 | 24";
      }
      default "0";
      units "dB";
    }
    list essCellScPairs {
      config false;
      min-elements 0;
      max-elements 14;
      uses EssCellScPair-struct;
    }
    leaf essEnabled {
      description "ESS service enabled between cells in this relation. Only one EUtranCellRelation instance under an NRCellCU instance can be essEnabled.; Default value: false.";
      type boolean;
      default "false";
    }
    leaf eUtranCellRelationId {
      description "The value component of the RDN..";
      type string;
      mandatory true;
    }
    leaf isHoAllowed {
      description "Whether handover between cells in this relation is allowed.; Default value: true.";
      type boolean;
      default "true";
    }
    leaf isRemoveAllowed {
      description "If ANR function is allowed to remove this instance. The setting does not restrict operator removal of object. Objects created by ANR have this parameter set to true initially. If empty, this attribute is handled as if it is false.; Default value: false.";
      type boolean;
      default "false";
    }
    leaf neighborCellRef {
      description "Reference to an instance of ExternalEUtranCell MO..";
      type string;
      mandatory true;
    }
    leaf preferredCellManual {
      description "Whether related cell must be selected as mobility target cell in PCI conflict cases. Used for manual selection of cell relations for handovers in PCI conflicts. If false, related cell is not selected as a handover target cell, if there is another handover candidate cell with same PCI and on same frequency with this attribute set to true. If true, related cell is always selected as a handover target cell, if there are other handover candidate cells with same PCI and on same frequency.; Default value: false.";
      type boolean;
      default "false";
    }
    leaf timeOfCreation {
      description "Time and date of MO creation. Format: YYYY-MM-DD HH:MM:SS..";
      type string;
      config false;
    }
    leaf userLabel {
      description "Label for free use..";
      type string;
    }
  }
  grouping EUtraNetwork-attributes {
    leaf eUtraNetworkId {
      description "The value component of the RDN..";
      type string;
      mandatory true;
    }
    leaf userLabel {
      description "Label for free use..";
      type string;
    }
  }
  grouping EUtranFreqRelation-attributes {
    leaf allowedMeasBandwidth {
      description "Maximum allowed measurement bandwidth on a carrier frequency. Value indicates number of resource blocks and corresponds to channel bandwidth 1.4 MHz, 3 MHz, 5 MHz, 10 MHz, 15 MHz and 20 MHz respectively specified in 3GPP TS 36.104, Evolved Universal Terrestrial Radio Access (E-UTRA); Base Station (BS) radio transmission and reception.; Default value: 6.";
      type int32 {
        range "6 | 15 | 25 | 50 | 75 | 100";
      }
      default "6";
      units "PRB";
    }
    list allowedPlmnList {
      key "id";
      leaf id {
        type uint32;
        description "Synthetic key for struct sequence entry.";
      }
      min-elements 0;
      max-elements 15;
      uses PLMNId-struct;
    }
    leaf anrMeasOn {
      description "Whether ANR measurement on frequency is enabled.; Default value: true.";
      type boolean;
      default "true";
    }
    leaf candidateForSib5 {
      description "Whether frequency is a candidate to be included in SIB5. If true in more than 8 EUtranFreqRelation instances, the 8 candidates with the higher priority, defined in cellReselectionPriority, are included in SIB5.; Default value: true.";
      type boolean;
      default "true";
    }
    leaf cellReselectionPriority {
      description "Absolute priority of the carrier frequency used by the cell reselection procedure. This attribute is broadcast in SIB5 and referred to for setting CellReselectionPriority in RRCRelease message. If 0, lowest priority is selected. Value must be unique between RATs. This means that equal priorities between RATs are not supported. If empty or -1, value is not broadcast in SIB5.; range -1..7; Default value: 6.";
      type eytypes:int32_range_-1-7;
      default "6";
    }
    leaf cellReselectionSubPriority {
      description "Subpriority value of E-UTRA carrier frequency. Subpriority value added to value of cellReselectionPriority to obtain absolute priority of carrier frequency. If empty, this attribute is not broadcast in SIB5. This attribute is broadcast accompanied by cellReselectionPriority in SIB5 and referred to for setting CellReselectionSubPriority in RRCRelease message..";
      type int32 {
        range "2 | 4 | 6 | 8";
      }
    }
    leaf eUtranFallbackPrioEc {
      description "Priority of E-UTRAN frequencies for emergency calls. Priority is among all frequencies related to the cell for UEs in connected mode. Sets priority to alternative target frequency to which release is made with redirection. If 0, lowest priority is selected. If 7, highest priority is selected. If empty or -1, the frequency is excluded.; range -1..7; Default value: 0.";
      type eytypes:int32_range_-1-7;
      default "0";
    }
    leaf eUtranFreqRelationId {
      description "The value component of the RDN..";
      type string;
      mandatory true;
    }
    leaf eUtranFrequencyRef {
      description "Reference to an instance of EUtranFrequency MO. Must be unique among EUtranFreqRelation instances under an NRCellCU instance..";
      type string;
      mandatory true;
    }
    leaf mcpcPCellEUtranFreqRelProfileRef {
      description "Reference to an instance of McpcPCellEUtranFreqRelProfile MO. Automatically set to McpcPCellEUtranFreqRelProfile=Default instance, unless manually set to refer to another MO instance..";
      type string;
    }
    leaf offloadEUtranFreqRelProfileRef {
      description "Reference to an instance of OffloadEUtranFreqRelProfile MO. Automatically set to OffloadEUtranFreqRelProfile=Default instance, unless manually set to refer to another MO instance..";
      type string;
    }
    leaf pMaxEUtra {
      description "Parameter used to calculate Pcompensation at cell reselection. Corresponds to parameter PEMAX in 3GPP TS 38.101.; range -30..33; Default value: 23.";
      type int32 {
        range "-30..33";
      }
      default "23";
      units "dBm";
    }
    leaf presenceAntennaPort1 {
      description "Use of Antenna Port 1 in neighboring cells. If true, UE expects at least two cell-specific antenna ports are used in neighboring cells.; Default value: false.";
      type boolean;
      default "false";
    }
    leaf qQualMin {
      description "Minimum required quality level in cell (dB). This attribute is broadcast in SIB5.; range -43..-12; Default value: -34.";
      type eytypes:int32_range_-43--12;
      default "-34";
      units "dB";
    }
    leaf qRxLevMin {
      description "Minimum received RSRP level for cell reselection. Corresponds to parameter Qrxlevmin in 3GPP TS 38.304.; range -140..-44; Default value: -140.";
      type eytypes:int32_range_-140--44;
      default "-140";
      units "dBm";
    }
    leaf threshXHighP {
      description "RSRP threshold level for reselection to higher priority. Each frequency of E-UTRAN can have a specific threshold.; range 0..62; Default value: 4.";
      type eytypes:int32_range_0-62;
      default "4";
      units "dB";
    }
    leaf threshXHighQ {
      description "RSRQ threshold level for reselection to higher priority. The threshold used by UE when reselecting towards a higher priority frequency X from the current serving frequency. Each frequency of E-UTRAN can have a specific threshold. If empty, value is not broadcast in SIB5.; range 0..31.";
      type eytypes:int32_range_0-31;
      units "dB";
    }
    leaf threshXLowP {
      description "RSRP threshold level for reselection to lower priority. Each frequency of E-UTRAN can have a specific threshold.; range 0..62; Default value: 0.";
      type eytypes:int32_range_0-62;
      default "0";
      units "dB";
    }
    leaf threshXLowQ {
      description "RSRQ threshold level for reselection to lower priority. The threshold used by UE when reselecting towards a lower priority frequency X from the current serving frequency. Each frequency of E-UTRAN can have a specific threshold. If empty, value is not broadcast in SIB5.; range 0..31.";
      type eytypes:int32_range_0-31;
      units "dB";
    }
    leaf tReselectionEUtra {
      description "Time for evaluation of criteria before reselection can be done. All values under same NRCellCU instance must be same.; range 0..7; Default value: 2.";
      type eytypes:int32_range_0-7-8;
      default "2";
      units "s";
    }
    leaf tReselectionEutraSfHigh {
      description "Speed-dependent scaling factor for TreselectionEUTRA. If non-empty, all values under same NRCellCU instance must be same. If empty, all values under same NRCellCU instance must be empty. For E-UTRAN cell reselection, concerned mobility control related parameter is multiplied with this factor if UE is in high mobility state. If empty, no t-ReselectionEUTRA-SF will be broadcast in SIB5..";
      type uint32 {
        range "25 | 50 | 75 | 100";
      }
    }
    leaf tReselectionEutraSfMedium {
      description "Speed-dependent scaling factor for TreselectionEUTRA. If non-empty, all values under same NRCellCU instance must be same. If empty, all values under same NRCellCU instance must be empty. For E-UTRAN cell reselection, concerned mobility control related parameter is multiplied with this factor if UE is in medium mobility state. If empty, no t-ReselectionEUTRA-SF will be broadcast in SIB5..";
      type uint32 {
        range "25 | 50 | 75 | 100";
      }
    }
    leaf trStSaEUtranFreqRelProfileRef {
      description "Reference to an instance of TrStSaEUtranFreqRelProfile MO. Automatically set to TrStSaEUtranFreqRelProfile=Default instance, unless manually set to refer to another MO instance..";
      type string;
    }
    leaf ucmEUtranFreqRelProfileRef {
      description "Reference to an instance of UcmEUtranFreqRelProfile MO. Automatically set to UcmEUtranFreqRelProfile=Default instance, unless manually set to refer to another MO instance..";
      type string;
    }
    leaf ueMCEUtranFreqRelProfileRef {
      description "Reference to an instance of UeMCEUtranFreqRelProfile MO. Automatically set to UeMCEUtranFreqRelProfile=Default instance, unless manually set to refer to another MO instance..";
      type string;
    }
    leaf userLabel {
      description "Label for free use..";
      type string;
    }
    leaf voicePrio {
      description "Prioritizes E-UTRAN frequencies among all frequencies related to the cell for UEs in connected mode. Sets priority to which frequency to perform mobility to, for a voice session. If 0, lowest priority is selected. If 7, highest priority is selected. If empty or -1, frequency is excluded.; range -1..7; Default value: 0.";
      type eytypes:int32_range_-1-7;
      default "0";
    }
  }
  grouping EUtranFrequency-attributes {
    leaf arfcnValueEUtranDl {
      description "ARFCN applicable to a downlink E-UTRA carrier frequency. For TDD this also indicates the ARFCN for uplink. Values that can be used depend on national operator-specific frequency allocation and supported frequency bands of the equipment in the eNodeB. Must match the eUtranFrequencyId..";
      type int32 {
        range "0..17999 | 36000..262143";
      }
      mandatory true;
    }
    leaf eUtranFrequencyId {
      description "The value component of the RDN..";
      type string;
      mandatory true;
    }
    leaf-list reservedBy {
      description "Contains a list of MO instances that reserve this MO instance..";
      type string;
      min-elements 0;
    }
    leaf userLabel {
      description "Label for free use..";
      type string;
    }
  }
  grouping ExternalBroadcastPLMNInfo-attributes {
    leaf externalBroadcastPLMNInfoId {
      description "The value component of the RDN..";
      type string;
      mandatory true;
    }
    leaf nRTAC {
      description "NR Tracking Area Code (TAC).; range 0..16777215.";
      type eytypes:int32_range_0-16777215;
      mandatory true;
    }
    list pLMNIdList {
      key "id";
      leaf id {
        type uint32;
        description "Synthetic key for struct sequence entry.";
      }
      min-elements 1;
      max-elements 12;
      uses PLMNId-struct;
    }
  }
  grouping ExternalENodeBFunction-attributes {
    leaf eNodeBId {
      description "The ID of an RBS within a Public Land Mobile Network (PLMN).; range 0..1048575.";
      type eytypes:int32_range_0-1048575;
      mandatory true;
    }
    leaf externalENodeBFunctionId {
      description "The value component of the RDN..";
      type string;
      mandatory true;
    }
    leaf independentGapConfigSupported {
      description "Whether external eNodeB supports independent gap configuration.; Default value: false.";
      type boolean;
      default "false";
    }
    leaf isRemoveAllowed {
      description "Whether ANR function can remove MO instance. Setting does not restrict operator to remove MO instance. Set to true for MO instances created by ANR.; Default value: false.";
      type boolean;
      default "false";
    }
    leaf noRelationTimeStamp {
      description "Point in time when MO instance has no relation to GNBCUCPFunction anymore. Periodic check compares this timestamp with AnrFunction::removeEnbTime. Format: EPOCH time - Number of seconds since 1970-01-01 00:00:00 UTC..";
      type int64;
      config false;
    }
    list pLMNId {
      key "id";
      leaf id {
        type uint32;
        description "Synthetic key for struct attribute.";
      }
      min-elements 1;
      description "PLMN identifier part of global RAN node identity. This and eNodeB ID form the global eNodeB ID. Value MCC=001, MNC=01 means PLMN is not initiated. This value cannot be used as a valid PLMN Identity..";
      uses PLMNId-struct;
    }
    leaf ulTrigHoAllowed {
      description "Whether handover triggered by poor uplink coverage is allowed towards external eNodeB. If true, Handover triggered by poor uplink coverage is allowed towards external eNodeB.; Default value: false.";
      type boolean;
      default "false";
    }
    leaf userLabel {
      description "Label for free use..";
      type string;
    }
  }
  grouping ExternalEUtranCell-attributes {
    list additionalPlmnList {
      key "id";
      leaf id {
        type uint32;
        description "Synthetic key for struct sequence entry.";
      }
      min-elements 0;
      max-elements 5;
      uses PLMNId-struct;
    }
    leaf cellLocalId {
      description "RBS internal ID attribute for EUtranCell. Together with node ID and PLMN, this is a universally unique cell ID. Updated through EN-DC X2 messages.; range 0..255; Default value: 0.";
      type eytypes:int32_range_0-255;
      default "0";
    }
    leaf dlChannelBandwidth {
      description "Downlink channel bandwidth in LTE cell. Updated through EN-DC X2 messages. Empty if there is no EN-DC X2 connection..";
      type int32 {
        range "1400 | 3000 | 5000 | 10000 | 15000 | 20000";
      }
      config false;
      units "kHz";
    }
    leaf earfcndl {
      description "Channel number for central downlink frequency. Mapping from channel number to physical frequency for specified E-UTRA bands is described in 3GPP TS 36.104. Values that can be used depend on national, operator-specific frequency allocation and on supported frequency bands in RBS. Updated through EN-DC X2 messages. Empty if there is no EN-DC X2 connection..";
      type int32 {
        range "1..17999 | 46590..262143";
      }
      config false;
    }
    leaf earfcnul {
      description "Channel number for central uplink frequency. Mapping from channel number to physical frequency for specified E-UTRA bands is described in 3GPP TS 36.104. Values that can be used depend on national, operator-specific frequency allocation and on supported frequency bands in RBS. Value 0 means uplink channel number is not available for DL-only bands. Updated through EN-DC X2 messages. Empty if there is no EN-DC X2 connection..";
      type int32 {
        range "0 | 18000..35999 | 46590..262143";
      }
      config false;
    }
    leaf eUtranFrequencyRef {
      description "Reference to an instance of EUtranFrequency MO. If empty, ExternalEUtranCell instance is not selected as target cell of IRAT handover from NR to LTE. Updated through EN-DC X2 messages or CGI measurement from UE..";
      type string;
    }
    leaf externalEUtranCellId {
      description "The value component of the RDN..";
      type string;
      mandatory true;
    }
    leaf-list isPciConflicted {
      description "Whether PCI conflict is detected or resolved. If true, PCI conflict is detected. PCI conflict is either collision or confusion. PCI confusion exists if source cell has relations to two neighbor cells where both neighbor cells have same PCI and frequency. PCI collision exists if source cell has relation to a neighbor cell where source cell and neighbor cell have same PCI and frequency. Only applicable if PciHandling::pciConflictHandlingEnabled is true..";
      type PciConflicted;
      min-elements 0;
      max-elements 6;
    }
    leaf operationalState {
      description "The operational state. Updated through EN-DC X2 messages..";
      type enumeration {
        enum DISABLED;
        enum ENABLED;
      }
      config false;
    }
    list pciConflictDetectingCell {
      config false;
      min-elements 0;
      max-elements 6;
      uses Ncgi-struct;
    }
    list pciConflictedCell {
      config false;
      min-elements 0;
      max-elements 6;
      uses EUtraCgi-struct;
    }
    leaf physicalLayerCellId {
      description "Physical-layer cell ID. Updated through EN-DC X2 messages.; range 0..503; Default value: 0.";
      type eytypes:int32_range_0-503;
      default "0";
    }
    leaf-list reservedBy {
      description "Contains a list of MO instances that reserve this MO instance..";
      type string;
      min-elements 0;
    }
    leaf tac {
      description "TAC for external E-UTRAN cell. Updated through EN-DC X2 messages or CGI measurement from UE.; range 0..65535; Default value: 0.";
      type eytypes:int32_range_0-65535-9;
      default "0";
    }
    leaf ulChannelBandwidth {
      description "Uplink channel bandwidth in LTE cell. Updated through EN-DC X2 messages. Empty if there is no EN-DC X2 connection..";
      type int32 {
        range "1400 | 3000 | 5000 | 10000 | 15000 | 20000";
      }
      config false;
      units "kHz";
    }
  }
  grouping ExternalGNBCUCPFunction-attributes {
    list amfRegionInfoList {
      key "id";
      leaf id {
        type uint32;
        description "Synthetic key for struct sequence entry.";
      }
      min-elements 0;
      max-elements 16;
      uses GlobalUniqueAmfRegionId-struct;
    }
    leaf externalGNBCUCPFunctionId {
      description "The value component of the RDN..";
      type string;
      mandatory true;
    }
    leaf gNBId {
      description "Identifies a gNodeB within a PLMN.; range 0..4294967295.";
      type eytypes:int64_range_0-4294967295;
      mandatory true;
    }
    leaf gNBIdLength {
      description "Number of bits for encoding gNodeB ID.; range 22..32; Default value: 22.";
      type eytypes:int32_range_22-32;
      default "22";
    }
    leaf isRemoveAllowed {
      description "Whether ANR function is allowed to remove this instance. Setting does not restrict operator removal of the object. Automatically created objects have this parameter set to true initially.; Default value: false.";
      type boolean;
      default "false";
    }
    leaf noRelationTimeStamp {
      description "Point in time when this MO instance had no relation to GNBCUCPFunction anymore. A periodic check will compare this timestamp with AnrFunction::removeGnbTime. Format: EPOCH time - Number of seconds since 1970-01-01 00:00:00 UTC..";
      type int64;
      config false;
    }
    list pLMNId {
      key "id";
      leaf id {
        type uint32;
        description "Synthetic key for struct attribute.";
      }
      min-elements 1;
      description "PLMN identifier part of global RAN node identity. This and gNodeB ID form the global gNodeB ID. Value MCC=001, MNC=01 means PLMN is not initiated. This value cannot be used as a valid PLMN Identity..";
      uses PLMNId-struct;
    }
    leaf sameUeGroupSelection {
      description "Whether UeGroupSelection instances on local and external node are equal..";
      type boolean;
      config false;
    }
    leaf timeOfCreation {
      description "Time and date of MO creation. Format: YYYY-MM-DD HH:MM:SS..";
      type string;
      config false;
    }
    leaf ulTrigHoAllowed {
      description "Whether inter-frequency handover triggered by poor uplink coverage is allowed towards gNodeB. Whether inter-frequency handover triggered by poor uplink coverage is allowed towards external gNodeB that does not support uplink-triggered Mobility Control at Poor Coverage. External gNodeB does not support uplink-triggered Mobility Control at Poor Coverage if ulTrigHoSupport is false or empty. If true, Inter-frequency handover triggered by poor uplink coverage is allowed towards external gNodeB that does not support uplink-triggered Mobility Control at Poor Coverage. If false, Inter-frequency handover triggered by poor uplink coverage is not allowed towards external gNodeB that does not support uplink-triggered Mobility Control at Poor Coverage.; Default value: false.";
      type boolean;
      default "false";
    }
    leaf ulTrigHoSupport {
      description "Whether uplink-triggered Mobility Control at Poor Coverage is supported in external gNodeB. Value is set if uplink-triggered Mobility Control at Poor Coverage is supported by external gNodeB and Xn connection exists. If true, Inter-frequency handover triggered by poor uplink coverage is allowed towards external gNodeB. If false or if empty, Inter-frequency handover triggered by poor uplink coverage might be initiated towards external gNodeB depending on setting of ulTrigHoAllowed..";
      type boolean;
      config false;
    }
  }
  grouping ExternalNRCellCU-attributes {
    leaf cellLocalId {
      description "Together with gNodeB identifier, identifies an NR cell within a PLMN. Together with gNBId, it forms NCI.; range 0..16383; Default value: 0.";
      type eytypes:int32_range_0-16383;
      default "0";
    }
    leaf externalNRCellCUId {
      description "The value component of the RDN..";
      type string;
      mandatory true;
    }
    leaf-list isPciConflicted {
      description "Whether PCI conflict is detected or resolved. If true, PCI conflict is detected. PCI conflict is either collision or confusion. PCI confusion exists if source cell has relations to two neighbor cells where both neighbor cells have same PCI and frequency. PCI collision exists if source cell has relation to a neighbor cell where source cell and neighbor cell have same PCI and frequency. Only applicable if PciHandling::pciConflictHandlingEnabled is true..";
      type PciConflicted;
      min-elements 0;
      max-elements 6;
    }
    leaf nRFrequencyRef {
      description "Reference to an instance of NRFrequency MO corresponding to cell SSB configuration..";
      type string;
      mandatory true;
    }
    leaf nRPCI {
      description "Physical cell identity of external NR cell.; range 0..1007.";
      type int32 {
        range "0..1007";
      }
      mandatory true;
    }
    leaf nRTAC {
      description "Tracking Area Code for external NR Cell. If empty, NR SA is not supported for the PLMN IDs in plmnIdList. If empty and there is no ExternalBroadcastPLMNInfo instance under this MO instance, NR SA is not supported. Only applicable to NR SA.; range 0..16777215.";
      type uint32 {
        range "0..16777215";
      }
    }
    list pciConflictDetectingCell {
      config false;
      min-elements 0;
      max-elements 6;
      uses Ncgi-struct;
    }
    list pciConflictedCell {
      config false;
      min-elements 0;
      max-elements 6;
      uses Ncgi-struct;
    }
    list plmnIdList {
      key "id";
      leaf id {
        type uint32;
        description "Synthetic key for struct sequence entry.";
      }
      min-elements 1;
      max-elements 12;
      uses PLMNId-struct;
    }
    list primaryPLMNId {
      config false;
      description "PLMN ID for NR CGI..";
      uses PLMNId-struct;
    }
    leaf-list reservedBy {
      description "Contains a list of MO instances that reserve this MO instance..";
      type string;
      min-elements 0;
    }
    leaf serviceState {
      description "Service state of external NR cell in remote gNodeB..";
      type enumeration {
        enum OUT_OF_SERVICE;
        enum IN_SERVICE;
      }
      config false;
    }
    list sNSSAIList {
      key "id";
      leaf id {
        type uint32;
        description "Synthetic key for struct sequence entry.";
      }
      min-elements 0;
      max-elements 1024;
      uses SliceSelectionAssistInfo-struct;
    }
    leaf timeOfCreation {
      description "Time and date of MO creation. Format: YYYY-MM-DD HH:MM:SS..";
      type string;
      config false;
    }
  }
  grouping GNBCUCPFunction-attributes {
    leaf advUePosPeriodicityMode {
      description "Periodicity mode for periodic positioning reports. Only applicable if license for NR Advanced UE Location Support is present and feature is active. Only applicable to Mid-Band TDD cells and radio equipment that supports AAS configuration..";
      type enumeration {
        enum COMB_PERIODICITY;
        enum AOA_PERIODICITY;
      }
    }
    leaf altDepHBoCSEnabled {
      description "Whether alternative deprecation handling for Booster Carrier Sleep is enabled. If enabled, following MOCs and attributes are used: - EpBoCS and its children - TimeSchedulingGroup and its children - NRCellCU::epBoCSMode - NRCellCU::epBoCSEnergySavingState - NRCellCU::epBoCSTimeSchedulingGroupRef Otherwise, following MOC and its attributes, to be deprecated, are used: - DESManagementFunction; Default value: false.";
      type boolean;
      default "false";
    }
    leaf altDepHNasInactTimeEnabled {
      description "Whether alternative deprecation handling for nasInactivityTime is enabled.; Default value: false.";
      type boolean;
      default "false";
    }
    leaf autoNRCellCUCleanupSupported {
      description "Whether automatic cleanup is supported at F1 Setup Procedure.; Default value: false.";
      type boolean;
      default "false";
    }
    list blockedGNodeBList {
      key "id";
      leaf id {
        type uint32;
        description "Synthetic key for struct sequence entry.";
      }
      min-elements 0;
      max-elements 512;
      uses BlockedGNodeBInfo-struct;
    }
    leaf caDepHEnabled {
      description "Whether deprecation handling for SCell related attributes in IntraFreqMC is enabled. If true, updating any of following deprecated attributes in IntraFreqMCCellProfileUeCfg instance -betterSCellReportConfigMode -rsrpBetterSCell -rsrpSCellCoverage -rsrqSCellCoverage -sCellCoverageTriggerQuantity also updates corresponding (replacing) attribute in corresponding CaCellMeasProfileUeCfg instance. Updating any of following attributes in IntraFreqMCCellProfileUeCfg instance -prefUeGroupList -ueConfGroupList -ueGroupList also updates corresponding attribute in corresponding CaCellMeasProfileUeCfg instance. Updating ueConfGroupType in IntraFreqMCCellProfile instance also updates corresponding ueConfGroupType in corresponding CaCellMeasProfile instance. Updating intraFreqMCCellProfileRef in NRCellCU instance also updates corresponding caCellMeasProfileRef. Updating any of following deprecated attributes in IntraFreqMCFreqRelProfileUeCfg instance -rsrpSCellCoverageThrOffset -rsrqSCellCoverageThrOffset -waitForBetterSCellRep -prefUeGroupList -ueConfGroupList -ueGroupList also updates corresponding (replacing) attribute in corresponding CaFreqRelMeasProfileUeCfg instance. Updating deprecated ueConfGroupType in IntraFreqMCFreqRelProfile instance also updates corresponding (replacing) ueConfGroupType in corresponding CaFreqRelMeasProfile instance. Updating deprecated intraFreqMCFreqRelProfileRef in NRFreqRelation also updates corresponding (replacing) caFreqRelMeasProfileRef. If false, CaCellMeasProfile, CaCellMeasProfileUeCfg, CaFreqRelMeasProfile and CaFreqRelMeasProfileUeCfg MO classes and caCellMeasProfileRef and caFreqRelMeasProfileRef are not updated. Node always uses SCell attributes configured in CaCellMeasProfile, CaCellMeasProfileUeCfg, CaFreqRelMeasProfile and CaFreqRelMeasProfileUeCfg MO classes. Updating those MO classes never updates attributes in IntraFreqMCCellProfile, IntraFreqMCCellProfileUeCfg, IntraFreqMCFreqRelProfile and IntraFreqMCFreqRelProfileUeCfg MO classes. Disabling deprecation handling prevents SCell related attributes in CaCellMeasProfile, CaCellMeasProfileUeCfg, CaFreqRelMeasProfile and CaFreqRelMeasProfileUeCfg MO classes from being overwritten in new management system versions where SCell related attributes in CaCellMeasProfile, CaCellMeasProfileUeCfg, CaFreqRelMeasProfile and CaFreqRelMeasProfileUeCfg MO classes are visible and used instead of deprecated attributes.; Default value: true.";
      type boolean;
      default "true";
    }
    leaf cellRelationMOThresh {
      description "Target number of cell relation MO instances that can be created on a node by ANR promotion. When ANR automatic promotion or demotion is enabled, ANR manages number of cell relation MO instance, which is less than or equal to attribute value. If 0, number of cell relation MO instance is not managed.; Default value: 1500.";
      type int32 {
        range "0 | 320..7000";
      }
      default "1500";
    }
    leaf completeCellListXnEnabled {
      description "Whether to support sending complete cell list indicator by Xn Setup Procedure.; Default value: false.";
      type boolean;
      default "false";
    }
    leaf dnsLookup5GsTaiPeriodicTimer {
      description "Periodicity of DNS lookup to get domain names of potential AMF nodes. DNS lookup is performed for 5GS TAI domain names. If 0, no periodic DNS Lookup is done.; range 0..1000; Default value: 0.";
      type int32 {
        range "0..1000";
      }
      default "0";
      units "h";
    }
    leaf dnsLookupOn5GsTai {
      description "Whether AMF domain names are resolved with DNS lookup on 5GS TAI. RBS uses 5GS TAI to automatically obtain all AMF domain names from DNS at RBS start or restart. AMF domain name list is refreshed periodically and AMF connections are released and set up according to new list. AMF domain name list can also be refreshed from ENM.; Default value: false.";
      type boolean;
      default "false";
    }
    leaf endcMdtM1DelayTimeForMeasGap {
      description "Initial delay time for inter-frequency MDT M1 configuration requiring measurement gap for EN-DC. Value 0 is deprecated since 24.Q3 and planned to be removed. Value 0 is automatically converted to 1.; range 0..2000; Default value: 1.";
      type int32 {
        range "0..2000";
      }
      default "1";
      units "ms";
    }
    leaf endpointResourceRef {
      description "Reference to an instance of EndpointResource MO. ResourcePartitionMember MO can also refer to EndpointResource instances only valid for specific PLMN or NSSAI. If ResourcePartitionMember::endpointResourceRef is empty, this reference is used..";
      type string;
    }
    leaf extEnbRemoveTime {
      description "Time a TermPointToENodeB instance can be disabled before it is removed.; range 0..10080; Default value: 1440.";
      type uint32 {
        range "0..10080";
      }
      default "1440";
      units "minute";
    }
    leaf extendedBandN77Supported {
      description "Whether 3450-3550 MHz range of band n77 is supported. If true, only UEs that indicate capability for extendedBand-n77-r16 can access 3450-3550 MHz range of band n77. Value must be true for 3450-3550 MHz range of band n77 in the USA. Only applicable to Mid-Band cells.; Default value: false.";
      type boolean;
      default "false";
    }
    leaf extendedBandN77TwoSupported {
      description "Whether 3650-3980 MHz range of band n77 is supported. If true, only UEs that indicate capability for extendedBand-n77-2-r17 can access 3650-3980 MHz range of band n77. Value must be true for 3650-3980 MHz range of band n77 in Canada. Only applicable to Mid-Band cells.; Default value: false.";
      type boolean;
      default "false";
    }
    leaf extendedXnConnAllowed {
      description "Whether extended Xn cardinality is allowed up to 512. If true, gNodeB allows up to 512 ExternalGNBCUCPFunction instances. If false, gNodeB allows up to 256 ExternalGNBCUCPFunction instances. ExternalGNBCUCPFunction instances exceeding 256 are not removed..";
      type boolean;
    }
    leaf extNrCellRemovalByXnSupported {
      description "Whether to support removal of external NR cell in Xn Setup Procedure. External NR cell is referenced by ExternalNRCellCU instance.; Default value: false.";
      type boolean;
      default "false";
    }
    leaf gNBCUCPFunctionId {
      description "The value component of the RDN..";
      type string;
      mandatory true;
    }
    leaf gNBCUName {
      description "Name of the gNodeB-CU. Allowed characters for value are as follows: - a-z - A-Z - 0-9 - Space - Apostrophe (') - Left and right parenthesis ((,)) - Plus and minus sign (+,-) - Comma (,) - Full stop (.) - Forward slash (/) - Colon (:) - Equal sign (=) - Question mark (?) Character case is preserved. Length of name cannot exceed 150 characters. For more information, see PrintableString of ITU-T Rec X.680. If attribute contains invalid characters, each invalid one is replaced by a space before the string is sent to gNodeB-DU. If empty, gNBCU-Name is not sent to gNodeB-DU.; length 1..150.";
      type string {
        length "1..150";
      }
    }
    leaf gNBId {
      description "Identity of gNodeB within a PLMN. Part of the NR Cell Global Identity. Identifies node over NG-C and X2.; range 0..4294967295.";
      type eytypes:int64_range_0-4294967295;
      mandatory true;
    }
    leaf gNBIdLength {
      description "Length of gNBId bit string representation. Must be at least minimum bit length that can accommodate gNBId if gNBId bit representation exceeds 22 bits. gNBId =< (2^gNBIdLength)-1; range 22..32; Default value: 22.";
      type eytypes:int32_range_22-32;
      default "22";
    }
    leaf iratDirectPktFwdEnabled {
      description "Whether IRAT direct packet forwarding is enabled.; Default value: true.";
      type boolean;
      default "true";
    }
    leaf lastUpdateAca {
      description "Timestamp of evaluation of Automated Carrier Aggregation feature. Format: YYYY-MM-DD HH:MM:SS..";
      type string;
      config false;
    }
    leaf maxCommonProcTime {
      description "Maximum time until an expected response message to a common procedure is considered lost.; range 1..60; Default value: 30.";
      type eytypes:int32_range_1-60;
      default "30";
      units "s";
    }
    leaf maxNgRetryTime {
      description "Maximum time between consecutive NG setup attempts. Time between retry attempts is increasing for every retry. This value sets an upperbound to it.; range 1..3600; Default value: 30.";
      type int32 {
        range "1..3600";
      }
      default "30";
      units "s";
    }
    leaf nasInactivityTime {
      description "NAS inactivity time to pass before UE can be released to RRC_IDLE or RRC_INACTIVE state.; range 1..60; Default value: 5.";
      type eytypes:int32_range_1-60;
      default "5";
      units "s";
    }
    leaf networkIdInUeCapEnq {
      description "Whether network identifier is included in RRC UECapabilityEnquiry message. If true, network identifier is included in RRC UECapabilityEnquiry message. If false, network identifier is excluded from RRC UECapabilityEnquiry message.; Default value: false.";
      type boolean;
      default "false";
    }
    leaf ngapHoAtXnHoFailEnabled {
      description "Whether NGAP handover can be triggered at Xn handover preparation failure. If true, NGAP handover is triggered if Xn handover preparation fails in target gNodeB because GUAMI that is currently assigned to UE context is not served by target gNodeB. If false, no NGAP handover is triggered for failure scenario above.; Default value: false.";
      type boolean;
      default "false";
    }
    leaf ngcDedProcTime {
      description "Time until response to UE-dedicated NGAP message is considered lost. Applicable to UE-dedicated NGAP procedures apart from following NGAP procedures: - NGAP Handover Preparation time defined by GNBCUCPFunction::tNgRelocPrep - Time for protection of overall handover procedure in source NG-RAN node defined by GNBCUCPFunction::tNgRelocOverall. - Time for protection of NGAP Path Switch Request procedure in target NG-RAN node defined by GNBCUCPFunction::tNgPathSwitchRequest.; range 1..60; Default value: 5.";
      type eytypes:int32_range_1-60;
      default "5";
      units "s";
    }
    leaf noOfSupportedNRCellCU {
      description "Supported number of NRCellCU instances in current deployment.; MOM flags: noNotification, isNillable=true; Status info: Since 24.Q4. Replaced by CardinalityLimits::maxNRCellCU. Planned to be removed..";
      type int32;
      config false;
      status deprecated;
    }
    leaf nrNeedForGapsSupported {
      description "Whether NR NeedForGaps is supported.; Default value: true.";
      type boolean;
      default "true";
    }
    leaf pimAutoDetectionEnabled {
      description "Whether automatic PIM detection is activated. Only applicable to FDD (Low-Band) cells.; Default value: false.";
      type boolean;
      default "false";
    }
    list pLMNId {
      key "id";
      leaf id {
        type uint32;
        description "Synthetic key for struct attribute.";
      }
      min-elements 1;
      description "PLMN identifier to be used as part of global RAN node identity. Value MCC=001, MNC=01 means PLMN is not initiated. This value cannot be used as a valid PLMN Identity..";
      uses PLMNId-struct;
    }
    leaf prefInterGnbHo {
      description "Preferred inter-gNodeB handover type..";
      type enumeration {
        enum XN_HO;
        enum NG_HO;
      }
    }
    leaf pwsBroadcastStarted {
      description "Whether PWS service is started..";
      type boolean;
      config false;
    }
    leaf ranNodeName {
      description "Name of RAN node. Allowed characters for value are as follows: - a-z - A-Z - 0-9 - Space - Apostrophe (') - Left and right parenthesis ((,)) - Plus and minus sign (+,-) - Comma (,) - Full stop (.) - Forward slash (/) - Colon (:) - Equal sign (=) - Question mark (?) Character case is preserved. Length of name cannot exceed 150 characters. For more information, see PrintableString of ITU-T Rec. X.680. If empty, this value is not sent to AMF.; length 1..150.";
      type string {
        length "1..150";
        pattern "[A-Za-z0-9 '()+\\,./:=?-]+";
      }
    }
    leaf release {
      description "The product release of the ManagedFunction..";
      type string;
      config false;
    }
    leaf resourceStatusReportDefault {
      description "Whether incoming subscriptions support for Standard Load Reporting is active. Value -2 means that incoming subscriptions support for Standard Load Reporting (that is, a gNodeB responses on Xn Resource Status Request from another gNodeB and initiates Xn Resource Status Reporting procedure) is inactive. Value greater than 0 means that incoming subscriptions support for Standard Load Reporting is active. When active, value also defines default value of maximum number of UEs in RRC_CONNECTED mode for all cells used in Standard Load Reporting. If NRCellCU::resourceStatusMaxConnUe is not greater than 0, this attribute must be used as maximum number of UEs in RRC_CONNECTED mode for cell in Standard Load Reporting. Otherwise, NRCellCU::resourceStatusMaxConnUe is used. Not applicable if private extensions are used in 3GPP procedures for Xn resource status reporting. Not applicable to High-Band cells.; Default value: -2.";
      type int32 {
        range "-2 | 1..65535";
      }
      default "-2";
    }
    leaf resourceStatusReportF1Enabled {
      description "Whether Resource Status Reporting over F1-C interface is enabled for gNodeB. If false, NR Unified Access Control does not use rejection ratio information for barring probability calculation.; Default value: true.";
      type boolean;
      default "true";
    }
    list rfspSpidPairList {
      key "id";
      leaf id {
        type uint32;
        description "Synthetic key for struct sequence entry.";
      }
      min-elements 0;
      max-elements 20;
      uses RfspSpidPair-struct;
    }
    leaf ribTmAutoMax {
      description "Maximum number of automatically created RibTmRelation instances for each NRCellCU instance. If 0, Radio Interface-Based Time Monitoring (RIB-TM) autoconfiguration is deactivated. Automatically created RibTmRelation instances are deleted automatically.; range 0..20; Default value: 0.";
      type eytypes:int32_range_0-20;
      default "0";
    }
    leaf rrcReestSupportType {
      description "Support type for RRC reestablishment..";
      type enumeration {
        enum NO_RRE_SUPPORT;
        enum INTRA_GNB_RRE;
        enum INTRA_INTER_GNB_RRE;
      }
    }
    leaf servAdapUPProfUlDepHEnabled {
      description "Whether deprecation handling for attributes in QciProfileEndcConfigExt is enabled. If true, updating any of following deprecated attributes in QciProfileEndcConfigExt also updates corresponding attribute in corresponding UlDataSplitUeCfg instance: - initialUplinkConf - ulDataSplitThreshold - ulDataSplitThresholdMcg If false, UlDataSplitUeCfg instance is not updated. Attributes in corresponding UlDataSplitUeCfg instance are always applied. Updating attributes in UlDataSplitUeCfg never updates corresponding deprecated attributes. Disabling deprecation handling prevents attributes in UlDataSplitUeCfg instance from being overwritten in new management system versions where UlDataSplitUeCfg instance is visible and used instead of deprecated attributes.; Default value: true.";
      type boolean;
      default "true";
    }
    leaf tCellStateSupervision {
      description "Guard timer for cellState alarm handling. Period of time after cellState change during which Cell State Inactive alarm is suppressed.; range 4..3600; Default value: 300.";
      type int32 {
        range "4..3600";
      }
      default "300";
      units "s";
    }
    leaf tDcOverall {
      description "Maximum waiting time in SgNB for completion of EN-DC procedures. Specifies maximum time in SgNB for either SgNB initiated SgNB Modification procedure or protection of E-UTRAN actions necessary to configure UE resources at SgNB Addition or MeNB initiated SgNB Modification. Used for SgNB Addition, SgNB initiated SgNB Modification, SgNB Change, and MeNB initiated SgNB Modification procedures.; range 1..20; Default value: 7.";
      type eytypes:int32_range_1-20;
      default "7";
      units "s";
    }
    leaf tInHoRrcReconfigComplete {
      description "Maximum time for protection of RRC Reconfiguration procedure in target handover NG-RAN node. Maximum time between sending NGAP or XnAP HANDOVER REQUEST ACKNOWLEDGE message and reception of RRC RRCReconfigurationComplete message in target handover NG-RAN node.; range 1..60; Default value: 5.";
      type eytypes:int32_range_1-60;
      default "5";
      units "s";
    }
    leaf tNgPathSwitchRequest {
      description "Maximum time for protection of NGAP Path Switch Request procedure NG-RAN node. Maximum time between sending of NGAP PATH SWITCH REQUEST message and reception of NGAP PATH SWITCH REQUEST ACKNOWLEDGE message in NG-RAN node.; range 1..60; Default value: 5.";
      type eytypes:int32_range_1-60;
      default "5";
      units "s";
    }
    leaf tNgRelocOverall {
      description "Maximum time for protection of overall handover procedure in source NG-RAN node. Maximum time between sending of RRC RRCReconfiguration (Handover Command) message to UE and reception of NGAP UE CONTEXT RELEASE COMMAND message in source NG-RAN node. Applicable when handover is performed as NGAP handover.; range 1..60; Default value: 5.";
      type eytypes:int32_range_1-60;
      default "5";
      units "s";
    }
    leaf tNgRelocPrep {
      description "Maximum time for NGAP Handover Preparation procedure in source NG-RAN node. Maximum time between sending of NGAP HANDOVER REQUIRED message and reception of NGAP HANDOVER COMMAND message in source NG-RAN node.; range 1..60; Default value: 5.";
      type eytypes:int32_range_1-60;
      default "5";
      units "s";
    }
    leaf tXnDcOverall {
      description "Maximum time used in the Secondary Node for protection of XnAP procedures. Used for either Secondary Node initiated Secondary Node Modification procedure or protection of NG-RAN actions necessary to configure UE resources at Secondary Node Addition, Master Node initiated Secondary Node Modification or Secondary Node initiated Secondary Node Change procedures.; range 1..20; Default value: 5.";
      type eytypes:int32_range_1-20;
      default "5";
      units "s";
    }
    leaf tXnDcPrep {
      description "Maximum time used in the Master Node for protection of XnAP procedures. Used for Secondary Node Addition Preparation or Master Node-initiated Secondary Node Modification Preparation.; range 1..20; Default value: 5.";
      type eytypes:int32_range_1-20;
      default "5";
      units "s";
    }
    leaf tXnRelocOverall {
      description "Maximum time for protection of overall handover procedure in source NG-RAN node. Maximum time between sending of RRC RRCReconfiguration (Handover Command) message to UE and reception of XnAP UE CONTEXT RELEASE message in source NG-RAN node. Applicable when handover is performed as Xn handover.; range 1..60; Default value: 5.";
      type eytypes:int32_range_1-60;
      default "5";
      units "s";
    }
    leaf tXnRelocPrep {
      description "Maximum time for Xn Handover Preparation procedure in source NG-RAN node. Maximum time between sending of XnAP HANDOVER REQUEST message and reception of XnAP HANDOVER REQUEST ACKNOWLEDGE message in source NG-RAN node.; range 1..60; Default value: 5.";
      type eytypes:int32_range_1-60;
      default "5";
      units "s";
    }
    leaf userLabel {
      description "Label for free use..";
      type string;
    }
    leaf xnIpAddrViaNgActive {
      description "Whether automatic lookup of Xn IP addresses over NG is active. NGAP Configuration Transfer Procedures are used for retrieving Xn IP addresses for neighbor gNodeB.; Default value: true.";
      type boolean;
      default "true";
    }
    leaf pmNgLinkBreak {
      description "Number of times there is link break in NG-C connection..";
      type uint64;
      config false;
    }
    leaf-list pmFwkStreamProducedEventDistr {
      description "Total number of PM events produced in each CTR stream in PM framework. Ranges: Bin[0]: Applicable for the Cell Trace Job ID 10000 Bin[1]: Applicable for the Cell Trace Job ID 10001 Bin[2]: Applicable for the Cell Trace Job ID 10002 Bin[3]: Applicable for the Cell Trace Job ID 10003 Bin[4]: Applicable for the Cell Trace Job ID 10004 Bin[5]: Applicable for the Cell Trace Job ID 10005.";
      type uint64;
      max-elements 6;
    }
    leaf pmPagDiscardedMpLoad {
      description "Number of paging messages discarded in NR SA because Baseband MP load control indicates OVERLOAD state. Paging messages can be NGAP or RAN..";
      type uint64;
      config false;
    }
    leaf-list pmFwkStreamDroppedEventSlowStreamDistr {
      description "Number of PM events dropped due to slow stream in each CTR stream in PM framework. Ranges: Bin[0]: Applicable for the Cell Trace Job ID 10000 Bin[1]: Applicable for the Cell Trace Job ID 10001 Bin[2]: Applicable for the Cell Trace Job ID 10002 Bin[3]: Applicable for the Cell Trace Job ID 10003 Bin[4]: Applicable for the Cell Trace Job ID 10004 Bin[5]: Applicable for the Cell Trace Job ID 10005.";
      type uint64;
      max-elements 6;
    }
    leaf pmXnSetupRequestOut {
      description "Number of outgoing XnAP XN SETUP REQUEST messages..";
      type uint64;
      config false;
    }
    leaf pmRrcInactRedCapLevelMax {
      description "Maximum number of RedCap UEs in RRC_INACTIVE mode in gNodeB-CU-CP..";
      type int64;
      config false;
    }
    leaf pmEndcInitAccessRejGnbBbIntens {
      description "Number of rejected SGNB ADDITION REQUEST messages in EN-DC setup because of connection intensity control..";
      type uint64;
      config false;
    }
    leaf pmNrdcInitAccessRejUeCapacityLimit {
      description "Number of rejected SN ADDITION REQUEST messages in NR-DC setup because of UE capacity limit..";
      type uint64;
      config false;
    }
    leaf pmEndcPSCellChangeRejInInterGnbUeAdmission {
      description "Number of inter-gNodeB PSCell change procedures rejected because of admission control. Deprecated: Since 23.Q4. Planned to be removed. Replaced by GNBCUCPFunction::pmEndcPSCellChangeRejInInterGnbUeCapacityLimit.; MOM flags: noNotification.";
      type uint64;
      config false;
      status deprecated;
    }
    leaf pmXnSetupRequestIn {
      description "Number of incoming XnAP XN SETUP REQUEST messages..";
      type uint64;
      config false;
    }
    leaf pmRrcInactLevelSum {
      description "Sum of all sample values recorded for number of UEs in RRC_INACTIVE mode in gNodeB-CU-CP..";
      type uint64;
      config false;
    }
    leaf pmEndcPSCellChangeRejInInterGnbUeCapacityLimit {
      description "Number of inter-gNodeB PSCell change procedures rejected because of UE capacity limit..";
      type uint64;
      config false;
    }
    leaf pmPagNgReceivedEdrx {
      description "Number of NGAP eDRX paging messages received from AMF in this gNodeB when eDRX IE is present in message. Subset of GNBCUCPFunction.pmPagNgReceived PM counter for all paging messages received from AMF..";
      type uint64;
      config false;
    }
    leaf-list pmFwkStreamDroppedEventSocketConnectionFailDistr {
      description "Number of PM events dropped due to socket connection failure in each CTR stream in PM framework. Ranges: Bin[0]: Applicable for the Cell Trace Job ID 10000 Bin[1]: Applicable for the Cell Trace Job ID 10001 Bin[2]: Applicable for the Cell Trace Job ID 10002 Bin[3]: Applicable for the Cell Trace Job ID 10003 Bin[4]: Applicable for the Cell Trace Job ID 10004 Bin[5]: Applicable for the Cell Trace Job ID 10005.";
      type uint64;
      max-elements 6;
    }
    leaf pmXnNodeConfigUpdateAckIn {
      description "Number of incoming XnAP NG-RAN NODE CONFIGURATION UPDATE ACKNOWLEDGE messages..";
      type uint64;
      config false;
    }
    leaf pmEndcPSCellChangeRejInInterGnbBbIntens {
      description "Number of inter-gNodeB PSCell change procedures rejected because of connection intensity control..";
      type uint64;
      config false;
    }
    leaf pmNrdcPSCellChangeRejInInterGnbUeCapacityLimit {
      description "Number of rejected SN ADDITION REQUEST messages in NR-DC PSCell change because of UE capacity limit..";
      type uint64;
      config false;
    }
    leaf pmEndcPSCellChangeRejInInterGnbMpLoad {
      description "Number of rejected incoming inter-PSCell changes in NR NSA because Baseband MP load control indicates OVERLOAD or VERY HIGH state..";
      type uint64;
      config false;
    }
    leaf pmRrcInactRedCapLevelSum {
      description "Sum of all sample values recorded for number of RedCap UEs in RRC_INACTIVE mode in gNodeB-CU-CP..";
      type uint64;
      config false;
    }
    leaf pmNrdcInitAccessRejUeAdmission {
      description "Number of rejected SN ADDITION REQUEST messages in NR-DC setup because of admission control. Deprecated: Since 23.Q4. Planned to be removed. Replaced by GNBCUCPFunction::pmNrdcInitAccessRejUeCapacityLimit.; MOM flags: noNotification.";
      type uint64;
      config false;
      status deprecated;
    }
    leaf pmNrdcPSCellChangeRejInInterGnbUeAdmission {
      description "Number of rejected SN ADDITION REQUEST messages in NR-DC PSCell change because of admission control. Deprecated: Since 23.Q4. Planned to be removed. Replaced by GNBCUCPFunction::pmNrdcPSCellChangeRejInInterGnbUeCapacityLimit.; MOM flags: noNotification.";
      type uint64;
      config false;
      status deprecated;
    }
    leaf-list pmFwkStreamDroppedEventDistr {
      description "Total number of PM events dropped in each CTR stream in PM framework. Ranges: Bin[0]: Applicable for the Cell Trace Job ID 10000 Bin[1]: Applicable for the Cell Trace Job ID 10001 Bin[2]: Applicable for the Cell Trace Job ID 10002 Bin[3]: Applicable for the Cell Trace Job ID 10003 Bin[4]: Applicable for the Cell Trace Job ID 10004 Bin[5]: Applicable for the Cell Trace Job ID 10005.";
      type uint64;
      max-elements 6;
    }
    leaf pmXnNodeConfigUpdateOut {
      description "Number of outgoing XnAP NG-RAN NODE CONFIGURATION UPDATE messages..";
      type uint64;
      config false;
    }
    leaf pmRrcConnLevelSumNrDc {
      description "Sum of all samples taken to track number of UEs configured with NR-DC. Counted on Secondary Node side..";
      type uint64;
      config false;
    }
    leaf pmPagNgReceivedPriority {
      description "Number of NGAP paging messages with a defined paging priority received from AMF in this gNodeB..";
      type uint64;
      config false;
    }
    leaf pmRrcConnLevelMaxEnDc {
      description "Peak number of NR EN-DC UEs in RRC_CONNECTED mode in gNodeB-CU-CP..";
      type int64;
      config false;
    }
    leaf pmXnSetupResponseIn {
      description "Number of incoming XnAP XN SETUP RESPONSE messages..";
      type uint64;
      config false;
    }
    leaf-list pmFwkStreamDroppedEventSocketErrorDistr {
      description "Number of PM events dropped due to socket error in each CTR stream in PM framework. Ranges: Bin[0]: Applicable for the Cell Trace Job ID 10000 Bin[1]: Applicable for the Cell Trace Job ID 10001 Bin[2]: Applicable for the Cell Trace Job ID 10002 Bin[3]: Applicable for the Cell Trace Job ID 10003 Bin[4]: Applicable for the Cell Trace Job ID 10004 Bin[5]: Applicable for the Cell Trace Job ID 10005.";
      type uint64;
      max-elements 6;
    }
    leaf pmXnNodeConfigUpdateFailIn {
      description "Number of incoming XnAP NG-RAN NODE CONFIGURATION UPDATE FAILURE messages..";
      type uint64;
      config false;
    }
    leaf pmRrcConnLevelSumEnDc {
      description "Sum of all sample values recorded for number of UEs configured for EN-DC in RRC_CONNECTED mode..";
      type uint64;
      config false;
    }
    leaf pmRrcInactLevelMax {
      description "Maximum number of UEs in RRC_INACTIVE mode in gNodeB-CU-CP. Used when no flexible filters are applied..";
      type int64;
      config false;
    }
    leaf pmRrcConnLevelMaxNrDc {
      description "Peak number of UEs configured with NR-DC, counted on Secondary Node side..";
      type int64;
      config false;
    }
    leaf pmEndcInitAccessRejUeCapacityLimit {
      description "Number of rejected SGNB ADDITION REQUEST messages in EN-DC setup because of UE capacity limit..";
      type uint64;
      config false;
    }
    leaf pmXnNodeConfigUpdateFailOut {
      description "Number of outgoing XnAP NG-RAN NODE CONFIGURATION UPDATE FAILURE messages..";
      type uint64;
      config false;
    }
    leaf pmPagRanIntraGnbNonTrig {
      description "Number of untriggered intra-gNodeB RAN PAGING messages..";
      type uint64;
      config false;
    }
    leaf pmRrcConnLevelMax {
      description "Peak number of following UEs in RRC_CONNECTED mode in gNodeB-CU-CP: - NR standalone UEs. NR standalone UEs configured with NR-DC are included on Master Node side. - EN-DC UEs. - UEs configured with NR-DC, counted on Secondary Node side..";
      type int64;
      config false;
    }
    leaf pmXnSetupFailIn {
      description "Number of incoming XnAP XN SETUP FAILURE messages..";
      type uint64;
      config false;
    }
    leaf pmPagDiscardedMpLoadEdrx {
      description "Number of eDRX paging messages discarded in NR standalone because Baseband main processor load control indicates OVERLOAD state. Paging messages is NGAP. Subset of GNBCUCPFunction.pmPagDiscardedMpLoad PM counter..";
      type uint64;
      config false;
    }
    leaf pmRrcConnLevelSamp {
      description "Number of times pmRrcConnLevelSumSa, pmRrcConnLevelSumEnDc and pmRrcConnLevelSumNrDc PM counters accumulate new sample..";
      type uint64;
      config false;
    }
    leaf pmPagNgDiscardedEdrx {
      description "Number of NGAP eDRX paging messages discarded in gNodeB-CU. Subset of GNBCUCPFunction.pmPagNgDiscarded PM counter for all paging messages discarded from AMF..";
      type uint64;
      config false;
    }
    leaf pmEndcInitAccessRejUeAdmission {
      description "Number of rejected SGNB ADDITION REQUEST messages in EN-DC setup because of admission control. Deprecated: Since 23.Q4. Planned to be removed. Replaced by GNBCUCPFunction::pmEndcInitAccessRejUeCapacityLimit.; MOM flags: noNotification.";
      type uint64;
      config false;
      status deprecated;
    }
    leaf pmRrcConnLevelSumSa {
      description "Sum of all sample values recorded for number of NR standalone UEs in RRC_CONNECTED mode in gNodeB-CU-CP. For NR-DC, NR standalone UEs on Master Node side configured with NR-DC are included..";
      type uint64;
      config false;
    }
    leaf pmPagNgReceived {
      description "Number of NGAP Paging messages received from AMF in this gNodeB..";
      type uint64;
      config false;
    }
    leaf pmUeCtxtRetrieveFailRrcReestNoUeCtxt {
      description "Number of failed Retrieve UE Context procedures due to no UE Context triggered by RRC Connection Reestablishment procedure. See 3GPP TS 38.423, Retrieve UE Context Request..";
      type uint64;
      config false;
    }
    leaf pmPagNgDiscarded {
      description "Number of NGAP Paging messages discarded in gNodeB-CU..";
      type uint64;
      config false;
    }
    leaf-list pmFwkStreamDroppedEventLicenseUnavailableDistr {
      description "Number of PM events dropped due to license unavailable in each CTR stream in PM framework Ranges: Bin[0]: Applicable for the Cell Trace Job ID 10000 Bin[1]: Applicable for the Cell Trace Job ID 10001 Bin[2]: Applicable for the Cell Trace Job ID 10002 Bin[3]: Applicable for the Cell Trace Job ID 10003 Bin[4]: Applicable for the Cell Trace Job ID 10004 Bin[5]: Applicable for the Cell Trace Job ID 10005.";
      type uint64;
      max-elements 6;
    }
    leaf pmXnSetupResponseOut {
      description "Number of outgoing XnAP XN SETUP RESPONSE messages..";
      type uint64;
      config false;
    }
    leaf pmEndcInitAccessRejGnbMpLoad {
      description "Number of rejected SGNB ADDITION REQUEST messages in EN-DC setup because Baseband MP load control indicates OVERLOAD or VERY HIGH state..";
      type uint64;
      config false;
    }
    leaf-list pmFwkStreamDroppedEventSocketSetupFailDistr {
      description "Number of PM events dropped due to socket setup failure in each CTR stream in PM framework. Ranges: Bin[0]: Applicable for the Cell Trace Job ID 10000 Bin[1]: Applicable for the Cell Trace Job ID 10001 Bin[2]: Applicable for the Cell Trace Job ID 10002 Bin[3]: Applicable for the Cell Trace Job ID 10003 Bin[4]: Applicable for the Cell Trace Job ID 10004 Bin[5]: Applicable for the Cell Trace Job ID 10005.";
      type uint64;
      max-elements 6;
    }
    leaf pmPagRanIntraGnbTrig {
      description "Number of triggered intra-gNodeB RAN PAGING messages..";
      type uint64;
      config false;
    }
    leaf pmXnSetupFailOut {
      description "Number of outgoing XnAP XN SETUP FAILURE messages..";
      type uint64;
      config false;
    }
    leaf pmXnNodeConfigUpdateIn {
      description "Number of incoming XnAP NG-RAN NODE CONFIGURATION UPDATE messages..";
      type uint64;
      config false;
    }
    leaf pmRrcConnLevelMaxSa {
      description "Peak number of NR standalone UEs in RRC_CONNECTED mode in gNodeB-CU-CP. For NR-DC, NR standalone UEs on Master Node side configured with NR-DC are included..";
      type int64;
      config false;
    }
    leaf pmRrcConnRedCapLevelSum {
      description "All sample values recorded for number of RedCap UEs in RRC_CONNECTED mode in gNodeB-CU-CP..";
      type uint64;
      config false;
    }
    leaf pmRrcConnRedCapLevelMax {
      description "Peak number of RedCap UEs in RRC_CONNECTED mode in gNodeB-CU-CP..";
      type int64;
      config false;
    }
    leaf pmXnNodeConfigUpdateAckOut {
      description "Number of outgoing XnAP NG-RAN NODE CONFIGURATION UPDATE ACKNOWLEDGE messages..";
      type uint64;
      config false;
    }
    leaf pmRrcInactLevelSamp {
      description "Number of times GNBCUCPFunction.pmRrcInactLevelSum counter accumulates new sample..";
      type uint64;
      config false;
    }
    leaf pmNeighborObjFootprint {
      description "Based on periodic internal event with five-second period time. Current CU-CP footprint of all neighbor MO instances (ExternalNRCellCU, NRCellRelation, ExternalEUtranCell, EUtranCellRelation, NRFreqRelation and EUtranFreqRelation) in relation to system limit. Value is shown in percentage as truncated integer. Value is latest available footprint calculation at ROP period end. When value reaches 100, further creation attempts for neighbor MO instances are rejected..";
      type int64;
      config false;
    }
  }
  grouping ImeiSvGroup-attributes {
    leaf imeiSvGroupId {
      description "The value component of the RDN..";
      type string;
      mandatory true;
    }
    list imeiTacSvSnList {
      key "id";
      leaf id {
        type uint32;
        description "Synthetic key for struct sequence entry.";
      }
      min-elements 0;
      max-elements 512;
      uses ImeiTacSvSn-struct;
    }
    leaf-list reservedBy {
      description "Contains a list of MO instances that reserve this MO instance..";
      type string;
      min-elements 0;
    }
    leaf userLabel {
      description "Label for free use..";
      type string;
    }
  }
  grouping ImeiSvGroups-attributes {
    leaf imeiSvGroupsId {
      description "The value component of the RDN..";
      type string;
      mandatory true;
    }
    leaf userLabel {
      description "Label for free use..";
      type string;
    }
  }
  grouping ImeiSvs-attributes {
    leaf-list imeiSvsGroupRef {
      description "References to instances of ImeiSvGroup MO. When using special <Value> \"ref\" for <Variable> imeisv in selectionCriteria, UE <Variable> imeisv is evaluated against each group referenced in this list. If empty, represented imeisv <ValueList> is empty..";
      type string;
      ordered-by user;
      min-elements 0;
      max-elements 512;
    }
    leaf imeiSvsId {
      description "The value component of the RDN..";
      type string;
      mandatory true;
    }
    leaf-list reservedBy {
      description "Contains a list of MO instances that reserve this MO instance..";
      type string;
      min-elements 0;
    }
    leaf userLabel {
      description "Label for free use..";
      type string;
    }
  }
  grouping InactivityProfile-attributes {
    leaf inactivityProfileId {
      description "The value component of the RDN..";
      type string;
      mandatory true;
    }
    leaf ueConfGroupType {
      description "UE configuration group type. UE configuration group type that is applied in contained InactivityProfileUeCfg instances..";
      type enumeration {
        enum UE_MOBILITY_GROUP;
        enum UE_SERVICE_GROUP;
        enum UE_ADMISSION_GROUP;
      }
    }
  }
  grouping InactivityProfileUeCfg-attributes {
    leaf inactivityProfileUeCfgId {
      description "The value component of the RDN..";
      type string;
      mandatory true;
    }
    leaf nasInactivityTime {
      description "Non-Access Stratum (NAS) inactivity time. Time of NAS inactivity before UE can be released to RRC_IDLE or RRC_INACTIVE state.; range 1..60; Default value: 5.";
      type eytypes:int32_range_1-60;
      default "5";
      units "s";
    }
    leaf-list prefUeGroupList {
      description "Preference UE group list. List of preference UE group identifiers. If empty, MO instance matches preference UE group identifiers not defined in prefUeGroupList of any other MO instances under parent MO instance. Value 0 is no longer allowed and is planned to be removed from valid range..";
      type eytypes:int32_range_0-255;
      ordered-by user;
      min-elements 0;
      max-elements 8;
    }
    leaf tInactivityTimer {
      description "Time NR SA UEs can be inactive before released.; range 1..7200; Default value: 10.";
      type eytypes:int32_range_1-7200;
      default "10";
      units "s";
    }
    leaf tInactivityTimerEndcSn {
      description "Time before inactivity is reported to master node for an EN-DC UE in Secondary Node.; range 1..7200; Default value: 5.";
      type eytypes:int32_range_1-7200;
      default "5";
      units "s";
    }
    leaf tInactivityTimerNrdcSn {
      description "Time before inactivity is reported to master node for an NR-DC UE in Secondary Node.; range 1..7200; Default value: 10.";
      type eytypes:int32_range_1-7200;
      default "10";
      units "s";
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 16;
    }
    leaf-list ueGroupList {
      description "UE group list. List of UE group identifiers. If empty, MO instance matches all UE group identifiers. Value 0 is no longer allowed and is planned to be removed from valid range..";
      type eytypes:int32_range_0-255;
      ordered-by user;
      min-elements 0;
      max-elements 16;
    }
    leaf userLabel {
      description "Label for free use..";
      type string;
    }
  }
  grouping InitialCg-attributes {
    leaf initialCgId {
      description "The value component of the RDN..";
      type string;
      mandatory true;
    }
    leaf-list reservedBy {
      description "Contains a list of MO instances that reserve this MO instance..";
      type string;
      min-elements 0;
    }
    leaf ueConfGroupType {
      description "UE configuration group type. UE configuration group type that is applied in contained InitialCgUeCfg instances..";
      type enumeration {
        enum UE_MOBILITY_GROUP;
        enum UE_SERVICE_GROUP;
        enum UE_ADMISSION_GROUP;
      }
    }
    leaf userLabel {
      description "Label for free use..";
      type string;
    }
  }
  grouping InitialCgUeCfg-attributes {
    leaf initialCgUeCfgId {
      description "The value component of the RDN..";
      type string;
      mandatory true;
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf ulScgInitialCritRsrpThresh {
      description "Critical RSRP threshold for target SCG RSRP level at dual-connectivity setup. Uplink primary path at dual-connectivity setup is configured to: - SCG, if UlDataSplitUeCfg::initialUlPrimaryPathMode is PREFER_SCG and SCG RSRP level is ulScgInitialLowRsrpThresh, or if UlDataSplitUeCfg::initialUlPrimaryPathMode is KEEP_SCG and SCG RSRP level is above this threshold. - MCG, if UlDataSplitUeCfg::initialUlPrimaryPathMode is PREFER_SCG and SCG RSRP level is below ulScgInitialLowRsrpThresh, if UlDataSplitUeCfg::initialUlPrimaryPathMode is KEEP_SCG and SCG RSRP level is below this threshold, or if UlDataSplitUeCfg::initialUlPrimaryPathMode is KEEP_MCG. Applicable to EN-DC and NR-DC.; range -156..-29; Default value: -140.";
      type eytypes:int32_range_-156--29;
      default "-140";
      units "dBm";
    }
    leaf ulScgInitialLowRsrpThresh {
      description "Low RSRP threshold for target SCG RSRP level at setup of secondary node-terminated split DRB. Applicable to both EN-DC and NR-DC when UlDataSplitUeCfg::initialUlPrimaryPathMode is COVERAGE_BASED. Uplink primary path is configured as follows at setup of secondary node-terminated split DRB: - SCG if UlDataSplitUeCfg::initialUlPrimaryPathMode is COVERAGE_BASED and SCG RSRP level is above this threshold. - MCG if UlDataSplitUeCfg::initialUlPrimaryPathMode is COVERAGE_BASED and SCG RSRP level is below this threshold.; range -156..-29; Default value: -110.";
      type eytypes:int32_range_-156--29;
      default "-110";
      units "dBm";
    }
    leaf userLabel {
      description "Label for free use..";
      type string;
    }
  }
  grouping IntraFreqMC-attributes {
    leaf intraFreqMCId {
      description "The value component of the RDN..";
      type string;
      mandatory true;
    }
    leaf sCellDepHEnabled {
      description "Whether deprecation handling for SCell related attributes in IntraFreqMCCellProfile MO is enabled. If true, updating any of following deprecated attributes in IntraFreqMCCellProfile instance -rsrpBetterSCell -rsrpSCellCoverage -rsrqSCellCoverage -sCellCoverageTriggerQuantity also updates corresponding (replacing) attribute in all child IntraFreqMCCellProfileUeCfg instances. If false, IntraFreqMCCellProfileUeCfg MO class is not updated. Node always uses SCell attributes configured in IntraFreqMCCellProfileUeCfg MO class. Updating that MO class never updates deprecated attributes. Disabling deprecation handling prevents SCell related attributes in IntraFreqMCCellProfileUeCfg MO class from being overwritten in new management system versions where SCell related attributes in IntraFreqMCCellProfileUeCfg MO are visible and used instead of deprecated attributes..";
      type boolean;
    }
  }
  grouping IntraFreqMCCellProfile-attributes {
    leaf betterSpCellTriggerQuantity {
      description "Measurement trigger quantity used when searching for better Special Cell. Special Cell is either PCell or PSCell..";
      type enumeration {
        enum RSRP;
        enum RSRQ;
      }
    }
    leaf endcActionEvalFail {
      description "Action taken when intra-frequency handover evaluation or Secondary Node change procedure fails. Applies to UE which use cell as PSCell in EN-DC configuration..";
      type enumeration {
        enum RELEASE;
        enum IGNORE;
      }
    }
    leaf intraFreqMCCellProfileId {
      description "The value component of the RDN..";
      type string;
      mandatory true;
    }
    leaf-list reservedBy {
      description "Contains a list of MO instances that reserve this MO instance..";
      type string;
      min-elements 0;
    }
    list rsrpBetterSCell {
      key "id";
      leaf id {
        type uint32;
        description "Synthetic key for struct attribute.";
      }
      description "Configures UE measurement to detect neighboring SCells with better coverage. The cell referring to this profile is used as a PCell or PSCell for UE. Measurement trigger quantity for SCell neighbor with better coverage is always RSRP..";
      uses ReportConfigA6Rsrp-struct;
    }
    list rsrpBetterSpCell {
      key "id";
      leaf id {
        type uint32;
        description "Synthetic key for struct attribute.";
      }
      description "Downlink RSRP measurement report criteria when searching for better Special Cell. Special Cell is either PCell or PSCell. Used only when triggerQuantity is set to RSRP..";
      uses ReportConfigA3Rsrp-struct;
    }
    list rsrpSCellCoverage {
      key "id";
      leaf id {
        type uint32;
        description "Synthetic key for struct attribute.";
      }
      description "Configures UE measurements to detect poor or good coverage in SCell. The cell referring to this profile is used as a PCell or PSCell for UE. Used only when triggerQuantity is set to RSRP..";
      uses ReportConfigA1A2Rsrp-struct;
    }
    list rsrqBetterSpCell {
      key "id";
      leaf id {
        type uint32;
        description "Synthetic key for struct attribute.";
      }
      description "Downlink RSRQ measurement report criteria when searching for better Special Cell. Special Cell is either PCell or PSCell. Used only when triggerQuantity is set to RSRQ..";
      uses ReportConfigA3Rsrq-struct;
    }
    list rsrqSCellCoverage {
      key "id";
      leaf id {
        type uint32;
        description "Synthetic key for struct attribute.";
      }
      description "Configures UE measurements to detect poor or good coverage in SCell. The cell referring to this profile is used as a PCell or PSCell for UE. Used only when triggerQuantity is set to RSRQ..";
      uses ReportConfigA1A2Rsrq-struct;
    }
    leaf sCellCoverageTriggerQuantity {
      description "Quantity that triggers SCell poor or good coverage measurements..";
      type enumeration {
        enum RSRP;
        enum RSRQ;
      }
    }
    leaf ueConfGroupType {
      description "UE configuration group type. UE configuration group type that is applied in contained IntraFreqMCCellProfileUeCfg instances..";
      type enumeration {
        enum UE_MOBILITY_GROUP;
        enum UE_SERVICE_GROUP;
        enum UE_ADMISSION_GROUP;
      }
    }
    leaf userLabel {
      description "Label for free use..";
      type string;
    }
  }
  grouping IntraFreqMCCellProfileUeCfg-attributes {
    leaf betterSCellReportConfigMode {
      description "Condition for better SCell A6 measurement report. Cell referring to parent of this class is used as a PCell or PSCell for UE. Not applicable to High-Band cells.; Default value: ALWAYS; Takes effect: New connection; Status info: Since 24.Q1. Replaced by CaCellMeasProfileUeCfg::betterSCellReportConfigMode. Planned to be removed..";
      type enumeration {
        enum ALWAYS;
        enum CONDITIONAL;
      }
      status deprecated;
      default "ALWAYS";
      reference "Takes effect: New connection.";
    }
    leaf betterSpCellTriggerQuantity {
      description "Measurement trigger quantity used when searching for better Special Cell. Special Cell is either PCell or PSCell..";
      type enumeration {
        enum RSRP;
        enum RSRQ;
        enum SINR_FALLBACK_RSRP;
        enum SINR_FALLBACK_RSRQ;
      }
    }
    leaf endcActionEvalFail {
      description "Action taken when intra-frequency PSCell change evaluation or PSCell change procedure fails. Applies to UEs that use cell as PSCell in EN-DC..";
      type enumeration {
        enum RELEASE;
        enum IGNORE;
      }
    }
    leaf intraFreqMCCellProfileUeCfgId {
      description "The value component of the RDN..";
      type string;
      mandatory true;
    }
    leaf maxReportCells {
      description "Maximum number of non-serving cells included in measurement report. Only applicable to event A3.; range 1..8; Default value: 1.";
      type eytypes:int32_range_1-8;
      default "1";
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    list rsrpBetterSCell {
      key "id";
      leaf id {
        type uint32;
        description "Synthetic key for struct attribute.";
      }
      description "Configures UE measurement to detect neighboring SCells with better coverage. Cell referring to parent of this class is used as a PCell or PSCell for UE. Measurement trigger quantity for SCell neighbor with better coverage is always RSRP. Not applicable to High-Band cells.; Takes effect: New connection; Status info: Since 24.Q1. Replaced by CaCellMeasProfileUeCfg::rsrpBetterSCell. Planned to be removed.; Specification: 3GPP TS 38.331.";
      uses ReportConfigA6Rsrp-struct;
    }
    list rsrpBetterSpCell {
      key "id";
      leaf id {
        type uint32;
        description "Synthetic key for struct attribute.";
      }
      description "Downlink RSRP measurement report criteria when searching for better Special Cell. Special Cell is either PCell or PSCell. Used only when betterSpCellTriggerQuantity is set to RSRP..";
      uses ReportConfigA3Rsrp-struct;
    }
    list rsrpSCellCoverage {
      key "id";
      leaf id {
        type uint32;
        description "Synthetic key for struct attribute.";
      }
      description "Configures UE measurements to detect poor or good coverage in SCell. Cell referring to parent of this class is used as a PCell or PSCell for UE. Used only when triggerQuantity is set to RSRP. Not applicable to High-Band cells.; Takes effect: New connection; Status info: Since 24.Q1. Replaced by CaCellMeasProfileUeCfg::rsrpSCellCoverage. Planned to be removed.; Specification: 3GPP TS 38.331.";
      uses ReportConfigA1A2Rsrp-struct;
    }
    list rsrqBetterSpCell {
      key "id";
      leaf id {
        type uint32;
        description "Synthetic key for struct attribute.";
      }
      description "Downlink RSRQ measurement report criteria when searching for better Special Cell. Special Cell is either PCell or PSCell. Used only when betterSpCellTriggerQuantity is set to RSRQ..";
      uses ReportConfigA3Rsrq-struct;
    }
    list rsrqSCellCoverage {
      key "id";
      leaf id {
        type uint32;
        description "Synthetic key for struct attribute.";
      }
      description "Configures UE measurements to detect poor or good coverage in SCell. Cell referring to parent of this class is used as a PCell or PSCell for UE. Used only when triggerQuantity is set to RSRQ. Not applicable to High-Band cells.; Takes effect: New connection; Status info: Since 24.Q1. Replaced by CaCellMeasProfileUeCfg::rsrqSCellCoverage. Planned to be removed.; Specification: 3GPP TS 38.331.";
      uses ReportConfigA1A2Rsrq-struct;
    }
    leaf sCellCoverageTriggerQuantity {
      description "Quantity that triggers SCell poor or good coverage measurements. Not applicable to High-Band cells.; Default value: RSRP; Takes effect: New connection; Status info: Since 24.Q1. Replaced by CaCellMeasProfileUeCfg::sCellCoverageTriggerQuantity. Planned to be removed.; Specification: 3GPP TS 38.331.";
      type enumeration {
        enum RSRP;
        enum RSRQ;
      }
      status deprecated;
      default "RSRP";
      reference "Takes effect: New connection.";
    }
    list sinrBetterSpCell {
      key "id";
      leaf id {
        type uint32;
        description "Synthetic key for struct attribute.";
      }
      description "Downlink SINR measurement report criteria when searching for better Special Cell. Special Cell is either PCell or PSCell. Used only when betterSpCellTriggerQuantity is set to SINR..";
      uses ReportConfigA3Sinr-struct;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 16;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
    leaf useT312BetterPCellCandidateA3 {
      description "Whether useT312 parameter is provided in report configuration for A3 measurement. Whether useT312 parameter is provided in reportConfigNR information element sent to UE for A3 measurement for better NR PCell. A3 measurement for better NR PCell is used to find PCell candidate on same frequency. If true, useT312 is provided in reportConfigNR information element with value true. If false, useT312 is not provided in reportConfigNR information element.; Default value: false.";
      type boolean;
      default "false";
    }
  }
  grouping IntraFreqMCFreqRelProfile-attributes {
    leaf intraFreqMCFreqRelProfileId {
      description "The value component of the RDN.; MOM flags: restricted, noNotification; Status info: Since 24.Q1. Planned to be removed..";
      type string;
      mandatory true;
      status deprecated;
    }
    leaf-list reservedBy {
      description "Contains a list of MO instances that reserve this MO instance.; Status info: Since 24.Q1. Planned to be removed..";
      type string;
      min-elements 0;
    }
    leaf ueConfGroupType {
      description "UE configuration group type. UE configuration group type that is applied in contained IntraFreqMCFreqRelProfileUeCfg instances.; Default value: UE_MOBILITY_GROUP; Takes effect: Next usage; Status info: Since 24.Q1. Replaced by CaFreqRelMeasProfile::ueConfGroupType. Planned to be removed..";
      type enumeration {
        enum UE_MOBILITY_GROUP;
        enum UE_SERVICE_GROUP;
        enum UE_ADMISSION_GROUP;
      }
      status deprecated;
      default "UE_MOBILITY_GROUP";
      reference "Takes effect: Next usage.";
    }
    leaf userLabel {
      description "Label for free use.; MOM flags: isNillable=true; Status info: Since 24.Q1. Planned to be removed..";
      type string;
      status deprecated;
    }
  }
  grouping IntraFreqMCFreqRelProfileUeCfg-attributes {
    leaf intraFreqMCFreqRelProfileUeCfgId {
      description "The value component of the RDN.; MOM flags: restricted, noNotification; Status info: Since 24.Q1. Planned to be removed..";
      type string;
      mandatory true;
      status deprecated;
    }
    leaf-list prefUeGroupList {
      description "Preference UE group list. List of preference UE group identifiers. If empty, MO instance matches preference UE group identifiers not defined in prefUeGroupList of any other MO instances under parent MO instance.; Takes effect: Next usage; Status info: Since 24.Q1. Replaced by CaFreqRelMeasProfileUeCfg::prefUeGroupList. Planned to be removed..";
      type eytypes:int32_range_1-255;
      ordered-by user;
      min-elements 0;
      max-elements 8;
    }
    leaf rsrpSCellCoverageThrOffset {
      description "NR frequency relation-specific RSRP threshold offset value for Event A1 and Event A2. Threshold offset used for detecting poor or good coverage in SCell. Not applicable to High-Band cells.; range -30..30; Default value: 0; Takes effect: Next usage; Status info: Since 24.Q1. Replaced by CaFreqRelMeasProfileUeCfg::rsrpSCellCoverageThrOffset. Planned to be removed.; Specification: 3GPP TS 38.331.";
      type eytypes:int32_range_-30-30;
      status deprecated;
      default "0";
      units "dB";
      reference "Takes effect: Next usage.";
    }
    leaf rsrqSCellCoverageThrOffset {
      description "NR frequency relation-specific RSRQ threshold offset value for Event A1 and Event A2. Threshold offset used for detecting poor or good coverage in SCell. Not applicable to High-Band cells.; range -300..300; Default value: 0; Takes effect: Next usage; Status info: Since 24.Q1. Replaced by CaFreqRelMeasProfileUeCfg::rsrqSCellCoverageThrOffset. Planned to be removed.; Specification: 3GPP TS 38.331.";
      type int32 {
        range "-300..300";
      }
      status deprecated;
      default "0";
      units "dB";
      reference "Takes effect: Next usage.";
    }
    leaf-list ueConfGroupList {
      description "UE configuration group list. List of UE configuration group identifiers. If empty, MO instance matches all UE configuration group identifiers. UE configuration group type is defined by ueConfGroupType in parent MO instance.; Takes effect: Next usage; Status info: Since 24.Q1. Replaced by CaFreqRelMeasProfileUeCfg::ueConfGroupList. Planned to be removed..";
      type eytypes:int32_range_1-255;
      ordered-by user;
      min-elements 0;
      max-elements 16;
    }
    leaf-list ueGroupList {
      description "UE group list. List of UE group identifiers. If empty, MO instance matches all UE group identifiers.; Takes effect: Next usage; Status info: Since 24.Q1. Replaced by CaFreqRelMeasProfileUeCfg::ueGroupList. Planned to be removed..";
      type eytypes:int32_range_1-255;
      ordered-by user;
      min-elements 0;
      max-elements 16;
    }
    leaf userLabel {
      description "Label for free use.; MOM flags: isNillable=true; Status info: Since 24.Q1. Planned to be removed..";
      type string;
      status deprecated;
    }
    leaf waitForBetterSCellRep {
      description "Controls time gNodeB waits after reception of an A2 measurement report until SCell is deconfigured. If SCell A1 or A6 measurement report is received before timer expires, no SCell deconfiguration is attempted. Value -1 means wait forever. Not applicable to High-Band cells.; range -1..32000; Default value: -1; Takes effect: New connection; Status info: Since 24.Q1. Replaced by CaFreqRelMeasProfileUeCfg::waitForBetterSCellRep. Planned to be removed..";
      type eytypes:int32_range_-1-32000;
      status deprecated;
      default "-1";
      units "ms";
      reference "Takes effect: New connection.";
    }
  }
  grouping LocalA1Endpoint-attributes {
    leaf addressRef {
      description "Reference to an instance of AddressIPv4 or AddressIPv6 MO. Reference to the IP address where A1 service is listening to incoming A1 messages. Dual stack is not supported, only one IP address can be referenced..";
      type string;
      mandatory true;
    }
    leaf localA1EndpointId {
      description "The value component of the RDN..";
      type string;
      mandatory true;
    }
    leaf nodeCredentialRef {
      description "Reference to an instance of NodeCredential MO. Reference to the credential used for A1 over HTTPS..";
      type string;
      mandatory true;
    }
    leaf portNumber {
      description "Port number where A1 service receives incoming A1 messages.; range 1..65535; Default value: 7443.";
      type ietfinet:port-number;
      default "7443";
    }
    leaf trustCategoryRef {
      description "Reference to an instance of TrustCategory MO. Reference to the set of certificates trusted by the A1 over HTTPS service..";
      type string;
      mandatory true;
    }
  }
  grouping LocalDnsEndpoint-attributes {
    leaf dnsClientRef {
      description "Reference to an instance of DnsClient MO. Must be unique among all LocalDnsEndpoint instances..";
      type string;
      mandatory true;
    }
    leaf interfaceUsed {
      description "Control plane interface that uses the referenced DnsClient. Allowed value: NG..";
      type enumeration {
        enum C5;
        enum E1;
        enum E6;
        enum F1;
        enum NG;
        enum S1;
        enum XN;
        enum X2;
      }
      mandatory true;
    }
    leaf localDnsEndpointId {
      description "The value component of the RDN..";
      type string;
      mandatory true;
    }
  }
  grouping LocalIpEndpoint-attributes {
    leaf-list addressRef {
      description "Reference to an instance of IP address MO. Reference to AddressIPv4 or AddressIPv6 MO. Must be unique among LocalIpEndpoint instances under EndpointResource instance. Dual stack is not supported, only one IP address can be referenced..";
      type string;
      ordered-by user;
      min-elements 1;
      max-elements 2;
    }
    leaf-list interfaceList {
      description "List of user plane interfaces that use the referenced AddressIPv4 or AddressIPv6. Allowed value: E1. Interface must be unique across LocalIpEndpoint instances under EndpointResource instance..";
      type InterfaceName;
      min-elements 1;
      max-elements 2;
    }
    leaf localIpEndpointId {
      description "The value component of the RDN..";
      type string;
      mandatory true;
    }
  }
  grouping LocalSctpEndpoint-attributes {
    leaf interfaceUsed {
      description "Control plane interface that uses the referenced SctpEndpoint. Allowed values: NG, F1, X2 or XN. Interface must be unique across LocalSctpEndpoint instances under EndpointResource instance..";
      type enumeration {
        enum C5;
        enum E1;
        enum E6;
        enum F1;
        enum NG;
        enum S1;
        enum XN;
        enum X2;
      }
      mandatory true;
    }
    leaf localSctpEndpointId {
      description "The value component of the RDN..";
      type string;
      mandatory true;
    }
    leaf sctpEndpointRef {
      description "Reference to an instance of SctpEndpoint MO. Must be unique among LocalSctpEndpoint instances under EndpointResource instance..";
      type string;
      mandatory true;
    }
    leaf pmSctpDtlsNegotiationFailed {
      description "Number of times DTLS negotiation and authentication chunks negotiation failed. Deprecated: Since 25.Q2. Planned to be removed.; MOM flags: noNotification.";
      type uint64;
      config false;
      status deprecated;
    }
  }
  grouping Mcfb-attributes {
    leaf epsFbDepHEnabled {
      description "Whether deprecation handling for epsFbAtSessionSetup in McfbCellProfile is enabled. If true, updating epsFbAtSessionSetup also updates corresponding (replacing) attribute in all child McfbCellProfileUeCfg instances. If false, McfbCellProfileUeCfg MO class is not updated. Node always uses epsFbAtSessionSetup configured in McfbCellProfileUeCfg MO class. Updating that MO class never updates deprecated attribute. Disabling deprecation handling prevents epsFbAtSessionSetup in McfbCellProfileUeCfg MO class from being overwritten in new management system versions where epsFbAtSessionSetup in McfbCellProfileUeCfg MO class is visible and used instead of deprecated attribute..";
      type boolean;
    }
    leaf mcfbId {
      description "The value component of the RDN..";
      type string;
      mandatory true;
    }
    leaf voiceEpsFbPossible {
      description "Whether EPS fallback is assumed possible. When Redirection for Voice EPS Fallback IE is not included from core network (AMF node), the IE is assumed set to possible. The IE Redirection for Voice EPS Fallback is indicated over NGAP from core network. This IE controls whether it is possible to perform EPS fallback. This IE is optional, and this attribute is used to define the behavior when this IE is not indicated from core network. This attribute should be false if core network supports CR S2-2007918 for NGAP in 3GPP TS 38.413 Rel-16.; Default value: true.";
      type boolean;
      default "true";
    }
  }
  grouping McfbCellProfile-attributes {
    leaf epsFallbackOperation {
      description "Policy for EPS fallback or Voice over NR (VoNR) for voice calls..";
      type enumeration {
        enum INACTIVE;
        enum ACTIVE;
        enum FORCED;
        enum ACTIVE_MEAS_RWR;
        enum ACTIVE_MEAS_IRAT_HO;
        enum FORCED_MEAS_RWR;
        enum FORCED_MEAS_IRAT_HO;
      }
    }
    leaf epsFallbackOperationEm {
      description "Policy for EPS fallback or Voice over NR (VoNR) for emergency calls..";
      type enumeration {
        enum ACTIVE;
        enum FORCED;
        enum ACTIVE_MEAS_RWR;
        enum ACTIVE_MEAS_IRAT_HO;
        enum FORCED_MEAS_RWR;
        enum FORCED_MEAS_IRAT_HO;
      }
    }
    leaf-list epsFallbackPrioritization {
      description "List of EPS fallback prioritization policies over an ongoing procedure. Used for voice and emergency call. If empty, EPS fallback is not prioritized over any of ongoing procedures. If PRIO_OVER_XN_HO, EPS fallback is prioritized over Xn handover for voice or emergency call of UE configuration group. Only applicable to Low-Band and Mid-Band cells..";
      type EpsFbPrioritizationType;
      min-elements 0;
      max-elements 2;
    }
    leaf epsFbAtSessionSetup {
      description "Policy for voice and emergency call handling when voice flow is included in PDU session setup..";
      type enumeration {
        enum INACTIVE;
        enum ACTIVE;
      }
    }
    leaf epsFbTargetSearchTimer {
      description "Length of time the gNodeB waits for reports from B1 measurement for EPS Fallback reasons.; range 1..12000.";
      type eytypes:int32_range_1-12000;
      units "ms";
    }
    leaf mcfbCellProfileId {
      description "The value component of the RDN..";
      type string;
      mandatory true;
    }
    leaf rejectVoiceIncHoAtEpsFb {
      description "Whether policy for EPS fallback is considered for rejecting incoming handover with voice service. If true, handover fails if voice service is not allowed when epsFallbackOperation is set to one of below values: - FORCED - FORCED_MEAS_RWR - FORCED_MEAS_IRAT_HO For emergency service EPS fallback emergency is considered. If true, handover fails if emergency service is not allowed when epsFallbackOperationEm set to FORCED. If false, voice and emergency services are always allowed at incoming handover procedure. For initial call setup procedure, EPS fallback operation or EPS fallback emergency operation policy is applied, rejectVoiceIncHoAtEpsFb has no impact..";
      type boolean;
    }
    leaf-list reservedBy {
      description "Contains a list of MO instances that reserve this MO instance..";
      type string;
      min-elements 0;
    }
    list rsrpCellCandidate {
      key "id";
      leaf id {
        type uint32;
        description "Synthetic key for struct attribute.";
      }
      description "RSRP B1 measurement report criteria when searching for E-UTRAN cell candidate..";
      uses ReportConfigB1Rsrp-struct;
    }
    list rsrpCriticalCoverage {
      key "id";
      leaf id {
        type uint32;
        description "Synthetic key for struct attribute.";
      }
      description "RSRP A2 measurement report criteria for detecting critical coverage..";
      uses ReportConfigA1A2Rsrp-struct;
    }
    list rsrqCellCandidate {
      key "id";
      leaf id {
        type uint32;
        description "Synthetic key for struct attribute.";
      }
      description "RSRQ B1 measurement report criteria when searching for E-UTRAN cell candidate..";
      uses ReportConfigB1Rsrq-struct;
    }
    list rsrqCriticalCoverage {
      key "id";
      leaf id {
        type uint32;
        description "Synthetic key for struct attribute.";
      }
      description "RSRQ A2 measurement report criteria for detecting critical coverage..";
      uses ReportConfigA1A2Rsrq-struct;
    }
    leaf triggerQuantity {
      description "Quantity that triggers the event B1 and A2..";
      type enumeration {
        enum RSRP;
        enum RSRQ;
      }
    }
    leaf ueConfGroupType {
      description "UE configuration group type. UE configuration group type that is applied in contained McfbCellProfileUeCfg instances..";
      type enumeration {
        enum UE_MOBILITY_GROUP;
        enum UE_SERVICE_GROUP;
        enum UE_ADMISSION_GROUP;
      }
    }
  }
  grouping McfbCellProfileUeCfg-attributes {
    leaf epsFallbackOperation {
      description "Policy for EPS fallback or Voice over NR (VoNR) for voice calls..";
      type enumeration {
        enum INACTIVE;
        enum ACTIVE;
        enum FORCED;
        enum ACTIVE_MEAS_RWR;
        enum ACTIVE_MEAS_IRAT_HO;
        enum FORCED_MEAS_RWR;
        enum FORCED_MEAS_IRAT_HO;
      }
    }
    leaf epsFallbackOperationEm {
      description "Policy for EPS fallback or Voice over NR (VoNR) for emergency calls..";
      type enumeration {
        enum ACTIVE;
        enum FORCED;
        enum ACTIVE_MEAS_RWR;
        enum ACTIVE_MEAS_IRAT_HO;
        enum FORCED_MEAS_RWR;
        enum FORCED_MEAS_IRAT_HO;
      }
    }
    leaf epsFbAtSessionSetup {
      description "Policy for voice and emergency call handling when voice flow is included in PDU session setup..";
      type enumeration {
        enum INACTIVE;
        enum ACTIVE;
      }
    }
    leaf epsFbTargetSearchTimer {
      description "Length of time the gNodeB waits for reports from B1 measurement for EPS fallback reasons.; range 1..12000; Default value: 500.";
      type eytypes:int32_range_1-12000;
      default "500";
      units "ms";
    }
    leaf epsFbVoiceIndication {
      description "Whether voice fallback indication is supported in release with redirect. If true, following applies: If EPS fallback for IMS voice user is identified in RRCRelease message in release with redirect procedure, then voice fallback indication flag is set.; Default value: false.";
      type boolean;
      default "false";
    }
    leaf maxReportCells {
      description "Maximum number of non-serving cells included in measurement report. Only applicable to event B1.; range 1..8; Default value: 4.";
      type eytypes:int32_range_1-8;
      default "4";
    }
    leaf mcfbCellProfileUeCfgId {
      description "The value component of the RDN..";
      type string;
      mandatory true;
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf rejectVoiceIncHoAtEpsFb {
      description "Whether policy for EPS fallback is considered for rejecting incoming handover with voice service. If true, handover fails if voice service is not allowed when epsFallbackOperation is set to one of below values: - FORCED - FORCED_MEAS_RWR - FORCED_MEAS_IRAT_HO For emergency service EPS fallback emergency is considered. If true, handover fails if emergency service is not allowed when epsFallbackOperationEm set to FORCED. If false, voice and emergency services are always allowed at incoming handover procedure. For initial call setup procedure, EPS fallback operation or EPS fallback emergency operation policy is applied, this attribute has no impact.; Default value: false.";
      type boolean;
      default "false";
    }
    list rsrpCellCandidate {
      key "id";
      leaf id {
        type uint32;
        description "Synthetic key for struct attribute.";
      }
      description "RSRP B1 measurement report criteria when searching for E-UTRAN cell candidate..";
      uses ReportConfigB1Rsrp-struct;
    }
    list rsrpCriticalCoverage {
      key "id";
      leaf id {
        type uint32;
        description "Synthetic key for struct attribute.";
      }
      description "RSRP A2 measurement report criteria for detecting critical coverage..";
      uses ReportConfigA1A2Rsrp-struct;
    }
    list rsrqCellCandidate {
      key "id";
      leaf id {
        type uint32;
        description "Synthetic key for struct attribute.";
      }
      description "RSRQ B1 measurement report criteria when searching for E-UTRAN cell candidate..";
      uses ReportConfigB1Rsrq-struct;
    }
    list rsrqCriticalCoverage {
      key "id";
      leaf id {
        type uint32;
        description "Synthetic key for struct attribute.";
      }
      description "RSRQ A2 measurement report criteria for detecting critical coverage..";
      uses ReportConfigA1A2Rsrq-struct;
    }
    list sinrCellCandidate {
      key "id";
      leaf id {
        type uint32;
        description "Synthetic key for struct attribute.";
      }
      description "SINR B1 measurement report criteria when searching for E-UTRAN cell candidate..";
      uses ReportConfigB1Sinr-struct;
    }
    list sinrCriticalCoverage {
      key "id";
      leaf id {
        type uint32;
        description "Synthetic key for struct attribute.";
      }
      description "SINR A2 measurement report criteria for detecting critical coverage..";
      uses ReportConfigA2Sinr-struct;
    }
    leaf triggerQuantity {
      description "Quantity that triggers the event B1 and A2..";
      type enumeration {
        enum RSRP;
        enum RSRQ;
        enum SINR_FALLBACK_RSRP;
        enum SINR_FALLBACK_RSRQ;
      }
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 16;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping Mcpc-attributes {
    leaf endcLowPrioPSCellCandHandling {
      description "Low priority PSCell candidate handling. Defines how a reported low priority PSCell candidate is treated when received during MCPC priority period. Applicable to UE in EN-DC mode. Priority of PSCell candidates on NR frequencies is defined by UeMCNrFreqRelProfileUeCfg::connModePrioPSCell. Whether priority of PSCell candidate is defined to be a low or a high priority candidate is defined by McpcPSCellProfileUeCfg::lowHighFreqPrioClassification..";
      type enumeration {
        enum STORE_LATEST_RECEIVED;
        enum STORE_HIGHEST_PRIO;
      }
    }
    leaf mcpcId {
      description "The value component of the RDN..";
      type string;
      mandatory true;
    }
    leaf nrLowPrioPCellCandHandling {
      description "Low priority PCell candidate handling. Defines how a reported low priority PCell candidate is treated when received during MCPC priority period. Applicable to UE in NR standalone mode. Priority of PCell candidates on NR and E-UTRAN frequencies are defined by UeMCNrFreqRelProfileUeCfg::connModePrioPCell and UeMCEUtranFreqRelProfileUeCfg::connModePrioPCell. Whether priority of PCell candidate is defined to be a low or a high priority candidate is defined by McpcPCellProfileUeCfg::lowHighFreqPrioClassification..";
      type enumeration {
        enum STORE_LATEST_RECEIVED;
        enum STORE_HIGHEST_PRIO;
      }
    }
  }
  grouping McpcNrdcPSCellProfile-attributes {
    leaf mcpcNrdcPSCellProfileId {
      description "The value component of the RDN..";
      type string;
      mandatory true;
    }
    leaf-list reservedBy {
      description "Contains a list of MO instances that reserve this MO instance..";
      type string;
      min-elements 0;
    }
    list rsrpCritical {
      key "id";
      leaf id {
        type uint32;
        description "Synthetic key for struct attribute.";
      }
      description "RSRP measurement report criteria for detecting critical coverage. Only applied if rsrpCriticalEnabled is true..";
      uses ReportConfigA2Rsrp-struct;
    }
    leaf rsrpCriticalEnabled {
      description "Whether RSRP measurements for detecting critical coverage is enabled. RSRP measurement criteria for detecting critical coverage is defined by rsrpCritical..";
      type boolean;
    }
    leaf ueConfGroupType {
      description "UE configuration group type. UE configuration group type that is applied in contained McpcNrdcPSCellProfileUeCfg instances..";
      type enumeration {
        enum UE_MOBILITY_GROUP;
        enum UE_SERVICE_GROUP;
        enum UE_ADMISSION_GROUP;
      }
    }
    leaf userLabel {
      description "Label for free use..";
      type string;
    }
  }
  grouping McpcNrdcPSCellProfileUeCfg-attributes {
    leaf mcpcA2Quantity {
      description "Combination of measurement quantities to apply for A2 critical measurements..";
      type enumeration {
        enum NONE;
        enum RSRP;
        enum RSRQ;
        enum SINR_FALLBACK_RSRP;
        enum SINR_FALLBACK_RSRQ;
        enum RSRP_AND_RSRQ;
        enum RSRP_AND_SINR_FALLBACK_RSRQ;
        enum RSRP_AND_SINR_NO_FALLBACK;
      }
    }
    leaf mcpcNrdcPSCellProfileUeCfgId {
      description "The value component of the RDN..";
      type string;
      mandatory true;
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    list rsrpCritical {
      key "id";
      leaf id {
        type uint32;
        description "Synthetic key for struct attribute.";
      }
      description "RSRP measurement report criteria for detecting critical coverage..";
      uses ReportConfigA2Rsrp-struct;
    }
    list rsrqCritical {
      key "id";
      leaf id {
        type uint32;
        description "Synthetic key for struct attribute.";
      }
      description "RSRQ measurement report criteria for detecting critical coverage..";
      uses ReportConfigA2Rsrq-struct;
    }
    list sinrCritical {
      key "id";
      leaf id {
        type uint32;
        description "Synthetic key for struct attribute.";
      }
      description "SINR measurement report criteria for detecting critical coverage..";
      uses ReportConfigA2Sinr-struct;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping McpcPCellEUtranFreqRelProfile-attributes {
    leaf inhibitMeasForCellCandidate {
      description "Whether UE measurement searching for PCell candidate on this frequency is inhibited..";
      type boolean;
    }
    leaf mcpcPCellEUtranFreqRelProfileId {
      description "The value component of the RDN..";
      type string;
      mandatory true;
    }
    leaf-list reservedBy {
      description "Contains a list of MO instances that reserve this MO instance..";
      type string;
      min-elements 0;
    }
    list rsrpCandidateB2Offsets {
      key "id";
      leaf id {
        type uint32;
        description "Synthetic key for struct attribute.";
      }
      description "Downlink RSRP B2 measurement offsets when searching for PCell candidate..";
      uses ReportConfigB2RsrpOffsets-struct;
    }
    leaf ueConfGroupType {
      description "UE configuration group type. UE configuration group type that is applied in contained McpcPCellEUtranFreqRelProfileUeCfg instances..";
      type enumeration {
        enum UE_MOBILITY_GROUP;
        enum UE_SERVICE_GROUP;
        enum UE_ADMISSION_GROUP;
      }
    }
    leaf userLabel {
      description "Label for free use..";
      type string;
    }
  }
  grouping McpcPCellEUtranFreqRelProfileUeCfg-attributes {
    leaf inhibitMeasForCellCandidate {
      description "Whether UE measurement searching for PCell candidate on this frequency is inhibited.; Default value: false.";
      type boolean;
      default "false";
    }
    leaf mcpcPCellEUtranFreqRelProfileUeCfgId {
      description "The value component of the RDN..";
      type string;
      mandatory true;
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    list rsrpCandidateB2Offsets {
      key "id";
      leaf id {
        type uint32;
        description "Synthetic key for struct attribute.";
      }
      description "Downlink RSRP B2 measurement offsets when searching for PCell candidate..";
      uses ReportConfigB2RsrpOffsets-struct;
    }
    list rsrqCandidateB2Offsets {
      key "id";
      leaf id {
        type uint32;
        description "Synthetic key for struct attribute.";
      }
      description "Downlink RSRQ B2 measurement offsets when searching for E-UTRAN PCell candidate..";
      uses ReportConfigB2RsrqOffsets-struct;
    }
    list sinrCandidateB2Offsets {
      key "id";
      leaf id {
        type uint32;
        description "Synthetic key for struct attribute.";
      }
      description "Downlink SINR B2 measurement offsets when searching for E-UTRAN PCell candidate..";
      uses ReportConfigB2SinrOffsets-struct;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping McpcPCellNrFreqRelProfile-attributes {
    leaf inhibitMeasForCellCandidate {
      description "Whether UE measurement searching for PCell candidate on this frequency is inhibited..";
      type boolean;
    }
    leaf mcpcPCellNrFreqRelProfileId {
      description "The value component of the RDN..";
      type string;
      mandatory true;
    }
    leaf-list reservedBy {
      description "Contains a list of MO instances that reserve this MO instance..";
      type string;
      min-elements 0;
    }
    list rsrpCandidateA5Offsets {
      key "id";
      leaf id {
        type uint32;
        description "Synthetic key for struct attribute.";
      }
      description "Downlink RSRP A5 measurement offsets when searching for PCell candidate..";
      uses ReportConfigA5RsrpOffsets-struct;
    }
    leaf ueConfGroupType {
      description "UE configuration group type. UE configuration group type that is applied in contained McpcPCellNrFreqRelProfileUeCfg instances..";
      type enumeration {
        enum UE_MOBILITY_GROUP;
        enum UE_SERVICE_GROUP;
        enum UE_ADMISSION_GROUP;
      }
    }
    leaf userLabel {
      description "Label for free use..";
      type string;
    }
  }
  grouping McpcPCellNrFreqRelProfileUeCfg-attributes {
    leaf inhibitMeasForCellCandidate {
      description "Whether UE measurement searching for PCell candidate on this frequency is inhibited.; Default value: false.";
      type boolean;
      default "false";
    }
    leaf mcpcPCellNrFreqRelProfileUeCfgId {
      description "The value component of the RDN..";
      type string;
      mandatory true;
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    list rsrpCandidateA5Offsets {
      key "id";
      leaf id {
        type uint32;
        description "Synthetic key for struct attribute.";
      }
      description "Downlink RSRP A5 measurement offsets when searching for PCell candidate..";
      uses ReportConfigA5RsrpOffsets-struct;
    }
    list rsrqCandidateA5Offsets {
      key "id";
      leaf id {
        type uint32;
        description "Synthetic key for struct attribute.";
      }
      description "Downlink RSRQ A5 measurement offsets when searching for NR PCell candidate..";
      uses ReportConfigA5RsrqOffsets-struct;
    }
    list sinrCandidateA5Offsets {
      key "id";
      leaf id {
        type uint32;
        description "Synthetic key for struct attribute.";
      }
      description "Downlink SINR A5 measurement offsets when searching for NR PCell candidate..";
      uses ReportConfigA5SinrOffsets-struct;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping McpcPCellProfile-attributes {
    leaf lowHighFreqPrioClassification {
      description "Classification of low and high frequency relation priority. NR frequency relation priorities are defined by UeMCNrFreqRelProfile::connModePrioPCell attribute. E-UTRAN frequency relation priorities are defined by UeMCEUtranFreqRelProfile::connModePrioPCell attribute. Frequency relation priority is classified as high priority if it equals or is higher than value of lowHighFreqPrioClassification, else classified as low priority.; range 0..7.";
      type eytypes:int32_range_0-7;
    }
    leaf mcpcPCellProfileId {
      description "The value component of the RDN..";
      type string;
      mandatory true;
    }
    leaf mcpcQuantityList {
      description "Measurement quantities on which PCell Mobility Control at Poor Coverage function shall be applied..";
      type enumeration {
        enum RSRP;
        enum RSRQ;
        enum SINR_NO_FALLBACK;
        enum SINR_FALLBACK_RSRQ;
        enum SINR_FALLBACK_RSRP;
        enum UL_SINR;
      }
    }
    leaf-list reservedBy {
      description "Contains a list of MO instances that reserve this MO instance..";
      type string;
      min-elements 0;
    }
    list rsrpCandidateA5 {
      key "id";
      leaf id {
        type uint32;
        description "Synthetic key for struct attribute.";
      }
      description "RSRP A5 measurement report criteria when searching for PCell candidate..";
      uses ReportConfigA5Rsrp-struct;
    }
    list rsrpCandidateB2 {
      key "id";
      leaf id {
        type uint32;
        description "Synthetic key for struct attribute.";
      }
      description "RSRP B2 measurement report criteria when searching for PCell candidate..";
      uses ReportConfigB2Rsrp-struct;
    }
    list rsrpCritical {
      key "id";
      leaf id {
        type uint32;
        description "Synthetic key for struct attribute.";
      }
      description "RSRP measurement report criteria for detecting critical coverage..";
      uses ReportConfigA1A2Rsrp-struct;
    }
    leaf rsrpCriticalEnabled {
      description "Whether RSRP measurement for detecting critical coverage is enabled. RSRP measurement criteria for detecting critical coverage is defined by rsrpCritical attribute..";
      type boolean;
    }
    leaf rsrpSearchTimeRestriction {
      description "Search time restriction when searching for PCell candidate using downlink RSRP measurements. If -1, no time restriction is applied..";
      type int32 {
        range "-1 | 10..12000";
      }
      units "ms";
    }
    list rsrpSearchZone {
      key "id";
      leaf id {
        type uint32;
        description "Synthetic key for struct attribute.";
      }
      description "RSRP measurement report criteria that define entering and leaving search zone..";
      uses ReportConfigA1A2Rsrp-struct;
    }
    leaf ueConfGroupType {
      description "UE configuration group type. UE configuration group type that is applied in contained McpcPCellProfileUeCfg instances..";
      type enumeration {
        enum UE_MOBILITY_GROUP;
        enum UE_SERVICE_GROUP;
        enum UE_ADMISSION_GROUP;
      }
    }
    leaf userLabel {
      description "Label for free use..";
      type string;
    }
  }
  grouping McpcPCellProfileUeCfg-attributes {
    leaf lowHighFreqPrioClassification {
      description "Classification of low and high frequency relation priority. NR frequency relation priorities are defined by UeMCNrFreqRelProfile::connModePrioPCell. E-UTRAN frequency relation priorities are defined by UeMCEUtranFreqRelProfile::connModePrioPCell. Frequency relation priority is classified as high priority if it equals or is higher than value of lowHighFreqPrioClassification, else classified as low priority.; range 0..7; Default value: 7.";
      type eytypes:int32_range_0-7;
      default "7";
    }
    leaf maxReportCells {
      description "Maximum number of non-serving cells included in measurement report. Only applicable to event A5 and event B2.; range 1..8; Default value: 1.";
      type eytypes:int32_range_1-8;
      default "1";
    }
    leaf mcpcPCellProfileUeCfgId {
      description "The value component of the RDN..";
      type string;
      mandatory true;
    }
    leaf-list mcpcQuantityList {
      description "Measurement quantities on which PCell Mobility Control at Poor Coverage function is applied. Following combinations of measurement quantities are supported: - RSRP - RSRQ - SINR_FALLBACK_RSRQ - SINR_FALLBACK_RSRP - UL_SINR - RSRP + RSRQ - RSRP + SINR_NO_FALLBACK - RSRP + SINR_FALLBACK_RSRQ - RSRP + UL_SINR - RSRQ + UL_SINR - SINR_FALLBACK_RSRQ + UL_SINR - SINR_FALLBACK_RSRP + UL_SINR - RSRP + RSRQ + UL_SINR - RSRP + SINR_NO_FALLBACK + UL_SINR - RSRP + SINR_FALLBACK_RSRQ + UL_SINR.";
      type McpcQuantity;
      min-elements 1;
      max-elements 3;
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    list rsrpCandidateA5 {
      key "id";
      leaf id {
        type uint32;
        description "Synthetic key for struct attribute.";
      }
      description "RSRP A5 measurement report criteria when searching for PCell candidate..";
      uses ReportConfigA5Rsrp-struct;
    }
    leaf rsrpCandidateA5AddTargEval {
      description "Additional target evaluation of other reported quantity. Applicable when searching for NR PCell candidate with A5 event with trigger quantity RSRP. Other reported quantity SINR is evaluated towards threshold value defined by following formula: threshold2 in sinrCandidateA5 + hysteresis in sinrCandidateA5 + threshold2Offset in McpcPCellNrFreqRelProfileUeCfg::sinrCandidateA5Offsets Other reported quantity RSRQ is evaluated towards threshold value defined by following formula: threshold2 in rsrqCandidateA5 + hysteresis in rsrqCandidateA5 + threshold2Offset in McpcPCellNrFreqRelProfileUeCfg::rsrqCandidateA5Offsets.";
      type enumeration {
        enum NONE;
        enum RSRQ;
        enum SINR_FALLBACK_RSRQ;
        enum SINR_NO_FALLBACK_RSRQ;
      }
    }
    list rsrpCandidateA5PcOffset {
      key "id";
      leaf id {
        type uint32;
        description "Synthetic key for struct sequence entry.";
      }
      min-elements 0;
      max-elements 3;
      uses ReportConfigA5RsrpPcOffset-struct;
    }
    list rsrpCandidateB2 {
      key "id";
      leaf id {
        type uint32;
        description "Synthetic key for struct attribute.";
      }
      description "RSRP B2 measurement report criteria when searching for PCell candidate..";
      uses ReportConfigB2Rsrp-struct;
    }
    leaf rsrpCandidateB2AddTargEval {
      description "Additional target evaluation of other reported quantity. Applicable when searching for E-UTRAN PCell candidate with B2 event with trigger quantity RSRP. Other reported quantity SINR is evaluated towards threshold value defined by following formula: threshold2EUtra in sinrCandidateB2 + hysteresis in sinrCandidateB2 + threshold2EUtraOffset in McpcPCellEUtranFreqRelProfileUeCfg::sinrCandidateB2Offsets Other reported quantity RSRQ is evaluated towards threshold value defined by following formula: threshold2EUtra in rsrqCandidateB2 + hysteresis in rsrqCandidateB2 + threshold2EUtraOffset in McpcPCellEUtranFreqRelProfileUeCfg::rsrqCandidateB2Offsets.";
      type enumeration {
        enum NONE;
        enum RSRQ;
        enum SINR_FALLBACK_RSRQ;
        enum SINR_NO_FALLBACK_RSRQ;
      }
    }
    list rsrpCandidateB2PcOffset {
      key "id";
      leaf id {
        type uint32;
        description "Synthetic key for struct sequence entry.";
      }
      min-elements 0;
      max-elements 3;
      uses ReportConfigB2NoThr2RsrpPcOffset-struct;
    }
    list rsrpCritical {
      key "id";
      leaf id {
        type uint32;
        description "Synthetic key for struct attribute.";
      }
      description "RSRP measurement report criteria for detecting critical coverage..";
      uses ReportConfigA1A2Rsrp-struct;
    }
    leaf rsrpCriticalEnabled {
      description "Whether RSRP measurement for detecting critical coverage is enabled. RSRP measurement criteria for detecting critical coverage is defined by rsrpCritical.; Default value: false.";
      type boolean;
      default "false";
    }
    list rsrpCriticalPcOffset {
      key "id";
      leaf id {
        type uint32;
        description "Synthetic key for struct sequence entry.";
      }
      min-elements 0;
      max-elements 3;
      uses ReportConfigA1A2RsrpPcOffset-struct;
    }
    leaf rsrpSearchTimeRestriction {
      description "Search time restriction when searching for PCell candidate using downlink RSRP measurements. If -1, no time restriction is applied.; Default value: -1.";
      type int32 {
        range "-1 | 10..12000";
      }
      default "-1";
      units "ms";
    }
    leaf rsrpSearchTimeRestrictionByUl {
      description "Search time restriction when searching for PCell candidate using RSRP. Triggered by uplink quality measurements. If -1, no time restriction is applied.; Default value: -1.";
      type int32 {
        range "-1 | 10..12000";
      }
      default "-1";
      units "ms";
    }
    list rsrpSearchZone {
      key "id";
      leaf id {
        type uint32;
        description "Synthetic key for struct attribute.";
      }
      description "RSRP measurement report criteria for detecting entering and leaving search zone..";
      uses ReportConfigA1A2Rsrp-struct;
    }
    list rsrpSearchZonePcOffset {
      key "id";
      leaf id {
        type uint32;
        description "Synthetic key for struct sequence entry.";
      }
      min-elements 0;
      max-elements 3;
      uses ReportConfigA1A2RsrpPcOffset-struct;
    }
    list rsrqCandidateA5 {
      key "id";
      leaf id {
        type uint32;
        description "Synthetic key for struct attribute.";
      }
      description "RSRQ A5 measurement report criteria when searching for NR PCell candidate..";
      uses ReportConfigA5Rsrq-struct;
    }
    leaf rsrqCandidateA5AddTargEval {
      description "Additional target evaluation of other reported quantity. Applicable when searching for NR PCell candidate with A5 event with trigger quantity RSRQ. Other reported quantity RSRP is evaluated towards threshold value defined by following formula: threshold2 in rsrpCandidateA5 + hysteresis in rsrpCandidateA5 + threshold2Offset in McpcPCellNrFreqRelProfileUeCfg::rsrpCandidateA5Offsets + threshold2Offset, for power class of UE, in rsrpCandidateA5PcOffset - NRCellRelation::cellIndividualOffsetNR.";
      type enumeration {
        enum NONE;
        enum RSRP;
      }
    }
    list rsrqCandidateB2 {
      key "id";
      leaf id {
        type uint32;
        description "Synthetic key for struct attribute.";
      }
      description "RSRQ B2 measurement report criteria when searching for E-UTRAN PCell candidate..";
      uses ReportConfigB2Rsrq-struct;
    }
    leaf rsrqCandidateB2AddTargEval {
      description "Additional target evaluation of other reported quantity. Applicable when searching for E-UTRAN PCell candidate with B2 event with trigger quantity RSRQ. Other reported quantity RSRP is evaluated towards threshold value defined by following formula: threshold2EUtra in rsrpCandidateB2 + hysteresis in rsrpCandidateB2 + threshold2EUtraOffset in McpcPCellEUtranFreqRelProfileUeCfg::rsrpCandidateB2Offsets - EUtranCellRelation::cellIndividualOffset.";
      type enumeration {
        enum NONE;
        enum RSRP;
      }
    }
    list rsrqCritical {
      key "id";
      leaf id {
        type uint32;
        description "Synthetic key for struct attribute.";
      }
      description "RSRQ measurement report criteria for detecting critical coverage..";
      uses ReportConfigA2Rsrq-struct;
    }
    leaf rsrqCriticalEnabled {
      description "Whether RSRQ measurement for detecting critical coverage is enabled. RSRQ measurement criteria for detecting critical coverage is defined by rsrqCritical.; Default value: false.";
      type boolean;
      default "false";
    }
    leaf rsrqSearchTimeRestriction {
      description "Search time restriction when searching for PCell candidate using downlink RSRQ measurements. If -1, no time restriction is applied.; Default value: -1.";
      type int32 {
        range "-1 | 10..12000";
      }
      default "-1";
      units "ms";
    }
    list rsrqSearchZone {
      key "id";
      leaf id {
        type uint32;
        description "Synthetic key for struct attribute.";
      }
      description "RSRQ measurement report criteria that define entering and leaving search zone..";
      uses ReportConfigA1A2Rsrq-struct;
    }
    list sinrCandidateA5 {
      key "id";
      leaf id {
        type uint32;
        description "Synthetic key for struct attribute.";
      }
      description "SINR A5 measurement report criteria when searching for NR PCell candidate..";
      uses ReportConfigA5Sinr-struct;
    }
    leaf sinrCandidateA5AddTargEval {
      description "Additional target evaluation of other reported quantity. Applicable when searching for NR PCell candidate with A5 event with trigger quantity SINR. Other reported quantity RSRP is evaluated towards threshold value defined by following formula: threshold2 in rsrpCandidateA5 + hysteresis in rsrpCandidateA5 + threshold2Offset in McpcPCellNrFreqRelProfileUeCfg::rsrpCandidateA5Offsets + threshold2Offset, for power class of UE, in rsrpCandidateA5PcOffset - NRCellRelation::cellIndividualOffsetNR Other reported quantity RSRQ is evaluated towards threshold value defined by following formula: threshold2 in rsrqCandidateA5 + hysteresis in rsrqCandidateA5 + threshold2Offset in McpcPCellNrFreqRelProfileUeCfg::rsrqCandidateA5Offsets.";
      type enumeration {
        enum NONE;
        enum RSRP;
        enum RSRQ;
        enum RSRP_AND_RSRQ;
      }
    }
    list sinrCandidateB2 {
      key "id";
      leaf id {
        type uint32;
        description "Synthetic key for struct attribute.";
      }
      description "SINR B2 measurement report criteria when searching for E-UTRAN PCell candidate..";
      uses ReportConfigB2Sinr-struct;
    }
    leaf sinrCandidateB2AddTargEval {
      description "Additional target evaluation of other reported quantity. Applicable when searching for E-UTRAN PCell candidate with B2 event with trigger quantity SINR. Other reported quantity RSRP is evaluated towards threshold value defined by following formula: threshold2EUtra in rsrpCandidateB2 + hysteresis in rsrpCandidateB2 + threshold2EUtraOffset in McpcPCellEUtranFreqRelProfileUeCfg::rsrpCandidateB2Offsets - EUtranCellRelation::cellIndividualOffset Other reported quantity RSRQ is evaluated towards threshold value defined by following formula: threshold2EUtra in rsrqCandidateB2 + hysteresis in rsrqCandidateB2 + threshold2EUtraOffset in McpcPCellEUtranFreqRelProfileUeCfg::rsrqCandidateB2Offsets.";
      type enumeration {
        enum NONE;
        enum RSRP;
        enum RSRQ;
        enum RSRP_AND_RSRQ;
      }
    }
    list sinrCritical {
      key "id";
      leaf id {
        type uint32;
        description "Synthetic key for struct attribute.";
      }
      description "SINR measurement report criteria for detecting critical coverage..";
      uses ReportConfigA2Sinr-struct;
    }
    leaf sinrCriticalEnabled {
      description "Whether SINR measurement for detecting critical coverage is enabled. SINR measurement criteria for detecting critical coverage is defined by sinrCritical.; Default value: false.";
      type boolean;
      default "false";
    }
    leaf sinrSearchTimeRestriction {
      description "Search time restriction when searching for PCell candidate using downlink SINR measurements. If -1, no time restriction is applied.; Default value: -1.";
      type int32 {
        range "-1 | 10..12000";
      }
      default "-1";
      units "ms";
    }
    list sinrSearchZone {
      key "id";
      leaf id {
        type uint32;
        description "Synthetic key for struct attribute.";
      }
      description "SINR measurement report criteria that define entering and leaving search zone..";
      uses ReportConfigA1A2Sinr-struct;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf ulQualCriticalEnabled {
      description "Whether uplink quality measurements for detecting critical coverage are enabled. Uplink quality measurement criteria for detecting critical coverage is defined by UlQualMcpcMeasCfg::ulQualCritical.; Default value: false.";
      type boolean;
      default "false";
    }
    leaf ulQualMcpcMeasCfgRef {
      description "Reference to an instance of UlQualMcpcMeasCfg MO. Automatically set to UlQualMcpcMeasCfg=Default instance, unless manually set to refer to another MO instance. Only applicable to Low-Band and Mid-Band cells..";
      type string;
    }
    leaf userLabel {
      description "Label for free use..";
      type string;
    }
    leaf useT312CandidateA5 {
      description "Whether useT312 parameter is provided in report configuration for A5 measurement. Whether useT312 parameter is provided in reportConfigNR information element sent to UE for A5 measurement for Mobility Control at Poor Coverage. A5 measurement for Mobility Control at Poor Coverage is used to find PCell candidate on another frequency. If true, useT312 is provided in reportConfigNR information element with value true. If false, useT312 is not provided in reportConfigNR information element.; Default value: false.";
      type boolean;
      default "false";
    }
  }
  grouping McpcPSCellNrFreqRelProfile-attributes {
    leaf mcpcPSCellNrFreqRelProfileId {
      description "The value component of the RDN..";
      type string;
      mandatory true;
    }
    leaf-list reservedBy {
      description "Contains a list of MO instances that reserve this MO instance..";
      type string;
      min-elements 0;
    }
    leaf ueConfGroupType {
      description "UE configuration group type. UE configuration group type that is applied in contained McpcPSCellNrFreqRelProfileUeCfg instances..";
      type enumeration {
        enum UE_MOBILITY_GROUP;
        enum UE_SERVICE_GROUP;
        enum UE_ADMISSION_GROUP;
      }
    }
    leaf userLabel {
      description "Label for free use..";
      type string;
    }
  }
  grouping McpcPSCellNrFreqRelProfileUeCfg-attributes {
    leaf inhibitMeasForCellCandidate {
      description "Whether UE measurement to detect PSCell candidate on this frequency is inhibited.; Default value: false.";
      type boolean;
      default "false";
    }
    leaf mcpcPSCellNrFreqRelProfileUeCfgId {
      description "The value component of the RDN..";
      type string;
      mandatory true;
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    list rsrpCandidateA5Offsets {
      key "id";
      leaf id {
        type uint32;
        description "Synthetic key for struct attribute.";
      }
      description "Downlink RSRP A5 measurement offsets when searching for PSCell candidate..";
      uses ReportConfigA5RsrpOffsets-struct;
    }
    list rsrqCandidateA5Offsets {
      key "id";
      leaf id {
        type uint32;
        description "Synthetic key for struct attribute.";
      }
      description "Downlink RSRQ A5 measurement offsets when searching for NR PSCell candidate..";
      uses ReportConfigA5RsrqOffsets-struct;
    }
    list sinrCandidateA5Offsets {
      key "id";
      leaf id {
        type uint32;
        description "Synthetic key for struct attribute.";
      }
      description "Downlink SINR A5 measurement offsets when searching for NR PSCell candidate..";
      uses ReportConfigA5SinrOffsets-struct;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping McpcPSCellProfile-attributes {
    leaf mcpcPSCellProfileId {
      description "The value component of the RDN..";
      type string;
      mandatory true;
    }
    leaf-list reservedBy {
      description "Contains a list of MO instances that reserve this MO instance..";
      type string;
      min-elements 0;
    }
    leaf ueConfGroupType {
      description "UE configuration group type. UE configuration group type that is applied in contained McpcPSCellProfileUeCfg instances..";
      type enumeration {
        enum UE_MOBILITY_GROUP;
        enum UE_SERVICE_GROUP;
        enum UE_ADMISSION_GROUP;
      }
    }
    leaf userLabel {
      description "Label for free use..";
      type string;
    }
  }
  grouping McpcPSCellProfileUeCfg-attributes {
    leaf lowHighFreqPrioClassification {
      description "Classification of low and high frequency relation priority. NR frequency relation priorities are defined by UeMCNrFreqRelProfileUeCfg::connModePrioPSCell. Frequency relation priority is classified as high priority if its value is higher or equal to value of lowHighFreqPrioClassification, else classified as low priority.; range 0..7; Default value: 7.";
      type eytypes:int32_range_0-7;
      default "7";
    }
    leaf maxReportCells {
      description "Maximum number of non-serving cells included in measurement report. Only applicable to event A5.; range 1..8; Default value: 1.";
      type eytypes:int32_range_1-8;
      default "1";
    }
    leaf mcpcPSCellProfileUeCfgId {
      description "The value component of the RDN..";
      type string;
      mandatory true;
    }
    leaf-list mcpcQuantityList {
      description "Measurement quantities on which PSCell Mobility Control at Poor Coverage function is applied. Following combinations of measurement quantities are supported: - RSRP - RSRQ - SINR_FALLBACK_RSRQ - SINR_FALLBACK_RSRP - RSRP + RSRQ - RSRP + SINR_NO_FALLBACK - RSRP + SINR_FALLBACK_RSRQ.";
      type McpcQuantity;
      min-elements 1;
      max-elements 2;
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    list rsrpCandidateA5 {
      key "id";
      leaf id {
        type uint32;
        description "Synthetic key for struct attribute.";
      }
      description "RSRP A5 measurement report criteria when searching for PSCell candidate..";
      uses ReportConfigA5Rsrp-struct;
    }
    leaf rsrpCandidateA5AddTargEval {
      description "Additional target evaluation of other reported quantity. Applicable when searching for NR PSCell candidate with A5 event with trigger quantity RSRP. Other reported quantity SINR is evaluated towards threshold value defined by following formula: threshold2 in sinrCandidateA5 + hysteresis in sinrCandidateA5 + threshold2Offset in McpcPSCellNrFreqRelProfileUeCfg::sinrCandidateA5Offsets Other reported quantity RSRQ is evaluated towards threshold value defined by following formula: threshold2 in rsrqCandidateA5 + hysteresis in rsrqCandidateA5 + threshold2Offset in McpcPSCellNrFreqRelProfileUeCfg::rsrqCandidateA5Offsets.";
      type enumeration {
        enum NONE;
        enum RSRQ;
        enum SINR_FALLBACK_RSRQ;
        enum SINR_NO_FALLBACK_RSRQ;
      }
    }
    list rsrpCritical {
      key "id";
      leaf id {
        type uint32;
        description "Synthetic key for struct attribute.";
      }
      description "RSRP measurement report criteria for detecting critical coverage. Only applied if rsrpCriticalEnabled is true..";
      uses ReportConfigA2Rsrp-struct;
    }
    leaf rsrpCriticalEnabled {
      description "Whether RSRP measurements for detecting critical coverage is enabled. RSRP measurement criteria for detecting critical coverage is defined by rsrpCritical.; Default value: false.";
      type boolean;
      default "false";
    }
    leaf rsrpSearchTimeRestriction {
      description "Search time restriction when searching for PSCell candidate using downlink RSRP measurements. If -1, no time restriction is applied.; Default value: -1.";
      type int32 {
        range "-1 | 200..12000";
      }
      default "-1";
      units "ms";
    }
    list rsrpSearchZone {
      key "id";
      leaf id {
        type uint32;
        description "Synthetic key for struct attribute.";
      }
      description "RSRP measurement report criteria that define entering and leaving search zone..";
      uses ReportConfigA1A2Rsrp-struct;
    }
    list rsrqCandidateA5 {
      key "id";
      leaf id {
        type uint32;
        description "Synthetic key for struct attribute.";
      }
      description "RSRQ A5 measurement report criteria when searching for NR PSCell candidate..";
      uses ReportConfigA5Rsrq-struct;
    }
    leaf rsrqCandidateA5AddTargEval {
      description "Additional target evaluation of other reported quantity. Applicable when searching for NR PSCell candidate with A5 event with trigger quantity RSRQ. Other reported quantity RSRP is evaluated towards threshold value defined by following formula: threshold2 in rsrpCandidateA5 + hysteresis in rsrpCandidateA5 + threshold2Offset in McpcPSCellNrFreqRelProfileUeCfg::rsrpCandidateA5Offsets - NRCellRelation::cellIndividualOffsetNR.";
      type enumeration {
        enum NONE;
        enum RSRP;
      }
    }
    list rsrqCritical {
      key "id";
      leaf id {
        type uint32;
        description "Synthetic key for struct attribute.";
      }
      description "RSRQ measurement report criteria for detecting critical coverage..";
      uses ReportConfigA2Rsrq-struct;
    }
    leaf rsrqCriticalEnabled {
      description "Whether RSRQ measurement for detecting critical coverage is enabled. RSRQ measurement criteria for detecting critical coverage is defined by rsrqCritical.; Default value: false.";
      type boolean;
      default "false";
    }
    leaf rsrqSearchTimeRestriction {
      description "Search time restriction when searching for PSCell candidate using downlink RSRQ measurements. If -1, no time restriction is applied.; Default value: -1.";
      type int32 {
        range "-1 | 10..12000";
      }
      default "-1";
      units "ms";
    }
    list rsrqSearchZone {
      key "id";
      leaf id {
        type uint32;
        description "Synthetic key for struct attribute.";
      }
      description "RSRQ measurement report criteria for detecting entering and leaving search zone..";
      uses ReportConfigA1A2Rsrq-struct;
    }
    list sinrCandidateA5 {
      key "id";
      leaf id {
        type uint32;
        description "Synthetic key for struct attribute.";
      }
      description "SINR A5 measurement report criteria when searching for NR PSCell candidate..";
      uses ReportConfigA5Sinr-struct;
    }
    leaf sinrCandidateA5AddTargEval {
      description "Additional target evaluation of other reported quantity. Applicable when searching for NR PSCell candidate with A5 event with trigger quantity SINR. Other reported quantity RSRP is evaluated towards threshold value defined by following formula: threshold2 in rsrpCandidateA5 + hysteresis in rsrpCandidateA5 + threshold2Offset in McpcPSCellNrFreqRelProfileUeCfg::rsrpCandidateA5Offsets - NRCellRelation::cellIndividualOffsetNR Other reported quantity RSRQ is evaluated towards threshold value defined by following formula: + threshold2 in rsrqCandidateA5 + hysteresis in rsrqCandidateA5 + threshold2Offset in McpcPSCellNrFreqRelProfileUeCfg::rsrqCandidateA5Offsets.";
      type enumeration {
        enum NONE;
        enum RSRP;
        enum RSRQ;
        enum RSRP_AND_RSRQ;
      }
    }
    list sinrCritical {
      key "id";
      leaf id {
        type uint32;
        description "Synthetic key for struct attribute.";
      }
      description "SINR measurement report criteria for detecting critical coverage..";
      uses ReportConfigA2Sinr-struct;
    }
    leaf sinrCriticalEnabled {
      description "Whether SINR measurement for detecting critical coverage is enabled. SINR measurement criteria for detecting critical coverage is defined by sinrCritical.; Default value: false.";
      type boolean;
      default "false";
    }
    leaf sinrSearchTimeRestriction {
      description "Search time restriction when searching for PSCell candidate using downlink SINR measurements. If -1, no time restriction is applied.; Default value: -1.";
      type int32 {
        range "-1 | 10..12000";
      }
      default "-1";
      units "ms";
    }
    list sinrSearchZone {
      key "id";
      leaf id {
        type uint32;
        description "Synthetic key for struct attribute.";
      }
      description "SINR measurement report criteria for detecting entering and leaving search zone..";
      uses ReportConfigA1A2Sinr-struct;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping Mdt-attributes {
    leaf mdtId {
      description "The value component of the RDN..";
      type string;
      mandatory true;
    }
    leaf userLabel {
      description "Label for free use..";
      type string;
    }
  }
  grouping MdtCellProfile-attributes {
    leaf mdtCellProfileId {
      description "The value component of the RDN..";
      type string;
      mandatory true;
    }
    leaf-list reservedBy {
      description "Contains a list of MO instances that reserve this MO instance..";
      type string;
      min-elements 0;
    }
    leaf ueConfGroupType {
      description "UE configuration group type. UE configuration group type that is applied in contained MdtCellProfileUeCfg instances..";
      type enumeration {
        enum UE_MOBILITY_GROUP;
        enum UE_SERVICE_GROUP;
        enum UE_ADMISSION_GROUP;
      }
    }
    leaf userLabel {
      description "Label for free use..";
      type string;
    }
  }
  grouping MdtCellProfileUeCfg-attributes {
    leaf immediateMdtGnssR16Check {
      description "Whether UE GNSS capability check is enabled at UE selection for immediate MDT. UE must support 3GPP Release 16 GNSS capabilities to provide detailed location information.; Default value: false.";
      type boolean;
      default "false";
    }
    leaf m1Enabled {
      description "Enables request for MDT M1 measurement report from UEs. M1: Downlink signal quantities measurement results for the serving cell and for neighbor cells. For NR cells, cell-level and beam-level measurements are included.; Default value: true.";
      type boolean;
      default "true";
    }
    leaf m1EventA2Hysteresis {
      description "Hysteresis value for MDT M1 event A2 measurement.; range 0..150; Default value: 10.";
      type eytypes:int32_range_0-150;
      default "10";
      units "dB";
    }
    leaf m1EventA2ThresholdRsrp {
      description "RSRP threshold value for event A2 that triggers MDT M1 UE measurement.; range -156..-29; Default value: -156.";
      type eytypes:int32_range_-156--29;
      default "-156";
      units "dBm";
    }
    leaf m1EventA2ThresholdRsrq {
      description "RSRQ threshold value for event A2 that triggers MDT M1 UE measurement.; range -435..200; Default value: -435.";
      type eytypes:int32_range_-435-200;
      default "-435";
      units "dB";
    }
    leaf m1EventA2ThresholdSinr {
      description "SINR threshold value for event A2 that triggers MDT M1 UE measurement.; range -230..405; Default value: -230.";
      type int32 {
        range "-230..405";
      }
      default "-230";
      units "dB";
    }
    leaf m1EventA2TimeToTrigger {
      description "Time-to-trigger value for MDT M1 event A2 measurement.; Default value: 640.";
      type int32 {
        range "0 | 40 | 64 | 80 | 100 | 128 | 160 | 256 | 320 | 480 | 512 | 640 | 1024 | 1280 | 2560 | 5120";
      }
      default "640";
    }
    leaf m1EventA2TriggerQuantity {
      description "RSRP, RSRQ, or SINR quantity that triggers MDT M1 event A2..";
      type enumeration {
        enum RSRP;
        enum RSRQ;
        enum SINR;
      }
    }
    leaf m1IncludeBeamMeasurement {
      description "Whether beam measurement results are included as indicated by m1ReportQuantityRsIndex.; Default value: false.";
      type boolean;
      default "false";
    }
    leaf m1IncludeCommonLocationInfo {
      description "Whether common location information is included in MDT M1 UE measurement. Provides detailed location information available to UE to correlate measurements and UE position information.; Default value: true.";
      type boolean;
      default "true";
    }
    leaf m1IncludeRrmReport {
      description "Whether RRM measurement reports are included in PM events for MDT M1 UE measurement.; Default value: true.";
      type boolean;
      default "true";
    }
    leaf m1InterFreqMeasAllowed {
      description "Whether MDT M1 inter-frequency measurement is allowed for UE. If false, MDT M1 intra-frequency measurement is configured for UE, instead of MDT M1 inter-frequency measurement.; Default value: true.";
      type boolean;
      default "true";
    }
    leaf m1MaxNoOfRsIndexToReport {
      description "Maximum number of RS indexes included in MDT M1 UE measurement.; range 1..32; Default value: 8.";
      type eytypes:int32_range_1-32;
      default "8";
    }
    leaf m1MaxReportCells {
      description "Maximum number of cells included in MDT M1 UE measurement.; range 1..8; Default value: 8.";
      type eytypes:int32_range_1-8;
      default "8";
    }
    leaf m1ReportAmount {
      description "Number of MDT M1 measurements taken for periodical reporting..";
      type enumeration {
        enum R1;
        enum R2;
        enum R4;
        enum R8;
        enum R16;
        enum R32;
        enum R64;
        enum INFINITY;
      }
    }
    leaf m1ReportInterval {
      description "Periodicity used by UE to perform and report MDT M1 UE measurement. Used for immediate MDT M1 measurement..";
      type enumeration {
        enum MS_120;
        enum MS_240;
        enum MS_480;
        enum MS_640;
        enum MS_1024;
        enum MS_2048;
        enum MS_5120;
        enum MS_10240;
        enum MS_20480;
        enum MS_40960;
        enum MIN_1;
        enum MIN_6;
        enum MIN_12;
        enum MIN_30;
      }
    }
    leaf m1ReportQuantityCell {
      description "Quantities included in measurement report for each cell for MDT M1 UE measurement..";
      type enumeration {
        enum RSRP;
        enum RSRQ;
        enum SINR;
        enum RSRP_RSRQ;
        enum RSRP_SINR;
        enum RSRQ_SINR;
        enum RSRP_RSRQ_SINR;
      }
    }
    leaf m1ReportQuantityRsIndex {
      description "Quantities included in measurement report for each RS index for MDT M1 UE measurement..";
      type enumeration {
        enum RSRP;
        enum RSRQ;
        enum SINR;
        enum RSRP_RSRQ;
        enum RSRP_SINR;
        enum RSRQ_SINR;
        enum RSRP_RSRQ_SINR;
      }
    }
    leaf m1ReportTrigger {
      description "Reporting trigger used for UE side MDT M1 measurement..";
      type enumeration {
        enum PERIODIC;
        enum A2EVENT_TRIGGERED;
        enum A2EVENT_TRIGGERED_PERIODIC;
      }
    }
    leaf m6Enabled {
      description "Whether MDT M6 measurement is enabled. M6: Packet delay measurement, separately for downlink and uplink.; Default value: true.";
      type boolean;
      default "true";
    }
    leaf m6ReportAmount {
      description "Number of immediate MDT M6 measurements taken for periodic reporting..";
      type enumeration {
        enum R1;
        enum R2;
        enum R4;
        enum R8;
        enum R16;
        enum R32;
        enum R64;
        enum INFINITY;
      }
    }
    leaf m6ReportInterval {
      description "Periodicity used to perform and report MDT M6 measurement. Used for immediate MDT M6 measurement..";
      type enumeration {
        enum MS_1024;
        enum MS_2048;
        enum MS_5120;
        enum MS_10240;
        enum MS_20480;
        enum MS_40960;
        enum MIN_1;
      }
    }
    leaf mdtCellProfileUeCfgId {
      description "The value component of the RDN..";
      type string;
      mandatory true;
    }
    leaf mdtUeSelectionRatio {
      description "UE selection ratio for immediate MDT measurement configuration.; range 0..1000; Default value: 1000.";
      type eytypes:int32_range_0-1000-10;
      default "1000";
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping Nccm-attributes {
    leaf nccmId {
      description "The value component of the RDN..";
      type string;
      mandatory true;
    }
    leaf ueConfGroupType {
      description "UE configuration group type. UE configuration group type that is applied in contained NccmUeCfg instances..";
      type enumeration {
        enum UE_MOBILITY_GROUP;
        enum UE_SERVICE_GROUP;
        enum UE_ADMISSION_GROUP;
      }
    }
    leaf userLabel {
      description "Label for free use..";
      type string;
    }
  }
  grouping NccmUeCfg-attributes {
    leaf nccmEnabled {
      description "Whether NCCM for UE groups is enabled. UE groups are identified by prefUeGroupList, ueGroupList, and ueConfGroupList. Note: Toggling can be inactivated by internal system capability..";
      type boolean;
    }
    leaf nccmUeCfgId {
      description "The value component of the RDN..";
      type string;
      mandatory true;
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping NRCellCU-attributes {
    leaf admissionLimitRef {
      description "Reference to an instance of AdmissionLimit MO. Automatically set to AdmissionLimit=Default instance, unless manually set to refer to another MO instance..";
      type string;
    }
    leaf admissionPriorityRef {
      description "Reference to an instance of AdmissionPriority MO. Automatically set to AdmissionPriority=Default instance, unless manually set to refer to another MO instance..";
      type string;
    }
    leaf advUePosMode {
      description "Positioning report mode for NR Advanced UE Location Support feature. Only applicable if license for NR Advanced UE Location Support is present and feature is active. Only applicable to Low-Band and Mid-Band cells..";
      type enumeration {
        enum NONE;
        enum ALL;
        enum TA_ONLY;
      }
    }
    leaf autoCleanupAllowed {
      description "Whether automatic cleanup is allowed for this NRCellCU instance.; Default value: true.";
      type boolean;
      default "true";
    }
    leaf caCellMeasProfileRef {
      description "Reference to an instance of CaCellMeasProfile MO. Automatically set to CaCellMeasProfile=Default instance, unless manually set to refer to another MO instance..";
      type string;
    }
    leaf caCellProfileRef {
      description "Reference to an instance of CaCellProfile MO. Automatically set to CaCellProfile=Default instance, unless manually set to refer to another MO instance..";
      type string;
    }
    leaf cellLocalId {
      description "Used together with gNodeB identifier to identify NR cell in PLMN. Used together with gNBId to form NCI.; range 0..16383.";
      type eytypes:int32_range_0-16383;
      mandatory true;
    }
    leaf cellState {
      description "Current cellState..";
      type enumeration {
        enum IDLE;
        enum INACTIVE;
        enum ACTIVE;
      }
      config false;
    }
    leaf checkUeGrpAtCellOffload {
      description "Whether protection of certain services during cell offload is enabled.; Default value: false.";
      type boolean;
      default "false";
    }
    leaf endcInitialCgRef {
      description "Reference to an instance of InitialCg MO. Automatically set to InitialCg=Default instance, unless manually set to refer to another MO instance. Applicable to EN-DC..";
      type string;
    }
    leaf epBoCSEnergySavingState {
      description "Current Booster Carrier Sleep energy saving state for cell..";
      type enumeration {
        enum NOT_ENERGYSAVING;
        enum ENERGYSAVING;
      }
      config false;
    }
    leaf epBoCSMode {
      description "Mode of operation for NR Booster Carrier Sleep. Only applicable to Low-Band and Mid-Band cells..";
      type enumeration {
        enum DISABLED;
        enum TIME;
        enum MULTI_LAYER_TRAFFIC;
      }
    }
    leaf epBoCSTimeSchedulingGroupRef {
      description "Reference to an instance of TimeSchedulingGroup MO. If empty, epBoCSMode must be DISABLED..";
      type string;
    }
    leaf hiPrioDetEnabled {
      description "Whether traffic steering function PSCell change to higher priority is enabled for NRCellCU.; Default value: false.";
      type boolean;
      default "false";
    }
    leaf interfaceSupervision {
      description "External interfaces which are considered when setting cellState. Not applicable to ESS cells..";
      type enumeration {
        enum ALL_LINKS;
        enum NO_SUPERVISION;
        enum NG_ONLY;
        enum X2_ONLY;
        enum XN_ONLY;
        enum NG_X2_COEXISTENCE;
        enum NG_XN_COEXISTENCE;
        enum X2_XN_COEXISTENCE;
      }
    }
    leaf intraFreqMCCellProfileRef {
      description "Reference to an instance of IntraFreqMCCellProfile MO. Automatically set to IntraFreqMCCellProfile=Default instance, unless manually set to refer to another MO instance..";
      type string;
    }
    leaf-list isPciConflicted {
      description "Whether PCI conflict is detected or resolved. If true, PCI conflict is detected. PCI conflict is either collision or confusion. PCI confusion exists if source cell has relations to two neighbor cells where both neighbor cells have same PCI and frequency. PCI collision exists if source cell has relation to a neighbor cell where source cell and neighbor cell have same PCI and frequency. Only applicable if PciHandling::pciConflictHandlingEnabled is true..";
      type PciConflicted;
      min-elements 0;
      max-elements 6;
    }
    list lwNeighborRel {
      config false;
      min-elements 0;
      uses LwNeighborRelInfo-struct;
    }
    list lwNeighborRelEUtran {
      config false;
      min-elements 0;
      uses LwNeighborRelEUtranInfo-struct;
    }
    leaf mcfbCellProfileRef {
      description "Reference to an instance of McfbCellProfile MO. Automatically set to McfbCellProfile=Default instance, unless manually set to refer to another MO instance..";
      type string;
    }
    leaf mcpcNrdcPSCellEnabled {
      description "Whether Mobility Control at Poor Coverage (MCPC) for PSCell in NR-DC is enabled for NRCellCU..";
      type boolean;
    }
    leaf mcpcNrdcPSCellProfileRef {
      description "Reference to an instance of McpcNrdcPSCellProfile MO. Automatically set to McpcNrdcPSCellProfile=Default instance, unless manually set to refer to another MO instance..";
      type string;
    }
    leaf mcpcPCellEnabled {
      description "Whether Mobility Control at Poor Coverage (MCPC) for PCell is enabled for NRCellCU.; Default value: false.";
      type boolean;
      default "false";
    }
    leaf mcpcPCellProfileRef {
      description "Reference to an instance of McpcPCellProfile MO. Automatically set to McpcPCellProfile=Default instance, unless manually set to refer to another MO instance..";
      type string;
    }
    leaf mcpcPSCellEnabled {
      description "Whether Mobility Control at Poor Coverage (MCPC) for PSCell is enabled for NRCellCU.; Default value: false.";
      type boolean;
      default "false";
    }
    leaf mcpcPSCellProfileRef {
      description "Reference to an instance of McpcPSCellProfile MO. Automatically set to McpcPSCellProfile=Default instance, unless manually set to refer to another MO instance..";
      type string;
    }
    leaf mdtCellProfileRef {
      description "Reference to an instance of MdtCellProfile MO. Automatically set to MdtCellProfile=Default instance, unless manually set to refer to another MO instance..";
      type string;
    }
    leaf mdtEnabled {
      description "Whether immediate MDT measurements are enabled for NRCellCU.; Default value: false.";
      type boolean;
      default "false";
    }
    leaf nCellChangeHigh {
      description "Maximum number of cell reselections to enter high mobility state. If empty, no mobility state parameters will be broadcast in SIB2.; range 1..16.";
      type uint32 {
        range "1..16";
      }
    }
    leaf nCellChangeMedium {
      description "Maximum number of cell reselections to enter medium mobility state. If empty, no mobility state parameters will be broadcast in SIB2.; range 1..16.";
      type uint32 {
        range "1..16";
      }
    }
    leaf nCI {
      description "NR Cell Identity.; range 0..68719476735.";
      type eytypes:int64_range_0-68719476735;
      config false;
    }
    leaf nRCellCUId {
      description "The value component of the RDN..";
      type string;
      mandatory true;
    }
    leaf nrdcInitialCgRef {
      description "Reference to an instance of InitialCg MO. Automatically set to InitialCg=Default instance, unless manually set to refer to another MO instance. Applicable to NR-DC..";
      type string;
    }
    leaf nrdcMnCellProfileRef {
      description "Reference to an instance of NrdcMnCellProfile MO. Automatically set to NrdcMnCellProfile=Default instance, unless manually set to refer to another MO instance..";
      type string;
    }
    leaf nRFrequencyRef {
      description "Reference to an instance of NRFrequency MO corresponding to cell SSB configuration..";
      type string;
    }
    leaf nRTAC {
      description "NR Tracking Area Code (TAC). If empty, NR standalone is not supported for PLMN IDs in pLMNIdList..";
      type int32;
      config false;
    }
    leaf offloadCellProfileRef {
      description "Reference to an instance of OffloadCellProfile MO. Automatically set to OffloadCellProfile=Default instance, unless manually set to refer to another MO instance..";
      type string;
    }
    list pciConflictDetectingCell {
      config false;
      min-elements 0;
      max-elements 6;
      uses Ncgi-struct;
    }
    list pciConflictedCell {
      config false;
      min-elements 0;
      max-elements 6;
      uses Ncgi-struct;
    }
    leaf pimDetectionRole {
      description "Role within victim aggressor groups for PIM detection. If empty, no role is selected for PIM detection. Only applicable to FDD (Low-Band) cells..";
      type enumeration {
        enum AGGRESSOR;
        enum VICTIM;
        enum VICTIM_AND_AGGRESSOR;
      }
      config false;
    }
    leaf pimDetectionStatus {
      description "Whether cell is identified as a PIM victim. PIM detection can identify a cell as a PIM victim if cell is affected by interference from passive intermodulation. Set to NO_PIM_DETECTED or PIM_DETECTED only if pimDetectionRole is VICTIM or VICTIM_AND_AGGRESSOR. Only applicable to FDD (Low-Band) cells..";
      type enumeration {
        enum NOT_APPLICABLE;
        enum NO_PIM_DETECTED;
        enum PIM_DETECTED;
      }
      config false;
    }
    list pLMNIdList {
      config false;
      min-elements 0;
      max-elements 12;
      uses PLMNId-struct;
    }
    leaf pmUeIntraFreqCellProfileRef {
      description "Reference to an instance of PmUeIntraFreqCellProfile MO. Automatically set to PmUeIntraFreqCellProfile=Default instance, unless manually set to refer to another MO instance..";
      type string;
    }
    leaf pmUeIntraFreqEnabled {
      description "Whether PM intra-frequency UE Measurements are enabled for NR cell.; Default value: false.";
      type boolean;
      default "false";
    }
    list primaryPLMNId {
      key "id";
      leaf id {
        type uint32;
        description "Synthetic key for struct attribute.";
      }
      description "PLMN ID for NR CGI. If empty, GNBCUCPFunction::pLMNId is used for PLMN ID in NR CGI..";
      uses PLMNId-struct;
    }
    leaf pSCellCapable {
      description "Whether cell is Primary Secondary Cell (PSCell) capable in EN-DC and NR-DC. For EN-DC: If false, cell is not shared over X2AP. For NR-DC: Regardless of value, all cells are shared over XnAP. If empty, it is unknown whether cell is Primary Secondary Cell (PSCell) capable..";
      type boolean;
      config false;
    }
    leaf puemCellProfileRef {
      description "Reference to an instance of PuemCellProfile MO. Automatically set to PuemCellProfile=Default instance, unless manually set to refer to another MO instance..";
      type string;
    }
    leaf puemEnabled {
      description "Whether periodic UE measurements are enabled for NRCellCU instance.; Default value: false.";
      type boolean;
      default "false";
    }
    leaf-list pwsEmergencyAreaIdList {
      description "List of emergency areas that cell belongs to. A cell that supports broadcast of warning messages can belong to 1 to 15 emergency areas. Emergency area is identified by an Emergency Area ID, set by the operator..";
      type eytypes:int32_range_0-16777215;
      ordered-by user;
      min-elements 0;
      max-elements 15;
    }
    leaf qHyst {
      description "Hysteresis value for ranking criteria at cell reselection.; Default value: 4.";
      type int32 {
        range "0..6 | 8 | 10 | 12 | 14 | 16 | 18 | 20 | 22 | 24";
      }
      default "4";
      units "dB";
    }
    leaf qHystSfHigh {
      description "Speed-dependent scaling factor for Qhyst parameter in sf-High for high mobility state. If empty, no q-HystSF will be broadcast in SIB2..";
      type int32 {
        range "-6 | -4 | -2 | 0";
      }
      units "dB";
    }
    leaf qHystSfMedium {
      description "Speed-dependent scaling factor for Qhyst parameter in sf-Medium for medium mobility state. If empty, no q-HystSF will be broadcast in SIB2..";
      type int32 {
        range "-6 | -4 | -2 | 0";
      }
      units "dB";
    }
    leaf relaxedRrmMeasCellProfileRef {
      description "Reference to an instance of RelaxedRrmMeasCellProfile MO. If empty, no relaxation parameters are broadcast in SIB2. Only applicable when relaxedRrmMeasEnabled is true. Only applicable if license for Relaxed Radio Resource Management Measurements feature is present and feature is active. Not applicable to High-Band cells..";
      type string;
    }
    leaf-list reservedBy {
      description "Contains a list of MO instances that reserve this MO instance..";
      type string;
      min-elements 0;
    }
    leaf resourceStatusMaxConnUe {
      description "Maximum number of UEs in RRC_CONNECTED mode in NR cell used in Standard Load Reporting. Value -2 means maximum number of UEs in RRC_CONNECTED mode for this cell used in Xn Resource Status Reporting procedure of Standard Load Reporting is defined by GNBCUCPFunction::resourceStatusReportDefault. Value greater than upper limit of Baseband capacity for cell is not recommended. Not applicable if GNBCUCPFunction::resourceStatusReportDefault is -2. Not applicable if private extensions are used in 3GPP procedures for Xn resource status reporting. Not applicable to High-Band cells.; Default value: -2.";
      type int32 {
        range "-2 | 1..65535";
      }
      default "-2";
    }
    leaf robustUeCapEnquiryMode {
      description "Control functionality of robust UE capability enquiry. If COMBINED_THEN_SPLIT, UE capability enquiry is sent to request capabilities for NR and EUTRA together. In case procedure fails with PDCP integrity validation, UE capability enquiry is split into separate UE capability enquiry requests, first with NR capabilities and then EUTRA capabilities. During this entire procedure, if UE capability enquiry fails with any other reason or fails with PDCP integrity validation failures more than once, UE capability enquiry procedure is stopped and failure is returned. If SPLIT_ONLY, UE capability enquiry is sent to request capabilities for NR and EUTRA separately. If only one of NR or EUTRA band capabilities is to be requested, NR or EUTRA capabilities are requested in UE capability enquiry. If both NR and EUTRA band capabilities are to be requested, NR capabilities are requested in first UE capability enquiry and EUTRA capabilities are requested in second UE capability enquiry. In case UE capability enquiry fails for any reason during this process, UE capability enquiry procedure is stopped and failure is returned. If COMBINED_ONLY, UE capability enquiry is sent to request capabilities for NR and EUTRA together. In case of any failure, UE capability procedure is stopped and failure is returned..";
      type enumeration {
        enum COMBINED_THEN_SPLIT;
        enum SPLIT_ONLY;
        enum COMBINED_ONLY;
      }
    }
    leaf serviceState {
      description "Current service state..";
      type enumeration {
        enum OUT_OF_SERVICE;
        enum IN_SERVICE;
      }
      config false;
    }
    leaf smtcDuration {
      description "Duration of SSB. Represents value received in RRC encoded MeasurementTimingInformation (SMTC) information element at F1 Setup or at gNodeB-DU Configuration Update.; range 1..5.";
      type eytypes:int32_range_1-5;
      config false;
      units "ms";
    }
    leaf smtcOffset {
      description "Offset of SSB. Represents value received in RRC encoded MeasurementTimingInformation (SMTC) information element at F1 Setup or at gNodeB-DU Configuration Update.; range 0..159.";
      type eytypes:int32_range_0-159;
      config false;
      units "ms";
    }
    leaf smtcPeriodicity {
      description "Periodicity of SSB. Represents value received in RRC encoded MeasurementTimingInformation (SMTC) information element at F1 Setup or at gNodeB-DU Configuration Update..";
      type int32 {
        range "5 | 10 | 20 | 40 | 80 | 160";
      }
      config false;
      units "ms";
    }
    leaf sNonIntraSearchP {
      description "Threshold when inter-frequency and inter-RAT measurements are required. If empty or -1, value is not broadcast in SIB2 and UE applies default value of infinity.; range -1..62; Default value: 0.";
      type int32 {
        range "-1..62";
      }
      default "0";
      units "dB";
    }
    leaf sNonIntraSearchQ {
      description "Threshold when inter-frequency and inter-RAT measurements are required. If empty, value is not broadcast in SIB2, and UE applies default value of 0 dB.; range 0..31.";
      type eytypes:int32_range_0-31;
      units "dB";
    }
    list sNSSAIList {
      config false;
      min-elements 0;
      max-elements 1024;
      uses SliceSelectionAssistInfo-struct;
    }
    leaf tEvaluation {
      description "Duration for evaluating criteria to enter mobility states. If empty, no mobility state parameters will be broadcast in SIB2..";
      type uint32 {
        range "30 | 60 | 120 | 180 | 240";
      }
      units "s";
    }
    leaf threshServingLowP {
      description "Srxlev used for cell reselection to lower priority RAT frequencies.; range 0..62; Default value: 0.";
      type eytypes:int32_range_0-62;
      default "0";
      units "dB";
    }
    leaf threshServingLowQ {
      description "Squal used for cell reselection to lower priority RAT frequencies. If empty, value is not broadcast in SIB.; range 0..31.";
      type eytypes:int32_range_0-31;
      units "dB";
    }
    leaf tHystNormal {
      description "Additional duration for evaluating criteria to enter normal mobility state. If empty, no mobility state parameters will be broadcast in SIB2..";
      type uint32 {
        range "30 | 60 | 120 | 180 | 240";
      }
      units "s";
    }
    leaf transmitSib2 {
      description "Broadcast status of SIB2.; Default value: false.";
      type boolean;
      default "false";
    }
    leaf transmitSib4 {
      description "Broadcast status of SIB4. If number of inter-frequency NRFreqRelation instances exceeds 8, only the 8 NRFreqRelation instances with higher priority according to cellReselectionPriority value are included in SIB4.; Default value: false.";
      type boolean;
      default "false";
    }
    leaf transmitSib5 {
      description "Broadcast status of SIB5. If number of EUtranFreqRelation instances where EUtranFreqRelation::candidateForSib5 is true exceeds 8, only 8 EUtranFreqRelation instances are included in SIB5 in which EUtranFreqRelation::candidateForSib5 is true with higher priority defined in EUtranFreqRelation::cellReselectionPriority.; Default value: false.";
      type boolean;
      default "false";
    }
    leaf transmitSib9 {
      description "Broadcast status of SIB9.; Default value: false.";
      type boolean;
      default "false";
    }
    leaf trStPSCellProfileRef {
      description "Reference to an instance of TrStPSCellProfile MO. Automatically set to TrStPSCellProfile=Default instance, unless manually set to refer to another MO instance..";
      type string;
    }
    leaf trStSaCellProfileRef {
      description "Reference to an instance of TrStSaCellProfile MO. Automatically set to TrStSaCellProfile=Default instance, unless manually set to refer to another MO instance..";
      type string;
    }
    leaf uacBroadcast {
      description "Whether unified access control information is included in SIB1 message for any access category..";
      type boolean;
      config false;
    }
    leaf uacProfileRef {
      description "Reference to an instance of UacProfile MO. Automatically set to UacProfile=Default instance, unless manually set to refer to another MO instance..";
      type string;
    }
    leaf ucmCellProfileRef {
      description "Reference to an instance of UcmCellProfile MO. Automatically set to UcmCellProfile=Default instance, unless manually set to refer to another MO instance..";
      type string;
    }
    leaf ueMCCellProfileRef {
      description "Reference to an instance of UeMCCellProfile MO. Automatically set to UeMCCellProfile=Default instance, unless manually set to refer to another MO instance..";
      type string;
    }
    leaf ueNoDrbPCellProfileRef {
      description "Reference to an instance of UeNoDrbPCellProfile MO. Automatically set to UeNoDrbPCellProfile=Default instance, unless manually set to refer to another MO instance..";
      type string;
    }
    leaf userLabel {
      description "Label for free use..";
      type string;
    }
    leaf pmHoPrepRejInEutranUeCapacityLimit {
      description "Number of failed incoming inter-RAT handovers from LTE in NR SA because of UE capacity limit..";
      type uint64;
      config false;
    }
    leaf-list pmDrbResumeSuccArp {
      description "Number of successful DRB resumes for each ARP level. Compressed: True.";
      type uint64;
      max-elements 16;
    }
    leaf pmUeCtxtRelAbnormalGnb {
      description "Number of abnormal NR SA UE Context Release procedures initiated by either local or external gNodeB..";
      type uint64;
      config false;
    }
    leaf pmRrcConnEstabAttReattEm {
      description "Number of RRC Setup Request procedures with establishmentCause emergency that are considered as reattempts. For more information, see 3GPP TS 38.331, RRC Setup Request..";
      type uint64;
      config false;
    }
    leaf pmEndcPSCellChangeRejInIntraGnbMpLoad {
      description "Number of rejected incoming intra-PSCell changes in NR NSA because Baseband MP load control indicates OVERLOAD or VERY HIGH state..";
      type uint64;
      config false;
    }
    leaf pmUeCapabilityInfoSegmented {
      description "Number of successfully assembled RRC UECapabilityInformation messages..";
      type uint64;
      config false;
    }
    leaf pmHoExeSuccOutInterGnb {
      description "Number of successful outgoing NR inter-gNodeB NG or Xn handover executions in source NR cell..";
      type uint64;
      config false;
    }
    leaf pmHoPrepFailInInterGnbPoorUl {
      description "Number of incoming NR inter-gNodeB handover preparation attempts that fail in NR cell because of poor uplink quality..";
      type uint64;
      config false;
    }
    leaf pmDrbRopEndEndc {
      description "Number of NR EN-DC DRBs at end of ROP..";
      type int64;
      config false;
    }
    leaf pmEndcRelUeAbnormalSgnb {
      description "Number of abnormal EN-DC SCG radio resource releases triggered by Secondary Node..";
      type uint64;
      config false;
    }
    leaf pmNrdcSetupUeMnAttHoIntraGnb {
      description "Number of successful NR-DC UE setup attempts during intra-gNodeB handover. Counted on Master Node side..";
      type uint64;
      config false;
    }
    leaf-list pmDrbRelAbnormalGnbArp {
      description "Number of abnormal DRB releases triggered by either local or external gNodeB for each Allocation and Retention Priority level. Compressed: True Deprecated: Since 24.Q4. Planned to be removed. Replaced by NRCellCU::pmDrbRelAbnormalGnb2Arp; MOM flags: noNotification.";
      type uint64;
      max-elements 16;
    }
    leaf pmHoExeAttOutIntraGnbTs {
      description "Number of NR intra-gNodeB handover execution attempts in source NR cell because of traffic steering..";
      type uint64;
      config false;
    }
    leaf pmRrcConnEstabSuccEm {
      description "Number of successfully completed RRC Connection Establishment procedures for establishmentCause emergency. For more information, see 3GPP TS 38.331, RRC Setup Complete..";
      type uint64;
      config false;
    }
    leaf pmPduSessionRelAbnormalAmf {
      description "Number of PDU sessions released by AMF when cause is considered abnormal..";
      type uint64;
      config false;
    }
    leaf pmEndcPSCellChangeSuccInterSgnb {
      description "Number of successful inter-SgNodeB PSCell changes for EN-DC in source NR cell. For definition of PSCell, see 3GPP TS 37.340..";
      type uint64;
      config false;
    }
    leaf pmHoPrepSuccOutInterGnbPciHandling {
      description "Number of successful outgoing NR inter-gNodeB NG or Xn handover preparations in source NR cell triggered by PCI conflict handling..";
      type uint64;
      config false;
    }
    leaf pmHoPrepRejInCellBarred {
      description "Number of rejected Xn, NG, Inter-RAT handovers in NR SA because cell is barred. Deprecated: Since 24.Q3. Planned to be removed. Replaced by NRCellCU.pmHoPrepRejCellInvalid.; MOM flags: noNotification.";
      type uint64;
      config false;
      status deprecated;
    }
    leaf pmHoPrepAttInNg {
      description "Number of NG Handover request attempts..";
      type uint64;
      config false;
    }
    leaf-list pmSessionTimeDrb5qi {
      description "Aggregated session time of released DRBs for each mapped 5QI in milliseconds. Compressed: True.";
      type uint64;
      max-elements 256;
    }
    leaf pmRrcInitAccessRejUeCapacityLimit {
      description "Number of RRCSetupRequest, RRCResumeRequest, and RRCReestablishmentRequest messages not permitted because of UE capacity limit..";
      type uint64;
      config false;
    }
    leaf pmHoPrepAttOutEutran {
      description "Number of outgoing inter-RAT handover preparation attemps from NR to LTE in source NR cell..";
      type uint64;
      config false;
    }
    leaf pmEndcRelUeAbnormalMenbActRaProblem {
      description "Number of abnormal EN-DC SCG radio resource releases triggered by MeNodeB with randomAccessProblem SCG failure. UE is considered in session at time of release..";
      type uint64;
      config false;
    }
    leaf pmNgSigConnEstabAttEm {
      description "Number of NG signaling connection establishment attempts for connections with Emergency RRC establishment cause..";
      type uint64;
      config false;
    }
    leaf-list pmDrbRelNormal5qi {
      description "Number of normal DRB releases for each 5QI. Compressed: True.";
      type uint64;
      max-elements 256;
    }
    leaf pmRrcConnLevelMaxNrDc {
      description "Peak number of UEs configured with NR-DC, counted on Secondary Node Mode side..";
      type int64;
      config false;
    }
    leaf pmUeCtxtEstabAttMdtConsent {
      description "Number of times MDT is allowed in UE context establishment attempts..";
      type uint64;
      config false;
    }
    leaf pmEndcUeMeasurementReportPuem {
      description "Sum of periodic UE measurement reports for EN-DC..";
      type uint64;
      config false;
    }
    leaf pmHoPrepRejCellInvalid {
      description "Number of rejected Xn, NG, Inter-RAT handovers in NR SA because cell is barred or reserved..";
      type uint64;
      config false;
    }
    leaf pmNrdcRelUeSnAbnormalSnInit {
      description "Number of abnormal NR-DC UE releases initiated by Secondary Node. Counted on Secondary Node side. If counter is stepped due to a RESET message this can be seen in sn_nrdc_release_initiating_message..";
      type uint64;
      config false;
    }
    leaf pmDrbLevelSumEndc {
      description "Sum of all sample values recorded for number of NR EN-DC DRBs..";
      type uint64;
      config false;
    }
    leaf pmHoPrepSuccOutInterGnb {
      description "Number of successful outgoing NR inter-gNodeB NG or Xn handover preparations in source NR cell..";
      type uint64;
      config false;
    }
    leaf pmHoPrepRejInInterGnbUeAdmission {
      description "Number of failed incoming inter-gNodeB handovers in NR SA because of admission control. Deprecated: Since 23.Q4. Planned to be removed. Replaced by NRCellCU::pmHoPrepRejInInterGnbUeCapacityLimit.; MOM flags: noNotification.";
      type uint64;
      config false;
      status deprecated;
    }
    leaf pmHoExeAttOutInterGnbIntraF {
      description "Number of outgoing NR intra-frequency inter-gNodeB NG or Xn handover execution attempts in source NR cell..";
      type uint64;
      config false;
    }
    leaf pmNrdcSetupUeRejCellInvalid {
      description "Number of rejected NR-DC UE setup attempts counted on Secondary Node side and rejected inter-gNodeB PSCell change resource allocation requests for NR-DC in target NR cell because cell is barred or reserved..";
      type uint64;
      config false;
    }
    leaf pmNrdcPSCellChangeResAllocSnAttInterSgnb {
      description "Number of inter-gNodeB PSCell change resource allocation requests for NR-DC in target NR cell..";
      type uint64;
      config false;
    }
    leaf-list pmDrbEstabAttInit5qi {
      description "Number of initial DRB establishment attempts for each 5QI. Compressed: True.";
      type uint64;
      max-elements 256;
    }
    leaf pmHoPrepSuccOutIntraGnb {
      description "Number of successful NR intra-gNodeB handover preparations in source NR cell..";
      type uint64;
      config false;
    }
    leaf pmSaUeMeasurementReport {
      description "Sum of all UE measurement reports for NR SA..";
      type uint64;
      config false;
    }
    leaf pmUeCtxtRetrieveSuccRrcReest {
      description "Number of successfully completed Retrieve UE Context procedures triggered by RRC Connection Reestablishment procedure. See 3GPP TS 38.423, Retrieve UE Context Response..";
      type uint64;
      config false;
    }
    leaf pmEndcRelUeAbnormalMenbActRlcMaxRetx {
      description "Number of abnormal EN-DC SCG radio resource releases triggered by MeNodeB with Rlc-MaxNumRetx SCG failure. UE is considered in session at time of release..";
      type uint64;
      config false;
    }
    leaf pmHoPrepSuccOutEutranTs {
      description "Number of successful outgoing inter-RAT handover preparations for traffic steering reason from NR to LTE in source NR cell..";
      type uint64;
      config false;
    }
    leaf pmHoPrepSuccOutIntraGnbIntraF {
      description "Number of successful NR intra-frequency intra-gNodeB handover preparations in source NR cell..";
      type uint64;
      config false;
    }
    leaf-list pmDrbRelAbnormalAmfAct5qi {
      description "Number of abnormal active DRB releases triggered by AMF for each mapped 5QI. Compressed: True.";
      type uint64;
      max-elements 256;
    }
    leaf pmNgSigConnEstabSuccMos {
      description "Number of successful NG signaling connection establishments for connections with RRC establishmentCause mo-Signalling. See 3GPP TS 38.331, RRC Setup Request..";
      type uint64;
      config false;
    }
    leaf pmEndcCaConfigSucc {
      description "Number of successful SCell configurations in serving PSCell, including configuration of first SCell..";
      type uint64;
      config false;
    }
    leaf pmEndcPSCellChangeAttIntraSgnbIntraF {
      description "Number of intra-SgNodeB intra-frequency PSCell change attempts for EN-DC in source NR cell that are not interrupted by a MeNodeB-initiated procedure, for example, MN mobility. See 3GPP TS 37.340 for definition of PSCell..";
      type uint64;
      config false;
    }
    leaf pmCaConfigSucc {
      description "Number of successful SCell configurations in serving PCell, including configuration of first SCell. Deprecated: Since 25.Q2. Planned to be removed. Replaced by NRCellCU::pmCaSCellConfigSucc.; MOM flags: noNotification.";
      type uint64;
      config false;
      status deprecated;
    }
    leaf pmDrbLevelMaxSa {
      description "Peak number of NR standalone DRBs for UEs in RRC Connected mode. For NR-DC, only DRBs from Master Node are included..";
      type int64;
      config false;
    }
    leaf pmCaSCellReselectionSuccTs {
      description "Number of successful SCell Reselections in PCell triggered by Multi-Layer Coordination or Periodic Multi-Layer Coordination. At SCell Reselection PCell remains unchanged. One or more SCell can be changed to a new frequency. One or more of current SCells can be reused at SCell Reselection..";
      type uint64;
      config false;
    }
    leaf pmNrdcSetupUeSnSucc {
      description "Number of successful NR-DC UE setup attempts. Counted on Secondary Node side..";
      type uint64;
      config false;
    }
    leaf pmRrcConnEstabSuccMos {
      description "Successful RRC Connection Establishment procedure where establishmentCause is mo-Signalling. See 3GPP TS 38.331, RRC Setup Complete..";
      type uint64;
      config false;
    }
    leaf pmHoPrepAttOutInterGnb {
      description "Number of outgoing NR inter-gNodeB NG or Xn handover preparation attempts in source NR cell..";
      type uint64;
      config false;
    }
    leaf pmEndcPSCellChangeAttInterSgnbIntraF {
      description "Number of inter-SgNodeB intra-frequency PSCell change attempts for EN-DC in source NR cell that are not interrupted by a MeNodeB-initiated procedure, for example, MN mobility. See 3GPP TS 37.340 for definition of PSCell..";
      type uint64;
      config false;
    }
    leaf pmHoPrepRejInIntraGnbMpLoad {
      description "Number of rejected intra-gNodeB handovers in NR SA because Baseband MP load control indicates OVERLOAD or VERY HIGH state..";
      type uint64;
      config false;
    }
    leaf pmAnrNeighbRelAddNr {
      description "Number of NR neighbor relations added by ANR function..";
      type uint64;
      config false;
    }
    leaf pmCaConfigMaxSa {
      description "Peak number of NR standalone UEs in Carrier Aggregation configuration that use this cell as PCell..";
      type int64;
      config false;
    }
    leaf pmAnrNeighbRelDemoteEutran {
      description "Number of E-UTRAN neighbor relations demoted by ANR function..";
      type uint64;
      config false;
    }
    leaf pmRrcResumeAttFallbackEm {
      description "Number of RRC connection resume attempts with resumeCause emergency with fallback to RRC Connection Establishment procedure..";
      type uint64;
      config false;
    }
    leaf pmCaConfigDelaySum {
      description "Aggregated duration of secondary cell addition in milliseconds..";
      type uint64;
      config false;
    }
    leaf pmCaDeconfigSucc {
      description "Number of successful SCell deconfigurations in serving PCell, including deconfiguration of last SCell. SCell release signaling to UE uses RRC Reconfiguration and RRC Connection Release procedures. SCell releases that use RRC Connection Release procedure are always successful in serving PCell. Deprecated: Since 25.Q2. Planned to be removed. Replaced by NRCellCU::pmCaSCellDeconfigSucc.; MOM flags: noNotification.";
      type uint64;
      config false;
      status deprecated;
    }
    leaf-list pmCaConfigUlSumSaDistr {
      description "Sum of UEs using this cell as PCell with configured uplink SCells for NR SA UEs. Ranges: Bin[0]: Number of NR SA UEs configured with one PCell and no uplink SCell. Bin[1]: Number of NR SA UEs configured with one PCell and one uplink SCell. Bin[2]: Number of NR SA UEs configured with one PCell and two uplink SCells. ... Bin[31]: Number of NR SA UEs configured with one PCell and thirty-one uplink SCells. Compressed: True.";
      type uint64;
      max-elements 32;
    }
    leaf pmEndcUeCapabilityGnssLocation {
      description "Number of UEs that support GNSS location capability for EN-DC..";
      type uint64;
      config false;
    }
    leaf pmNrdcPSCellChangeMnAttInterSgnb {
      description "Number of NR-DC inter-SgNodeB PSCell Change attempts counted on Master Node side..";
      type uint64;
      config false;
    }
    leaf pmCellBoosterCarrWakeUp {
      description "Number of times a decision is made to wake corresponding cell up because of traffic load. For more information, see NR Booster Carrier Sleep in CPI library..";
      type uint64;
      config false;
    }
    leaf-list pmCaConfigDlSumEndcDistr {
      description "Sum of UEs using this cell as PSCell with configured downlink (DL) SCells for EN-DC UEs. Ranges: Bin[0]: Number of EN-DC UEs configured with one PSCell only and no SCell. Bin[1]: Number of EN-DC UEs configured with one PSCell and one SCell. Bin[2]: Number of EN-DC UEs configured with one PSCell and two SCells. ... Bin[31]: Number of EN-DC UEs configured with one PSCell and thirty-one SCells. Compressed: True.";
      type uint64;
      max-elements 32;
    }
    leaf pmNrdcSetupUeMnAttInitBufUl {
      description "Number of NR-DC UE initial setup attempts after high buffer is detected in uplink. Counted on Master Node side..";
      type uint64;
      config false;
    }
    leaf-list pmDrbEstabSucc5qi {
      description "Number of successful DRB establishments for each 5QI. Compressed: True.";
      type uint64;
      max-elements 256;
    }
    leaf pmPduSessionEstabAtt {
      description "Number of attempted PDU session establishments..";
      type uint64;
      config false;
    }
    leaf pmRrcConnLevelSumEnDc {
      description "Sum of all sample values recorded for number of NR EN-DC UEs in RRC_CONNECTED mode in NR cell..";
      type uint64;
      config false;
    }
    leaf pmHoPrepSuccOutEutranPciHandling {
      description "Number of successful outgoing inter-RAT handover preparations from NR to LTE in source NR cell triggered by PCI conflict handling..";
      type uint64;
      config false;
    }
    leaf pmEndcPSCellChangeSuccInterSgnbIntraF {
      description "Number of successful inter-SgNodeB intra-frequency PSCell changes for EN-DC in source NR cell. See 3GPP TS 37.340 for definition of PSCell.";
      type uint64;
      config false;
    }
    leaf pmEndcMnHoPSCellKeepAtt {
      description "Number of attempts of keeping PSCell during MeNodeB handover with the Intra- or Inter-MN Handover without MN-Initiated SN Change procedure that are not interrupted by SgNodeB due to ongoing procedure. See 3GPP TS 37.340..";
      type uint64;
      config false;
    }
    leaf pmRrcConnLevelSumNrDc {
      description "Sum of all samples taken to track the number of UEs configured with NR-DC. Counted on Secondary Node side..";
      type uint64;
      config false;
    }
    leaf pmEndcMnHoPSCellKeepSucc {
      description "Number of successful attempts of keeping PSCell during MeNodeB handover with the Intra- or Inter-MN Handover without MN-Initiated SN Change procedure. See 3GPP TS 37.340..";
      type uint64;
      config false;
    }
    leaf pmNgSigConnEstabAtt {
      description "The number of NG signaling connection establishment attempts..";
      type uint64;
      config false;
    }
    leaf pmHoPrepRejInInterGnbBbIntens {
      description "Number of failed incoming inter-gNodeB handovers in NR SA because of connection intensity control..";
      type uint64;
      config false;
    }
    leaf pmEndcRelUeAbnormalMenbRlcMaxRetx {
      description "Number of abnormal EN-DC SCG radio resource releases triggered by MeNodeB with Rlc-MaxNumRetx SCG failure..";
      type uint64;
      config false;
    }
    leaf pmEndcRelUeAbnormalMenbSyncReconfigFail {
      description "Number of abnormal EN-DC SCG radio resource releases triggered by MeNodeB with synchRecofigFailure-SCG SCG failure..";
      type uint64;
      config false;
    }
    leaf-list pmDrbEstabSuccInitArp {
      description "Number of successful initial DRB establishment for each ARP level. Compressed: True.";
      type uint64;
      max-elements 16;
    }
    leaf pmNrdcPSCellChangeResAllocSnSuccInterSgnb {
      description "Number of successful inter-gNodeB PSCell change resource allocation requests for NR-DC in target NR cell..";
      type uint64;
      config false;
    }
    leaf-list pmDrbEstabSuccArp {
      description "Number of successful DRB establishments for each Allocation and Retention Priority level. Compressed: True.";
      type uint64;
      max-elements 16;
    }
    leaf pmAnrNcgiMeasFailUeCap {
      description "Number of NCGI measurements for ANR that cannot be requested because of insufficient UE capabilities..";
      type uint64;
      config false;
    }
    leaf pmRrcConnLevelSumSa {
      description "Sum of all samples taken to track the number of NR standalone UEs in RRC_CONNECTED mode. For NR-DC, NR standalone UEs on Master Node side, configured with NR-DC are included..";
      type uint64;
      config false;
    }
    leaf pmRrcConnRedCapLevelSum {
      description "Sum of all samples that tracks number of RedCap UEs in RRC_CONNECTED mode..";
      type uint64;
      config false;
    }
    leaf pmHoPrepAttInNgMdtConsent {
      description "Number of times MDT is allowed in attempts of NG Handover request..";
      type uint64;
      config false;
    }
    leaf pmEndcCaDeconfigSucc {
      description "Number of successful SCell deconfigurations in serving PSCell, including deconfiguration of last SCell..";
      type uint64;
      config false;
    }
    leaf pmHoPrepRejInEutranBbIntens {
      description "Number of failed incoming inter-RAT handovers from LTE in NR SA because of connection intensity control..";
      type uint64;
      config false;
    }
    leaf pmHoExeSuccOutEutranOffload {
      description "Number of successful outgoing inter-RAT handover executions for traffic offload from NR to LTE in source NR cell..";
      type uint64;
      config false;
    }
    leaf pmCaSCellConfigAtt {
      description "Number of SCell configuration attempts in serving PCell, including configuration of first SCell..";
      type uint64;
      config false;
    }
    leaf pmPduSessionEstabSucc {
      description "Number of successfully established PDU sessions..";
      type uint64;
      config false;
    }
    leaf pmAnrNcgiMeasRcvNoSib1NoTacCell {
      description "Number of received NCGI measurements with noSib1 or no NR TAC indication set. See 3GPP TS 38.331..";
      type uint64;
      config false;
    }
    leaf pmMeasReportUlSa {
      description "Sum of all uplink quality measurement reports for NR standalone..";
      type uint64;
      config false;
    }
    leaf pmHoExeAttOutIntraGnbIntraF {
      description "Number of NR intra-frequency intra-gNodeB handover execution attempts in source NR cell..";
      type uint64;
      config false;
    }
    leaf pmHoExeSuccOutIntraGnbIntraF {
      description "Number of successful outgoing NR intra-frequency intra-gNodeB handover executions in source NR cell..";
      type uint64;
      config false;
    }
    leaf pmHoExeSuccOutEutranPciHandling {
      description "Number of successful outgoing inter-RAT handovers from NR to LTE in source NR cell triggered by PCI conflict handling..";
      type uint64;
      config false;
    }
    leaf-list pmUeMeasSsRsrpEndcDistr {
      description "Distribution of SS-RSRP received by gNodeB from UEs in cell. Periodic UE measurement reports to all or a subset of UEs must be triggered by gNodeB in measured NR cell. See 3GPP TS 38.133, RSRP Measurement Report Mapping. Unit: N/A Ranges: Bin[0]: Number of measurement reports with RSRP in dBm range [..-156[ dBm for PSCell. Bin[1]: Number of measurement reports with RSRP in dBm range [-156..-155[ dBm for PSCell. Bin[2]: Number of measurement reports with RSRP in dBm range [-155..-154[ dBm for PSCell. Bin[3]: Number of measurement reports with RSRP in dBm range [-154..-153[ dBm for PSCell. Bin[4]: Number of measurement reports with RSRP in dBm range [-153..-152[ dBm for PSCell. Bin[5]: Number of measurement reports with RSRP in dBm range [-152..-151[ dBm for PSCell. Bin[6]: Number of measurement reports with RSRP in dBm range [-151..-150[ dBm for PSCell. Bin[7]: Number of measurement reports with RSRP in dBm range [-150..-149[ dBm for PSCell. Bin[8]: Number of measurement reports with RSRP in dBm range [-149..-148[ dBm for PSCell. Bin[9]: Number of measurement reports with RSRP in dBm range [-148..-147[ dBm for PSCell. Bin[10]: Number of measurement reports with RSRP in dBm range [-147..-146[ dBm for PSCell. Bin[11]: Number of measurement reports with RSRP in dBm range [-146..-145[ dBm for PSCell. Bin[12]: Number of measurement reports with RSRP in dBm range [-145..-144[ dBm for PSCell. Bin[13]: Number of measurement reports with RSRP in dBm range [-144..-143[ dBm for PSCell. Bin[14]: Number of measurement reports with RSRP in dBm range [-143..-152[ dBm for PSCell. Bin[15]: Number of measurement reports with RSRP in dBm range [-142..-141[ dBm for PSCell. Bin[16]: Number of measurement reports with RSRP in dBm range [-141..-140[ dBm for PSCell. Bin[17]: Number of measurement reports with RSRP in dBm range [-140..-139[ dBm for PSCell. Bin[18]: Number of measurement reports with RSRP in dBm range [-139..-138[ dBm for PSCell. Bin[19]: Number of measurement reports with RSRP in dBm range [-138..-137[ dBm for PSCell. Bin[20]: Number of measurement reports with RSRP in dBm range [-137..-136[ dBm for PSCell. Bin[21]: Number of measurement reports with RSRP in dBm range [-136..-135[ dBm for PSCell. Bin[22]: Number of measurement reports with RSRP in dBm range [-135..-134[ dBm for PSCell. Bin[23]: Number of measurement reports with RSRP in dBm range [-134..-133[ dBm for PSCell. Bin[24]: Number of measurement reports with RSRP in dBm range [-133..-132[ dBm for PSCell. Bin[25]: Number of measurement reports with RSRP in dBm range [-132..-131[ dBm for PSCell. Bin[26]: Number of measurement reports with RSRP in dBm range [-131..-130[ dBm for PSCell. Bin[27]: Number of measurement reports with RSRP in dBm range [-130..-129[ dBm for PSCell. Bin[28]: Number of measurement reports with RSRP in dBm range [-129..-128[ dBm for PSCell. Bin[29]: Number of measurement reports with RSRP in dBm range [-128..-127[ dBm for PSCell. Bin[30]: Number of measurement reports with RSRP in dBm range [-127..-126[ dBm for PSCell. Bin[31]: Number of measurement reports with RSRP in dBm range [-126..-125[ dBm for PSCell. Bin[32]: Number of measurement reports with RSRP in dBm range [-125..-124[ dBm for PSCell. Bin[33]: Number of measurement reports with RSRP in dBm range [-124..-123[ dBm for PSCell. Bin[34]: Number of measurement reports with RSRP in dBm range [-123..-122[ dBm for PSCell. Bin[35]: Number of measurement reports with RSRP in dBm range [-122..-121[ dBm for PSCell. Bin[36]: Number of measurement reports with RSRP in dBm range [-121..-120[ dBm for PSCell. Bin[37]: Number of measurement reports with RSRP in dBm range [-120..-119[ dBm for PSCell. Bin[38]: Number of measurement reports with RSRP in dBm range [-119..-118[ dBm for PSCell. Bin[39]: Number of measurement reports with RSRP in dBm range [-118..-117[ dBm for PSCell. Bin[40]: Number of measurement reports with RSRP in dBm range [-117..-116[ dBm for PSCell. Bin[41]: Number of measurement reports with RSRP in dBm range [-116..-115[ dBm for PSCell. Bin[42]: Number of measurement reports with RSRP in dBm range [-115..-114[ dBm for PSCell. Bin[43]: Number of measurement reports with RSRP in dBm range [-114..-113[ dBm for PSCell. Bin[44]: Number of measurement reports with RSRP in dBm range [-113..-112[ dBm for PSCell. Bin[45]: Number of measurement reports with RSRP in dBm range [-112..-111[ dBm for PSCell. Bin[46]: Number of measurement reports with RSRP in dBm range [-111..-110[ dBm for PSCell. Bin[47]: Number of measurement reports with RSRP in dBm range [-110..-109[ dBm for PSCell. Bin[48]: Number of measurement reports with RSRP in dBm range [-109..-108[ dBm for PSCell. Bin[49]: Number of measurement reports with RSRP in dBm range [-108..-107[ dBm for PSCell. Bin[50]: Number of measurement reports with RSRP in dBm range [-107..-106[ dBm for PSCell. Bin[51]: Number of measurement reports with RSRP in dBm range [-106..-105[ dBm for PSCell. Bin[52]: Number of measurement reports with RSRP in dBm range [-105..-104[ dBm for PSCell. Bin[53]: Number of measurement reports with RSRP in dBm range [-104..-103[ dBm for PSCell. Bin[54]: Number of measurement reports with RSRP in dBm range [-103..-102[ dBm for PSCell. Bin[55]: Number of measurement reports with RSRP in dBm range [-102..-101[ dBm for PSCell. Bin[56]: Number of measurement reports with RSRP in dBm range [-101..-100[ dBm for PSCell. Bin[57]: Number of measurement reports with RSRP in dBm range [-100..-99[ dBm for PSCell. Bin[58]: Number of measurement reports with RSRP in dBm range [-99..-98[ dBm for PSCell. Bin[59]: Number of measurement reports with RSRP in dBm range [-98..-97[ dBm for PSCell. Bin[60]: Number of measurement reports with RSRP in dBm range [-97..-96[ dBm for PSCell. Bin[61]: Number of measurement reports with RSRP in dBm range [-96..-95[ dBm for PSCell. Bin[62]: Number of measurement reports with RSRP in dBm range [-95..-94[ dBm for PSCell. Bin[63]: Number of measurement reports with RSRP in dBm range [-94..-93[ dBm for PSCell. Bin[64]: Number of measurement reports with RSRP in dBm range [-93..-92[ dBm for PSCell. Bin[65]: Number of measurement reports with RSRP in dBm range [-92..-91[ dBm for PSCell. Bin[66]: Number of measurement reports with RSRP in dBm range [-91..-90[ dBm for PSCell. Bin[67]: Number of measurement reports with RSRP in dBm range [-90..-89[ dBm for PSCell. Bin[68]: Number of measurement reports with RSRP in dBm range [-89..-88[ dBm for PSCell. Bin[69]: Number of measurement reports with RSRP in dBm range [-88..-87[ dBm for PSCell. Bin[70]: Number of measurement reports with RSRP in dBm range [-87..-86[ dBm for PSCell. Bin[71]: Number of measurement reports with RSRP in dBm range [-86..-85[ dBm for PSCell. Bin[72]: Number of measurement reports with RSRP in dBm range [-85..-84[ dBm for PSCell. Bin[73]: Number of measurement reports with RSRP in dBm range [-84..-83[ dBm for PSCell. Bin[74]: Number of measurement reports with RSRP in dBm range [-83..-82[ dBm for PSCell. Bin[75]: Number of measurement reports with RSRP in dBm range [-82..-81[ dBm for PSCell. Bin[76]: Number of measurement reports with RSRP in dBm range [-81..-80[ dBm for PSCell. Bin[77]: Number of measurement reports with RSRP in dBm range [-80..-79[ dBm for PSCell. Bin[78]: Number of measurement reports with RSRP in dBm range [-79..-78[ dBm for PSCell. Bin[79]: Number of measurement reports with RSRP in dBm range [-78..-77[ dBm for PSCell. Bin[80]: Number of measurement reports with RSRP in dBm range [-77..-76[ dBm for PSCell. Bin[81]: Number of measurement reports with RSRP in dBm range [-76..-75[ dBm for PSCell. Bin[82]: Number of measurement reports with RSRP in dBm range [-75..-74[ dBm for PSCell. Bin[83]: Number of measurement reports with RSRP in dBm range [-74..-73[ dBm for PSCell. Bin[84]: Number of measurement reports with RSRP in dBm range [-73..-72[ dBm for PSCell. Bin[85]: Number of measurement reports with RSRP in dBm range [-72..-71[ dBm for PSCell. Bin[86]: Number of measurement reports with RSRP in dBm range [-71..-70[ dBm for PSCell. Bin[87]: Number of measurement reports with RSRP in dBm range [-70..-69[ dBm for PSCell. Bin[88]: Number of measurement reports with RSRP in dBm range [-69..-68[ dBm for PSCell. Bin[89]: Number of measurement reports with RSRP in dBm range [-68..-67[ dBm for PSCell. Bin[90]: Number of measurement reports with RSRP in dBm range [-67..-66[ dBm for PSCell. Bin[91]: Number of measurement reports with RSRP in dBm range [-66..-65[ dBm for PSCell. Bin[92]: Number of measurement reports with RSRP in dBm range [-65..-64[ dBm for PSCell. Bin[93]: Number of measurement reports with RSRP in dBm range [-64..-63[ dBm for PSCell. Bin[94]: Number of measurement reports with RSRP in dBm range [-63..-62[ dBm for PSCell. Bin[95]: Number of measurement reports with RSRP in dBm range [-62..-61[ dBm for PSCell. Bin[96]: Number of measurement reports with RSRP in dBm range [-61..-60[ dBm for PSCell. Bin[97]: Number of measurement reports with RSRP in dBm range [-60..-59[ dBm for PSCell. Bin[98]: Number of measurement reports with RSRP in dBm range [-59..-58[ dBm for PSCell. Bin[99]: Number of measurement reports with RSRP in dBm range [-58..-57[ dBm for PSCell. Bin[100]: Number of measurement reports with RSRP in dBm range [-57..-56[ dBm for PSCell. Bin[101]: Number of measurement reports with RSRP in dBm range [-56..-55[ dBm for PSCell. Bin[102]: Number of measurement reports with RSRP in dBm range [-55..-54[ dBm for PSCell. Bin[103]: Number of measurement reports with RSRP in dBm range [-54..-53[ dBm for PSCell. Bin[104]: Number of measurement reports with RSRP in dBm range [-53..-52[ dBm for PSCell. Bin[105]: Number of measurement reports with RSRP in dBm range [-52..-51[ dBm for PSCell. Bin[106]: Number of measurement reports with RSRP in dBm range [-51..-50[ dBm for PSCell. Bin[107]: Number of measurement reports with RSRP in dBm range [-50..-49[ dBm for PSCell. Bin[108]: Number of measurement reports with RSRP in dBm range [-49..-48[ dBm for PSCell. Bin[109]: Number of measurement reports with RSRP in dBm range [-48..-47[ dBm for PSCell. Bin[110]: Number of measurement reports with RSRP in dBm range [-47..-46[ dBm for PSCell. Bin[111]: Number of measurement reports with RSRP in dBm range [-46..-45[ dBm for PSCell. Bin[112]: Number of measurement reports with RSRP in dBm range [-45..-44[ dBm for PSCell. Bin[113]: Number of measurement reports with RSRP in dBm range [-44..-43[ dBm for PSCell. Bin[114]: Number of measurement reports with RSRP in dBm range [-43..-42[ dBm for PSCell. Bin[115]: Number of measurement reports with RSRP in dBm range [-42..-41[ dBm for PSCell. Bin[116]: Number of measurement reports with RSRP in dBm range [-41..-40[ dBm for PSCell. Bin[117]: Number of measurement reports with RSRP in dBm range [-40..-39[ dBm for PSCell. Bin[118]: Number of measurement reports with RSRP in dBm range [-39..-38[ dBm for PSCell. Bin[119]: Number of measurement reports with RSRP in dBm range [-38..-37[ dBm for PSCell. Bin[120]: Number of measurement reports with RSRP in dBm range [-37..-36[ dBm for PSCell. Bin[121]: Number of measurement reports with RSRP in dBm range [-36..-35[ dBm for PSCell. Bin[122]: Number of measurement reports with RSRP in dBm range [-35..-34[ dBm for PSCell. Bin[123]: Number of measurement reports with RSRP in dBm range [-34..-33[ dBm for PSCell. Bin[124]: Number of measurement reports with RSRP in dBm range [-33..-32[ dBm for PSCell. Bin[125]: Number of measurement reports with RSRP in dBm range [-32..-31[ dBm for PSCell. Bin[126]: Number of measurement reports with RSRP in dBm range [-31..] dBm for PSCell. Compressed: True Deprecated: Since 24.Q3. Planned to be removed. Replaced by NRCellCU.pmUeMeasEndcSsRsrp.; MOM flags: noNotification.";
      type uint64;
      max-elements 127;
    }
    leaf pmHoPrepAttOutIntraGnbOffload {
      description "Number of NR intra-gNodeB handover preparation attempts for traffic offload in source NR cell..";
      type uint64;
      config false;
    }
    leaf pmAnrNcgiMeasRcvDrx {
      description "Number of received NCGI measurements using measurement method DRX..";
      type uint64;
      config false;
    }
    leaf-list pmDrbRelAbnormalGnb2Arp {
      description "Number of abnormal DRB releases triggered by either local or external gNodeB for each Allocation and Retention Priority (ARP) level. Compressed: True.";
      type uint64;
      max-elements 16;
    }
    leaf pmCaConfiguredSwitchedUl {
      description "Number of successful uplink TX switching configurations in serving PCell..";
      type uint64;
      config false;
    }
    leaf pmCaSCellDeconfigAtt {
      description "Number of SCell deconfiguration attempts in serving PCell, including deconfiguration of last SCell. SCell release signaling to UE uses RRC Reconfiguration and RRC Connection Release procedures..";
      type uint64;
      config false;
    }
    leaf pmEndcSetupScgUeSucc {
      description "Number of successful EN-DC SCG setups..";
      type uint64;
      config false;
    }
    leaf pmRrcConnEstabAttEm {
      description "Number of attempted RRC Connection Establishment procedures with establishmentCause emergency. See 3GPP TS 38.331, RRC Setup Request..";
      type uint64;
      config false;
    }
    leaf pmEndcRelUeAbnormalMenbScgReconfigFail {
      description "Number of abnormal EN-DC SCG radio resource releases triggered by MeNodeB with Scg-reconfigFailure SCG failure..";
      type uint64;
      config false;
    }
    leaf pmAnrNeighbRelPromoteRejNr {
      description "Number of events when NR neighbor relations are rejected to be promoted by ANR function..";
      type uint64;
      config false;
    }
    leaf pmRrcResumeRelIdle {
      description "Number of RRC Resume procedures followed by network release..";
      type uint64;
      config false;
    }
    leaf-list pmDrbRelNormalArp {
      description "Number of normal DRB releases for each Allocation and Retention Priority level. Compressed: True.";
      type uint64;
      max-elements 16;
    }
    leaf pmUeMeasNcgiFailUeCapPciHandling {
      description "Number of NCGI measurements initiated by PCI handling that cannot be requested because of insufficient UE capabilities..";
      type uint64;
      config false;
    }
    leaf pmPwsCancelRespEtws {
      description "Number of times when NGAP PWS CANCEL REQUEST message that contains ETWS notification is successfully processed in a cell. Measured for ongoing messages..";
      type uint64;
      config false;
    }
    leaf-list pmDrbRelAbnormalAmfActArp {
      description "Number of abnormal active DRB releases triggered by AMF for each Allocation and Retention Priority level. Compressed: True.";
      type uint64;
      max-elements 16;
    }
    leaf pmRrcResumeAttRnaUpdate {
      description "Number of RRC connection resume attempts with resumeCause rna-Update..";
      type uint64;
      config false;
    }
    leaf pmHoPrepRejInInterGnbMpLoad {
      description "Number of rejected Xn and NG inter-gNodeB handovers in NR SA because Baseband MP load control indicates OVERLOAD or VERY HIGH state..";
      type uint64;
      config false;
    }
    leaf pmRrcConnRedCapLevelMax {
      description "Peak number of RedCap UEs in RRC_CONNECTED mode..";
      type int64;
      config false;
    }
    leaf pmRwrEutranUeSuccTs {
      description "Number of UE Release with Redirection to E-UTRAN procedures triggered by NR Traffic Steering..";
      type uint64;
      config false;
    }
    leaf pmUeMeasEcgiRcvDrxPciHandling {
      description "Number of successfully received ECGI measurements with DRX, initiated by PCI conflict handling..";
      type uint64;
      config false;
    }
    leaf pmNrdcRelUeSnNormal {
      description "Number of normal NR-DC UE releases counted on Secondary Node side..";
      type uint64;
      config false;
    }
    leaf pmHoExeSuccOutInterGnbOffload {
      description "Number of successful outgoing NR inter-gNodeB NG or Xn handover executions for traffic offload in source NR cell..";
      type uint64;
      config false;
    }
    leaf-list pmUeCtxtLowEndDistr {
      description "Distribution of low-capability UEs by Access Stratum Release and low-capability UE type. Unit: N/A Ranges: Bin[0]: RedCap UEs Bin[1]: Access Stratum Release 15 low-capability UEs Bin[2]: Access Stratum Release 16 low-capability UEs Bin[3]: Access Stratum Release 17 low-capability UEs Bin[4]: Access Stratum Release 18 low-capability UEs.";
      type uint64;
      max-elements 5;
    }
    leaf-list pmDrbRelAbnormalGnbInact5qi {
      description "Number of abnormal DRB releases triggered by gNodeB for each 5QI for UEs in RRC_INACTIVE state. Compressed: True.";
      type uint64;
      max-elements 256;
    }
    leaf pmPwsReqSuccCmas {
      description "Number of times when NGAP WRITE-REPLACE WARNING REQUEST message that contains CMAS notification is successfully processed in a cell. Includes duplicated messages..";
      type uint64;
      config false;
    }
    leaf pmHoPrepAttOutEutranTs {
      description "Number of outgoing inter-RAT handover preparation attempts for traffic steering reason from NR to LTE in source NR cell..";
      type uint64;
      config false;
    }
    leaf pmEndcSetupFailReconfigFail {
      description "Number of EN-DC setup failures triggered by MeNodeB due to LTE reestablishment with reconfigurationFailure cause..";
      type uint64;
      config false;
    }
    leaf pmAnrEcgiMeasTriggerDrx {
      description "Number of triggered ECGI measurements with DRX in UE initiated by ANR function..";
      type uint64;
      config false;
    }
    leaf pmPwsReqSuccEtwsSecondary {
      description "Number of times when NGAP WRITE-REPLACE WARNING REQUEST message that contains ETWS secondary or primary_and_secondary notification is successfully processed in a cell. Includes duplicated messages..";
      type uint64;
      config false;
    }
    leaf pmPwsCancelRespCmas {
      description "Number of times when NGAP PWS CANCEL REQUEST message that contains CMAS notification is successfully processed in a cell. Measured for ongoing messages..";
      type uint64;
      config false;
    }
    leaf pmEndcPSCellChangeResAllocReqInterSgnb {
      description "Number of inter-SgNodeB PSCell change resource allocation requests for EN-DC in target NR cell. For definition of PSCell, see 3GPP TS 37.340..";
      type uint64;
      config false;
    }
    leaf pmPwsReqSuccEtwsPrimary {
      description "Number of times when NGAP WRITE-REPLACE WARNING REQUEST message that contains ETWS primary or primary_and_secondary notification is successfully processed in a cell. Includes duplicated messages..";
      type uint64;
      config false;
    }
    leaf-list pmHoExeSuccOutDrbEutran5qi {
      description "Number of DRBs for each 5QI at successful outgoing inter-RAT handover executions from NR to LTE in source NR cell. Compressed: True.";
      type uint64;
      max-elements 256;
    }
    leaf pmEndcUeCapabilityUlPdcpDelay {
      description "Number of UEs that support uplink delay capability for EN-DC..";
      type uint64;
      config false;
    }
    leaf pmHoPrepSuccOutEutranOffload {
      description "Number of successful outgoing inter-RAT handover preparations for traffic offload from NR to LTE in source NR cell..";
      type uint64;
      config false;
    }
    leaf pmNrdcSetupUeMnSucc {
      description "Number of successful NR-DC UE setup attempts. Counted on Master Node side..";
      type uint64;
      config false;
    }
    leaf pmRrcResumeAttRelInact {
      description "Number of RRC connection resume attempts followed by network suspension..";
      type uint64;
      config false;
    }
    leaf pmNrdcSetupUeMnAttHoIntraCell {
      description "Number of NR-DC UE setup attempts during intra-gNodeB, intra-cell handover. Counted on Master Node side..";
      type uint64;
      config false;
    }
    leaf pmEndcSetupScgUeAtt {
      description "Number of EN-DC SCG setup attempts initiated by by MeNodeB, excluding EN-DC setups performed after LTE handover if the SCG resource could be kept, and after gNB PSCell change..";
      type uint64;
      config false;
    }
    leaf pmNrdcSetupUeMnSuccHoIntraCell {
      description "Number of successful NR-DC UE setup attempts during intra-gNodeB, intra-cell handover. Counted on Master Node side..";
      type uint64;
      config false;
    }
    leaf pmAnrNeighbRelRemEutran {
      description "Number of E-UTRAN neighbor relations removed by ANR function..";
      type uint64;
      config false;
    }
    leaf pmCaConfigDelaySamp {
      description "Number of times NRCellCU.pmCaConfigDelaySum PM counter accumulates new sample..";
      type uint64;
      config false;
    }
    leaf-list pmDrbRelAbnormalAmfArp {
      description "Number of abnormal DRB releases triggered by AMF for each Allocation and Retention Priority level. Compressed: True.";
      type uint64;
      max-elements 16;
    }
    leaf pmRrcResumeSuccRnaUpdate {
      description "Number of successful RRC connection resumptions for resumeCause rna-Update..";
      type uint64;
      config false;
    }
    leaf pmX2DowntimeInterfaceSupervision {
      description "Length of time in seconds when X2 link type is unavailable in NR Cell..";
      type uint64;
      config false;
    }
    leaf pmCaSCellReselectionAttTs {
      description "Number of SCell Reselection attempts in PCell triggered by Multi-Layer Coordination or Periodic Multi-Layer Coordination. At SCell Reselection PCell remains unchanged. One or more SCell can be changed to a new frequency. One or more of current SCells can be reused at SCell Reselection..";
      type uint64;
      config false;
    }
    leaf pmSaUeCapabilityUlPdcpDelay {
      description "Number of UEs that support uplink delay capability for NR SA..";
      type uint64;
      config false;
    }
    leaf pmEndcRelUeNormal {
      description "Number of normal EN-DC SCG radio resource releases..";
      type uint64;
      config false;
    }
    leaf pmNrdcSetupUeMnSuccHoInterGnb {
      description "Number of successful NR-DC UE setup attempts during inter-gNodeB handover. Counted on Master Node side..";
      type uint64;
      config false;
    }
    leaf pmEndcRelUeAbnormalMenbActT310Expiry {
      description "Number of abnormal EN-DC SCG radio resource releases triggered by MeNodeB with T310-Expiry SCG failure. UE is considered in session at time of release..";
      type uint64;
      config false;
    }
    leaf pmUeCtxtEstabAtt {
      description "Number of UE context establishment attempts..";
      type uint64;
      config false;
    }
    leaf pmEndcRejCellBarred {
      description "Number of rejected ENDC setups including cases triggered by LTE handover without PSCell change and by PSCell change, and SCG setups because of barred cell. Deprecated: Since 24.Q3. Planned to be removed. Replaced by NRCellCU.pmEndcSetupUeRejCellInvalid.; MOM flags: noNotification.";
      type uint64;
      config false;
      status deprecated;
    }
    leaf pmRwrEutranUeNonPerfEpsfbEm {
      description "Number of times Release with Redirect procedure triggered by EPS fallback for emergency call cannot be performed..";
      type uint64;
      config false;
    }
    leaf pmEndcPSCellChangeSuccIntraSgnbIntraF {
      description "Number of successful intra-SgNodeB intra-frequency PSCell changes for EN-DC in source NR cell. See 3GPP TS 37.340 for definition of PSCell..";
      type uint64;
      config false;
    }
    leaf pmEndcRelUeNormalUeAssisted {
      description "Number of special EN-DC SCG radio resource releases triggered by MeNodeB with custom signature..";
      type uint64;
      config false;
    }
    leaf pmEndcRelUeAbnormalMenbT310Expiry {
      description "Number of abnormal EN-DC SCG radio resource releases triggered by MeNodeB with T310-Expiry SCG failure..";
      type uint64;
      config false;
    }
    leaf pmNrdcRelRelocUeMnSucc {
      description "Number of successful attempts to release NR-DC with relocation of PDCP from source Secondary Node to target Master Node or target Secondary Node. Counted on source Master Node side. Release is initiated by source Master Node or source Secondary Node. Source and target Node might be same, depending on use case..";
      type uint64;
      config false;
    }
    leaf pmRrcInactRedCapLevelMax {
      description "Maximum number of RedCap UEs in RRC_INACTIVE mode in NR cell CU..";
      type int64;
      config false;
    }
    leaf pmEndcRelUeAbnormalMenbActSyncReconfigFail {
      description "Number of abnormal EN-DC SCG radio resource releases triggered by MeNodeB with synchRecofigFailure-SCG SCG failure. UE is considered in session at time of release..";
      type uint64;
      config false;
    }
    leaf pmRrcInactRedCapLevelSum {
      description "Sum of all sample values recorded for number of RedCap UEs in RRC_INACTIVE mode in NR cell CU..";
      type uint64;
      config false;
    }
    leaf pmHoExeAttOutIntraGnbPciHandling {
      description "Number of outgoing NR intra-gNodeB handover execution attempts in source NR cell triggered by PCI conflict handling..";
      type uint64;
      config false;
    }
    leaf pmSaUeCapabilityGnssLocation {
      description "Number of UEs that support GNSS location capability for NR SA..";
      type uint64;
      config false;
    }
    leaf pmCaSCellDeconfigAttUl {
      description "Number of uplink SCell deconfiguration attempts in serving PCell, including deconfiguration of last SCell with both uplink and downlink aspects. SCell release signaling to UE uses RRC Reconfiguration and RRC Connection Release procedures..";
      type uint64;
      config false;
    }
    leaf pmUeCapabilityRefresh {
      description "Number of initialized RRC UE Capability Refresh procedures. Deprecated: Since 24.Q4. Planned to be removed.; MOM flags: noNotification.";
      type uint64;
      config false;
      status deprecated;
    }
    leaf pmNrdcPSCellChangeMnSuccInterSgnb {
      description "Number of successful NR-DC inter-SgNodeB PSCell Changes counted on Master Node side..";
      type uint64;
      config false;
    }
    leaf pmNrdcPSCellChangeSnAttInterSgnb {
      description "Number of outgoing NR-DC inter-SgNodeB PSCell Change Attempts on Secondary Node side..";
      type uint64;
      config false;
    }
    leaf pmCellBoosterCarrSleep {
      description "Number of times a decision is made to put corresponding cell to sleep because of traffic load. For more information, see NR Booster Carrier Sleep in CPI library..";
      type uint64;
      config false;
    }
    leaf pmRwrEutranUeSuccEpsfb {
      description "Number of UE Release with Redirection to E-UTRAN procedures triggered by EPS fallback..";
      type uint64;
      config false;
    }
    leaf pmHoExeAttOutInterGnb {
      description "Number of outgoing NR inter-gNodeB NG or Xn handover execution attempts in source NR cell..";
      type uint64;
      config false;
    }
    leaf pmEndcPSCellChangeAttInterSgnb {
      description "Number of inter-SgNodeB PSCell change attempts for EN-DC in source NR cell that are not interrupted by MeNodeB initiated procedure, for example, MN mobility. For definition of PSCell, see 3GPP TS 37.340..";
      type uint64;
      config false;
    }
    leaf pmPduSessionRelNormal {
      description "Number of PDU sessions released when cause is considered normal for each cell..";
      type uint64;
      config false;
    }
    leaf pmPwsReqAttEtwsPrimary {
      description "Number of NGAP WRITE-REPLACE WARNING REQUEST messages that contain ETWS primary or primary_and_secondary notification received in a cell. Includes duplicated messages..";
      type uint64;
      config false;
    }
    leaf pmPwsReqAttCmas {
      description "Number of NGAP WRITE-REPLACE WARNING REQUEST messages that contain CMAS notification received in a cell. Includes duplicated messages..";
      type uint64;
      config false;
    }
    leaf pmEndcCaConfigAtt {
      description "Number of SCell configuration attempts in serving PSCell, including configuration of first SCell..";
      type uint64;
      config false;
    }
    leaf-list pmDrbResumeAtt5qi {
      description "Number of DRB resume attempts for each 5QI. Compressed: True.";
      type uint64;
      max-elements 256;
    }
    leaf pmUeCtxtRelAbnormalAmf {
      description "Number of abnormal NR SA UE Context Release procedures initiated by AMF..";
      type uint64;
      config false;
    }
    leaf pmNgSigConnEstabSuccEm {
      description "Number of successful NG signaling connection establishments for connections with Emergency RRC establishment cause..";
      type uint64;
      config false;
    }
    leaf pmEndcRelUeAbnormalMenb {
      description "Number of abnormal EN-DC SCG radio resource releases triggered by MeNodeB..";
      type uint64;
      config false;
    }
    leaf pmHoExeSuccOutInterGnbTs {
      description "Number of successful outgoing NR inter-gNodeB NG or Xn handover executions in source NR cell because of traffic steering..";
      type uint64;
      config false;
    }
    leaf-list pmUeMeasSaSsRsrp {
      description "Distribution of SS-RSRP received by gNodeB from UEs in cell. Periodic UE measurement reports for all or a subset of UEs must be triggered by gNodeB in measured NR cell. See 3GPP TS 38.133, RSRP Measurement Report Mapping. Unit: N/A Ranges: Bin[0]: Number of measurement reports with RSRP in dBm range [..-156[ dBm for PCell. Bin[1]: Number of measurement reports with RSRP in dBm range [-156..-155[ dBm for PCell. Bin[2]: Number of measurement reports with RSRP in dBm range [-155..-154[ dBm for PCell. Bin[3]: Number of measurement reports with RSRP in dBm range [-154..-153[ dBm for PCell. Bin[4]: Number of measurement reports with RSRP in dBm range [-153..-152[ dBm for PCell. Bin[5]: Number of measurement reports with RSRP in dBm range [-152..-151[ dBm for PCell. Bin[6]: Number of measurement reports with RSRP in dBm range [-151..-150[ dBm for PCell. Bin[7]: Number of measurement reports with RSRP in dBm range [-150..-149[ dBm for PCell. Bin[8]: Number of measurement reports with RSRP in dBm range [-149..-148[ dBm for PCell. Bin[9]: Number of measurement reports with RSRP in dBm range [-148..-147[ dBm for PCell. Bin[10]: Number of measurement reports with RSRP in dBm range [-147..-146[ dBm for PCell. Bin[11]: Number of measurement reports with RSRP in dBm range [-146..-145[ dBm for PCell. Bin[12]: Number of measurement reports with RSRP in dBm range [-145..-144[ dBm for PCell. Bin[13]: Number of measurement reports with RSRP in dBm range [-144..-143[ dBm for PCell. Bin[14]: Number of measurement reports with RSRP in dBm range [-143..-152[ dBm for PCell. Bin[15]: Number of measurement reports with RSRP in dBm range [-142..-141[ dBm for PCell. Bin[16]: Number of measurement reports with RSRP in dBm range [-141..-140[ dBm for PCell. Bin[17]: Number of measurement reports with RSRP in dBm range [-140..-139[ dBm for PCell. Bin[18]: Number of measurement reports with RSRP in dBm range [-139..-138[ dBm for PCell. Bin[19]: Number of measurement reports with RSRP in dBm range [-138..-137[ dBm for PCell. Bin[20]: Number of measurement reports with RSRP in dBm range [-137..-136[ dBm for PCell. Bin[21]: Number of measurement reports with RSRP in dBm range [-136..-135[ dBm for PCell. Bin[22]: Number of measurement reports with RSRP in dBm range [-135..-134[ dBm for PCell. Bin[23]: Number of measurement reports with RSRP in dBm range [-134..-133[ dBm for PCell. Bin[24]: Number of measurement reports with RSRP in dBm range [-133..-132[ dBm for PCell. Bin[25]: Number of measurement reports with RSRP in dBm range [-132..-131[ dBm for PCell. Bin[26]: Number of measurement reports with RSRP in dBm range [-131..-130[ dBm for PCell. Bin[27]: Number of measurement reports with RSRP in dBm range [-130..-129[ dBm for PCell. Bin[28]: Number of measurement reports with RSRP in dBm range [-129..-128[ dBm for PCell. Bin[29]: Number of measurement reports with RSRP in dBm range [-128..-127[ dBm for PCell. Bin[30]: Number of measurement reports with RSRP in dBm range [-127..-126[ dBm for PCell. Bin[31]: Number of measurement reports with RSRP in dBm range [-126..-125[ dBm for PCell. Bin[32]: Number of measurement reports with RSRP in dBm range [-125..-124[ dBm for PCell. Bin[33]: Number of measurement reports with RSRP in dBm range [-124..-123[ dBm for PCell. Bin[34]: Number of measurement reports with RSRP in dBm range [-123..-122[ dBm for PCell. Bin[35]: Number of measurement reports with RSRP in dBm range [-122..-121[ dBm for PCell. Bin[36]: Number of measurement reports with RSRP in dBm range [-121..-120[ dBm for PCell. Bin[37]: Number of measurement reports with RSRP in dBm range [-120..-119[ dBm for PCell. Bin[38]: Number of measurement reports with RSRP in dBm range [-119..-118[ dBm for PCell. Bin[39]: Number of measurement reports with RSRP in dBm range [-118..-117[ dBm for PCell. Bin[40]: Number of measurement reports with RSRP in dBm range [-117..-116[ dBm for PCell. Bin[41]: Number of measurement reports with RSRP in dBm range [-116..-115[ dBm for PCell. Bin[42]: Number of measurement reports with RSRP in dBm range [-115..-114[ dBm for PCell. Bin[43]: Number of measurement reports with RSRP in dBm range [-114..-113[ dBm for PCell. Bin[44]: Number of measurement reports with RSRP in dBm range [-113..-112[ dBm for PCell. Bin[45]: Number of measurement reports with RSRP in dBm range [-112..-111[ dBm for PCell. Bin[46]: Number of measurement reports with RSRP in dBm range [-111..-110[ dBm for PCell. Bin[47]: Number of measurement reports with RSRP in dBm range [-110..-109[ dBm for PCell. Bin[48]: Number of measurement reports with RSRP in dBm range [-109..-108[ dBm for PCell. Bin[49]: Number of measurement reports with RSRP in dBm range [-108..-107[ dBm for PCell. Bin[50]: Number of measurement reports with RSRP in dBm range [-107..-106[ dBm for PCell. Bin[51]: Number of measurement reports with RSRP in dBm range [-106..-105[ dBm for PCell. Bin[52]: Number of measurement reports with RSRP in dBm range [-105..-104[ dBm for PCell. Bin[53]: Number of measurement reports with RSRP in dBm range [-104..-103[ dBm for PCell. Bin[54]: Number of measurement reports with RSRP in dBm range [-103..-102[ dBm for PCell. Bin[55]: Number of measurement reports with RSRP in dBm range [-102..-101[ dBm for PCell. Bin[56]: Number of measurement reports with RSRP in dBm range [-101..-100[ dBm for PCell. Bin[57]: Number of measurement reports with RSRP in dBm range [-100..-99[ dBm for PCell. Bin[58]: Number of measurement reports with RSRP in dBm range [-99..-98[ dBm for PCell. Bin[59]: Number of measurement reports with RSRP in dBm range [-98..-97[ dBm for PCell. Bin[60]: Number of measurement reports with RSRP in dBm range [-97..-96[ dBm for PCell. Bin[61]: Number of measurement reports with RSRP in dBm range [-96..-95[ dBm for PCell. Bin[62]: Number of measurement reports with RSRP in dBm range [-95..-94[ dBm for PCell. Bin[63]: Number of measurement reports with RSRP in dBm range [-94..-93[ dBm for PCell. Bin[64]: Number of measurement reports with RSRP in dBm range [-93..-92[ dBm for PCell. Bin[65]: Number of measurement reports with RSRP in dBm range [-92..-91[ dBm for PCell. Bin[66]: Number of measurement reports with RSRP in dBm range [-91..-90[ dBm for PCell. Bin[67]: Number of measurement reports with RSRP in dBm range [-90..-89[ dBm for PCell. Bin[68]: Number of measurement reports with RSRP in dBm range [-89..-88[ dBm for PCell. Bin[69]: Number of measurement reports with RSRP in dBm range [-88..-87[ dBm for PCell. Bin[70]: Number of measurement reports with RSRP in dBm range [-87..-86[ dBm for PCell. Bin[71]: Number of measurement reports with RSRP in dBm range [-86..-85[ dBm for PCell. Bin[72]: Number of measurement reports with RSRP in dBm range [-85..-84[ dBm for PCell. Bin[73]: Number of measurement reports with RSRP in dBm range [-84..-83[ dBm for PCell. Bin[74]: Number of measurement reports with RSRP in dBm range [-83..-82[ dBm for PCell. Bin[75]: Number of measurement reports with RSRP in dBm range [-82..-81[ dBm for PCell. Bin[76]: Number of measurement reports with RSRP in dBm range [-81..-80[ dBm for PCell. Bin[77]: Number of measurement reports with RSRP in dBm range [-80..-79[ dBm for PCell. Bin[78]: Number of measurement reports with RSRP in dBm range [-79..-78[ dBm for PCell. Bin[79]: Number of measurement reports with RSRP in dBm range [-78..-77[ dBm for PCell. Bin[80]: Number of measurement reports with RSRP in dBm range [-77..-76[ dBm for PCell. Bin[81]: Number of measurement reports with RSRP in dBm range [-76..-75[ dBm for PCell. Bin[82]: Number of measurement reports with RSRP in dBm range [-75..-74[ dBm for PCell. Bin[83]: Number of measurement reports with RSRP in dBm range [-74..-73[ dBm for PCell. Bin[84]: Number of measurement reports with RSRP in dBm range [-73..-72[ dBm for PCell. Bin[85]: Number of measurement reports with RSRP in dBm range [-72..-71[ dBm for PCell. Bin[86]: Number of measurement reports with RSRP in dBm range [-71..-70[ dBm for PCell. Bin[87]: Number of measurement reports with RSRP in dBm range [-70..-69[ dBm for PCell. Bin[88]: Number of measurement reports with RSRP in dBm range [-69..-68[ dBm for PCell. Bin[89]: Number of measurement reports with RSRP in dBm range [-68..-67[ dBm for PCell. Bin[90]: Number of measurement reports with RSRP in dBm range [-67..-66[ dBm for PCell. Bin[91]: Number of measurement reports with RSRP in dBm range [-66..-65[ dBm for PCell. Bin[92]: Number of measurement reports with RSRP in dBm range [-65..-64[ dBm for PCell. Bin[93]: Number of measurement reports with RSRP in dBm range [-64..-63[ dBm for PCell. Bin[94]: Number of measurement reports with RSRP in dBm range [-63..-62[ dBm for PCell. Bin[95]: Number of measurement reports with RSRP in dBm range [-62..-61[ dBm for PCell. Bin[96]: Number of measurement reports with RSRP in dBm range [-61..-60[ dBm for PCell. Bin[97]: Number of measurement reports with RSRP in dBm range [-60..-59[ dBm for PCell. Bin[98]: Number of measurement reports with RSRP in dBm range [-59..-58[ dBm for PCell. Bin[99]: Number of measurement reports with RSRP in dBm range [-58..-57[ dBm for PCell. Bin[100]: Number of measurement reports with RSRP in dBm range [-57..-56[ dBm for PCell. Bin[101]: Number of measurement reports with RSRP in dBm range [-56..-55[ dBm for PCell. Bin[102]: Number of measurement reports with RSRP in dBm range [-55..-54[ dBm for PCell. Bin[103]: Number of measurement reports with RSRP in dBm range [-54..-53[ dBm for PCell. Bin[104]: Number of measurement reports with RSRP in dBm range [-53..-52[ dBm for PCell. Bin[105]: Number of measurement reports with RSRP in dBm range [-52..-51[ dBm for PCell. Bin[106]: Number of measurement reports with RSRP in dBm range [-51..-50[ dBm for PCell. Bin[107]: Number of measurement reports with RSRP in dBm range [-50..-49[ dBm for PCell. Bin[108]: Number of measurement reports with RSRP in dBm range [-49..-48[ dBm for PCell. Bin[109]: Number of measurement reports with RSRP in dBm range [-48..-47[ dBm for PCell. Bin[110]: Number of measurement reports with RSRP in dBm range [-47..-46[ dBm for PCell. Bin[111]: Number of measurement reports with RSRP in dBm range [-46..-45[ dBm for PCell. Bin[112]: Number of measurement reports with RSRP in dBm range [-45..-44[ dBm for PCell. Bin[113]: Number of measurement reports with RSRP in dBm range [-44..-43[ dBm for PCell. Bin[114]: Number of measurement reports with RSRP in dBm range [-43..-42[ dBm for PCell. Bin[115]: Number of measurement reports with RSRP in dBm range [-42..-41[ dBm for PCell. Bin[116]: Number of measurement reports with RSRP in dBm range [-41..-40[ dBm for PCell. Bin[117]: Number of measurement reports with RSRP in dBm range [-40..-39[ dBm for PCell. Bin[118]: Number of measurement reports with RSRP in dBm range [-39..-38[ dBm for PCell. Bin[119]: Number of measurement reports with RSRP in dBm range [-38..-37[ dBm for PCell. Bin[120]: Number of measurement reports with RSRP in dBm range [-37..-36[ dBm for PCell. Bin[121]: Number of measurement reports with RSRP in dBm range [-36..-35[ dBm for PCell. Bin[122]: Number of measurement reports with RSRP in dBm range [-35..-34[ dBm for PCell. Bin[123]: Number of measurement reports with RSRP in dBm range [-34..-33[ dBm for PCell. Bin[124]: Number of measurement reports with RSRP in dBm range [-33..-32[ dBm for PCell. Bin[125]: Number of measurement reports with RSRP in dBm range [-32..-31[ dBm for PCell. Bin[126]: Number of measurement reports with RSRP in dBm range [-31..] dBm for PCell. Compressed: True.";
      type uint64;
      max-elements 127;
    }
    leaf pmNrdcSetupUeMnSuccHoInterGnbPSCellKeep {
      description "Number of successful NR-DC UE setup attempts keeping PSCell during inter-gNodeB handover. Counted on Master Node side..";
      type uint64;
      config false;
    }
    leaf pmHoExeAttOutIntraGnbOffload {
      description "Number of NR intra-gNodeB handover execution attempts for traffic offload in source NR cell..";
      type uint64;
      config false;
    }
    leaf-list pmCellBoosterCarrSleepReadyNoSchedDistr {
      description "Number of times booster cell can and cannot be put to sleep while outside configured sleep scheduling window. For more information See NR Booster Carrier Sleep FED. Unit: N/A Bin[0]: Sleep condition not fulfilled Bin[1]: Sleep condition fulfilled.";
      type uint64;
      max-elements 2;
    }
    leaf pmAnrNcgiMeasTriggerDrx {
      description "Number of triggered NCGI measurements with DRX in UE initiated by ANR function or ACA..";
      type uint64;
      config false;
    }
    leaf pmNrdcSetupUeMnSuccInit {
      description "Number of successful NR-DC UE initial setup attempts. Counted on Master Node side..";
      type uint64;
      config false;
    }
    leaf pmHoExeAttOutEutranOffload {
      description "Number of outgoing inter-RAT handover execution attempts for traffic offload from NR to LTE in source NR cell..";
      type uint64;
      config false;
    }
    leaf pmAnrNeighbRelRemNr {
      description "Number of NR neighbor relations removed by ANR function..";
      type uint64;
      config false;
    }
    leaf pmRwrEutranUeSuccRi {
      description "Number of UE Release with Redirection to E-UTRAN procedures triggered by remote interference..";
      type uint64;
      config false;
    }
    leaf pmHoPrepSuccOutInterGnbOffload {
      description "Number of successful outgoing NR inter-gNodeB NG or Xn handover preparations for traffic offload in source NR cell..";
      type uint64;
      config false;
    }
    leaf pmHoPrepFailInEutranRi {
      description "Number of failed incoming inter-RAT inter-system handovers from E-UTRAN because of NR remote interference..";
      type uint64;
      config false;
    }
    leaf-list pmDrbEstabSuccInit5qi {
      description "Number of successful initial DRB establishments for each 5QI. Compressed: True.";
      type uint64;
      max-elements 256;
    }
    leaf pmPwsReqAttEtwsSecondary {
      description "Number of NGAP WRITE-REPLACE WARNING REQUEST messages that contain ETWS secondary or primary_and_secondary notification received in a cell. Includes duplicated messages..";
      type uint64;
      config false;
    }
    leaf pmAnrEcgiMeasFailUeCap {
      description "Number of ECGI measurements for ANR that cannot be requested because of insufficient UE capabilities..";
      type uint64;
      config false;
    }
    leaf-list pmDrbResumeAttArp {
      description "Number of DRB resume attempts for each ARP level. Compressed: True.";
      type uint64;
      max-elements 16;
    }
    leaf pmCaDeconfiguredSwitchedUl {
      description "Number of successful uplink TX switching deconfigurations in serving PCell..";
      type uint64;
      config false;
    }
    leaf pmEndcSgnbAdditionRequestMdtConsent {
      description "Number of times MDT is allowed in addition requests for EN-DC secondary gNodeB..";
      type uint64;
      config false;
    }
    leaf pmHoExeAttOutEutran {
      description "Number of outgoing inter-RAT handover execution attempts from NR to LTE in source NR cell..";
      type uint64;
      config false;
    }
    leaf pmCaSCellConfigSucc {
      description "Number of successful SCell configurations in serving PCell, including configuration of first SCell..";
      type uint64;
      config false;
    }
    leaf pmPduSessionModifyAtt {
      description "Number of attempted PDU session modifications..";
      type uint64;
      config false;
    }
    leaf pmRrcResumeAttFallbackRnaUpdate {
      description "Number of RRC connection resume attempts with resumeCause rna-Update with fallback to RRC Connection Establishment procedure..";
      type uint64;
      config false;
    }
    leaf pmNrdcSetupUeMnAttInit {
      description "Number of NR-DC UE initial setup attempts. Counted on Master Node side..";
      type uint64;
      config false;
    }
    leaf-list pmDrbEstabAtt5qi {
      description "Number of DRB establishment attempts for each 5QI. Compressed: True.";
      type uint64;
      max-elements 256;
    }
    leaf pmRrcResumeAtt {
      description "Number of RRC connection resume attempts..";
      type uint64;
      config false;
    }
    leaf pmHoPrepFailOutInterGnbTargetPoorUl {
      description "Number of NR inter-gNodeB handover preparation attempts in source NR cell that fail because of poor uplink quality in target NR cell..";
      type uint64;
      config false;
    }
    leaf pmHoPrepAttOutIntraGnbIntraF {
      description "Number of NR intra-frequency intra-gNodeB handover preparation attempts in source NR cell..";
      type uint64;
      config false;
    }
    leaf-list pmCaConfigDlSumSaDistr {
      description "Sum of UEs using this cell as PCell with configured downlink (DL) SCells for NR SA UEs. For NR-DC, NR SA UEs on Master Node side configured with NR-DC are included. Ranges: Bin[0]: Number of NR SA UEs configured with one PCell only and no SCell. Bin[1]: Number of NR SA UEs configured with one PCell and one SCell. Bin[2]: Number of NR SA UEs configured with one PCell and two SCells. ... Bin[31]: Number of NR SA UEs configured with one PCell and thirty-one SCells. Compressed: True.";
      type uint64;
      max-elements 32;
    }
    leaf pmNgSigConnEstabAttMos {
      description "Number of attempts to establish NG signaling connection for connections with RRC establishmentCause mo-Signalling. Attempt is triggered by receiving first message from AMF. See 3GPP TS 38.331, RRC Setup Request..";
      type uint64;
      config false;
    }
    leaf pmUeCtxtSuspend {
      description "Number of suspended UE contexts..";
      type uint64;
      config false;
    }
    leaf-list pmHoExeSuccOutDrbInterGnb5qi {
      description "Number of DRBs for each 5QI at successful outgoing inter-gNodeB handover executions in source NR cell. Compressed: True.";
      type uint64;
      max-elements 256;
    }
    leaf pmRwrIntraNrUeSuccCoverage {
      description "Number of UE RwR procedure to another NR frequency triggered by poor coverage on current NR frequency..";
      type uint64;
      config false;
    }
    leaf pmHoExeAttOutInterGnbTs {
      description "Number of outgoing NR inter-gNodeB NG or Xn handover execution attempts in source NR cell because of traffic steering..";
      type uint64;
      config false;
    }
    leaf pmHoExeSuccOutIntraGnb {
      description "Number of successful NR intra-gNodeB handover executions in source NR cell..";
      type uint64;
      config false;
    }
    leaf pmRwrEutranUeSuccNrCoverage {
      description "Number of UE Release with Redirection to E-UTRAN procedures triggered by poor coverage in NR..";
      type uint64;
      config false;
    }
    leaf pmNrdcUeMeasurementReport {
      description "Sum of all UE measurement reports for NR-DC..";
      type uint64;
      config false;
    }
    leaf pmHoPrepAttOutEutranPciHandling {
      description "Number of outgoing inter-RAT handover preparation attempts from NR to LTE in source NR cell triggered by PCI conflict handling..";
      type uint64;
      config false;
    }
    leaf pmHoPrepFailInIntraGnbRi {
      description "Number of incoming NR intra-gNodeB handover preparation attempts that fail in target NR cell because of NR remote interference. Deprecated: Since 23.Q4. Planned to be removed.; MOM flags: noNotification.";
      type uint64;
      config false;
      status deprecated;
    }
    leaf pmUeMeasEcgiFailUeCapPciHandling {
      description "Number of ECGI measurements initiated by PCI handling that cannot be requested because of insufficient UE capabilities..";
      type uint64;
      config false;
    }
    leaf pmRrcInactLevelSamp {
      description "Number of times pmRrcInactLevelSum counter accumulates new sample..";
      type uint64;
      config false;
    }
    leaf pmRwrEutranUeSuccEpsfbEmFbInd {
      description "Number of successful Release with Redirect procedures triggered by EPS fallback for emergency calls for UE contexts for each cell because of Emergency Fallback Indicator IE..";
      type uint64;
      config false;
    }
    leaf pmHoPrepAttOutInterGnbOffload {
      description "Number of outgoing NR inter-gNodeB NG or Xn handover preparation attempts for traffic offload in source NR cell..";
      type uint64;
      config false;
    }
    leaf pmHoExeSuccOutInterGnbIntraF {
      description "Number of successful outgoing NR intra-frequency inter-gNodeB NG or Xn handover executions in source NR cell..";
      type uint64;
      config false;
    }
    leaf pmRrcInitAccessRejUeAdmission {
      description "Number of RRCSetupRequest, RRCResumeRequest, and RRCReestablishmentRequest messages not permitted because of admission control. Deprecated: Since 23.Q4. Planned to be removed. Replaced by NRCellCU::pmRrcInitAccessRejUeCapacityLimit.; MOM flags: noNotification.";
      type uint64;
      config false;
      status deprecated;
    }
    leaf-list pmDrbRelAbnormalAmfInact5qi {
      description "Number of abnormal DRB releases triggered by AMF for each 5QI for UEs in RRC_INACTIVE state. Compressed: True.";
      type uint64;
      max-elements 256;
    }
    leaf pmRrcInactLevelSum {
      description "Sum of all sample values recorded for number of UEs in RRC_INACTIVE mode in NR cell CU..";
      type uint64;
      config false;
    }
    leaf pmHoPrepSuccOutIntraGnbPciHandling {
      description "Number of successful outgoing NR intra-gNodeB handover preparations in source NR cell triggered by PCI conflict handling..";
      type uint64;
      config false;
    }
    leaf pmEndcCaDeconfigAtt {
      description "Number of SCell deconfiguration attempts in serving PSCell, including deconfiguration of last SCell..";
      type uint64;
      config false;
    }
    leaf pmNrdcSetupUeSnAtt {
      description "Number of NR-DC UE setup attempts. Counted on Secondary Node side..";
      type uint64;
      config false;
    }
    leaf pmHoPrepSuccOutInterGnbIntraF {
      description "Number of successful outgoing NR intra-frequency inter-gNodeB NG or Xn handover preparations in source NR cell..";
      type uint64;
      config false;
    }
    leaf pmHoPrepFailInInterGnbRi {
      description "Number of incoming NR inter-gNodeB NG or Xn handover preparation attempts that fail in target NR cell because of NR remote interference..";
      type uint64;
      config false;
    }
    leaf-list pmRruCompAvailCapacityDlDistr2 {
      description "Distribution of composite available capacity in downlink in NR cell. Number of reports with load in percentage range is counted in respective bin. Unit: N/A Ranges: Bin[0]: [0.0..2.5] % Bin[1]: ]2.5..5.0] % Bin[2]: ]5.0..7.5] % Bin[3]: ]7.5..10.0] % Bin[4]: ]10.0..12.5] % Bin[5]: ]12.5..15.0] % Bin[6]: ]15.0..17.5] % Bin[7]: ]17.5..20.0] % Bin[8]: ]20.0..22.5] % Bin[9]: ]22.5..25.0] % Bin[10]: ]25.0..27.5] % Bin[11]: ]27.5..30.0] % Bin[12]: ]30.0..32.5] % Bin[13]: ]32.5..35.0] % Bin[14]: ]35.0..37.5] % Bin[15]: ]37.5..40.0] % Bin[16]: ]40.0..42.5] % Bin[17]: ]42.5..45.0] % Bin[18]: ]45.0..47.5] % Bin[19]: ]47.5..50.0] % Bin[20]: ]50.0..52.5] % Bin[21]: ]52.5..55.0] % Bin[22]: ]55.0..57.5] % Bin[23]: ]57.5..60.0] % Bin[24]: ]60.0..62.5] % Bin[25]: ]62.5..65.0] % Bin[26]: ]65.0..67.5] % Bin[27]: ]67.5..70.0] % Bin[28]: ]70.0..72.5] % Bin[29]: ]72.5..75.0] % Bin[30]: ]75.0..77.5] % Bin[31]: ]77.5..80.0] % Bin[32]: ]80.0..82.5] % Bin[33]: ]82.5..85.0] % Bin[34]: ]85.0..87.5] % Bin[35]: ]87.5..90.0] % Bin[36]: ]90.0..92.5] % Bin[37]: ]92.5..95.0] % Bin[38]: ]95.0..97.5] % Bin[39]: ]97.5..100.0] % Bin[40]: Number of reports without load information for cell..";
      type uint64;
      max-elements 41;
    }
    leaf-list pmDrbRelAbnormalGnbActArp {
      description "Number of abnormal active DRB releases triggered by either local or external gNodeB for each Allocation and Retention Priority level. Compressed: True Deprecated: Since 24.Q4. Planned to be removed. Replaced by NRCellCU::pmDrbRelAbnormalGnbAct2Arp; MOM flags: noNotification.";
      type uint64;
      max-elements 16;
    }
    leaf pmHoExeSuccOutEutranTs {
      description "Number of successful outgoing inter-RAT handovers for traffic steering reasons from NR to LTE in source NR cell..";
      type uint64;
      config false;
    }
    leaf pmNrdcSetupUeMnSuccHoIntraGnb {
      description "Number of successful NR-DC UE setup attempts during intra-gNodeB handover. Counted on Master Node side..";
      type uint64;
      config false;
    }
    leaf-list pmDrbResumeSucc5qi {
      description "Number of successful DRB resumes for each 5QI. Compressed: True.";
      type uint64;
      max-elements 256;
    }
    leaf pmCaConfigAttUl {
      description "Number of uplink SCell configuration attempts in serving PCell, including configuration of first SCell with both uplink and downlink aspects. Deprecated: Since 25.Q2. Planned to be removed. Replaced by NRCellCU::pmCaSCellConfigAttUl.; MOM flags: noNotification.";
      type uint64;
      config false;
      status deprecated;
    }
    leaf pmPwsCancelReqCmas {
      description "Number of NGAP PWS CANCEL REQUEST messages that contain CMAS notification received in each cell. Includes duplicated messages..";
      type uint64;
      config false;
    }
    leaf pmEndcPSCellChangeResAllocSuccInterSgnb {
      description "Number of successful inter-SgNodeB PSCell change resource allocations for EN-DC in target NR cell. For definition of PSCell, see 3GPP TS 37.340..";
      type uint64;
      config false;
    }
    leaf pmUeCtxtRelNormalInact {
      description "Number of NR SA UE Context Release procedures for UEs in RRC_INACTIVE state when cause is considered normal..";
      type uint64;
      config false;
    }
    leaf-list pmDrbRelAbnormalGnb25qi {
      description "Number of abnormal DRB releases triggered by either local or external gNodeB for each 5QI. Compressed: True.";
      type uint64;
      max-elements 256;
    }
    leaf pmHoPrepRejInIntraGnbBbIntens {
      description "Number of failed incoming intra-gNodeB handovers in NR SA because of connection intensity control..";
      type uint64;
      config false;
    }
    leaf pmPduSessionModifySucc {
      description "Number of successfully modified PDU sessions..";
      type uint64;
      config false;
    }
    leaf pmNrdcSetupUeMnAttInitBufDl {
      description "Number of NR-DC UE initial setup attempts after high buffer is detected in downlink. Counted on Master Node side..";
      type uint64;
      config false;
    }
    leaf pmRrcConnReestFallbackAtt {
      description "Number of attempted RRC Connection Reestablishment procedures with fallback to RRC Connection Establishment. See 3GPP TS 38.331, RRC Reestablishment Request..";
      type uint64;
      config false;
    }
    leaf pmRrcConnEstabAttMos {
      description "Number of attempted RRC Connection Establishment procedures with establishmentCause mo-Signalling. See 3GPP TS 38.331, RRC Setup Request..";
      type uint64;
      config false;
    }
    leaf pmPduSessionEstabAttIntgProt64kbps {
      description "Number of PDU sessions that require integrity protection of user plane while UE only supports a maximum-integrity-protected data rate of 64 kbps..";
      type uint64;
      config false;
    }
    leaf pmNrdcSetupUeMnAtt {
      description "Number of NR-DC UE setup attempts. Counted on Master Node side..";
      type uint64;
      config false;
    }
    leaf pmUeCtxtRelNormal {
      description "Number of NR SA UE Context Release procedures when cause is considered normal..";
      type uint64;
      config false;
    }
    leaf pmCaConfigDlSamp {
      description "Number of times corresponding pmCaConfigDlSumEndcDistr, pmCaConfigDlSumSaDistr and pmCaConfigDlSumNrdcDistr counters accumulate new sample..";
      type uint64;
      config false;
    }
    leaf pmHoExeSuccOutIntraGnbPciHandling {
      description "Number of successful outgoing NR intra-gNodeB handover executions in source NR cell triggered by PCI conflict handling..";
      type uint64;
      config false;
    }
    leaf pmNrdcSetupUeMnAttHoInterGnb {
      description "Number of NR-DC UE setup attempts during inter-gNodeB handover. Counted on Master Node side..";
      type uint64;
      config false;
    }
    leaf pmPduSessionLevelSamp {
      description "Number of times pmPduSessionLevelSum accumulates new sample..";
      type uint64;
      config false;
    }
    leaf pmCaConfigSuccUl {
      description "Number of successful uplink SCell configurations in serving PCell, including configuration of first SCell with both uplink and downlink aspects. Deprecated: Since 25.Q2. Planned to be removed. Replaced by NRCellCU::pmCaSCellConfigSuccUl.; MOM flags: noNotification.";
      type uint64;
      config false;
      status deprecated;
    }
    leaf pmHoExeAttOutEutranPciHandling {
      description "Number of outgoing inter-RAT handover execution attempts from NR to LTE in source NR cell triggered by PCI conflict handling..";
      type uint64;
      config false;
    }
    leaf pmRrcConnLevelMaxEnDc {
      description "Peak number of NR EN-DC UEs in RRC_CONNECTED mode in NR cell..";
      type int64;
      config false;
    }
    leaf pmPduSessionLevelSum {
      description "Sum of all sample values recorded for number of PDU Sessions for UEs in RRC Connected mode..";
      type uint64;
      config false;
    }
    leaf pmCaSCellConfigSuccUl {
      description "Number of successful uplink SCell configurations in serving PCell, including configuration of first SCell with both uplink and downlink aspects..";
      type uint64;
      config false;
    }
    leaf pmSaUeMeasurementReportPuem {
      description "Sum of periodic UE measurement reports for NR standalone..";
      type uint64;
      config false;
    }
    leaf pmRrcConnEstabSucc {
      description "Number of successfully completed RRC Connection Establishment procedures. See 3GPP TS 38.331, RRC Setup Complete..";
      type uint64;
      config false;
    }
    leaf pmRrcResumeAttResumeEm {
      description "Number of RRC connection resumption attempts for resumeCause emergency followed by RRC Resume procedure..";
      type uint64;
      config false;
    }
    leaf pmPduSessionRelAbnormalGnb {
      description "Number of PDU sessions released by either local or external gNodeB when cause is considered abnormal. Deprecated: Since 24.Q4. Planned to be removed. Replaced by NRCellCU::pmPduSessionRelAbnormalGnb2; MOM flags: noNotification.";
      type uint64;
      config false;
      status deprecated;
    }
    leaf pmUeCtxtRelAbnormalGnbAct {
      description "Number of abnormal NR SA UE Context Release procedures initiated by either local or external gNodeB. UE is considered in session at time of release..";
      type uint64;
      config false;
    }
    leaf pmHoPrepRejInEutranMpLoad {
      description "Number of rejected inter-RAT handovers from LTE in NR SA because Baseband MP load control indicates OVERLOAD or VERY HIGH state..";
      type uint64;
      config false;
    }
    leaf pmAnrNeighbRelAddEutran {
      description "Number of E-UTRAN neighbor relations added by ANR function..";
      type uint64;
      config false;
    }
    leaf pmHoExeSuccOutEutran {
      description "Number of successful outgoing inter-RAT handovers from NR to LTE in source NR cell..";
      type uint64;
      config false;
    }
    leaf pmEndcPSCellChangeAttIntraSgnb {
      description "Number of intra-SgNodeB PSCell change attempts for EN-DC in source NR cell that are not interrupted by MeNodeB initiated procedure, for example, MN mobility. For definition of PSCell, see 3GPP TS 37.340..";
      type uint64;
      config false;
    }
    leaf pmAnrNeighbRelPromoteRejEutran {
      description "Number of events when E-UTRAN neighbor relations are rejected to be promoted by ANR function..";
      type uint64;
      config false;
    }
    leaf pmHoPrepSuccOutIntraGnbOffload {
      description "Number of successful NR intra-gNodeB handover preparations for traffic offload in source NR cell..";
      type uint64;
      config false;
    }
    leaf-list pmDrbRelAbnormalGnbAct25qi {
      description "Number of abnormal active DRB releases triggered by either local or external gNodeB for each mapped 5QI. Compressed: True.";
      type uint64;
      max-elements 256;
    }
    leaf pmHoPrepRejInEutranUeAdmission {
      description "Number of failed incoming inter-RAT handovers from LTE in NR SA because of admission control. Deprecated: Since 23.Q4. Planned to be removed. Replaced by NRCellCU::pmHoPrepRejInEutranUeCapacityLimit.; MOM flags: noNotification.";
      type uint64;
      config false;
      status deprecated;
    }
    leaf pmPwsCancelReqEtws {
      description "Number of NGAP PWS CANCEL REQUEST messages that contain ETWS notification received in each cell. Includes duplicated messages..";
      type uint64;
      config false;
    }
    leaf pmPduSessionLevelMax {
      description "Peak number of PDU Sessions for UEs in RRC Connected mode..";
      type int64;
      config false;
    }
    leaf pmCaDeconfigSuccUl {
      description "Number of successful uplink SCell deconfigurations in serving PCell, including deconfiguration of last SCell with both uplink and downlink aspects. SCell release signaling to UE uses RRC Reconfiguration and RRC Connection Release procedures. SCell releases that use RRC Connection Release procedure are always successful in serving PCell. Deprecated: Since 25.Q2. Planned to be removed. Replaced by NRCellCU::pmCaSCellDeconfigSuccUl.; MOM flags: noNotification.";
      type uint64;
      config false;
      status deprecated;
    }
    leaf pmHoExeSuccOutIntraGnbTs {
      description "Number of successful NR intra-gNodeB handover executions in source NR cell because of traffic steering..";
      type uint64;
      config false;
    }
    leaf pmDrbRopEndSa {
      description "Number of NR SA DRBs at end of ROP..";
      type int64;
      config false;
    }
    leaf pmRrcConnReestAtt {
      description "Number of attempted RRC Connection Reestablishment procedures without fallback. See 3GPP TS 38.331, RRC Reestablishment Request..";
      type uint64;
      config false;
    }
    leaf-list pmUeMeasEndcSsRsrp {
      description "Distribution of SS-RSRP received by gNodeB from UEs in cell. Periodic UE measurement reports to all or a subset of UEs must be triggered by gNodeB in measured NR cell. See 3GPP TS 38.133, RSRP Measurement Report Mapping. Unit: N/A Ranges: Bin[0]: Number of measurement reports with RSRP in dBm range [..-156[ dBm for PSCell. Bin[1]: Number of measurement reports with RSRP in dBm range [-156..-155[ dBm for PSCell. Bin[2]: Number of measurement reports with RSRP in dBm range [-155..-154[ dBm for PSCell. Bin[3]: Number of measurement reports with RSRP in dBm range [-154..-153[ dBm for PSCell. Bin[4]: Number of measurement reports with RSRP in dBm range [-153..-152[ dBm for PSCell. Bin[5]: Number of measurement reports with RSRP in dBm range [-152..-151[ dBm for PSCell. Bin[6]: Number of measurement reports with RSRP in dBm range [-151..-150[ dBm for PSCell. Bin[7]: Number of measurement reports with RSRP in dBm range [-150..-149[ dBm for PSCell. Bin[8]: Number of measurement reports with RSRP in dBm range [-149..-148[ dBm for PSCell. Bin[9]: Number of measurement reports with RSRP in dBm range [-148..-147[ dBm for PSCell. Bin[10]: Number of measurement reports with RSRP in dBm range [-147..-146[ dBm for PSCell. Bin[11]: Number of measurement reports with RSRP in dBm range [-146..-145[ dBm for PSCell. Bin[12]: Number of measurement reports with RSRP in dBm range [-145..-144[ dBm for PSCell. Bin[13]: Number of measurement reports with RSRP in dBm range [-144..-143[ dBm for PSCell. Bin[14]: Number of measurement reports with RSRP in dBm range [-143..-152[ dBm for PSCell. Bin[15]: Number of measurement reports with RSRP in dBm range [-142..-141[ dBm for PSCell. Bin[16]: Number of measurement reports with RSRP in dBm range [-141..-140[ dBm for PSCell. Bin[17]: Number of measurement reports with RSRP in dBm range [-140..-139[ dBm for PSCell. Bin[18]: Number of measurement reports with RSRP in dBm range [-139..-138[ dBm for PSCell. Bin[19]: Number of measurement reports with RSRP in dBm range [-138..-137[ dBm for PSCell. Bin[20]: Number of measurement reports with RSRP in dBm range [-137..-136[ dBm for PSCell. Bin[21]: Number of measurement reports with RSRP in dBm range [-136..-135[ dBm for PSCell. Bin[22]: Number of measurement reports with RSRP in dBm range [-135..-134[ dBm for PSCell. Bin[23]: Number of measurement reports with RSRP in dBm range [-134..-133[ dBm for PSCell. Bin[24]: Number of measurement reports with RSRP in dBm range [-133..-132[ dBm for PSCell. Bin[25]: Number of measurement reports with RSRP in dBm range [-132..-131[ dBm for PSCell. Bin[26]: Number of measurement reports with RSRP in dBm range [-131..-130[ dBm for PSCell. Bin[27]: Number of measurement reports with RSRP in dBm range [-130..-129[ dBm for PSCell. Bin[28]: Number of measurement reports with RSRP in dBm range [-129..-128[ dBm for PSCell. Bin[29]: Number of measurement reports with RSRP in dBm range [-128..-127[ dBm for PSCell. Bin[30]: Number of measurement reports with RSRP in dBm range [-127..-126[ dBm for PSCell. Bin[31]: Number of measurement reports with RSRP in dBm range [-126..-125[ dBm for PSCell. Bin[32]: Number of measurement reports with RSRP in dBm range [-125..-124[ dBm for PSCell. Bin[33]: Number of measurement reports with RSRP in dBm range [-124..-123[ dBm for PSCell. Bin[34]: Number of measurement reports with RSRP in dBm range [-123..-122[ dBm for PSCell. Bin[35]: Number of measurement reports with RSRP in dBm range [-122..-121[ dBm for PSCell. Bin[36]: Number of measurement reports with RSRP in dBm range [-121..-120[ dBm for PSCell. Bin[37]: Number of measurement reports with RSRP in dBm range [-120..-119[ dBm for PSCell. Bin[38]: Number of measurement reports with RSRP in dBm range [-119..-118[ dBm for PSCell. Bin[39]: Number of measurement reports with RSRP in dBm range [-118..-117[ dBm for PSCell. Bin[40]: Number of measurement reports with RSRP in dBm range [-117..-116[ dBm for PSCell. Bin[41]: Number of measurement reports with RSRP in dBm range [-116..-115[ dBm for PSCell. Bin[42]: Number of measurement reports with RSRP in dBm range [-115..-114[ dBm for PSCell. Bin[43]: Number of measurement reports with RSRP in dBm range [-114..-113[ dBm for PSCell. Bin[44]: Number of measurement reports with RSRP in dBm range [-113..-112[ dBm for PSCell. Bin[45]: Number of measurement reports with RSRP in dBm range [-112..-111[ dBm for PSCell. Bin[46]: Number of measurement reports with RSRP in dBm range [-111..-110[ dBm for PSCell. Bin[47]: Number of measurement reports with RSRP in dBm range [-110..-109[ dBm for PSCell. Bin[48]: Number of measurement reports with RSRP in dBm range [-109..-108[ dBm for PSCell. Bin[49]: Number of measurement reports with RSRP in dBm range [-108..-107[ dBm for PSCell. Bin[50]: Number of measurement reports with RSRP in dBm range [-107..-106[ dBm for PSCell. Bin[51]: Number of measurement reports with RSRP in dBm range [-106..-105[ dBm for PSCell. Bin[52]: Number of measurement reports with RSRP in dBm range [-105..-104[ dBm for PSCell. Bin[53]: Number of measurement reports with RSRP in dBm range [-104..-103[ dBm for PSCell. Bin[54]: Number of measurement reports with RSRP in dBm range [-103..-102[ dBm for PSCell. Bin[55]: Number of measurement reports with RSRP in dBm range [-102..-101[ dBm for PSCell. Bin[56]: Number of measurement reports with RSRP in dBm range [-101..-100[ dBm for PSCell. Bin[57]: Number of measurement reports with RSRP in dBm range [-100..-99[ dBm for PSCell. Bin[58]: Number of measurement reports with RSRP in dBm range [-99..-98[ dBm for PSCell. Bin[59]: Number of measurement reports with RSRP in dBm range [-98..-97[ dBm for PSCell. Bin[60]: Number of measurement reports with RSRP in dBm range [-97..-96[ dBm for PSCell. Bin[61]: Number of measurement reports with RSRP in dBm range [-96..-95[ dBm for PSCell. Bin[62]: Number of measurement reports with RSRP in dBm range [-95..-94[ dBm for PSCell. Bin[63]: Number of measurement reports with RSRP in dBm range [-94..-93[ dBm for PSCell. Bin[64]: Number of measurement reports with RSRP in dBm range [-93..-92[ dBm for PSCell. Bin[65]: Number of measurement reports with RSRP in dBm range [-92..-91[ dBm for PSCell. Bin[66]: Number of measurement reports with RSRP in dBm range [-91..-90[ dBm for PSCell. Bin[67]: Number of measurement reports with RSRP in dBm range [-90..-89[ dBm for PSCell. Bin[68]: Number of measurement reports with RSRP in dBm range [-89..-88[ dBm for PSCell. Bin[69]: Number of measurement reports with RSRP in dBm range [-88..-87[ dBm for PSCell. Bin[70]: Number of measurement reports with RSRP in dBm range [-87..-86[ dBm for PSCell. Bin[71]: Number of measurement reports with RSRP in dBm range [-86..-85[ dBm for PSCell. Bin[72]: Number of measurement reports with RSRP in dBm range [-85..-84[ dBm for PSCell. Bin[73]: Number of measurement reports with RSRP in dBm range [-84..-83[ dBm for PSCell. Bin[74]: Number of measurement reports with RSRP in dBm range [-83..-82[ dBm for PSCell. Bin[75]: Number of measurement reports with RSRP in dBm range [-82..-81[ dBm for PSCell. Bin[76]: Number of measurement reports with RSRP in dBm range [-81..-80[ dBm for PSCell. Bin[77]: Number of measurement reports with RSRP in dBm range [-80..-79[ dBm for PSCell. Bin[78]: Number of measurement reports with RSRP in dBm range [-79..-78[ dBm for PSCell. Bin[79]: Number of measurement reports with RSRP in dBm range [-78..-77[ dBm for PSCell. Bin[80]: Number of measurement reports with RSRP in dBm range [-77..-76[ dBm for PSCell. Bin[81]: Number of measurement reports with RSRP in dBm range [-76..-75[ dBm for PSCell. Bin[82]: Number of measurement reports with RSRP in dBm range [-75..-74[ dBm for PSCell. Bin[83]: Number of measurement reports with RSRP in dBm range [-74..-73[ dBm for PSCell. Bin[84]: Number of measurement reports with RSRP in dBm range [-73..-72[ dBm for PSCell. Bin[85]: Number of measurement reports with RSRP in dBm range [-72..-71[ dBm for PSCell. Bin[86]: Number of measurement reports with RSRP in dBm range [-71..-70[ dBm for PSCell. Bin[87]: Number of measurement reports with RSRP in dBm range [-70..-69[ dBm for PSCell. Bin[88]: Number of measurement reports with RSRP in dBm range [-69..-68[ dBm for PSCell. Bin[89]: Number of measurement reports with RSRP in dBm range [-68..-67[ dBm for PSCell. Bin[90]: Number of measurement reports with RSRP in dBm range [-67..-66[ dBm for PSCell. Bin[91]: Number of measurement reports with RSRP in dBm range [-66..-65[ dBm for PSCell. Bin[92]: Number of measurement reports with RSRP in dBm range [-65..-64[ dBm for PSCell. Bin[93]: Number of measurement reports with RSRP in dBm range [-64..-63[ dBm for PSCell. Bin[94]: Number of measurement reports with RSRP in dBm range [-63..-62[ dBm for PSCell. Bin[95]: Number of measurement reports with RSRP in dBm range [-62..-61[ dBm for PSCell. Bin[96]: Number of measurement reports with RSRP in dBm range [-61..-60[ dBm for PSCell. Bin[97]: Number of measurement reports with RSRP in dBm range [-60..-59[ dBm for PSCell. Bin[98]: Number of measurement reports with RSRP in dBm range [-59..-58[ dBm for PSCell. Bin[99]: Number of measurement reports with RSRP in dBm range [-58..-57[ dBm for PSCell. Bin[100]: Number of measurement reports with RSRP in dBm range [-57..-56[ dBm for PSCell. Bin[101]: Number of measurement reports with RSRP in dBm range [-56..-55[ dBm for PSCell. Bin[102]: Number of measurement reports with RSRP in dBm range [-55..-54[ dBm for PSCell. Bin[103]: Number of measurement reports with RSRP in dBm range [-54..-53[ dBm for PSCell. Bin[104]: Number of measurement reports with RSRP in dBm range [-53..-52[ dBm for PSCell. Bin[105]: Number of measurement reports with RSRP in dBm range [-52..-51[ dBm for PSCell. Bin[106]: Number of measurement reports with RSRP in dBm range [-51..-50[ dBm for PSCell. Bin[107]: Number of measurement reports with RSRP in dBm range [-50..-49[ dBm for PSCell. Bin[108]: Number of measurement reports with RSRP in dBm range [-49..-48[ dBm for PSCell. Bin[109]: Number of measurement reports with RSRP in dBm range [-48..-47[ dBm for PSCell. Bin[110]: Number of measurement reports with RSRP in dBm range [-47..-46[ dBm for PSCell. Bin[111]: Number of measurement reports with RSRP in dBm range [-46..-45[ dBm for PSCell. Bin[112]: Number of measurement reports with RSRP in dBm range [-45..-44[ dBm for PSCell. Bin[113]: Number of measurement reports with RSRP in dBm range [-44..-43[ dBm for PSCell. Bin[114]: Number of measurement reports with RSRP in dBm range [-43..-42[ dBm for PSCell. Bin[115]: Number of measurement reports with RSRP in dBm range [-42..-41[ dBm for PSCell. Bin[116]: Number of measurement reports with RSRP in dBm range [-41..-40[ dBm for PSCell. Bin[117]: Number of measurement reports with RSRP in dBm range [-40..-39[ dBm for PSCell. Bin[118]: Number of measurement reports with RSRP in dBm range [-39..-38[ dBm for PSCell. Bin[119]: Number of measurement reports with RSRP in dBm range [-38..-37[ dBm for PSCell. Bin[120]: Number of measurement reports with RSRP in dBm range [-37..-36[ dBm for PSCell. Bin[121]: Number of measurement reports with RSRP in dBm range [-36..-35[ dBm for PSCell. Bin[122]: Number of measurement reports with RSRP in dBm range [-35..-34[ dBm for PSCell. Bin[123]: Number of measurement reports with RSRP in dBm range [-34..-33[ dBm for PSCell. Bin[124]: Number of measurement reports with RSRP in dBm range [-33..-32[ dBm for PSCell. Bin[125]: Number of measurement reports with RSRP in dBm range [-32..-31[ dBm for PSCell. Bin[126]: Number of measurement reports with RSRP in dBm range [-31..] dBm for PSCell. Compressed: True.";
      type uint64;
      max-elements 127;
    }
    leaf-list pmDrbEstabAttInitArp {
      description "Number of initial DRB establishment attempts for each ARP level. Compressed: True.";
      type uint64;
      max-elements 16;
    }
    leaf pmCaSCellDeconfigSucc {
      description "Number of successful SCell deconfigurations in serving PCell, including deconfiguration of last SCell. SCell release signaling to UE uses RRC Reconfiguration and RRC Connection Release procedures. SCell releases that use RRC Connection Release procedure are always successful in serving PCell..";
      type uint64;
      config false;
    }
    leaf pmEndcRelUeMenbReconfigFail {
      description "Number of EN-DC SCG radio resource releases triggered by MeNodeB due to LTE reestablishment with reconfigurationFailure cause..";
      type uint64;
      config false;
    }
    leaf pmUeCapabilityInfo {
      description "Number of RRC UECapabilityInformation messages received or assembled from received RRC ULDedicatedMessageSegment messages..";
      type uint64;
      config false;
    }
    leaf pmUeCtxtEstabSucc {
      description "Number of successful UE context establishments..";
      type uint64;
      config false;
    }
    leaf pmEndcSetupUeAtt {
      description "Number of EN-DC setup attempts initiated by MeNodeB, excluding EN-DC setups performed after LTE handover if the SCG resource could be kept, and after gNB PSCell change..";
      type uint64;
      config false;
    }
    leaf pmCaSCellDeconfigSuccUl {
      description "Number of successful uplink SCell deconfigurations in serving PCell, including deconfiguration of last SCell with both uplink and downlink aspects. SCell release signaling to UE uses RRC Reconfiguration and RRC Connection Release procedures. SCell releases that use RRC Connection Release procedure are always successful in serving PCell..";
      type uint64;
      config false;
    }
    leaf pmNrdcSetupUeMnSuccHoIntraGnbPSCellKeep {
      description "Number of successful NR-DC UE setup attempts that keep PSCell during intra-gNodeB handover. Counted on Master Node side..";
      type uint64;
      config false;
    }
    leaf pmAnrNeighbRelDemoteNr {
      description "Number of NR neighbor relations demoted by ANR function..";
      type uint64;
      config false;
    }
    leaf pmRwrEutranUeSuccEpsfbEm {
      description "Number of successful Release with Redirect procedures triggered by EPS fallback for emergency calls for UE contexts for each cell..";
      type uint64;
      config false;
    }
    leaf pmDrbEstabFailIntgProt {
      description "Number of DRBs that fail during setup because hardware does not support integrity protection of user plane..";
      type uint64;
      config false;
    }
    leaf pmEndcSgnbAdditionRequest {
      description "Number of EN-DC addition requests for secondary gNodeB..";
      type uint64;
      config false;
    }
    leaf pmRrcConnReestFallbackSucc {
      description "Number of successfully completed RRC Connection Reestablishment procedures with fallback to RRC Connection Establishment. 3GPP TS 38.331, RRC Setup Complete..";
      type uint64;
      config false;
    }
    leaf pmCaDeconfigAtt {
      description "Number of SCell deconfiguration attempts in serving PCell, including deconfiguration of last SCell. SCell release signaling to UE uses RRC Reconfiguration and RRC Connection Release procedures. Deprecated: Since 25.Q2. Planned to be removed. Replaced by NRCellCU::pmCaSCellDeconfigAtt.; MOM flags: noNotification.";
      type uint64;
      config false;
      status deprecated;
    }
    leaf pmNrdcRelUeSnAbnormalSnInitAct {
      description "Number of abnormal NR-DC UE releases initiated by Secondary Node. Counted on Secondary Node side. UE has active data transmission. If counter is stepped due to a RESET message this can be seen in sn_nrdc_release_initiating_message..";
      type uint64;
      config false;
    }
    leaf pmUeMeasNcgiRcvDrxPciHandling {
      description "Number of successfully received NCGI measurements with DRX, initiated by PCI conflict handling..";
      type uint64;
      config false;
    }
    leaf pmRwrIntraNrUeSuccRi {
      description "Number of UE Release with Redirection procedure to another NR frequency triggered by remote interference..";
      type uint64;
      config false;
    }
    leaf pmUeCtxtRelAbnormalGnbInact {
      description "Number of abnormal NR SA UE Context Release procedures initiated by gNodeB for UEs in RRC_INACTIVE state..";
      type uint64;
      config false;
    }
    leaf pmHoPrepAttOutInterGnbPciHandling {
      description "Number of outgoing NR inter-gNodeB NG or Xn handover preparation attempts in source NR cell triggered by PCI conflict handling..";
      type uint64;
      config false;
    }
    leaf pmHoPrepAttOutIntraGnbTs {
      description "Number of NR intra-gNodeB handover preparation attempts in source NR cell because of traffic steering..";
      type uint64;
      config false;
    }
    leaf pmHoPrepSuccOutEutran {
      description "Number of successful outgoing inter-RAT handover preparations from NR to LTE in source NR cell..";
      type uint64;
      config false;
    }
    leaf-list pmDrbEstabAttArp {
      description "Number of DRB establishment attempts for each Allocation and Retention Priority level. Compressed: True.";
      type uint64;
      max-elements 16;
    }
    leaf pmRrcConnLevelSamp {
      description "Number of times corresponding pmRrcConnLevelSumSa, pmRrcConnLevelSumEnDc, pmRrcConnLevSumNrDc and pmRrcConnDrbLevelSumSaDistr PM counters accumulate a new sample..";
      type uint64;
      config false;
    }
    leaf-list pmDrbRelAbnormalAmf5qi {
      description "Number of abnormal DRB releases triggered by AMF for each 5QI. Compressed: True.";
      type uint64;
      max-elements 256;
    }
    leaf-list pmDrbSuspend5qi {
      description "Number of suspended DRBs for each 5QI. Compressed: True.";
      type uint64;
      max-elements 256;
    }
    leaf pmRrcResumeSuccResume {
      description "Number of successful RRC connection resumptions followed by RRC Resume..";
      type uint64;
      config false;
    }
    leaf-list pmDrbRelAbnormalGnbAct5qi {
      description "Number of abnormal active DRB releases triggered by either local or external gNodeB for each mapped 5QI. Compressed: True Deprecated: Since 24.Q4. Planned to be removed. Replaced by NRCellCU::pmDrbRelAbnormalGnbAct25qi; MOM flags: noNotification.";
      type uint64;
      max-elements 256;
    }
    leaf pmRrcConnLevelMaxSa {
      description "Peak number of NR standalone UEs in RRC_CONNECTED mode. For NR-DC, NR standalone UEs on Master Node side, configured with NR-DC are included..";
      type int64;
      config false;
    }
    leaf pmRrcResumeAttResume {
      description "Number of RRC connection resume attempts followed by RRC Resume..";
      type uint64;
      config false;
    }
    leaf pmEndcRelUeAbnormalSgnbAct {
      description "Number of abnormal releases of SCG radio resources triggered by Secondary Node. UE is considered in session at time of release..";
      type uint64;
      config false;
    }
    leaf pmAnrNeighbRelPromoteEutran {
      description "Number of E-UTRAN neighbor relations promoted by ANR function..";
      type uint64;
      config false;
    }
    leaf pmAnrNoActionTooWeakEndc {
      description "Number of events when ANR is not triggered because of weak signal in EN-DC..";
      type uint64;
      config false;
    }
    leaf pmUeCtxtRetrieveAttRrcReest {
      description "Number of attempted Retrieve UE Context procedures triggered by RRC Connection Reestablishment procedure. See 3GPP TS 38.423, Retrieve UE Context Request..";
      type uint64;
      config false;
    }
    leaf pmRrcResumeAttFallback {
      description "Number of RRC connection resume attempts with fallback to RRC Connection Establishment procedure..";
      type uint64;
      config false;
    }
    leaf pmNgDowntimeInterfaceSupervision {
      description "Length of time in seconds when NG link type is unavailable in NR Cell..";
      type uint64;
      config false;
    }
    leaf pmHoPrepAttOutEutranOffload {
      description "Number of outgoing inter-RAT handover preparation attempts for traffic offload from NR to LTE in source NR cell..";
      type uint64;
      config false;
    }
    leaf pmRrcConnReestSucc {
      description "Number of successfully completed RRC Connection Reestablishment procedures without fallback. See 3GPP TS 38.331, RRC Reestablishment Complete..";
      type uint64;
      config false;
    }
    leaf pmHoPrepSuccOutInterGnbTs {
      description "Number of successful outgoing NR inter-gNodeB NG or Xn handover preparations in source NR cell because of traffic steering..";
      type uint64;
      config false;
    }
    leaf pmXnDowntimeInterfaceSupervision {
      description "Length of time in seconds when XN link type is unavailable in NR Cell..";
      type uint64;
      config false;
    }
    leaf pmHoExeAttOutEutranTs {
      description "Number of outgoing inter-RAT handover execution attempts for traffic steering reason from NR to LTE in source NR cell..";
      type uint64;
      config false;
    }
    leaf pmHoPrepAttOutInterGnbIntraF {
      description "Number of outgoing NR intra-frequency inter-gNodeB NG or Xn handover preparation attempts in source NR cell..";
      type uint64;
      config false;
    }
    leaf pmNrdcRelRelocUeMnAtt {
      description "Number of attempts to release NR-DC with relocation of PDCP from source Secondary Node to target Master Node or target Secondary Node. Counted on source Master Node side. Release is initiated by source Master Node or source Secondary Node. Source and target Node might be same, depending on use case..";
      type uint64;
      config false;
    }
    leaf pmInterfaceSupervisionSamp {
      description "A sample counter for use with the Interface Supervision counters pmNgDowntimeInterfaceSupervision, pmX2DowntimeInterfaceSupervision and pmXnDowntimeInterfaceSupervision. See Manage Radio Network NR..";
      type uint64;
      config false;
    }
    leaf pmCellTimeBoosterCarrSleepReadyNoEpCell {
      description "Number of seconds booster cell is ready to sleep but no energy performance related cells are. For more information See NR Booster Carrier Sleep FED..";
      type uint64;
      config false;
    }
    leaf pmHoExeSuccOutIntraGnbOffload {
      description "Number of successful NR intra-gNodeB handover executions for traffic offload in source NR cell..";
      type uint64;
      config false;
    }
    leaf pmDrbLevelSamp {
      description "Number of times pmDrbLevelSumSa and pmDrbLevelSumEndc accumulate new sample..";
      type uint64;
      config false;
    }
    leaf pmEndcPSCellChangeRejInIntraGnbBbIntens {
      description "Number of failures of incoming intra-gNodeB PSCell change in EN-DC because of connection intensity control..";
      type uint64;
      config false;
    }
    leaf pmUeCtxtRelAbnormalAmfInact {
      description "Number of abnormal NR SA UE Context Release procedures initiated by AMF for UEs in RRC_INACTIVE state..";
      type uint64;
      config false;
    }
    leaf pmRrcResumeSuccResumeEm {
      description "Number of successful RRC connection resumptions for resumeCause emergency followed by RRC Resume procedure..";
      type uint64;
      config false;
    }
    leaf-list pmCaConfigDlSumNrdcDistr {
      description "Sum of UEs using this cell as PSCell with configured downlink SCells for NR-DC UEs. Ranges: Bin[0]: Number of NR-DC UEs configured with one PCell only and no SCell. Bin[1]: Number of NR-DC UEs configured with one PCell and one SCell. Bin[2]: Number of NR-DC UEs configured with one PCell and two SCells. ... Bin[31]: Number of NR-DC UEs configured with one PCell and thirty-one SCells. Compressed: True.";
      type uint64;
      max-elements 32;
    }
    leaf pmEndcRelUeAbnormalMenbRaProblem {
      description "Number of abnormal EN-DC SCG radio resource releases triggered by MeNodeB with randomAccessProblem SCG failure..";
      type uint64;
      config false;
    }
    leaf pmNrdcRelUeSnAbnormalMnInit {
      description "Number of abnormal NR-DC UE releases initiated by Master Node. Counted on Secondary Node side. If counter is stepped due to a RESET message this can be seen in sn_nrdc_release_initiating_message..";
      type uint64;
      config false;
    }
    leaf pmPduSessionRelAbnormalGnb2 {
      description "Number of PDU sessions released by gNodeB when cause is considered abnormal..";
      type uint64;
      config false;
    }
    leaf pmCaDeconfigAttUl {
      description "Number of uplink SCell deconfiguration attempts in serving PCell, including deconfiguration of last SCell with both uplink and downlink aspects. SCell release signaling to UE uses RRC Reconfiguration and RRC Connection Release procedures. Deprecated: Since 25.Q2. Planned to be removed. Replaced by NRCellCU::pmCaSCellDeconfigAttUl.; MOM flags: noNotification.";
      type uint64;
      config false;
      status deprecated;
    }
    leaf pmRrcResumeSuccFallback {
      description "Number of successful RRC Resume procedures with fallback to RRC Connection Establishment procedure..";
      type uint64;
      config false;
    }
    leaf pmEndcUeMeasurementReportMdt {
      description "Sum of MDT UE measurement reports for EN-DC..";
      type uint64;
      config false;
    }
    leaf pmEndcRelUeAbnormalMenbAct {
      description "Number of abnormal releases of EN-DC SCG radio resources triggered by MeNodeB. UE is considered in session at time of release..";
      type uint64;
      config false;
    }
    leaf pmUeCapabilityRefreshNetworkId {
      description "Number of RRC UE Capability Refresh procedures triggered by Network Id requirements. Deprecated: Since 24.Q4. Planned to be removed.; MOM flags: noNotification.";
      type uint64;
      config false;
      status deprecated;
    }
    leaf pmHoPrepAttOutInterGnbTs {
      description "Number of outgoing NR inter-gNodeB NG or Xn handover preparation attempts in source NR cell because of traffic steering..";
      type uint64;
      config false;
    }
    leaf pmRrcResumeSuccFallbackRnaUpdate {
      description "Number of successful RRC connection resumptions for resumeCause rna-Update with fallback to RRC Connection Establishment procedure..";
      type uint64;
      config false;
    }
    leaf pmCaConfigAtt {
      description "Number of SCell configuration attempts in serving PCell, including configuration of first SCell. Deprecated: Since 25.Q2. Planned to be removed. Replaced by NRCellCU::pmCaSCellConfigAtt.; MOM flags: noNotification.";
      type uint64;
      config false;
      status deprecated;
    }
    leaf-list pmRruCompAvailCapacityUlDistr {
      description "Distribution of composite available capacity in uplink in NR cell. Number of reports with load in percentage range is counted in respective bin. Unit: N/A Ranges: Bin[0]: [0.0..2.5] % Bin[1]: ]2.5..5.0] % Bin[2]: ]5.0..7.5] % Bin[3]: ]7.5..10.0] % Bin[4]: ]10.0..12.5] % Bin[5]: ]12.5..15.0] % Bin[6]: ]15.0..17.5] % Bin[7]: ]17.5..20.0] % Bin[8]: ]20.0..22.5] % Bin[9]: ]22.5..25.0] % Bin[10]: ]25.0..27.5] % Bin[11]: ]27.5..30.0] % Bin[12]: ]30.0..32.5] % Bin[13]: ]32.5..35.0] % Bin[14]: ]35.0..37.5] % Bin[15]: ]37.5..40.0] % Bin[16]: ]40.0..42.5] % Bin[17]: ]42.5..45.0] % Bin[18]: ]45.0..47.5] % Bin[19]: ]47.5..50.0] % Bin[20]: ]50.0..52.5] % Bin[21]: ]52.5..55.0] % Bin[22]: ]55.0..57.5] % Bin[23]: ]57.5..60.0] % Bin[24]: ]60.0..62.5] % Bin[25]: ]62.5..65.0] % Bin[26]: ]65.0..67.5] % Bin[27]: ]67.5..70.0] % Bin[28]: ]70.0..72.5] % Bin[29]: ]72.5..75.0] % Bin[30]: ]75.0..77.5] % Bin[31]: ]77.5..80.0] % Bin[32]: ]80.0..82.5] % Bin[33]: ]82.5..85.0] % Bin[34]: ]85.0..87.5] % Bin[35]: ]87.5..90.0] % Bin[36]: ]90.0..92.5] % Bin[37]: ]92.5..95.0] % Bin[38]: ]95.0..97.5] % Bin[39]: ]97.5..100.0] % Bin[40]: Number of reports without load information for cell..";
      type uint64;
      max-elements 41;
    }
    leaf-list pmRruCompAvailCapacityDlDistr {
      description "Distribution of Composite Available Capacity for downlink (DL) in NR cell. Unit: N/A Ranges: Bin[0]: Number of reports with load in percentage range 2.0-2.2%. Bin[1]: Number of reports with load in percentage range 2.3-2.4%. Bin[2]: Number of reports with load in percentage range 2.5-2.6%. Bin[3]: Number of reports with load in percentage range 2.7-2.8%. Bin[4]: Number of reports with load in percentage range 2.9-3.1%. Bin[5]: Number of reports with load in percentage range 3.2-3.5%. Bin[6]: Number of reports with load in percentage range 3.6-3.7%. Bin[7]: Number of reports with load in percentage range 3.8-4.0%. Bin[8]: Number of reports with load in percentage range 4.1-4.4%. Bin[9]: Number of reports with load in percentage range 4.5-4.9%. Bin[10]: Number of reports with load in percentage range 5.0-5.4%. Bin[11]: Number of reports with load in percentage range 5.5-6.2%. Bin[12]: Number of reports with load in percentage range 6.3-7.0%. Bin[13]: Number of reports with load in percentage range 7.1-8.2%. Bin[14]: Number of reports with load in percentage range 8.3-9.9%. Bin[15]: Number of reports with load in percentage range 10.0-12.4%. Bin[16]: Number of reports with load in percentage range 12.5-16.6%. Bin[17]: Number of reports with load in percentage range 16.7-24.9%. Bin[18]: Number of reports with load in percentage range 25.0-49.9%. Bin[19]: Number of reports with load in percentage range 50.0-100%. Bin[20]: Number of reports without load information for cell. Compressed: True Deprecated: Since 24.Q2. Planned to be removed. Replaced by NRCellCU::pmRruCompAvailCapacityDlDistr2; MOM flags: noNotification.";
      type uint64;
      max-elements 21;
    }
    leaf pmDrbLevelMaxEndc {
      description "Peak number of NR EN-DC DRBs..";
      type int64;
      config false;
    }
    leaf-list pmDrbRelAbnormalAmfActNoSessionInfo5qi {
      description "Number of abnormal active DRB releases by AMF for each mapped 5QI. These DRBs are assumed to be active as the DRB released in session information received over E1AP is not available for one of following reasons: - E1AP procedure timeout - E1AP Reset Compressed: True.";
      type uint64;
      max-elements 256;
    }
    leaf pmEndcRelUeAbnormalMenbActScgReconfigFail {
      description "Number of abnormal EN-DC SCG radio resource releases triggered by MeNodeB with Scg-reconfigFailure SCG failure. UE is considered in session at time of release..";
      type uint64;
      config false;
    }
    leaf pmRrcConnEstabAttReattMos {
      description "Number of RRC Setup Request procedures with establishmentCause mo-Signalling that are considered as reattempts. See 3GPP TS 38.331, RRC Setup Request..";
      type uint64;
      config false;
    }
    leaf pmHoPrepFailOutEpsfb {
      description "Number of NR inter-gNodeB handover preparation attempts in source NR cell cancelled due to EPS fallback..";
      type uint64;
      config false;
    }
    leaf pmNrdcPSCellChangeSnSuccInterSgnb {
      description "Number of successful outgoing NR-DC inter-SgNodeB PSCell Change on Secondary Node side..";
      type uint64;
      config false;
    }
    leaf pmNrdcRejCellBarred {
      description "Number of rejected NR-DC UE setup attempts counted on Secondary Node side and rejected inter-gNodeB PSCell change resource allocation requests for NR-DC in target NR cell because cell is barred. Deprecated: Since 24.Q3. Planned to be removed. Replaced by NRCellCU.pmNrdcSetupUeRejCellInvalid.; MOM flags: noNotification.";
      type uint64;
      config false;
      status deprecated;
    }
    leaf pmUeMeasNcgiTriggerDrxPciHandling {
      description "Number of NCGI measurements with DRX, initiated by PCI conflict handling..";
      type uint64;
      config false;
    }
    leaf pmEndcUeMeasurementReport {
      description "Sum of all UE measurement reports for EN-DC..";
      type uint64;
      config false;
    }
    leaf-list pmDrbRelNormalInact5qi {
      description "Number of normal DRB releases for each 5QI for UEs in RRC_INACTIVE state. Compressed: True.";
      type uint64;
      max-elements 256;
    }
    leaf-list pmDrbRelAbnormalGnbActNoSessionInfo5qi {
      description "Number of abnormal active DRB releases by either local or external gNodeB for each mapped 5QI. These DRBs are assumed to be active as the DRB released in session information received over E1AP is not available because of one of following reasons: - E1AP procedure timeout - E1AP Reset - F1AP Reset - XnAP Reset Compressed: True.";
      type uint64;
      max-elements 256;
    }
    leaf pmAnrNeighbRelPromoteNr {
      description "Number of NR neighbor relations promoted by ANR function..";
      type uint64;
      config false;
    }
    leaf pmHoExeAttOutInterGnbOffload {
      description "Number of outgoing NR inter-gNodeB NG or Xn handover execution attempts for traffic offload in source NR cell..";
      type uint64;
      config false;
    }
    leaf pmNgSigConnEstabSucc {
      description "Number of successful NG signaling connection establishments..";
      type uint64;
      config false;
    }
    leaf pmSaUeMeasurementReportMdt {
      description "Sum of MDT UE measurement reports for NR SA..";
      type uint64;
      config false;
    }
    leaf pmAnrEcgiMeasRcvDrx {
      description "Number of received ECGI measurements using measurement method DRX..";
      type uint64;
      config false;
    }
    leaf pmHoPrepAttOutIntraGnbPciHandling {
      description "Number of outgoing NR intra-gNodeB handover preparation attempts in source NR cell triggered by PCI conflict handling..";
      type uint64;
      config false;
    }
    leaf pmRrcConnEstabAttReatt {
      description "Number of RRC Setup Request procedures considered as reattempts. See 3GPP TS 38.331, RRC Setup Request..";
      type uint64;
      config false;
    }
    leaf pmHoPrepRejInInterGnbUeCapacityLimit {
      description "Number of failed incoming inter-gNodeB handovers in NR SA because of UE capacity limit..";
      type uint64;
      config false;
    }
    leaf pmHoExeAttOutInterGnbPciHandling {
      description "Number of outgoing NR inter-gNodeB NG or Xn handover execution attempts in source NR cell triggered by PCI conflict handling..";
      type uint64;
      config false;
    }
    leaf pmCaSCellConfigAttUl {
      description "Number of uplink SCell configuration attempts in serving PCell, including configuration of first SCell with both uplink and downlink aspects..";
      type uint64;
      config false;
    }
    leaf pmUeMeasEcgiTriggerDrxPciHandling {
      description "Number of ECGI measurements with DRX, initiated by PCI conflict handling..";
      type uint64;
      config false;
    }
    leaf pmNrdcRelUeSnAbnormalMnInitAct {
      description "Number of abnormal NR-DC UE releases initiated by Master Node. Counted on Secondary Node side. UE has active data transmission. If counter is stepped due to a RESET message this can be seen in sn_nrdc_release_initiating_message..";
      type uint64;
      config false;
    }
    leaf pmRrcResumeSuccRelInact {
      description "Number of successful RRC connection resumptions followed by network suspension..";
      type uint64;
      config false;
    }
    leaf pmHoPrepAttOutIntraGnb {
      description "Number of NR intra-gNodeB handover preparation attempts in source NR cell..";
      type uint64;
      config false;
    }
    leaf pmRrcConnEstabAtt {
      description "Number of attempted RRC Connection Establishment procedures. See 3GPP TS 38.331, RRC Setup Request..";
      type uint64;
      config false;
    }
    leaf pmHoPrepSuccOutIntraGnbTs {
      description "Number of successful NR intra-gNodeB handover preparations in source NR cell because of traffic steering..";
      type uint64;
      config false;
    }
    leaf pmRrcResumeSuccFallbackEm {
      description "Number of successful RRC connection resumptions for resumeCause emergency with fallback to RRC Connection Establishment procedure..";
      type uint64;
      config false;
    }
    leaf-list pmDrbRelAbnormalGnb5qi {
      description "Number of abnormal DRB releases triggered by either local or external gNodeB for each 5QI. Compressed: True Deprecated: Since 24.Q4. Planned to be removed. Replaced by NRCellCU::pmDrbRelAbnormalGnb25qi; MOM flags: noNotification.";
      type uint64;
      max-elements 256;
    }
    leaf pmEndcSetupUeRejCellInvalid {
      description "Number of rejected EN-DC setup attempts triggered by PSCell change, LTE handover without PSCell change, or SCG setups because of barred or reserved cell..";
      type uint64;
      config false;
    }
    leaf-list pmDrbRelAbnormalGnbAct2Arp {
      description "Number of abnormal active DRB releases triggered by either local or external gNodeB for each Allocation and Retention Priority (ARP) level. Compressed: True.";
      type uint64;
      max-elements 16;
    }
    leaf pmEndcPSCellChangeSuccIntraSgnb {
      description "Number of successful intra-SgNodeB PSCell changes for EN-DC in source NR cell. For definition of PSCell, see 3GPP TS 37.340..";
      type uint64;
      config false;
    }
    leaf pmDrbLevelSumSa {
      description "Sum of all sample values recorded for number of NR standalone DRBs for UEs in RRC Connected mode. For NR-DC, only DRBs from Master Node are included..";
      type uint64;
      config false;
    }
    leaf pmRrcInactLevelMax {
      description "Maximum number of UEs in RRC_INACTIVE mode in NR cell CU. Used when no flexible filters are applied..";
      type int64;
      config false;
    }
    leaf pmHoExeSuccOutInterGnbPciHandling {
      description "Number of successful outgoing NR inter-gNodeB NG or Xn handover executions in source NR cell triggered by PCI conflict handling..";
      type uint64;
      config false;
    }
    leaf pmEndcSetupUeSucc {
      description "Number of successful EN-DC setups..";
      type uint64;
      config false;
    }
    leaf pmSaUeMeasurementReportUcm {
      description "Sum of measurement reports for UE coverage measurement for NR SA..";
      type uint64;
      config false;
    }
    leaf pmAnrNoActionTooWeakSa {
      description "Number of events when ANR is not triggered because of weak signal in NR SA..";
      type uint64;
      config false;
    }
    leaf pmHoExeAttOutIntraGnb {
      description "Number of NR intra-gNodeB handover execution attempts in source NR cell..";
      type uint64;
      config false;
    }
  }
  grouping NRCellRelation-attributes {
    leaf acaMode {
      description "Whether NRCellRelation instance is managed by Automated Carrier Aggregation feature. Changing this attribute to AUTO can override value of sCellCandidate. Only applicable if license for Automated Carrier Aggregation feature is present and feature is active. Only applicable to Low-Band and Mid-Band cells..";
      type enumeration {
        enum AUTO;
        enum MANUAL;
      }
    }
    leaf caStatusActive {
      description "Active status of carrier aggregation for this NRCellRelation instance..";
      type boolean;
      config false;
    }
    leaf caStatusInfo {
      description "Additional information on status of carrier aggregation for this NRCellRelation instance. Empty when caStatusActive information or additional status information is unavailable..";
      type enumeration {
        enum E5_TUNNEL_CAP;
        enum E5_TUNNEL_CAP_REMOTE;
        enum E5_CELL_ALLOC_CAP;
        enum E5_CELL_ALLOC_CAP_REMOTE;
        enum E5_SW_VERSION_MISMATCH;
        enum E5_MAND_CAP_MISMATCH;
        enum E5_DLCA_CAP_ONLY;
        enum INTRA_BAND_CA_BLOCKED;
        enum ESS_ULCA_BLOCKED;
      }
      config false;
    }
    leaf cellIndividualOffsetNR {
      description "Offset value for neighbor cell. Used when UE is in connected mode.; Default value: 0.";
      type int32 {
        range "-24 | -22 | -20 | -18 | -16 | -14 | -12 | -10 | -8 | -6..6 | 8 | 10 | 12 | 14 | 16 | 18 | 20 | 22 | 24";
      }
      default "0";
      units "dB";
    }
    leaf colocationIndicator {
      description "Colocation indicator. Information on colocation deployment between cell referenced by nRCellRef and current cell. Used to validate timing alignment requirements when cell referenced by nRCellRef can be SCell for carrier aggregation. Only applicable to Low-Band and Mid-Band cells..";
      type enumeration {
        enum UNKNOWN;
        enum COLOCATED;
        enum NON_COLOCATED;
      }
    }
    leaf coordinationType {
      description "Type of inter-cell coordination between carriers in baseband for this NRCellRelation instance..";
      type enumeration {
        enum INTRA_CM;
        enum INTER_CM;
        enum EXT_CM;
      }
      config false;
    }
    leaf coverageIndicator {
      description "Coverage indication. Relation between coverage area of cell referenced by nRCellRef and current cell. Can be: - overlap - referenced cell contains current cell - current cell contains reference cell.";
      type enumeration {
        enum NONE;
        enum COVERS;
        enum OVERLAP;
        enum CONTAINED_IN;
      }
    }
    leaf epLoadMonitoringEnabled {
      description "Whether traffic load monitoring is enabled for energy performance. If true, current cell monitors traffic load in cell referenced by nRCellRef.; Default value: false.";
      type boolean;
      default "false";
    }
    leaf isHoAllowed {
      description "Specifies if handover between the cells in this relation is allowed.; Default value: true.";
      type boolean;
      default "true";
    }
    leaf isRemoveAllowed {
      description "Whether ANR function is allowed to remove this instance. The setting does not restrict operator removal of the object. Objects created by ANR have this parameter set to true initially.; Default value: false.";
      type boolean;
      default "false";
    }
    leaf nRCellRef {
      description "Reference to an instance of NRCellCU or ExternalNRCellCU MO. Cannot refer to parent NRCellCU instance..";
      type string;
      mandatory true;
    }
    leaf nRCellRelationId {
      description "The value component of the RDN..";
      type string;
      mandatory true;
    }
    leaf nRFreqRelationRef {
      description "Reference to an instance of NRFreqRelation MO under same parent NRCellCU instance. NRFreqRelation instance refers to the NRFrequency instance referenced by neighboring NRCellCU or ExternalNRCellCU instance..";
      type string;
      mandatory true;
    }
    leaf preferredCellManual {
      description "Whether related cell must be selected as mobility target cell in PCI conflict cases. Used for manual selection of cell relations for handovers in PCI conflicts. If false, related cell is not selected as a handover target cell, if there is another handover candidate cell with same PCI and on same frequency with this attribute set to true. If true, related cell is always selected as a handover target cell, if there are other handover candidate cells with same PCI and on same frequency.; Default value: false.";
      type boolean;
      default "false";
    }
    leaf sCellCandidate {
      description "SCell candidate status. Whether cell referenced by nRCellRef can be SCell for carrier aggregation. This attribute can be overwritten if Automated Carrier Aggregation feature is active and acaMode is AUTO..";
      type enumeration {
        enum NOT_ALLOWED;
        enum ALLOWED;
        enum ONLY_ALLOWED_FOR_DL;
      }
    }
    leaf timeOfCreation {
      description "Time and date of MO creation. Format: YYYY-MM-DD HH:MM:SS..";
      type string;
      config false;
    }
  }
  grouping NrdcControl-attributes {
    leaf nrdcControlId {
      description "The value component of the RDN..";
      type string;
      mandatory true;
    }
  }
  grouping NrdcMnCellProfile-attributes {
    leaf nrdcMnCellProfileId {
      description "The value component of the RDN..";
      type string;
      mandatory true;
    }
    leaf-list reservedBy {
      description "Contains a list of MO instances that reserve this MO instance..";
      type string;
      min-elements 0;
    }
    leaf ueConfGroupType {
      description "UE configuration group type. UE configuration group type that is applied in contained NrdcMnCellProfileUeCfg instances..";
      type enumeration {
        enum UE_MOBILITY_GROUP;
        enum UE_SERVICE_GROUP;
        enum UE_ADMISSION_GROUP;
      }
    }
  }
  grouping NrdcMnCellProfileUeCfg-attributes {
    leaf maxReportCells {
      description "Maximum number of non-serving cells included in measurement report. Only applicable to event A4.; range 1..8; Default value: 1.";
      type eytypes:int32_range_1-8;
      default "1";
    }
    leaf nrdcEnabled {
      description "Whether NR-NR Dual Connectivity is enabled for the PCell in Master Node.; Default value: false.";
      type boolean;
      default "false";
    }
    leaf nrdcMaxMeasFreqA4 {
      description "Maximum allowed number of simultaneously configured FR2 frequencies in UE for event A4. Note: Maximum allowed FR2 frequencies in UE for event A4 can be limited with total of 7 allowed inter-frequency measurements simultaneously configured in UE as specified by 3GPP TS 38.133.; range 1..7; Default value: 2.";
      type eytypes:int32_range_1-7;
      default "2";
    }
    leaf nrdcMeasRestartTime {
      description "Time to wait for next A4 measurement period to find suitable PSCell candidate for NR-DC.; range 40..240000; Default value: 15000.";
      type int32 {
        range "40..240000";
      }
      default "15000";
      units "ms";
    }
    leaf nrdcMeasTime {
      description "Time in which UE performs A4 measurements to find suitable PSCell candidate for NR-DC.; range 40..120000; Default value: 2000.";
      type int32 {
        range "40..120000";
      }
      default "2000";
      units "ms";
    }
    leaf nrdcMnCellProfileUeCfgId {
      description "The value component of the RDN..";
      type string;
      mandatory true;
    }
    leaf nrdcSetupDlPktAgeThr {
      description "NR-DC setup parameter representing a threshold for age of packets in RLC SDU buffer. If 0, age buffer measurement is disabled.; Default value: 0.";
      type int32 {
        range "0 | 10..500";
      }
      default "0";
      units "ms";
    }
    leaf nrdcSetupDlPktVolThr {
      description "NR-DC setup parameter representing a threshold for total volume of packets in RLC SDU buffer. If 0, volume buffer measurement is disabled.; Default value: 0.";
      type int32 {
        range "0 | 10..30000";
      }
      default "0";
      units "kB";
    }
    leaf nrdcSetupUlBufferMonCfgRef {
      description "Reference to an instance of UlBufferMonCfg MO. Automatically set to UlBufferMonCfg=Default instance, unless manually set to refer to another MO instance. Applicable to NR-DC setup..";
      type string;
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    list rsrpPSCellCandidate {
      key "id";
      leaf id {
        type uint32;
        description "Synthetic key for struct attribute.";
      }
      description "RSRP A4 measurement report criteria when searching for PSCell candidate..";
      uses ReportConfigA4Rsrp-struct;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 16;
    }
    leaf-list ueGroupList {
      description "UE group list. List of UE group identifiers. If empty, MO instance matches all UE group identifiers..";
      type eytypes:int32_range_1-255;
      ordered-by user;
      min-elements 0;
      max-elements 16;
    }
  }
  grouping NrdcSnTermination-attributes {
    leaf defaultNrdcSnTerm {
      description "Whether this instance is default NrdcSnTermination instance. Default instance is used when nrdcSnTerminationRef is empty for CUCP5qi.; Default value: false.";
      type boolean;
      default "false";
    }
    leaf nrdcSnTerminationId {
      description "The value component of the RDN..";
      type string;
      mandatory true;
    }
    leaf-list reservedBy {
      description "Contains a list of MO instances that reserve this MO instance..";
      type string;
      min-elements 0;
    }
    leaf ueConfGroupType {
      description "UE configuration group type. UE configuration group type that is applied in contained NrdcSnTerminationUeCfg instances..";
      type enumeration {
        enum UE_MOBILITY_GROUP;
        enum UE_SERVICE_GROUP;
        enum UE_ADMISSION_GROUP;
      }
    }
  }
  grouping NrdcSnTerminationUeCfg-attributes {
    leaf nrdcSnTermAllowed {
      description "Whether Secondary Node termination for NR-DC is allowed for each ARP. Bitmap [1-15], each bit corresponds to one ARP value. First or rightmost bit is for ARP1, second bit is for ARP2, and so on. Each bit has one of following values: 0: Secondary Node termination is not allowed for this ARP. 1: Secondary Node termination is allowed for this ARP. Bitmap is displayed as decimal value { 0..32767 }. Examples of decimal value definitions of certain ARP combinations for allowing Secondary Node termination: * 0: Not allowed for any ARP. * 1: Allowed for ARP1. * 2: Allowed for ARP2. * 3: Allowed for ARP1 and ARP2. * 4: Allowed for ARP3. * 5: Allowed for ARP1 and ARP3. * 15: Allowed for ARP1, ARP2, ARP3 and ARP4. * 128: Allowed for ARP8. * 256: Allowed for ARP9. * 4097: Allowed for ARP1 and ARP13. * 32767: Allowed for all ARPs.; range 0..32767; Default value: 0.";
      type uint16 {
        range "0..32767";
      }
      default "0";
    }
    leaf nrdcSnTerminationUeCfgId {
      description "The value component of the RDN..";
      type string;
      mandatory true;
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 16;
    }
    leaf-list ueGroupList {
      description "UE group list. List of UE group identifiers. If empty, MO instance matches all UE group identifiers..";
      type eytypes:int32_range_1-255;
      ordered-by user;
      min-elements 0;
      max-elements 16;
    }
  }
  grouping NRFreqRelation-attributes {
    leaf addSCellCandidateThresh {
      description "Threshold for adding SCell candidate.; range 0..100.";
      type eytypes:int32_range_0-100;
      units "percent";
    }
    leaf addSCellCandThresh {
      description "Threshold for adding SCell candidate. Used by Automated Carrier Aggregation feature.; range 1..100; Default value: 15.";
      type eytypes:int32_range_1-100;
      default "15";
      units "percent";
    }
    leaf anrMeasOn {
      description "Whether ANR measurement on referenced frequency is enabled.; Default value: true.";
      type boolean;
      default "true";
    }
    leaf caFreqRelMeasProfileRef {
      description "Reference to an instance of CaFreqRelMeasProfile MO. Automatically set to CaFreqRelMeasProfile=Default instance, unless manually set to refer to another MO instance..";
      type string;
    }
    leaf cellReselectionPriority {
      description "Absolute priority of carrier frequency used by cell reselection procedure. This attribute is broadcast in SIB2 or SIB4, depending on whether related frequency is intra-frequency or inter-frequency. If 0, lowest priority is selected. If -1, related frequency is not broadcast in SIB2 nor SIB4. Value must be unique between RATs. This means that equal priorities between RATs are not supported.; range -1..7; Default value: 7.";
      type eytypes:int32_range_-1-7;
      default "7";
    }
    leaf cellReselectionSubPriority {
      description "Subpriority value of NR carrier frequency. Subpriority value added to value of cellReselectionPriority to obtain absolute priority of carrier frequency. If empty, this attribute is not broadcast in SIB2 and SIB4. This attribute is broadcast accompanied by cellReselectionPriority in SIB2 or SIB4, depending on whether related frequency is intra-frequency or inter-frequency..";
      type int32 {
        range "2 | 4 | 6 | 8";
      }
    }
    leaf intraFreqMCFreqRelProfileRef {
      description "Reference to an instance of IntraFreqMCFreqRelProfile MO. Automatically set to IntraFreqMCFreqRelProfile=Default instance, unless manually set to refer to another MO instance.; Takes effect: Next usage; MOM flags: isNillable=true; Status info: Since 24.Q1. Replaced by caFreqRelMeasProfileRef. Planned to be removed..";
      type string;
      status deprecated;
      reference "Takes effect: Next usage.";
    }
    leaf mcpcPCellNrFreqRelProfileRef {
      description "Reference to an instance of McpcPCellNrFreqRelProfile MO. Automatically set to McpcPCellNrFreqRelProfile=Default instance, unless manually set to refer to another MO instance..";
      type string;
    }
    leaf mcpcPSCellNrFreqRelProfileRef {
      description "Reference to an instance of McpcPSCellNrFreqRelProfile MO. Automatically set to McpcPSCellNrFreqRelProfile=Default instance, unless manually set to refer to another MO instance..";
      type string;
    }
    leaf mdtMeasOn {
      description "Whether MDT measurements are performed on this frequency. Only applicable if following all apply: - NRCellCU::mdtEnabled is true. - MdtCellProfileUeCfg::m1ReportTrigger is PERIODIC and MdtCellProfileUeCfg::m1InterFreqMeasAllowed is true under MdtCellProfile instance referenced from parent NRCellCU instance.; Default value: true.";
      type boolean;
      default "true";
    }
    leaf nccmTargetHigh {
      description "Maximum target number of periodic measurements per hour for each NRFreqRelation instance. Number of measurements can deviate from target. If 0, no measurements are performed during high intensity.; range 0..100.";
      type eytypes:int32_range_0-100-2;
    }
    leaf nccmTargetLow {
      description "Minimum target number of periodic measurements per hour for each NRFreqRelation instance. Number of measurements can deviate from target. If 0, no measurements are performed during low intensity.; range 0..100.";
      type eytypes:int32_range_0-100-2;
    }
    leaf nrdcA4ThrRsrpFreqOffset {
      description "Frequency relation specific offset for absolute RSRP threshold for event A4 in NR-DC. Only applicable to Low-Band and Mid-Band cells.; range -30..30; Default value: 0.";
      type eytypes:int32_range_-30-30;
      default "0";
      units "dB";
    }
    leaf nRFreqRelationId {
      description "The value component of the RDN..";
      type string;
      mandatory true;
    }
    leaf nRFrequencyRef {
      description "Reference to an instance of NRFrequency MO. Must be unique among NRFreqRelation instances under an NRCellCU instance..";
      type string;
      mandatory true;
    }
    leaf offloadNrFreqRelProfileRef {
      description "Reference to an instance of OffloadNrFreqRelProfile MO. Automatically set to OffloadNrFreqRelProfile=Default instance, unless manually set to refer to another MO instance..";
      type string;
    }
    list plmnIdList {
      key "id";
      leaf id {
        type uint32;
        description "Synthetic key for struct sequence entry.";
      }
      min-elements 0;
      max-elements 15;
      uses PLMNId-struct;
    }
    leaf plmnRestriction {
      description "Whether PLMN restriction is defined for frequency relation. PLMN restriction is defined by plmnIdList.; Default value: false.";
      type boolean;
      default "false";
    }
    leaf pMax {
      description "Parameter used to calculate Pcompensation at cell reselection. Corresponds to parameter PEMAX in 3GPP TS 38.101. This attribute is broadcast in SIB2 or SIB4, depending on whether related frequency is intra-frequency or inter-frequency. If empty or 1000, value is not broadcast in SIB2 and SIB4 and UE applies maximum power according to 3GPP TS 38.101. Only applicable to Low-Band and Mid-Band cells.; Default value: 23.";
      type int32 {
        range "-30..33 | 1000";
      }
      default "23";
      units "dBm";
    }
    leaf qOffsetFreq {
      description "Offset applied when evaluating candidates for cell reselection.; Default value: 0.";
      type int32 {
        range "-24 | -22 | -20 | -18 | -16 | -14 | -12 | -10 | -8 | -6..6 | 8 | 10 | 12 | 14 | 16 | 18 | 20 | 22 | 24";
      }
      default "0";
      units "dB";
    }
    leaf qQualMin {
      description "Minimum required quality level RSRQ in cell. This attribute is broadcast in SIB2 or SIB4, depending on whether the related frequency is intra-frequency or inter-frequency. If empty, value is not broadcast in SIB2 or SIB4, and UE applies default value of negative infinity for Qqualmin in 3GPP TS 38.304.; range -43..-12.";
      type eytypes:int32_range_-43--12;
      units "dB";
    }
    leaf qRxLevMin {
      description "Minimum received RSRP level in cell reselection. This attribute is broadcast in SIB2 or SIB4, depending on whether the related frequency is intra-frequency or inter-frequency. Corresponds to parameter Qrxlevmin in 3GPP TS 38.304.; range -140..-44; Default value: -140.";
      type eytypes:int32_range_-140--44;
      default "-140";
      units "dBm";
    }
    leaf redCapEnabled {
      description "Whether Reduced Capability UE on frequency relation is enabled. If true: - IE redCapAccessAllowed-r17 is transmitted in SIB4 with value true, that is, cell reselections to NRFrequency instance are allowed. - UE measurement can be initiated for NRFrequency instance, that is, inter-frequency handovers are allowed. If false: - IE redCapAccessAllowed-r17 is not transmitted in SIB4, that is, cell reselections to NRFrequency instance are restricted. - UE measurement cannot be initiated for NRFrequency instance, that is, inter-frequency handovers are restricted.; Default value: false.";
      type boolean;
      default "false";
    }
    leaf removeSCellCandidateThresh {
      description "Threshold for removing SCell candidate.; range 0..100.";
      type eytypes:int32_range_0-100;
      units "percent";
    }
    leaf removeSCellCandThresh {
      description "Threshold for removing SCell candidate. Used by Automated Carrier Aggregation feature.; range 0..99; Default value: 5.";
      type int32 {
        range "0..99";
      }
      default "5";
      units "percent";
    }
    leaf-list reservedBy {
      description "Contains a list of MO instances that reserve this MO instance..";
      type string;
      min-elements 0;
    }
    leaf sIntraSearchP {
      description "Srxlev threshold indicating when intra-frequency measurements are required.; range 0..62; Default value: 62.";
      type eytypes:int32_range_0-62;
      default "62";
      units "dB";
    }
    leaf sIntraSearchQ {
      description "Squal threshold indicating when intra-frequency measurements are required. If empty, value is not broadcast in SIB2.; range 0..31.";
      type eytypes:int32_range_0-31;
      units "dB";
    }
    leaf threshXHighP {
      description "RSRP threshold level for reselection to higher priority. Each frequency of NR can have a specific threshold.; range 0..62; Default value: 4.";
      type eytypes:int32_range_0-62;
      default "4";
      units "dB";
    }
    leaf threshXHighQ {
      description "RSRQ threshold level for reselection to higher priority. Threshold used by UE when reselecting towards a higher priority frequency X from the actual serving frequency. Each frequency of NR can have a specific threshold. If empty, value is not broadcast in SIB4.; range 0..31.";
      type eytypes:int32_range_0-31;
      units "dB";
    }
    leaf threshXLowP {
      description "RSRP threshold level for reselection to lower priority. Each frequency of NR can have a specific threshold.; range 0..62; Default value: 0.";
      type eytypes:int32_range_0-62;
      default "0";
      units "dB";
    }
    leaf threshXLowQ {
      description "RSRQ threshold level for reselection to lower priority. The threshold used by UE when reselecting towards a lower priority frequency X from the current serving frequency. Each frequency of NR can have a specific threshold. If empty, value is not broadcast in SIB.; range 0..31.";
      type eytypes:int32_range_0-31;
      units "dB";
    }
    leaf tReselectionNR {
      description "Time interval that evaluates the criteria before the reselection can be done. This attribute is broadcast in SIB2 or SIB4, depending on whether the related frequency is intra-frequency or inter-frequency.; range 0..7; Default value: 2.";
      type eytypes:int32_range_0-7-8;
      default "2";
      units "s";
    }
    leaf tReselectionNrSfHigh {
      description "Speed-dependent scaling factor for TreselectionNR. For NR intra-frequency or inter-frequency cell reselection, concerned mobility control related parameter is multiplied with this factor if UE is in high mobility state. This attribute is broadcast in SIB2 or SIB4, depending on whether related frequency is intra-frequency or inter-frequency. If empty, no t-ReselectionNR-SF will be broadcast in SIB2 or SIB4..";
      type uint32 {
        range "25 | 50 | 75 | 100";
      }
    }
    leaf tReselectionNrSfMedium {
      description "Speed-dependent scaling factor for TreselectionNR. For NR intra-frequency or inter-frequency cell reselection, concerned mobility control related parameter is multiplied with this factor if UE is in medium mobility state. This attribute is broadcast in SIB2 or SIB4, depending on whether related frequency is intra-frequency or inter-frequency. If empty, no t-ReselectionNR-SF will be broadcast in SIB2 or SIB4..";
      type uint32 {
        range "25 | 50 | 75 | 100";
      }
    }
    leaf trStPSCellNrFreqRelProfileRef {
      description "Reference to an instance of TrStPSCellNrFreqRelProfile MO. Automatically set to TrStPSCellNrFreqRelProfile=Default instance, unless manually set to refer to another MO instance..";
      type string;
    }
    leaf trStSaNrFreqRelProfileRef {
      description "Reference to an instance of TrStSaNrFreqRelProfile MO. Automatically set to TrStSaNrFreqRelProfile=Default instance, unless manually set to refer to another MO instance..";
      type string;
    }
    leaf ucmNrFreqRelProfileRef {
      description "Reference to an instance of UcmNrFreqRelProfile MO. Automatically set to UcmNrFreqRelProfile=Default instance, unless manually set to refer to another MO instance..";
      type string;
    }
    leaf ueMCNrFreqRelProfileRef {
      description "Reference to an instance of UeMCNrFreqRelProfile MO. Automatically set to UeMCNrFreqRelProfile=Default instance, unless manually set to refer to another MO instance..";
      type string;
    }
  }
  grouping NRFreqRelationTemplate-attributes {
    leaf arfcnValueNRDlHigh {
      description "Higher ARFCN value which is applicable to NR carrier frequency. NRFreqRelation instances can be automatically created below this value. NRFreqRelationTemplate instances cannot have overlapping nRFrequencyRange values under same NRCellCU instance.; range 0..3279165.";
      type eytypes:int32_range_0-3279165;
      mandatory true;
    }
    leaf arfcnValueNRDlLow {
      description "Lower ARFCN value which is applicable to NR carrier frequency. NRFreqRelation instances can be automatically created above this value. NRFreqRelationTemplate instances cannot have overlapping nRFrequencyRange values under same NRCellCU instance.; range 0..3279165.";
      type eytypes:int32_range_0-3279165;
      mandatory true;
    }
    leaf defaultNRFreqRelationRef {
      description "Reference to an instance of NRFreqRelation MO..";
      type string;
      mandatory true;
    }
    leaf nRFreqRelationTemplateId {
      description "The value component of the RDN..";
      type string;
      mandatory true;
    }
  }
  grouping NRFrequency-attributes {
    leaf arfcnValueNRDl {
      description "Absolute frequency applicable to a downlink NR carrier frequency associated with the SSB. This attribute is broadcast in SIB4.; range 0..3279165.";
      type eytypes:int32_range_0-3279165;
      mandatory true;
    }
    leaf-list bandList {
      description "List of all NR bands the NRFrequency belongs to. Calculated by the system based on arfcnValueNRDl and smtcScs. If configured, bandListManual is used instead of bandList..";
      type eytypes:int32_range_1-1024;
      min-elements 0;
      max-elements 32;
    }
    leaf-list bandListManual {
      description "Configured list of bands to be used by NRFrequency. If present, this list is used instead of bandList. Bands specified in bandListManual must be intersection of possible bands for given NRFrequency configuration. Possible bands are displayed in bandList. Example, if bandList contains only bands 77 and 78, this attribute must contain 77, 78, or both. Recommendation is that this list has same content as NRCellDU::bandListManual for cells with same frequency. This recommendation is for 3GPP compliance. Order of NR bands listed in bandListManual corresponds to order of bands in frequencyBandList in SIB4..";
      type int32 {
        range "1..3 | 5 | 7..8 | 12..14 | 18 | 20 | 24..26 | 28..31 | 34 | 38..41 | 46 | 48 | 50..51 | 53..54 | 65..67 | 70..72 | 74..86 | 89..102 | 104..106 | 109 | 257..262";
      }
      ordered-by user;
      min-elements 0;
      max-elements 32;
    }
    leaf gscn {
      description "NR frequencies on the Global Synchronization Channel Raster. If empty, SSB is not placed on synchronization raster..";
      type int32;
      config false;
    }
    leaf nRFrequencyId {
      description "The value component of the RDN..";
      type string;
      mandatory true;
    }
    leaf-list reservedBy {
      description "Contains a list of MO instances that reserve this MO instance..";
      type string;
      min-elements 0;
    }
    leaf smtcDuration {
      description "Duration of measurement window where SSBs are received. Broadcast in SIB2 and SIB4.; range 1..5; Default value: 5.";
      type eytypes:int32_range_1-5;
      default "5";
      units "ms";
    }
    leaf smtcOffset {
      description "Offset of measurement window where SSBs are received. Broadcast in SIB2 and SIB4. All NRFrequencies in the network must align within a measurement window for successful RRC connected mode inter-frequency measurements.; range 0..159; Default value: 0.";
      type eytypes:int32_range_0-159;
      default "0";
      units "ms";
    }
    leaf smtcPeriodicity {
      description "Periodicity of measurement window where SSBs are received. Broadcast in SIB2 and SIB4. A value greater than 20 ms is not supported for RRC connected mode inter-frequency measurements.; Default value: 20.";
      type int32 {
        range "5 | 10 | 20 | 40 | 80 | 160";
      }
      default "20";
      units "ms";
    }
    leaf smtcScs {
      description "Subcarrier Spacing for the SSBs. This attribute is broadcast in SIB4..";
      type int32 {
        range "15 | 30 | 120 | 240";
      }
      mandatory true;
      units "kHz";
    }
    leaf ssbToMeasureIdle {
      description "Set of SS/PBCH blocks used for measurements. Applicable to UE in RRC Idle state or in RRC Inactive state when performing SS-RSRP measurement. Regardless of value of this attribute, SS/PBCH blocks outside of applicable SMTC window are not to be measured. Defined by bit string with string length equal to or less than maximum number of SS/PBCH blocks within half radio frame. First leftmost bit corresponds to SS/PBCH block index 0, second bit corresponds to SS/PBCH block index 1, and so on. Bit value 0 indicates that corresponding SS/PBCH block is not to be measured while bit value 1 indicates that corresponding SS/PBCH block is to be measured. If non-empty: - Information element SSB-ToMeasure is broadcasted in SIB2 and SIB4 according to setting. - At least one bit must be set to 1. If empty, information element SSB-ToMeasure is omitted in SIB2 and SIB4. According to 3GPP specifications, UE then performs SS-RSRP measurements using all SS/PBCH blocks within SMTC window.; length 1..64.";
      type string {
        length "1..64";
        pattern "[0]*1[01]*";
      }
    }
    list ssRssiMeasIdle {
      key "id";
      leaf id {
        type uint32;
        description "Synthetic key for struct attribute.";
      }
      description "Set of slots and symbols, within SMTC measurement duration, configured for SS-RSSI measurement. Applicable to UE in RRC Idle state or in RRC Inactive state when performing SS-RSSI measurement. If non-empty, information element SS-RSSI-Measurement is broadcasted in SIB2 and SIB4 according to SsRssiMeasurement.measurementSlots and SsRssiMeasurement.endSymbol settings. If empty, information element SS-RSSI-Measurement is omitted in SIB2 and SIB4. According to 3GPP specifications, UE performs SS-RSSI measurement using all slots and symbols within SSB Measurement Timing Configuration (SMTC) measurement duration, in case information element SS-RSSI-Measurement is not provided to UE..";
      uses SsRssiMeasurement-struct;
    }
    leaf ueConfGroupType {
      description "UE configuration group type. UE configuration group type that is applied in contained NRFrequencyUeCfg instances..";
      type enumeration {
        enum UE_MOBILITY_GROUP;
        enum UE_SERVICE_GROUP;
        enum UE_ADMISSION_GROUP;
      }
    }
  }
  grouping NRFrequencyUeCfg-attributes {
    leaf nRFrequencyUeCfgId {
      description "The value component of the RDN..";
      type string;
      mandatory true;
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf ssbToMeasureConnected {
      description "Set of SS/PBCH blocks used for measurements. Applicable to UE in RRC Connected state when performing SS-RSRP measurement. Regardless of value of this attribute, SS/PBCH blocks outside of applicable SMTC window are not to be measured. Defined by bit string with string length equal to maximum number of SS/PBCH blocks within half radio frame. First leftmost bit corresponds to SS/PBCH block index 0, second bit corresponds to SS/PBCH block index 1, and so on. Bit value 0 indicates that corresponding SS/PBCH block is not to be measured while bit value 1 indicates that corresponding SS/PBCH block is to be measured. If non-empty: - UE is configured with information element SSB-ToMeasure according to setting. - At least one bit must be set to 1. If empty: - For intra-frequency measurements on frequency of current PCell or current PSCell, UE is configured with information element SSB-ToMeasure if such information is received from DU over F1 interface. - For intra-frequency measurements on frequency of current PCell or current PSCell, UE is not configured with information element SSB-ToMeasure if such information is not received from DU over F1 interface. - If not intra-frequency measurements, UE is not configured with information element SSB-ToMeasure. According to 3GPP specifications, UE then performs SS-RSRP measurement using all SS/PBCH blocks within SMTC window.; length 1..64.";
      type string {
        length "1..64";
        pattern "[0]*1[01]*";
      }
    }
    list ssRssiMeasConnected {
      key "id";
      leaf id {
        type uint32;
        description "Synthetic key for struct attribute.";
      }
      description "Set of slots and symbols, within SMTC measurement duration, used for SS-RSSI measurement. Applicable to UE in RRC Connected state when performing SS-RSSI measurement on serving or non-serving frequencies. If non-empty: - UE is configured with information element SS-RSSI-Measurement according to SsRssiMeasurement.measurementSlots and SsRssiMeasurement.endSymbol settings. If empty: - For intra-frequency measurements on frequency of current PCell or current PSCell, UE is configured with information element SS-RSSI-Measurement if such information is received from DU over F1 interface. - For intra-frequency measurements on frequency of current PCell or current PSCell, UE is not configured with information element SS-RSSI-Measurement if such information is not received from DU over F1 interface. - If not intra-frequency measurements, UE is not configured with information element SS-RSSI-Measurement. According to 3GPP specifications, UE performs SS-RSSI measurement using all slots and symbols within SSB Measurement Timing Configuration (SMTC) measurement duration, in case information element SS-RSSI-Measurement is not provided to UE..";
      uses SsRssiMeasurement-struct;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 16;
    }
    leaf-list ueGroupList {
      description "UE group list. List of UE group identifiers. If empty, MO instance matches all UE group identifiers..";
      type eytypes:int32_range_1-255;
      ordered-by user;
      min-elements 0;
      max-elements 32;
    }
    leaf userLabel {
      description "Label for free use..";
      type string;
    }
  }
  grouping NRNetwork-attributes {
    leaf nRNetworkId {
      description "The value component of the RDN..";
      type string;
      mandatory true;
    }
  }
  grouping OffloadCellProfile-attributes {
    leaf offloadCellProfileId {
      description "The value component of the RDN..";
      type string;
      mandatory true;
    }
    leaf-list reservedBy {
      description "Contains a list of MO instances that reserve this MO instance..";
      type string;
      min-elements 0;
    }
    leaf softUeReleaseTime {
      description "Time period for procedure of emptying a cell from traffic.; range 10..180.";
      type int32 {
        range "10..180";
      }
      units "s";
    }
    leaf ueConfGroupType {
      description "UE configuration group type. UE configuration group type that is applied in contained OffloadCellProfileUeCfg instances..";
      type enumeration {
        enum UE_MOBILITY_GROUP;
        enum UE_SERVICE_GROUP;
        enum UE_ADMISSION_GROUP;
      }
    }
  }
  grouping OffloadCellProfileUeCfg-attributes {
    leaf cellOffloadPriority {
      description "UE group priority for initiating measurements for cell offload. If 0, cell offload is not performed for UE group. If 7, UE group has highest priority for initiating cell offload-related measurements. Offload measurements are first initiated for UE group with the highest priority, on a best effort basis. Cell offload is only applicable to SA UE group.; range 0..7; Default value: 1.";
      type eytypes:int32_range_0-7;
      default "1";
    }
    leaf checkForOffloadEnd {
      description "Whether checking presence of UE during cell offload is enabled. Valid for UE in this UE configuration group. Applicable to SA and EN-DC.; Default value: false.";
      type boolean;
      default "false";
    }
    leaf maxReportCells {
      description "Maximum number of non-serving cells included in measurement report. Only applicable to event A5 and event B1.; range 1..8; Default value: 1.";
      type eytypes:int32_range_1-8;
      default "1";
    }
    leaf offloadCellProfileUeCfgId {
      description "The value component of the RDN..";
      type string;
      mandatory true;
    }
    leaf offloadISHoEnabled {
      description "Whether offload inter-system handover is enabled.; Default value: false.";
      type boolean;
      default "false";
    }
    leaf pCellCandidateTriggerQuantity {
      description "Measurement trigger quantity used when searching for NR or E-UTRAN PCell candidate. Used when doing offload for following features: - NR Cell Soft Lock - NR Booster Carrier Sleep - NR Traffic Offload - NR Mobility (Prohibited Cell-Triggered Mobility function).";
      type enumeration {
        enum RSRP;
        enum RSRQ;
        enum SINR_FALLBACK_RSRP;
        enum SINR_FALLBACK_RSRQ;
      }
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf rimOffloadIncHoRsrpThresh {
      description "Required minimum received RSRP level for allowing incoming handover if cell is in RIM condition. If empty, IE q-RxLevMin in SIB1 from message F1AP GNB-DU CONFIGURATION UPDATE is used for checking against the received RSRP. Only applicable to Mid-Band cells.; range -140..-44.";
      type eytypes:int32_range_-140--44;
      units "dBm";
    }
    leaf rsrpPCellCandAddTargEval {
      description "Additional target evaluation of other reported quantity. Applicable when searching for NR PCell candidate with A5 event with trigger quantity RSRP. Other reported quantity SINR is evaluated towards threshold value defined by following formula: threshold2 in sinrPCellCandidate + hysteresis in sinrPCellCandidate + OffloadNrFreqRelProfileUeCfg::sinrPCellCandidateOffset Other reported quantity RSRQ is evaluated towards threshold value defined by following formula: threshold2 in rsrqPCellCandidate + hysteresis in rsrqPCellCandidate + OffloadNrFreqRelProfileUeCfg::rsrqPCellCandidateOffset.";
      type enumeration {
        enum NONE;
        enum RSRQ;
        enum SINR_FALLBACK_RSRQ;
        enum SINR_NO_FALLBACK_RSRQ;
      }
    }
    leaf rsrpPCellCandB1AddTargEval {
      description "Additional target evaluation of other reported quantity. Applicable when searching for E-UTRAN PCell candidate with B1 event with trigger quantity RSRP. Other reported quantity SINR is evaluated towards threshold value defined by following formula: threshold2 in sinrPCellCandidateB1 + hysteresis in sinrPCellCandidateB1 + OffloadEUtranFreqRelProfileUeCfg::sinrPCellCandidateB1Offset Other reported quantity RSRQ is evaluated towards threshold value defined by following formula: threshold2 in rsrqPCellCandidateB1 + hysteresis in rsrqPCellCandidateB1 + OffloadEUtranFreqRelProfileUeCfg::rsrqPCellCandidateB1Offset.";
      type enumeration {
        enum NONE;
        enum RSRQ;
        enum SINR_FALLBACK_RSRQ;
        enum SINR_NO_FALLBACK_RSRQ;
      }
    }
    list rsrpPCellCandidate {
      key "id";
      leaf id {
        type uint32;
        description "Synthetic key for struct attribute.";
      }
      description "RSRP A5 measurement report criteria when searching for NR PCell candidate. Used when pCellCandidateTriggerQuantity is RSRP..";
      uses ReportConfigA5NoThr1Rsrp-struct;
    }
    list rsrpPCellCandidateB1 {
      key "id";
      leaf id {
        type uint32;
        description "Synthetic key for struct attribute.";
      }
      description "RSRP B1 measurement report criteria when searching for E-UTRAN PCell candidate. Used when pCellCandidateTriggerQuantity is RSRP..";
      uses ReportConfigB1Rsrp-struct;
    }
    leaf rsrqPCellCandAddTargEval {
      description "Additional target evaluation of other reported quantity. Applicable when searching for NR PCell candidate with A5 event with trigger quantity RSRQ. Other reported quantity RSRP is evaluated towards threshold value defined by following formula: threshold2 in rsrpPCellCandidate + hysteresis in rsrpPCellCandidate + OffloadNrFreqRelProfileUeCfg::rsrpPCellCandidateOffset - NRCellRelation::cellIndividualOffsetNR.";
      type enumeration {
        enum NONE;
        enum RSRP;
      }
    }
    leaf rsrqPCellCandB1AddTargEval {
      description "Additional target evaluation of other reported quantity. Applicable when searching for E-UTRAN PCell candidate with B1 event with trigger quantity RSRQ. Other reported quantity RSRP is evaluated towards threshold value defined by following formula: threshold2 in rsrpPCellCandidateB1 + hysteresis in rsrpPCellCandidateB1 + OffloadEUtranFreqRelProfileUeCfg::rsrpPCellCandidateB1Offset - EUtranCellRelation::cellIndividualOffset.";
      type enumeration {
        enum NONE;
        enum RSRP;
      }
    }
    list rsrqPCellCandidate {
      key "id";
      leaf id {
        type uint32;
        description "Synthetic key for struct attribute.";
      }
      description "RSRQ A5 measurement report criteria when searching for NR PCell candidate. Used when pCellCandidateTriggerQuantity is RSRQ..";
      uses ReportConfigA5NoThr1Rsrq-struct;
    }
    list rsrqPCellCandidateB1 {
      key "id";
      leaf id {
        type uint32;
        description "Synthetic key for struct attribute.";
      }
      description "RSRQ B1 measurement report criteria when searching for E-UTRAN PCell candidate. Used when pCellCandidateTriggerQuantity is RSRQ..";
      uses ReportConfigB1Rsrq-struct;
    }
    leaf sinrPCellCandAddTargEval {
      description "Additional target evaluation of other reported quantity. Applicable when searching for NR PCell candidate with A5 event with trigger quantity SINR. Other reported quantity RSRP is evaluated towards threshold value defined by following formula: threshold2 in rsrpPCellCandidate + hysteresis in rsrpPCellCandidate + OffloadNrFreqRelProfileUeCfg::rsrpPCellCandidateOffset - NRCellRelation::cellIndividualOffsetNR Other reported quantity RSRQ is evaluated towards threshold value defined by following formula: threshold2 in rsrqPCellCandidate + hysteresis in rsrqPCellCandidate + OffloadNrFreqRelProfileUeCfg::rsrqPCellCandidateOffset.";
      type enumeration {
        enum NONE;
        enum RSRP;
        enum RSRQ;
        enum RSRP_AND_RSRQ;
      }
    }
    leaf sinrPCellCandB1AddTargEval {
      description "Additional target evaluation of other reported quantity. Applicable when searching for E-UTRAN PCell candidate with B1 event with trigger quantity SINR. Other reported quantity RSRP is evaluated towards threshold value defined by following formula: threshold2 in rsrpPCellCandidateB1 + hysteresis in rsrpPCellCandidateB1 + OffloadEUtranFreqRelProfileUeCfg::rsrpPCellCandidateB1Offset - EUtranCellRelation::cellIndividualOffset Other reported quantity RSRQ is evaluated towards threshold value defined by following formula: threshold2 in rsrqPCellCandidateB1 + hysteresis in rsrqPCellCandidateB1 + OffloadEUtranFreqRelProfileUeCfg::rsrqPCellCandidateB1Offset.";
      type enumeration {
        enum NONE;
        enum RSRP;
        enum RSRQ;
        enum RSRP_AND_RSRQ;
      }
    }
    list sinrPCellCandidate {
      key "id";
      leaf id {
        type uint32;
        description "Synthetic key for struct attribute.";
      }
      description "SINR A5 measurement report criteria when searching for NR PCell candidate. Used when pCellCandidateTriggerQuantity is SINR..";
      uses ReportConfigA5NoThr1Sinr-struct;
    }
    list sinrPCellCandidateB1 {
      key "id";
      leaf id {
        type uint32;
        description "Synthetic key for struct attribute.";
      }
      description "SINR B1 measurement report criteria when searching for E-UTRAN PCell candidate. Used when pCellCandidateTriggerQuantity is set to SINR..";
      uses ReportConfigB1Sinr-struct;
    }
    leaf softUeReleasePriority {
      description "Handover priority for a UE group during Soft UE Release. If 0, no handover is required for UE group and 7 is highest priority.; range 0..7.";
      type eytypes:int32_range_0-7;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf ueOffloadISHoRatio {
      description "Threshold that can trigger offload inter-system handover. Used as a factor to adjust AdmissionLimit::maxConnectedUeOffloadISHo for selected UEs. If 1000, no adjustment.; range 0..1000; Default value: 1000.";
      type eytypes:int32_range_0-1000-11;
      default "1000";
      units "percent";
    }
  }
  grouping OffloadEUtranFreqRelProfile-attributes {
    leaf offloadEUtranFreqRelProfileId {
      description "The value component of the RDN..";
      type string;
      mandatory true;
    }
    leaf-list reservedBy {
      description "Contains a list of MO instances that reserve this MO instance..";
      type string;
      min-elements 0;
    }
    leaf ueConfGroupType {
      description "UE configuration group type. UE configuration group type that is applied in contained OffloadEUtranFreqRelProfileUeCfg instances..";
      type enumeration {
        enum UE_MOBILITY_GROUP;
        enum UE_SERVICE_GROUP;
        enum UE_ADMISSION_GROUP;
      }
    }
  }
  grouping OffloadEUtranFreqRelProfileUeCfg-attributes {
    leaf offloadEUtranFreqRelProfileUeCfgId {
      description "The value component of the RDN..";
      type string;
      mandatory true;
    }
    leaf offloadISHoAllowed {
      description "Whether this frequency relation is allowed for offload-triggered inter-system handover.; Default value: false.";
      type boolean;
      default "false";
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf rimOffloadType {
      description "RIM offloading method in target frequency. Only applicable to Mid-Band cells..";
      type enumeration {
        enum NOT_ALLOWED;
        enum BLIND_RWR;
      }
    }
    leaf rsrpPCellCandidateB1Offset {
      description "RSRP B1 measurement threshold offset when searching for E-UTRAN PCell candidate. Used in combination with OffloadCellProfileUeCfg::rsrpPCellCandidateB1.; range -100..100; Default value: 0.";
      type eytypes:int32_range_-100-100;
      default "0";
      units "dB";
    }
    leaf rsrqPCellCandidateB1Offset {
      description "RSRQ B1 measurement threshold offset when searching for E-UTRAN PCell candidate. Used in combination with OffloadCellProfileUeCfg::rsrqPCellCandidateB1.; range -100..100; Default value: 0.";
      type eytypes:int32_range_-100-100;
      default "0";
      units "dB";
    }
    leaf sinrPCellCandidateB1Offset {
      description "SINR B1 measurement threshold offset when searching for E-UTRAN PCell candidate. Used in combination with OffloadCellProfileUeCfg::sinrPCellCandidateB1.; range -100..100; Default value: 0.";
      type eytypes:int32_range_-100-100;
      default "0";
      units "dB";
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
  }
  grouping OffloadNrFreqRelProfile-attributes {
    leaf offloadNrFreqRelProfileId {
      description "The value component of the RDN..";
      type string;
      mandatory true;
    }
    leaf-list reservedBy {
      description "Contains a list of MO instances that reserve this MO instance..";
      type string;
      min-elements 0;
    }
    leaf ueConfGroupType {
      description "UE configuration group type. UE configuration group type that is applied in contained OffloadNrFreqRelProfileUeCfg instances..";
      type enumeration {
        enum UE_MOBILITY_GROUP;
        enum UE_SERVICE_GROUP;
        enum UE_ADMISSION_GROUP;
      }
    }
  }
  grouping OffloadNrFreqRelProfileUeCfg-attributes {
    leaf offloadNrFreqRelProfileUeCfgId {
      description "The value component of the RDN..";
      type string;
      mandatory true;
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf rimOffloadType {
      description "RIM offloading method in target frequency. Only applicable to Mid-Band cells..";
      type enumeration {
        enum NOT_ALLOWED;
        enum BLIND_RWR;
      }
    }
    leaf rsrpPCellCandidateOffset {
      description "RSRP A5 measurement threshold2 offset when searching for NR PCell candidate. Used in combination with OffloadCellProfileUeCfg::rsrpPCellCandidate.; range -100..100; Default value: 0.";
      type eytypes:int32_range_-100-100;
      default "0";
      units "dB";
    }
    leaf rsrqPCellCandidateOffset {
      description "RSRQ A5 measurement threshold2 offset when searching for NR PCell candidate. Used in combination with OffloadCellProfileUeCfg::rsrqPCellCandidate.; range -100..100; Default value: 0.";
      type eytypes:int32_range_-100-100;
      default "0";
      units "dB";
    }
    leaf sinrPCellCandidateOffset {
      description "SINR A5 measurement threshold2 offset when searching for NR PCell candidate. Used in combination with OffloadCellProfileUeCfg::sinrPCellCandidate.; range -100..100; Default value: 0.";
      type eytypes:int32_range_-100-100;
      default "0";
      units "dB";
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
  }
  grouping PciConflictEUtran-attributes {
    leaf pciConflictDetectionThreshLTE {
      description "Criteria for handover execution success ratio suspected of PCI conflict in E-UTRAN. If empty, detection of suspicious EUtran cells is deactivated.; range 1..99.";
      type eytypes:int32_range_1-99;
    }
    leaf pciConflictEUtranId {
      description "The value component of the RDN..";
      type string;
      mandatory true;
    }
    leaf ueConfGroupType {
      description "UE configuration group type. UE configuration group type that is applied in contained PciConflictEUtranUeCfg instances..";
      type enumeration {
        enum UE_MOBILITY_GROUP;
        enum UE_SERVICE_GROUP;
        enum UE_ADMISSION_GROUP;
      }
    }
  }
  grouping PciConflictEUtranUeCfg-attributes {
    leaf pciConflictDetectionEcgiMeas {
      description "ECGI measurement to UE for cell suspected of PCI conflict..";
      type enumeration {
        enum DISABLED;
        enum ENABLED;
      }
    }
    leaf pciConflictDrxInactivityTimer {
      description "Number of consecutive PDCCH subframes after successfully decoding PDCCH. Used to read CGI for PCI conflict function..";
      type enumeration {
        enum INACTIVITYTIMER_0MS;
        enum INACTIVITYTIMER_1MS;
        enum INACTIVITYTIMER_2MS;
        enum INACTIVITYTIMER_3MS;
        enum INACTIVITYTIMER_4MS;
        enum INACTIVITYTIMER_5MS;
        enum INACTIVITYTIMER_6MS;
        enum INACTIVITYTIMER_8MS;
        enum INACTIVITYTIMER_10MS;
        enum INACTIVITYTIMER_20MS;
        enum INACTIVITYTIMER_30MS;
        enum INACTIVITYTIMER_40MS;
        enum INACTIVITYTIMER_50MS;
        enum INACTIVITYTIMER_60MS;
        enum INACTIVITYTIMER_80MS;
        enum INACTIVITYTIMER_100MS;
        enum INACTIVITYTIMER_200MS;
        enum INACTIVITYTIMER_300MS;
        enum INACTIVITYTIMER_500MS;
        enum INACTIVITYTIMER_750MS;
        enum INACTIVITYTIMER_1280MS;
        enum INACTIVITYTIMER_1920MS;
        enum INACTIVITYTIMER_2560MS;
      }
    }
    leaf pciConflictDrxLongCycle {
      description "Long DRX cycle in number of subframes. Used to read CGI for PCI conflict function..";
      type enumeration {
        enum LONGCYCLE_10MS;
        enum LONGCYCLE_20MS;
        enum LONGCYCLE_32MS;
        enum LONGCYCLE_40MS;
        enum LONGCYCLE_60MS;
        enum LONGCYCLE_64MS;
        enum LONGCYCLE_70MS;
        enum LONGCYCLE_80MS;
        enum LONGCYCLE_128MS;
        enum LONGCYCLE_160MS;
        enum LONGCYCLE_256MS;
        enum LONGCYCLE_320MS;
        enum LONGCYCLE_512MS;
        enum LONGCYCLE_640MS;
        enum LONGCYCLE_1024MS;
        enum LONGCYCLE_1280MS;
        enum LONGCYCLE_2048MS;
        enum LONGCYCLE_2560MS;
        enum LONGCYCLE_5120MS;
        enum LONGCYCLE_10240MS;
      }
    }
    leaf pciConflictDrxOnDurationTimer {
      description "Number of consecutive PDCCH subframes at beginning of DRX cycle. Used to read CGI for PCI conflict function..";
      type enumeration {
        enum ONDURATIONTIMER_1SUBMS;
        enum ONDURATIONTIMER_2SUBMS;
        enum ONDURATIONTIMER_3SUBMS;
        enum ONDURATIONTIMER_4SUBMS;
        enum ONDURATIONTIMER_5SUBMS;
        enum ONDURATIONTIMER_6SUBMS;
        enum ONDURATIONTIMER_7SUBMS;
        enum ONDURATIONTIMER_8SUBMS;
        enum ONDURATIONTIMER_9SUBMS;
        enum ONDURATIONTIMER_10SUBMS;
        enum ONDURATIONTIMER_11SUBMS;
        enum ONDURATIONTIMER_12SUBMS;
        enum ONDURATIONTIMER_13SUBMS;
        enum ONDURATIONTIMER_14SUBMS;
        enum ONDURATIONTIMER_15SUBMS;
        enum ONDURATIONTIMER_16SUBMS;
        enum ONDURATIONTIMER_17SUBMS;
        enum ONDURATIONTIMER_18SUBMS;
        enum ONDURATIONTIMER_19SUBMS;
        enum ONDURATIONTIMER_20SUBMS;
        enum ONDURATIONTIMER_21SUBMS;
        enum ONDURATIONTIMER_22SUBMS;
        enum ONDURATIONTIMER_23SUBMS;
        enum ONDURATIONTIMER_24SUBMS;
        enum ONDURATIONTIMER_25SUBMS;
        enum ONDURATIONTIMER_26SUBMS;
        enum ONDURATIONTIMER_27SUBMS;
        enum ONDURATIONTIMER_28SUBMS;
        enum ONDURATIONTIMER_29SUBMS;
        enum ONDURATIONTIMER_30SUBMS;
        enum ONDURATIONTIMER_31SUBMS;
        enum ONDURATIONTIMER_1MS;
        enum ONDURATIONTIMER_2MS;
        enum ONDURATIONTIMER_3MS;
        enum ONDURATIONTIMER_4MS;
        enum ONDURATIONTIMER_5MS;
        enum ONDURATIONTIMER_6MS;
        enum ONDURATIONTIMER_8MS;
        enum ONDURATIONTIMER_10MS;
        enum ONDURATIONTIMER_20MS;
        enum ONDURATIONTIMER_30MS;
        enum ONDURATIONTIMER_40MS;
        enum ONDURATIONTIMER_50MS;
        enum ONDURATIONTIMER_60MS;
        enum ONDURATIONTIMER_80MS;
        enum ONDURATIONTIMER_100MS;
        enum ONDURATIONTIMER_200MS;
        enum ONDURATIONTIMER_300MS;
        enum ONDURATIONTIMER_400MS;
        enum ONDURATIONTIMER_500MS;
        enum ONDURATIONTIMER_600MS;
        enum ONDURATIONTIMER_800MS;
        enum ONDURATIONTIMER_1000MS;
        enum ONDURATIONTIMER_1200MS;
        enum ONDURATIONTIMER_1600MS;
      }
    }
    leaf pciConflictEUtranUeCfgId {
      description "The value component of the RDN..";
      type string;
      mandatory true;
    }
    leaf pciConflictMobilityEcgiMeas {
      description "ECGI measurement-based IRAT mobility. Only applicable if PciHandling::pciConflictHandlingEnabled is true..";
      type enumeration {
        enum DISABLED;
        enum ENABLED;
      }
    }
    leaf pciConflictTargetSelectMode {
      description "A mobility target selection mode in PCI conflicting configuration. If DISABLED, first found cell relation is selected for mobility in PCI conflict configuration. If HITRATE_BASED, target cell with higher ECGI hit-rate is selected for mobility in PCI conflict configuration. If MANUAL_BASED, target cell that EUtranCellRelation::preferredCellManual is true is selected for mobility in PCI conflict configuration. If HITRATE_MANUAL_BASED, target cell is selected based on ECGI hit-rate if it is valid. If fails, target cell EUtranCellRelation::preferredCellManual is true is selected. If MANUAL_HITRATE_BASED, target cell that EUtranCellRelation::preferredCellManual is true is selected for mobility in PCI conflict configuration. If fails, target cell with higher ECGI hit-rate is selected, first found cell relation is selected cell for mobility in PCI configuration. If ECGI hit-rate based or manual configuration based target cell selection fails, first found cell relation is selected for mobility in PCI configuration. Only applicable if PciHandling::pciConflictHandlingEnabled is true..";
      type enumeration {
        enum DISABLED;
        enum HITRATE_BASED;
        enum MANUAL_BASED;
        enum HITRATE_MANUAL_BASED;
        enum MANUAL_HITRATE_BASED;
      }
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
  }
  grouping PciConflictNR-attributes {
    leaf pciConflictDetectionThreshNr {
      description "Criteria for handover execution success ratio suspected of PCI conflict in NR. If empty, detection of suspicious NR cells is deactivated.; range 1..99.";
      type eytypes:int32_range_1-99;
    }
    leaf pciConflictNRId {
      description "The value component of the RDN..";
      type string;
      mandatory true;
    }
    leaf ueConfGroupType {
      description "UE configuration group type. UE configuration group type that is applied in contained PciConflictNRUeCfg instances..";
      type enumeration {
        enum UE_MOBILITY_GROUP;
        enum UE_SERVICE_GROUP;
        enum UE_ADMISSION_GROUP;
      }
    }
  }
  grouping PciConflictNRUeCfg-attributes {
    leaf pciConflictDetectionNcgiMeas {
      description "NCGI measurement to UE for cell suspected of PCI conflict..";
      type enumeration {
        enum DISABLED;
        enum FR1;
      }
    }
    leaf pciConflictDrxInactivityTimer {
      description "Number of consecutive PDCCH subframes after successfully decoding PDCCH. Used to read CGI for PCI conflict function. Only applicable to Low-Band and Mid-Band cells..";
      type enumeration {
        enum INACTIVITYTIMER_0MS;
        enum INACTIVITYTIMER_1MS;
        enum INACTIVITYTIMER_2MS;
        enum INACTIVITYTIMER_3MS;
        enum INACTIVITYTIMER_4MS;
        enum INACTIVITYTIMER_5MS;
        enum INACTIVITYTIMER_6MS;
        enum INACTIVITYTIMER_8MS;
        enum INACTIVITYTIMER_10MS;
        enum INACTIVITYTIMER_20MS;
        enum INACTIVITYTIMER_30MS;
        enum INACTIVITYTIMER_40MS;
        enum INACTIVITYTIMER_50MS;
        enum INACTIVITYTIMER_60MS;
        enum INACTIVITYTIMER_80MS;
        enum INACTIVITYTIMER_100MS;
        enum INACTIVITYTIMER_200MS;
        enum INACTIVITYTIMER_300MS;
        enum INACTIVITYTIMER_500MS;
        enum INACTIVITYTIMER_750MS;
        enum INACTIVITYTIMER_1280MS;
        enum INACTIVITYTIMER_1920MS;
        enum INACTIVITYTIMER_2560MS;
      }
    }
    leaf pciConflictDrxLongCycle {
      description "Long DRX cycle in number of subframes. Used to read CGI for PCI conflict function. Only applicable to Low-Band and Mid-Band cells..";
      type enumeration {
        enum LONGCYCLE_10MS;
        enum LONGCYCLE_20MS;
        enum LONGCYCLE_32MS;
        enum LONGCYCLE_40MS;
        enum LONGCYCLE_60MS;
        enum LONGCYCLE_64MS;
        enum LONGCYCLE_70MS;
        enum LONGCYCLE_80MS;
        enum LONGCYCLE_128MS;
        enum LONGCYCLE_160MS;
        enum LONGCYCLE_256MS;
        enum LONGCYCLE_320MS;
        enum LONGCYCLE_512MS;
        enum LONGCYCLE_640MS;
        enum LONGCYCLE_1024MS;
        enum LONGCYCLE_1280MS;
        enum LONGCYCLE_2048MS;
        enum LONGCYCLE_2560MS;
        enum LONGCYCLE_5120MS;
        enum LONGCYCLE_10240MS;
      }
    }
    leaf pciConflictDrxOnDurationTimer {
      description "Number of consecutive PDCCH subframes at beginning of DRX cycle. Used to read CGI for PCI conflict function. Only applicable to Low-Band and Mid-Band cells..";
      type enumeration {
        enum ONDURATIONTIMER_1SUBMS;
        enum ONDURATIONTIMER_2SUBMS;
        enum ONDURATIONTIMER_3SUBMS;
        enum ONDURATIONTIMER_4SUBMS;
        enum ONDURATIONTIMER_5SUBMS;
        enum ONDURATIONTIMER_6SUBMS;
        enum ONDURATIONTIMER_7SUBMS;
        enum ONDURATIONTIMER_8SUBMS;
        enum ONDURATIONTIMER_9SUBMS;
        enum ONDURATIONTIMER_10SUBMS;
        enum ONDURATIONTIMER_11SUBMS;
        enum ONDURATIONTIMER_12SUBMS;
        enum ONDURATIONTIMER_13SUBMS;
        enum ONDURATIONTIMER_14SUBMS;
        enum ONDURATIONTIMER_15SUBMS;
        enum ONDURATIONTIMER_16SUBMS;
        enum ONDURATIONTIMER_17SUBMS;
        enum ONDURATIONTIMER_18SUBMS;
        enum ONDURATIONTIMER_19SUBMS;
        enum ONDURATIONTIMER_20SUBMS;
        enum ONDURATIONTIMER_21SUBMS;
        enum ONDURATIONTIMER_22SUBMS;
        enum ONDURATIONTIMER_23SUBMS;
        enum ONDURATIONTIMER_24SUBMS;
        enum ONDURATIONTIMER_25SUBMS;
        enum ONDURATIONTIMER_26SUBMS;
        enum ONDURATIONTIMER_27SUBMS;
        enum ONDURATIONTIMER_28SUBMS;
        enum ONDURATIONTIMER_29SUBMS;
        enum ONDURATIONTIMER_30SUBMS;
        enum ONDURATIONTIMER_31SUBMS;
        enum ONDURATIONTIMER_1MS;
        enum ONDURATIONTIMER_2MS;
        enum ONDURATIONTIMER_3MS;
        enum ONDURATIONTIMER_4MS;
        enum ONDURATIONTIMER_5MS;
        enum ONDURATIONTIMER_6MS;
        enum ONDURATIONTIMER_8MS;
        enum ONDURATIONTIMER_10MS;
        enum ONDURATIONTIMER_20MS;
        enum ONDURATIONTIMER_30MS;
        enum ONDURATIONTIMER_40MS;
        enum ONDURATIONTIMER_50MS;
        enum ONDURATIONTIMER_60MS;
        enum ONDURATIONTIMER_80MS;
        enum ONDURATIONTIMER_100MS;
        enum ONDURATIONTIMER_200MS;
        enum ONDURATIONTIMER_300MS;
        enum ONDURATIONTIMER_400MS;
        enum ONDURATIONTIMER_500MS;
        enum ONDURATIONTIMER_600MS;
        enum ONDURATIONTIMER_800MS;
        enum ONDURATIONTIMER_1000MS;
        enum ONDURATIONTIMER_1200MS;
        enum ONDURATIONTIMER_1600MS;
      }
    }
    leaf pciConflictMobilityNcgiMeas {
      description "NCGI measurement-based intra-NR mobility. Only applicable if PciHandling::pciConflictHandlingEnabled is true..";
      type enumeration {
        enum DISABLED;
        enum FR1;
      }
    }
    leaf pciConflictNRUeCfgId {
      description "The value component of the RDN..";
      type string;
      mandatory true;
    }
    leaf pciConflictTargetSelectMode {
      description "A mobility target selection mode in PCI conflicting configuration. If DISABLED, first found cell relation is selected for mobility in PCI conflict configuration. If HITRATE_BASED, target cell with higher NCGI hit-rate is selected for mobility in PCI conflict configuration. If MANUAL_BASED, target cell where NRCellRelation::preferredCellManual is true is selected for mobility in PCI conflict configuration. If HITRATE_MANUAL_BASED, target cell is selected based on NCGI hit-rate if it is valid. If fails, target cell that NRCellRelation::preferredCellManual is true is selected. If MANUAL_HITRATE_BASED, target cell that NRCellRelation::preferredCellManual is true is selected for mobility in PCI conflict configuration. If fails, target cell with higher NCGI hit-rate is selected. If NCGI hit-rate based or manual configuration based target cell selection fails, first found cell relation is selected for mobility in PCI configuration. Only applicable if PciHandling::pciConflictHandlingEnabled is true..";
      type enumeration {
        enum DISABLED;
        enum HITRATE_BASED;
        enum MANUAL_BASED;
        enum HITRATE_MANUAL_BASED;
        enum MANUAL_HITRATE_BASED;
      }
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
  }
  grouping PciHandling-attributes {
    leaf pciConflictHandlingEnabled {
      description "Whether PCI conflict detection and resolution reporting is enabled. If true, following is supported: - finding PCI conflict suspicious cells along with PciConflictNR::pciConflictDetectionThreshNr and PciConflictNRUeCfg::pciConflictDetectionNcgiMeas. - PCI conflict mitigation in addition to PciConflictNRUeCfg::pciConflictDetectionNcgiMeas.; Default value: false.";
      type boolean;
      default "false";
    }
    leaf pciHandlingId {
      description "The value component of the RDN..";
      type string;
      mandatory true;
    }
  }
  grouping PeriodicUeMeas-attributes {
    leaf periodicUeMeasId {
      description "The value component of the RDN..";
      type string;
      mandatory true;
    }
    leaf userLabel {
      description "Label for free use..";
      type string;
    }
  }
  grouping PmUeIntraFreqCellProfile-attributes {
    leaf maxReportCells {
      description "Maximum number of non-serving cells included in measurement report.; range 1..8; Default value: 4.";
      type eytypes:int32_range_1-8;
      default "4";
    }
    leaf pmUeIntraFreqCellProfileId {
      description "The value component of the RDN..";
      type string;
      mandatory true;
    }
    leaf pmUeReportType {
      description "Report type used in PM UE measurement..";
      type enumeration {
        enum PERIODICAL;
        enum EVENT_A2;
        enum EVENT_A3;
      }
    }
    leaf reportAmount {
      description "Number of periodical or event-triggered measurement reports..";
      type enumeration {
        enum R1;
        enum R2;
        enum R4;
        enum R8;
        enum R16;
        enum R32;
        enum R64;
        enum INFINITY;
      }
    }
    list reportConfigA2Rsrp {
      key "id";
      leaf id {
        type uint32;
        description "Synthetic key for struct attribute.";
      }
      description "Event A2 measurement reporting criteria. Applied if reportType is EVENT_A2 and trigger quantity is RSRP..";
      uses ReportConfigA1A2Rsrp-struct;
    }
    list reportConfigA2Rsrq {
      key "id";
      leaf id {
        type uint32;
        description "Synthetic key for struct attribute.";
      }
      description "Event A2 measurement reporting criteria. Applied if reportType is EVENT_A2 and trigger quantity is RSRQ..";
      uses ReportConfigA1A2Rsrq-struct;
    }
    list reportConfigA3Rsrp {
      key "id";
      leaf id {
        type uint32;
        description "Synthetic key for struct attribute.";
      }
      description "Event A3 measurement reporting criteria. Applied if reportType is EVENT_A3 and trigger quantity is RSRP..";
      uses ReportConfigA3Rsrp-struct;
    }
    list reportConfigA3Rsrq {
      key "id";
      leaf id {
        type uint32;
        description "Synthetic key for struct attribute.";
      }
      description "Event A3 measurement reporting criteria. Applied if reportType is EVENT_A3 and trigger quantity is RSRQ..";
      uses ReportConfigA3Rsrq-struct;
    }
    leaf reportInterval {
      description "Interval for periodical or event-triggered measurement reports..";
      type enumeration {
        enum MS_120;
        enum MS_240;
        enum MS_480;
        enum MS_640;
        enum MS_1024;
        enum MS_2048;
        enum MS_5120;
        enum MS_10240;
        enum MS_20480;
        enum MS_40960;
        enum MIN_1;
        enum MIN_6;
        enum MIN_12;
        enum MIN_30;
      }
    }
    list reportQuantityCell {
      key "id";
      leaf id {
        type uint32;
        description "Synthetic key for struct attribute.";
      }
      description "Cell measurement quantities to be included in measurement report..";
      uses ReportQuantityCell-struct;
    }
    leaf-list reservedBy {
      description "Contains a list of MO instances that reserve this MO instance..";
      type string;
      min-elements 0;
    }
    leaf triggerQuantity {
      description "Measurement quantity that triggers event A2 or A3 measurements. Applied when reportType is EVENT_A2 or EVENT_A3..";
      type enumeration {
        enum RSRP;
        enum RSRQ;
      }
    }
    leaf ueSelectionRatio {
      description "UE selection ratio for PM UE measurements configuration.; range 0..1000; Default value: 100.";
      type eytypes:int32_range_0-1000-11;
      default "100";
      units "percent";
    }
    leaf userLabel {
      description "Label for free use..";
      type string;
    }
  }
  grouping PmUeMeas-attributes {
    leaf pmUeMeasId {
      description "The value component of the RDN..";
      type string;
      mandatory true;
    }
  }
  grouping PrefUeGroupSelectionProfile-attributes {
    leaf chipsetRef {
      description "Reference to an instance of Chipsets MO. Special <Value> \"ref\" for <Variable> chipset in selectionCriteria represents chipset <ValueList> defined via this reference. If empty, represented chipset <ValueList> is empty..";
      type string;
    }
    leaf imeiSvRef {
      description "Reference to an instance of ImeiSvs MO. Special <Value> \"ref\" for <Variable> imeisv in selectionCriteria represents imeisv <ValueList> defined via this reference. If empty, represented imeisv <ValueList> is empty..";
      type string;
    }
    leaf prefUeGroupId {
      description "Preference UE group identifier.; range 1..255.";
      type eytypes:int32_range_1-255;
      mandatory true;
    }
    leaf prefUeGroupPriority {
      description "Relative priority among preference UE groups. If UE fulfills more than one PrefUeGroupSelectionProfile, PrefUeGroupSelectionProfile with the highest relative priority is applied. Higher value gives higher priority.; range 1..65535.";
      type eytypes:int32_range_1-65535;
      mandatory true;
    }
    leaf prefUeGroupSelectionProfileId {
      description "The value component of the RDN..";
      type string;
      mandatory true;
    }
    leaf selectionCriteria {
      description "Preference UE group selection criteria. Defines selection criteria that UE needs to fulfill to belong to the Preference UE group instance. If selection criteria evaluates to True, UE fulfills Preference UE group instance. If selection criteria evaluates to False or Unknown, UE does not fulfill Preference UE group instance. If selection criteria evaluates to True for more than one Preference UE group instance, UE belongs to the Preference UE group instance with highest setting of prefUeGroupPriority. Syntax: ====== The syntax of selection criteria is defined using Backus-Naur form. <SelectionCriteria> ::= <ParentExpressionList> | \"\" <ParentExpressionList> ::= <ParentExpressionList> <AndOr> < ParentExpressionList> | <Not>? \"(\" <ParentExpressionList> \")\" | <ExpressionList> | <FlowExpressionList> <FlowExpressionList> ::= <FlowExpressionList> <AndOr> <FlowExpressionList> | <Not>? <FlowExpression> <FlowExpression> ::= \"[\"<ExpressionList>\"]\" <ExpressionList> ::= <ExpressionList> <AndOr> <ExpressionList> | <Not>? \"(\" <ExpressionList> \")\" | <Not>? <VariableExpression> <VariableExpression> ::= <Variable> <RelationalOperator> <Value> | <Variable> \"==\" \"{\" <ValueList> \"}\" <ValueList> ::= <Value> \",\" <ValueList> | <Value> <Variable> ::= \"5qi\" | \"arp\" | \"cgrole\" | \"chipset\" | \"imeisv\" | \"imeisvn\" | \"imeitac\" | \"pagingPrio\" | \"pCellOnlyUe\" | \"plmn\" | \"qci\" | \"redCapUe\" | \"rfsp\" | \"rrcEstResCause\" | \"snssai\" | \"spid\" | \"voNrUe\" <AndOr> ::= \"&&\" | \"||\" <Not> ::= \"!\" <RelationalOperator> ::= \"==\" | \"!=\" | \"<\" | \"<=\" | \">=\" | \">\" A list of possible values can be specified in the form <Variable> == {<value1>, <value2>, ... , <valueN>}. This statement is equivalent to writing (<Variable> == <value1> || <Variable> == <value2> || ... || <Variable> == <valueN>). Up to 4 <FlowExpression> can be defined in <SelectionCriteria>. Whitespaces are allowed in the string for improved readability and are removed prior to evaluation. Question mark (?) means zero or one occurrence. For example, <Not>? makes <Not> optional. Syntax is case sensitive. Semantic: ======== Selection criteria evaluation is defined by the following semantic rules. If empty or set to empty string \"\", selection criteria always evaluates to True. Selection criteria evaluation is done per UE with the current applicable UE <Variable> values as input. List of UE <Variable> values that are applicable to NR standalone and EN-DC, respectively, is defined in Variable Definitions section below. Selection criteria for a UE is evaluated separately for each flow using applicable flow-dependent <Variable> together with rest of applicable UE <Variable>. For UE in NR standalone flow-dependent <Variable> 5qi, arp, and snssai are applicable. For UE in EN-DC flow-dependent <Variable> qci, and arp are applicable. Selection criteria evaluates to True if any of the flows evaluates to True. If UE does not have a flow, flow-dependent <Variable> values are evaluated as unknown variable values. If selection criteria shall match combination of flow-dependent <Variable>, then <FlowExpression> and <FlowExpressionList> must be used. Note: An <ExpressionList> defined as <VariableExpression> && <VariableExpression>, for which both <VariableExpression> relate to flow-dependent <Variable>, needs special attention. Example: <ExpressionList> = \"5qi==5 && 5qi==9\" always evaluate to False for UE in NR standalone even if UE has one flow with 5qi=5 and one flow with 5qi=9. Example: <ExpressionList> = \"5qi>=7 && 5qi<=11\" will evaluate to True for UE in NR standalone if UE has any flow with 5qi between 7 and 11. <FlowExpression> is defined as \"[\"<ExpressionList>\"]\" and indicates that an <ExpressionList> is evaluated per QoS flow independent of other <ExpressionList>. Example: <FlowExpressionList> = \"[5qi==1] && [5qi==5]\" evaluates to True for UE in NR standalone if UE has any flow with 5qi=1 and any flow with 5qi=5. In the example, [5qi==1] must match one flow, and [5qi==5] must match one flow. <VariableExpression> evaluates to Unknown if <Variable> is not known or if the <Variable> value is not valid. <VariableExpression> evaluates to True or False if <Variable> value is known and valid. <Value> \"ref\" is a special <Value> of <Variable> representing <ValueList> defined via corresponding reference attribute. For <Variable> chipset, and imeisv, corresponding reference attribute is chipsetRef, and imeiSvRef respectively. If reference attribute is empty, represented <ValueList> is empty. The logical operators <AndOr> and <Not> apply three way logic as defined below: F=False; T=True; U=Unknown A=Evaluation result of <ExpressionList> or <VariableExpression> B=Evaluation result of <ExpressionList> or <VariableExpression> NOT operator: A !A ----------------- F T U U T F AND operator: A B A && B ------------------- F F F F T F F U F T F F T T T T U U U F F U T U U U U OR operator: A B A || B ------------------ F F F F T T F U U T F T T T T T U T U F U U T T U U U Variable Definitions: ================= Allowed <Value> and <RelationalOperator> depend on <Variable> with limitations given below. 5qi: 5G QoS Identifier (3GPP TS 23.501). Applicable to NR standalone. Operator: ==, !=, <=, >=, <, and >. Value: Integer in range 0..255 given in decimal. arp: Priority Level part of the Allocation and Retention Priority (3GPP TS 38.413, 3GPP TS 36.423). Applicable to both NR standalone and EN-DC. Operator: ==, !=, <=, >=, <, and >. Value: Integer in range 1..15 given in decimal. cgrole: Cell group role. Applicable to both NR standalone and EN-DC. Operator: ==, and !=. Value: mcg or scg, where mcg is only applicable to NR standalone. chipset: Chipset identifier. Applicable to both NR standalone and EN-DC. Operator: ==, and !=. Value: String in format \"<vendor>.<variant>.<version>\" matched by regular expression \"(1[0-6]|[0-9])\\\\.(6[0-4]|[1-5]?[0-9])\\\\.(12[0-8]|1[01][0-9]|[1-9]?[0-9])\", or a string constant \"ref\". Description: Chipset identifier composed of three distinct elements: - vendor: 1-2 digit decimal number in range 0..16 - variant: 1-2 digit decimal number in range 0..64 - version: 1-3 digit decimal number in range 0..128 UEs that do not support chipset identifier reporting are represented internally as 0.0.0. Example values: 0.0.0, 1.1.1, 1.2.3, 16.10.100, 16.64.128, ref. imeisv: International Mobile Station Equipment Identity Software Version. Applicable to both NR standalone and EN-DC. Operator: ==, and !=. Value: String in format \"<TAC><SNR><SVN>\" matched by regular expression \"[0-9]{10}[0-9fF]{4}[0-9]{2}\", or string constant \"ref\". Description: IMEISV composed of three distinct elements: - TAC (Type Allocation Code): 8 digit decimal number - SNR (or SN, Serial Number): 2 digit decimal number + 4 digit hexa-decimal number, last four digits are automatically masked with 0xFFFF to match with masked IMEISV - SVN (Software Version Number): 2 digit decimal number Example values: 1234567890123456, 1234567890FFFF12, 1234567890ffff12, ref. imeitac: Type Allocation Code (TAC) part of imeisv. Applicable to both NR standalone and EN-DC. Operator: ==, !=, <=, >=, <, and >. Value: 8 digit decimal number. imeisvn: Software Version Number (SVN) part of imeisv. Applicable to both NR standalone and EN-DC. Operator: ==, !=, <=, >=, <, and >. Value: 2 digit decimal number. pagingPrio: Paging Priority (3GPP TS 23.501). Applicable to NR standalone. Operator: ==, !=, <=, >=, <, and > Value: Integer in range 1..8 given in decimal. Description: Paging priority value received in NGAP Paging message. The received value is valid in UE grouping framework when performing UE group evaluation during time specified by UeGroupSelection::validityTimePagingPrio. pCellOnlyUe: Low-Band and Mid-Band PCell-only capability. Indicates whether the UE is not capable of carrier aggregation in Low-Band or Mid-Band. Only applicable when performing UE group evaluation in NR standalone Master Node. Operator: ==, and !=. Value: Integer in range 0..1 given in decimal, where 0 means false and 1 means true. Only applicable if license for Flexible UE Grouping for Limited Capability UEs is present and feature is active. plmn: Public Land and Mobile Network identifier. Applicable to both NR standalone and EN-DC. Operator: ==, and !=. Value: A string matched by regular expression \"[02-79][0-9][0-9]-[0-9][0-9][0-9]?\". Example values: 070-007, 070-07, 234-56. qci: QoSClass Identifier (3GPP TS 23.401). Applicable to EN-DC. Operator: ==, !=, <=, >=, <, and >. Value: Integer in range 0..255 given in decimal. redCapUe: Reduced Capabilities UE indicator. Applicable to NR standalone. Operator: ==, and !=. Value: Integer in range 0..1 given in decimal, where 0 means false and 1 means true. Description: RedCap UE identification received via LCID in MSG3 (see 3GPP TS 38.331). rfsp: Index to RAT/Frequency Selection Priority (3GPP TS 23.501). Applicable to NR standalone. Operator: ==, !=, <=, >=, <, and >. Value: Integer in range 1..256 given in decimal. rrcEstResCause: RRC establishment cause or RRC resume cause. Applicable to NR standalone. Operator: ==, and !=. Value: One of emergency, highPriorityAccess, mt-Access, mo-Signaling, mo-Data, mo-VoiceCall, mo-VideoCall, mo-SMS, mps-PriorityAccess, or mcs-PriorityAccess. Description: Establishment cause value received in RRC Setup Request message or resume cause received in RRC Resume Request message (see 3GPP TS 38.331). The received establishment cause or resume cause is valid in UE grouping framework when performing UE group evaluation during time specified by corresponding validity time attribute value in MO class UeGroupSelection. snssai: Single Network Slice Selection Assistance Information (3GPP TS 23.003). Applicable to NR standalone. Operator: ==, !=, <=, >=, <, and >. Value: input option 1: String in format \"<SST><SD>\" matched by regular expression [0][x][0-9a-fA-F]{8} (8 digit hexa-decimal number). Value: input option 2: Integer in range 0x0..0xffffffff given in hexadecimal. Description: S-NSSAI is composed of two distinct elements: - SST (Slice/Service Type): 2 digit hexa-decimal number - SD (Slice Differentiator): 6 digit hexa-decimal number The SD field has a reserved value \"no SD value associated with the SST\" defined as hexadecimal FFFFFF/ffffff. Example values, input option 1: - 0x050000EE (SST=0x05,SD=0x0000EE) - 0x2effffff (SST=0x2e,SD=0xffffff // no SD associated with the SST) Example values, input option 2: - 0x1 (SST=0x00,SD=0x000001) - 0x50000EE (SST=0x05,SD=0x0000EE) - 0x150000EE (SST=0x15,SD=0x0000EE) spid: Subscriber Profile ID for RAT/Frequency Priority (3GPP TS 36.300). Applicable to EN-DC. Operator: ==, !=, <=, >=, <, and >. Value: Integer in range 1..256 given in decimal. voNrUe: Low-Band and Mid-Band VoNR capability. Only applicable when performing UE group evaluation in NR standalone Master Node. Operator: ==, and !=. Value: Integer in range 0..1 given in decimal, where 0 means false and 1 means true. Operator Precedence Order: ======================= The logical and relation operators are evaluated according to the precedence order listed below. --------------------------------------------- 1 (highest precedence) < Less than <= Less than or equal > Greater than >= Greater than or equal == Equal != Not equal ------------------------------------------- 2 ! (Not) --------------------------------------------- 3 && (And) --------------------------------------------- 4 (lowest precedence) || (Or) --------------------------------------------- The NOT operator \"!\" negates the following <ParentExpressionList>, <VariableExpression>, <FlowExpression> or an <ExpressionList> encapsulated in parenthesis. Therefore, expression !a==b && c==d is equivalent to ((!(a==b)) && (c==d)) and different from !(a==b && c==d). Expression !a==b and !(a==b) are equivalent. Since AND operator \"&&\" has higher precedence than OR operator \"||\", a<b || a<c && c<d is equivalent to (a<b || (a<c && c<d)). Surround expression list including OR operator with parenthesis to force OR operator to be evaluated before AND operators outside of the expression list, for example (a<b || a<c) && c<d. Examples: ========= Simple one valued expressions: plmn == 234-56 spid == 1 cgrole == mcg arp > 3 snssai == 0xfedcba98 rrcEstResCause == mo-VoiceCall imeisv == 1234567890FFFF12 imeisv == ref //Special <value> ref represents <ValueList> defined via imeiSvRef. chipset == ref chipset == 1.1.1 //Matches all UEs with chipset identifier: vendor = 1, variant = 1 and version = 1. chipset == 0.0.0 //Matches all UEs that do not support chipset identifier reporting. Value list expressions: spid == {8,9,10,1,155} !plmn == {234-56, 434-567} chipset == {1.1.1, 1.1.2, 1.1.3, ref} //Matches all UEs with chipset identifier: vendor = 1, variant = 1 and version = 1, 2 or 3, or the corresponding vendor, variant and version defined via chipsetRef. imeisv == {1234567890FFFF12, ref, 1234567890FFFF13} //Matches all UEs with imeisv: TAC = 12345678, SNR = 90FFFF and SVN = 12 or 13, or the corresponding TAC, SN and SVN defined via imeiSvRef. Equivalent expressions using ||: (spid == 8 || spid == 9 || spid == 10 || spid == 1 || spid == 155) //Equals to spid == {8, 9, 10, 1, 155}. !(plmn == 234-56 || plmn == 434-567) //Equals to !plmn == {234-56, 434-567}. imeisv == ref || imeisv == 1234567890FFFF12|| imeisv == 1234567890FFFF13 //Equals to imeisv == {ref, 1234567890FFFF12, 1234567890FFFF13}. chipset == 1.1.1 || chipset == ref || chipset == 1.1.2 // Equals to chipset == {1.1.1, ref, 1.1.2}. Negative expressions: !5qi==1 //Matches flows with 5qi not equal to 1. 5qi!=1 //Matches flows with 5qi not equal to 1. Negative <FlowExpressions> that produce same result: [!5qi==1] //Matches flows with 5qi not equal to 1. [5qi!=1] //Matches flows with 5qi not equal to 1. <FlowExpressionList> negative expressions: !([5qi==1]) //Matches UEs that do not have flows with 5qi 1. ![5qi==1] //Matches UEs that do not have flows with 5qi 1. Mixed examples: spid == 1 && cgrole == mcg !(spid != 1 || cgrole != mcg) (spid == 8 || spid == 9 || spid == 10 || spid == 1 || spid == 155) && (plmn == 234-56 || plmn == 434-567) Precedence given by \"()\" and sequence alter the evaluation order and result: [5qi==1] && chipset==ref || imeisv==ref && [5qi==5] //Equals to ([5qi==1] && chipset==ref) || (imeisv==ref && [5qi==5]) [5qi==1] && (chipset==ref || imeisv==ref) && [5qi==5] ([5qi==1] && chipset==ref || imeisv==ref) && [5qi==5] [5qi==1] && (chipset==ref || imeisv==ref && [5qi==5]) chipset==ref || [5qi==1] && [5qi==5] && imeisv==ref Examples of selection criteria that shall be avoided since they will always be evaluated to False. <FlowExpression> can be used in these cases. 5qi==5 && 5qi==9 snssai==0x15000000 && snssai==0x17000000 arp==5 && arp==10 qci==5 && qci==9 Example of selection criteria for UE variable snssai: snssai>=15000000 && snssai<=15FFFFFF //Matches UE which has a flow with S-NSSAI SST part equal to 15 regardless of value of S-NSSAI SD part. snssai==15FFFFFF //Matches UE which has a flow with S-NSSAI SST part equal to 15 and S-NSSAI SD part value equal to FFFFFF, meaning no SD value associated with the SST. Flow expressions combined with UE variables: plmn == 234-56 && [5qi==1] && [5qi==9] //Matches UE which has plmn equal to 234-56, any QoS flow with 5qi equal to 1, and any QoS flow with 5qi equal to 9. chipset==1.5.32 && [5qi==9] && ![5qi==1] //Matches UE which has chipset identifier equal to 1.5.32, any QoS flow with 5qi equal to 9, and no QoS flow with 5qi equal to 1. [5qi==1 && snssai == 0xfedcba98] || ([5qi==2] && [snssai == 0xfedcba77]) //Matches UE which has any QoS flow with 5qi equal to 1 and snssai equal to 0xfedcba98, or has any QoS flow with 5qi equal to 2 and snssai equal to 0xfedcba77. voNrUe==1 && chipset==1.1.1 && [5qi==1] //Matches UEs with Low-Band and Mid-Band VoNR capability using chipset 1.1.1, and have an ongoing flow 5qi.; length 1..1000.";
      type string {
        length "1..1000";
      }
    }
    leaf userLabel {
      description "Label for free use..";
      type string;
    }
  }
  grouping PriorityService-attributes {
    list arp5qiPairList {
      key "id";
      leaf id {
        type uint32;
        description "Synthetic key for struct sequence entry.";
      }
      min-elements 0;
      max-elements 8;
      uses Arp5qiPair-struct;
    }
    leaf mpsPriorityForRwr {
      description "Whether MPS priority indication is supported in release with redirect. If true, following applies: If Multimedia Priority Services (MPS) user is identified, then in RRCRelease message in release with redirect procedure, the MPS priority indication flag is set.; Default value: false.";
      type boolean;
      default "false";
    }
    list pLMNIdList {
      key "id";
      leaf id {
        type uint32;
        description "Synthetic key for struct sequence entry.";
      }
      min-elements 0;
      max-elements 12;
      uses PLMNId-struct;
    }
    leaf priorityServiceId {
      description "The value component of the RDN..";
      type string;
      mandatory true;
    }
    leaf userLabel {
      description "Label for free use..";
      type string;
    }
  }
  grouping PuemCellProfile-attributes {
    leaf puemCellProfileId {
      description "The value component of the RDN..";
      type string;
      mandatory true;
    }
    leaf puemCellTargetIntensity {
      description "Target intensity of periodic UE measurements for each hour for cell. If 0, no measurements are configured.; Default value: 360.";
      type int32 {
        range "0..720 | 1440 | 2160 | 2880 | 3600";
      }
      default "360";
    }
    leaf-list reservedBy {
      description "Contains a list of MO instances that reserve this MO instance..";
      type string;
      min-elements 0;
    }
    leaf ueConfGroupType {
      description "UE configuration group type. UE configuration group type that is applied in contained PuemCellProfileUeCfg instances..";
      type enumeration {
        enum UE_MOBILITY_GROUP;
        enum UE_SERVICE_GROUP;
        enum UE_ADMISSION_GROUP;
      }
    }
    leaf userLabel {
      description "Label for free use..";
      type string;
    }
  }
  grouping PuemCellProfileUeCfg-attributes {
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf puemCellProfileUeCfgId {
      description "The value component of the RDN..";
      type string;
      mandatory true;
    }
    list puemReportConfigPeriodical {
      key "id";
      leaf id {
        type uint32;
        description "Synthetic key for struct attribute.";
      }
      description "Report configuration setting for periodical UE measurements..";
      uses PuemReportConfigPeriodical-struct;
    }
    leaf puemUeGroupEnabled {
      description "Whether periodic UE measurements are enabled for UE group.; Default value: true.";
      type boolean;
      default "true";
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping QciProfileEndcConfigExt-attributes {
    leaf initialUplinkConf {
      description "Initial uplink configuration for EN-DC and NR-DC. Whether to use MCG or SCG leg for uplink at initial state. Set when dual connectivity is configured.; Default value: MCG; Takes effect: New connection; Status info: Since 25.Q1. Replaced by UlDataSplitUeCfg::initialUlPrimaryPathMode. Planned to be removed..";
      type enumeration {
        enum MCG;
        enum SCG;
      }
      status deprecated;
      default "MCG";
      reference "Takes effect: New connection.";
    }
    leaf qciProfileEndcConfigExtId {
      description "The value component of the RDN.; MOM flags: restricted, noNotification; Status info: Since 25.Q1. Planned to be removed..";
      type string;
      mandatory true;
      status deprecated;
    }
    leaf ulDataSplitThreshold {
      description "Buffer threshold for uplink PDCP split for capable UE instances. Specifies buffer level where capable UE instances can split data on both main and secondary leg when primary path is SCG. A capable UE is a UE with dual connectivity supporting split DRB with uplink on both MCG and SCG. This UE can submit uplink PDCP PDUs to both primary RLC entity and secondary RLC entity if total amount of PDCP and RLC data volume for initial transmission in two associated RLC entities is equal or larger than used threshold. If 0, uplink PDCP split is always active for capable UE instances. If -1, used threshold is infinity meaning that PDCP split is not allowed even for capable UE instances. The attribute is common for EN-DC and NR-DC. If empty, used threshold will be automatically controlled for EN-DC users and set to infinity for NR-DC users. Without license for LTE-NR Uplink Aggregation a value of infinity is used for EN-DC and NR-DC users.; Takes effect: New connection; MOM flags: isNillable=true; Status info: Since 25.Q1. Replaced by UlDataSplitUeCfg::ulDataSplitThreshScg. Planned to be removed.; Specification: 3GPP TS 38.463, 3GPP TS 38.331, 3GPP TS 38.323.";
      type int32 {
        range "-1..0 | 100 | 200 | 400 | 800 | 1600 | 3200 | 6400 | 12800 | 25600 | 51200 | 102400 | 204800 | 409600 | 819200 | 1228800 | 1638400 | 2457600 | 3276800 | 4096000 | 4915200 | 5734400 | 6553600";
      }
      status deprecated;
      units "byte";
      reference "Takes effect: New connection.";
    }
    leaf ulDataSplitThresholdMcg {
      description "Buffer threshold for uplink PDCP split for capable UE instances when primary path is MCG. This attribute is only applicable to EN-DC UEs. For NR-DC UEs used threshold is infinity meaning that PDCP split is not allowed when primary path is MCG. Only applicable if license for LTE-NR Uplink Aggregation is present and feature is active. Following settings are possible: - If empty and value for ulDataSplitThreshold is also empty, threshold is 51200. - If empty and value for ulDataSplitThreshold is non-empty, value according to ulDataSplitThreshold is used. - If -1, threshold is infinity meaning that PDCP split is not allowed. - If 0, UL PDCP split is always active. - Value -1 is recommended when NRCellDU::endcUlLegSwitchEnabled is true and a low value is set for NRCellDU::endcUlNrLowQualThresh. - Values 0 to 1600 are only recommended for operators for temporary testing purposes.; Takes effect: New connection; MOM flags: isNillable=true; Status info: Since 25.Q1. Replaced by UlDataSplitUeCfg::ulDataSplitThreshMcg. Planned to be removed.; Specification: 3GPP TS 38.463, 3GPP TS 38.331, 3GPP TS 38.323.";
      type int32 {
        range "-1..0 | 100 | 200 | 400 | 800 | 1600 | 3200 | 6400 | 12800 | 25600 | 51200 | 102400 | 204800 | 409600 | 819200 | 1228800 | 1638400 | 2457600 | 3276800 | 4096000 | 4915200 | 5734400 | 6553600";
      }
      status deprecated;
      units "byte";
      reference "Takes effect: New connection.";
    }
  }
  grouping RelaxedRrmMeas-attributes {
    leaf relaxedRrmMeasId {
      description "The value component of the RDN..";
      type string;
      mandatory true;
    }
  }
  grouping RelaxedRrmMeasCellProfile-attributes {
    leaf combineRelaxedMeasCondition {
      description "Whether UE must fulfill both low mobility and cell edge criteria for relaxed measurements. Only applicable when sSearchDeltaP, tSearchDeltaP and sSearchThresholdP are non-empty.; Default value: false.";
      type boolean;
      default "false";
    }
    leaf combineRelaxedMeasCondition2 {
      description "Whether UE must fulfill both stationary and cell edge criteria for relaxed measurements. Only applicable when sSearchDeltaPStationary, tSearchDeltaPStationary and sSearchThresholdP2 are non-empty. Only applicable to RedCap devices.; Default value: false.";
      type boolean;
      default "false";
    }
    leaf highPriorityMeasRelax {
      description "Whether low mobility is sufficient for higher priority frequency measurements to be relaxed. Only applicable when sSearchDeltaP and tSearchDeltaP are non-empty.; Default value: false.";
      type boolean;
      default "false";
    }
    leaf relaxedRrmMeasCellProfileId {
      description "The value component of the RDN..";
      type string;
      mandatory true;
    }
    leaf-list reservedBy {
      description "Contains a list of MO instances that reserve this MO instance..";
      type string;
      min-elements 0;
    }
    leaf sSearchDeltaP {
      description "Threshold for Srxlev variation in low mobility criterion for relaxed measurements. If empty, value is not broadcast in SIB2, and UE is not configured for low mobility evaluation. Only applicable when tSearchDeltaP is non-empty..";
      type int32 {
        range "3 | 6 | 9 | 12 | 15";
      }
      units "dB";
    }
    leaf sSearchDeltaPStationary {
      description "Threshold for Srxlev variation in stationary criterion for relaxed measurements. If empty, value is not broadcast in SIB2, and UE is not configured for stationary evaluation. Only applicable when tSearchDeltaPStationary is non-empty. Only applicable to RedCap devices..";
      type int32 {
        range "2..3 | 6 | 9 | 12 | 15";
      }
      units "dB";
    }
    leaf sSearchThresholdP {
      description "Threshold for Srxlev in not-at-cell-edge criterion for relaxed measurements. If empty, value is not broadcast in SIB2, and UE is not configured for evaluation of not-at-cell-edge.; range 0..62.";
      type eytypes:int32_range_0-62;
      units "dB";
    }
    leaf sSearchThresholdP2 {
      description "Threshold for Srxlev in not-at-cell-edge while stationary criterion for relaxed measurements. If empty, value is not broadcast in SIB2, and UE is not configured for evaluation of not-at-cell-edge while stationary. Only applicable when sSearchDeltaPStationary and tSearchDeltaPStationary are non-empty. Only applicable to RedCap devices.; range 0..62.";
      type eytypes:int32_range_0-62;
      units "dB";
    }
    leaf sSearchThresholdQ {
      description "Threshold for Squal in not-at-cell-edge criterion for relaxed measurements. If empty, value is not broadcast in SIB2. Only applicable when sSearchThresholdP is non-empty.; range 0..31.";
      type eytypes:int32_range_0-31;
      units "dB";
    }
    leaf sSearchThresholdQ2 {
      description "Threshold for Squal in not-at-cell-edge while stationary criterion for relaxed measurements. If empty, value is not broadcast in SIB2. Only applicable when sSearchThresholdP2 is non-empty. Only applicable to RedCap devices.; range 0..31.";
      type eytypes:int32_range_0-31;
      units "dB";
    }
    leaf tSearchDeltaP {
      description "Duration of Srxlev variation measurement in low mobility criterion for relaxed measurements. If empty, value is not broadcast in SIB2, and UE is not configured for low mobility evaluation. Only applicable when sSearchDeltaP is non-empty..";
      type int32 {
        range "5 | 10 | 20 | 30 | 60 | 120 | 180 | 240 | 300";
      }
      units "s";
    }
    leaf tSearchDeltaPStationary {
      description "Duration of Srxlev variation measurement in stationary criterion for relaxed measurements. If empty, value is not broadcast in SIB2, and UE is not configured for stationary evaluation. Only applicable when sSearchDeltaPStationary is non-empty. Only applicable to RedCap devices..";
      type int32 {
        range "5 | 10 | 20 | 30 | 60 | 120 | 180 | 240 | 300";
      }
      units "s";
    }
    leaf userLabel {
      description "Label for free use..";
      type string;
    }
  }
  grouping ResourcePartition-attributes {
    leaf related5qiTableRef {
      description "Reference to an instance of CUCP5qiTable MO..";
      type string;
    }
    leaf-list reservedBy {
      description "Contains a list of MO instances that reserve this MO instance. Currently not used..";
      type string;
      min-elements 0;
    }
    leaf resourcePartitionId {
      description "The value component of the RDN..";
      type string;
      mandatory true;
    }
    leaf resourcePartitionName {
      description "Name of a resource partition.; length 1..255.";
      type string {
        length "1..255";
      }
    }
  }
  grouping ResourcePartitionMember-attributes {
    leaf endpointResourceRef {
      description "Reference to an instance of EndpointResource MO. Defines transport network configuration for specific PLMN or NSSAI. If empty, GNBCUCPFunction::endpointResourceRef is used. Cannot refer to EndpointResource MO which has LocalSctpEndpoint::interfaceUsed set to F1. F1 SctpEndpoint can only be referenced from GNBCUCPFunction::endpointResourceRef..";
      type string;
    }
    list pLMNIdList {
      key "id";
      leaf id {
        type uint32;
        description "Synthetic key for struct sequence entry.";
      }
      min-elements 0;
      max-elements 12;
      uses PLMNId-struct;
    }
    leaf resourcePartitionMemberId {
      description "The value component of the RDN..";
      type string;
      mandatory true;
    }
    list sNSSAIList {
      key "id";
      leaf id {
        type uint32;
        description "Synthetic key for struct sequence entry.";
      }
      min-elements 0;
      max-elements 1024;
      uses SliceSelectionAssistInfo-struct;
    }
  }
  grouping ResourcePartitions-attributes {
    leaf resourcePartitionsId {
      description "The value component of the RDN..";
      type string;
      mandatory true;
    }
  }
  grouping RibTmRelation-attributes {
    leaf additionalInfo {
      description "Information about any Radio Interface-Based Time Monitoring error..";
      type enumeration {
        enum FEATURE_DEACTIVATED;
        enum PEER_FEATURE_DEACTIVATED;
        enum UNSUPP_HW_CONF;
        enum PEER_UNSUPP_HW_CONF;
        enum MAX_PAIRS;
        enum PEER_MAX_PAIRS;
        enum NO_RESP_FROM_PEER;
        enum PCI_CONFLICT;
        enum INCOMPATIBLE_CELLS;
        enum CELL_DISABLED;
        enum PEER_CELL_DISABLED;
      }
      config false;
    }
    leaf administrativeState {
      description "The administrative state. If set to SHUTTINGDOWN, the state is immediately brought to LOCKED..";
      type enumeration {
        enum LOCKED;
        enum UNLOCKED;
        enum SHUTTINGDOWN;
      }
    }
    leaf-list availabilityStatus {
      description "The availability status. It contains details about operationalState..";
      type AvailStatus;
      min-elements 0;
    }
    leaf isRemoveAllowed {
      description "Whether Radio Interface-Based Time Monitoring (RIB-TM) autoconfiguration can remove this instance. This setting does not restrict operator removal of object. Objects created by RIB-TM autoconfiguration have this attribute set to true initially.; Default value: false.";
      type boolean;
      default "false";
    }
    leaf measurementQuality {
      description "Quality of Radio Interface-Based Time Monitoring measurements..";
      type enumeration {
        enum NO_MEASUREMENTS;
        enum UNKNOWN;
        enum RELIABLE;
        enum UNRELIABLE;
      }
      config false;
    }
    leaf operationalState {
      description "The operational state..";
      type enumeration {
        enum DISABLED;
        enum ENABLED;
      }
      config false;
    }
    leaf peerCellRef {
      description "Reference to the assisting cell. Can be an instance of ExternalNRCellCU MO..";
      type string;
      mandatory true;
    }
    leaf ribTmRelationId {
      description "The value component of the RDN..";
      type string;
      mandatory true;
    }
    leaf-list pmRibtmTimeErrorDistr {
      description "Node time alignment error measured on radio interface-based time monitoring relation by Radio Interface-Based Time Monitoring feature. Covers all sector carrier pairs valid for radio interface-based time monitoring relation. Unit: N/A Ranges: Bin[0]: [..-3000[ nanoseconds Bin[1]: [-3000..-2500[ nanoseconds Bin[2]: [-2500..-2000[ nanoseconds Bin[3]: [-2000..-1500[ nanoseconds Bin[4]: [-1500..-1000[ nanoseconds Bin[5]: [-1000..-500[ nanoseconds Bin[6]: [-500..0[ nanoseconds Bin[7]: [0..500] nanoseconds Bin[8]: ]500..1000] nanoseconds Bin[9]: ]1000..1500] nanoseconds Bin[10]: ]1500..2000] nanoseconds Bin[11]: ]2000..2500] nanoseconds Bin[12]: ]2500..3000] nanoseconds Bin[13]: ]3000..] nanoseconds.";
      type uint64;
      max-elements 14;
    }
  }
  grouping Rohc-attributes {
    leaf rohcId {
      description "The value component of the RDN..";
      type string;
      mandatory true;
    }
    leaf ueConfGroupType {
      description "UE configuration group type. UE configuration group type that is applied in contained RohcUeCfg instances..";
      type enumeration {
        enum UE_MOBILITY_GROUP;
        enum UE_SERVICE_GROUP;
        enum UE_ADMISSION_GROUP;
      }
    }
  }
  grouping RohcUeCfg-attributes {
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf-list rohc5qiList {
      description "Rohc5qi list. List of 5QIs for which Robust Header Compression is enabled.; Default values sequence: 1.";
      type int32 {
        range "1 | 65..66";
      }
      ordered-by user;
      min-elements 0;
      max-elements 16;
    }
    leaf rohcUeCfgId {
      description "The value component of the RDN..";
      type string;
      mandatory true;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping Rrc-attributes {
    leaf rrcId {
      description "The value component of the RDN..";
      type string;
      mandatory true;
    }
    leaf t312 {
      description "Timer t312. Waiting time for fast radio link failure recovery. Recommended to be less than t310 under GNBDUFunction instance for fast radio link failure recovery. Otherwise, there is no benefit.; Default value: 1000.";
      type int32 {
        range "0 | 50 | 100 | 200 | 300 | 400 | 500 | 1000";
      }
      default "1000";
      units "ms";
    }
    leaf ueConfGroupType {
      description "UE configuration group type. UE configuration group type that is applied in contained RrcUeCfg instances..";
      type enumeration {
        enum UE_MOBILITY_GROUP;
        enum UE_SERVICE_GROUP;
        enum UE_ADMISSION_GROUP;
      }
    }
  }
  grouping RrcInactiveProfile-attributes {
    leaf rrcInactiveProfileId {
      description "The value component of the RDN..";
      type string;
      mandatory true;
    }
    leaf ueConfGroupType {
      description "UE configuration group type. UE configuration group type that is applied in contained RrcInactiveProfileUeCfg instances..";
      type enumeration {
        enum UE_MOBILITY_GROUP;
        enum UE_SERVICE_GROUP;
        enum UE_ADMISSION_GROUP;
      }
    }
  }
  grouping RrcInactiveProfileUeCfg-attributes {
    leaf periodicRnaUpdateCount {
      description "Indicates the amount of periodic RNA update procedure before UE becomes RRC_IDLE. If 0, UE becomes RRC_INACTIVE when RRCResumeRequest message is received. If n, and n is greater than 0, - UE becomes RRC_IDLE when nth RRCResumeRequest message is received. - UE becomes RRC_INACTIVE every time an RRCResumeRequests message is received, except for nth one.; range 0..5; Default value: 1.";
      type eytypes:int32_range_0-5;
      default "1";
    }
    leaf periodicRnaUpdateTimer {
      description "Configuration of t380. Value of t380 for UE is calculated based on this attribute and Periodic Registration Update timer provided by Core Network.; Default value: 60.";
      type int32 {
        range "5 | 10 | 20 | 30 | 60 | 120 | 360 | 720";
      }
      default "60";
      units "minute";
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf rrcInactiveProfileUeCfgId {
      description "The value component of the RDN..";
      type string;
      mandatory true;
    }
    leaf rrcInactiveStateSupport {
      description "Whether RRC Inactive state is supported. Applies to RRC Release procedure triggered by user plane and control plane inactivity.; Default value: true.";
      type boolean;
      default "true";
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping RrcUeCfg-attributes {
    leaf dedicatedSib1AtHo {
      description "Whether dedicatedSIB1-Delivery IE is included in RRCReconfiguration message at handover.; Default value: false.";
      type boolean;
      default "false";
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf rrcReestForcedFallback {
      description "Whether forced fallback to RRC connection establishment is enabled. If true, fallback to RRC connection establishment is performed regardless of other conditions when RRC reestablishment procedure is triggered.; Default value: false.";
      type boolean;
      default "false";
    }
    leaf rrcUeCfgId {
      description "The value component of the RDN..";
      type string;
      mandatory true;
    }
    leaf tWaitForRrcReestRequest {
      description "Waiting time for the RRC Reestablishment Request message upon detecting Radio Link Failure. Used by RBS.; range 1..20; Default value: 6.";
      type eytypes:int32_range_1-20;
      default "6";
      units "s";
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping SecurityHandling-attributes {
    leaf-list cipheringAlgoPrio {
      description "Array of allowed ciphering algorithms with priority order. Minimum length of 1, maximum length of 4. Algorithm in index zero has highest priority. Each algorithm written only once in array..";
      type CipheringAlgorithmID;
      min-elements 1;
      max-elements 4;
    }
    leaf featCtrlIntegProtUserPlane {
      description "Whether the feature Integrity Protection of User Plane is on or off..";
      type enumeration {
        enum OFF;
        enum ON;
      }
    }
    leaf integProtUserPlaneLowRate {
      description "Whether a low rate Integrity Protection is handled by reject or no Integrity Protection..";
      type enumeration {
        enum REJECT;
        enum NO_INTEGRITY_PROTECTION;
      }
    }
    leaf-list integrityProtectAlgoPrio {
      description "Array of allowed integrity algorithms with priority order. Minimum length of 1, maximum length of 3. Algorithm in index zero has highest priority. Each algorithm written only once in array..";
      type IntegrityAlgorithmID;
      min-elements 1;
      max-elements 3;
    }
    leaf personalDataProtectionEnabled {
      description "Whether personal data protection is enabled. When personal data protection is enabled, subscriber personal data is not logged. If protection is disabled, there are rare traffic occasions when subscriber personal data is revealed and can be logged in PM events and other short-lived on-demand troubleshooting logs. Alert is raised when personal data protection is set to be disabled.; Default value: true.";
      type boolean;
      default "true";
    }
    leaf securityHandlingId {
      description "The value component of the RDN..";
      type string;
      mandatory true;
    }
  }
  grouping TermPointToAmf-attributes {
    list additionalOperatorPlmnIdList {
      key "id";
      leaf id {
        type uint32;
        description "Synthetic key for struct sequence entry.";
      }
      min-elements 0;
      max-elements 11;
      uses PLMNId-struct;
    }
    leaf administrativeState {
      description "The administrative state. If set to SHUTTINGDOWN, the state is immediately brought to LOCKED..";
      type enumeration {
        enum LOCKED;
        enum UNLOCKED;
        enum SHUTTINGDOWN;
      }
    }
    leaf amfName {
      description "AMF name used by ENM to identify an AMF. Set by RBS at NG-SETUP or AMF CONFIGURATION UPDATE..";
      type string;
      config false;
    }
    leaf-list availabilityStatus {
      description "The availability status. It contains details about operationalState..";
      type AvailStatus;
      min-elements 0;
    }
    leaf defaultAmf {
      description "Whether TermPointToAmf instance is a default AMF.; Default value: true.";
      type boolean;
      default "true";
    }
    leaf domainName {
      description "Fully qualified domain name of AMF. Consists of one or more labels, separated by dots (.). Valid characters for labels are limited to letters a - z, A - Z, digits 0 - 9, and character - (dash). Character case is preserved. Length of labels cannot exceed 255 characters. NOTE: First and last character in domain name cannot be the character - (dash). For more information, see RFC 952, 1101 and 1123.; length 1..255.";
      type string {
        length "1..255";
        pattern "(((([a-zA-Z0-9]([a-zA-Z0-9\\-]){0,255})?[a-zA-Z0-9]\\.)*([a-zA-Z0-9]([a-zA-Z0-9\\-]){0,255})?[a-zA-Z0-9]\\.?)|\\.)";
      }
    }
    leaf ipv4Address1 {
      description "Primary IPv4 address of AMF for NG-C interface. The input format is four fields of digits, separated by dots. Each field consists of three digits. The value of each field must be in the range 0..255.; length 7..15; Default value: 0.0.0.0.";
      type string {
        length "7..15";
        pattern "((25[0-5]|(2[0-4]|1{0,1}[0-9]){0,1}[0-9])\\.){3}(25[0-5]|(2[0-4]|1{0,1}[0-9]){0,1}[0-9])";
      }
      default "0.0.0.0";
    }
    leaf ipv4Address2 {
      description "Secondary IPv4 address of AMF for NG-C interface. The input format is four fields of digits, separated by dots. Each field consists of three digits. The value of each field must be in the range 0..255.; length 7..15; Default value: 0.0.0.0.";
      type string {
        length "7..15";
        pattern "((25[0-5]|(2[0-4]|1{0,1}[0-9]){0,1}[0-9])\\.){3}(25[0-5]|(2[0-4]|1{0,1}[0-9]){0,1}[0-9])";
      }
      default "0.0.0.0";
    }
    leaf ipv6Address1 {
      description "Primary IPv6 address of AMF for NG-C interface. The input format is eight fields, separated by colons. Each field consists of four hexadecimal characters. The value of each field must be in the range 0..FFFF. Leading zeroes can be omitted in a field, and multiple groups of 16 bits of zeroes can be compressed to ::. The :: can be used only once in an address.; length 2..39; Default value: ::.";
      type string {
        length "2..39";
        pattern "(::|((([0-9A-Fa-f]{1,4}):){7}(([0-9A-Fa-f]{1,4})|:))|((([0-9A-Fa-f]{1,4}):){6}(:([0-9A-Fa-f]{1,4})|:))|((([0-9A-Fa-f]{1,4}):){5}(((:([0-9A-Fa-f]{1,4})){1,2})|:))|((([0-9A-Fa-f]{1,4}):){4}(((:([0-9A-Fa-f]{1,4})){1,3})|:))|((([0-9A-Fa-f]{1,4}):){3}(((:([0-9A-Fa-f]{1,4})){1,4})|:))|((([0-9A-Fa-f]{1,4}):){2}(((:([0-9A-Fa-f]{1,4})){1,5})|:))|((([0-9A-Fa-f]{1,4}):)(((:([0-9A-Fa-f]{1,4})){1,6})|:))|(:(:([0-9A-Fa-f]{1,4})){1,7}))";
      }
      default "::";
    }
    leaf ipv6Address2 {
      description "Secondary IPv6 address of AMF for NG-C interface. The input format is eight fields, separated by colons. Each field consists of four hexadecimal characters. The value of each field must be in the range 0..FFFF. Leading zeroes can be omitted in a field, and multiple groups of 16 bits of zeroes can be compressed to ::. The :: can be used only once in an address.; length 2..39; Default value: ::.";
      type string {
        length "2..39";
        pattern "(::|((([0-9A-Fa-f]{1,4}):){7}(([0-9A-Fa-f]{1,4})|:))|((([0-9A-Fa-f]{1,4}):){6}(:([0-9A-Fa-f]{1,4})|:))|((([0-9A-Fa-f]{1,4}):){5}(((:([0-9A-Fa-f]{1,4})){1,2})|:))|((([0-9A-Fa-f]{1,4}):){4}(((:([0-9A-Fa-f]{1,4})){1,3})|:))|((([0-9A-Fa-f]{1,4}):){3}(((:([0-9A-Fa-f]{1,4})){1,4})|:))|((([0-9A-Fa-f]{1,4}):){2}(((:([0-9A-Fa-f]{1,4})){1,5})|:))|((([0-9A-Fa-f]{1,4}):)(((:([0-9A-Fa-f]{1,4})){1,6})|:))|(:(:([0-9A-Fa-f]{1,4})){1,7}))";
      }
      default "::";
    }
    leaf isRemoveAllowed {
      description "Whether Discovery of AMFs via DNS function can remove this instance. If false, Discovery of AMFs via DNS function also does not modify this object. Setting does not restrict operator removal of object. Objects created by Discovery of AMFs via DNS function have this attribute set to true initially.; Default value: false.";
      type boolean;
      default "false";
    }
    leaf operationalState {
      description "The operational state..";
      type enumeration {
        enum DISABLED;
        enum ENABLED;
      }
      config false;
    }
    list operatorPLMNId {
      key "id";
      leaf id {
        type uint32;
        description "Synthetic key for struct attribute.";
      }
      description "PLMN identifier used to select transport configuration for NG-C interface. PLMN identifier is also used for alarm filtering purposes. If empty, GNBCUCPFunction::pLMNId is used..";
      uses PLMNId-struct;
    }
    list pLMNIdList {
      config false;
      min-elements 0;
      max-elements 12;
      uses PLMNId-struct;
    }
    leaf pwsRestartHandling {
      description "Whether the NG-C link is used to send restart and failure messages related to PWS. Note: If ENABLED but no connection exists between AMF and CBC function, the PWS restart and failure messages are lost..";
      type enumeration {
        enum DISABLED;
        enum ENABLED;
      }
    }
    leaf relativeCapacity {
      description "Relative processing capacity of an AMF to other AMFs in pool. Capacity is used to balance the load between AMFs in a pool.; range 0..255.";
      type eytypes:int32_range_0-255;
      config false;
    }
    list servedGuamiList {
      config false;
      min-elements 0;
      max-elements 256;
      uses GlobalUniqueAmfId-struct;
    }
    list sNSSAIList {
      config false;
      min-elements 0;
      max-elements 1024;
      uses SliceSelectionAssistInfo-struct;
    }
    leaf termPointToAmfId {
      description "The value component of the RDN..";
      type string;
      mandatory true;
    }
    list unavailableGuamiList {
      config false;
      min-elements 0;
      max-elements 256;
      uses GlobalUniqueAmfId-struct;
    }
    leaf usedIpAddress {
      description "The destination address used for initialization of underlying SCTP association. Contains the address of the latest successful NGAP Setup. The IP address can be an IPv4 or an IPv6 address.; length 2..39.";
      type string {
        length "2..39";
      }
      config false;
    }
  }
  grouping TermPointToENodeB-attributes {
    leaf administrativeState {
      description "The administrative state. If set to SHUTTINGDOWN, the state is immediately brought to LOCKED..";
      type enumeration {
        enum LOCKED;
        enum UNLOCKED;
        enum SHUTTINGDOWN;
      }
    }
    leaf-list availabilityStatus {
      description "The availability status. It contains details about operational state..";
      type AvailStatus;
      min-elements 0;
    }
    leaf ipsecEpAddress {
      description "Outer IP address of X2 eNodeB neighbor in EN-DC case. Manual configuration is only applicable if peer node is not upgraded to support automatic direct X2 IPsec configuration. Outer IP address received from X2 neighbor node overwrites manual configuration by operator. If empty, no direct IPsec VPN connection is to be established. Can be IPv4 or IPv6 address. For IPv4, input format is four fields of digits, separated by dots. Each field can consist of three digits. Value of each field is in range 0..255. For IPv6, input format is eight fields, separated by colons. Each field consists of four hexadecimal characters. Value of each field is in range 0..FFFF. Leading zeroes can be omitted in a field. Multiple groups of 16 bits of zeroes can be compressed to :: and can appear once in address.; length 2..39.";
      type string {
        length "2..39";
        pattern "(::|((([0-9A-Fa-f]{1,4}):){7}(([0-9A-Fa-f]{1,4})|:))|((([0-9A-Fa-f]{1,4}):){6}(:([0-9A-Fa-f]{1,4})|:))|((([0-9A-Fa-f]{1,4}):){5}(((:([0-9A-Fa-f]{1,4})){1,2})|:))|((([0-9A-Fa-f]{1,4}):){4}(((:([0-9A-Fa-f]{1,4})){1,3})|:))|((([0-9A-Fa-f]{1,4}):){3}(((:([0-9A-Fa-f]{1,4})){1,4})|:))|((([0-9A-Fa-f]{1,4}):){2}(((:([0-9A-Fa-f]{1,4})){1,5})|:))|((([0-9A-Fa-f]{1,4}):)(((:([0-9A-Fa-f]{1,4})){1,6})|:))|(:(:([0-9A-Fa-f]{1,4})){1,7})|((25[0-5]|(2[0-4]|1{0,1}[0-9]){0,1}[0-9])\\.){3}(25[0-5]|(2[0-4]|1{0,1}[0-9]){0,1}[0-9]))";
      }
    }
    leaf operationalState {
      description "The operational state..";
      type enumeration {
        enum DISABLED;
        enum ENABLED;
      }
      config false;
    }
    leaf termPointToENodeBId {
      description "The value component of the RDN..";
      type string;
      mandatory true;
    }
    leaf upIpAddress {
      description "User plane address of X2 eNodeB neighbor in EN-DC case. Manual configuration is only applicable if peer node is not upgraded to support automatic direct X2 IPsec configuration. User plan address received from X2 neighbor node overwrites manual configuration by operator. If empty, no direct IPsec VPN connection is to be established. Can be IPv4 or IPv6 address. For IPv4, input format is four fields of digits, separated by dots. Each field can consist of three digits. Value of each field is in range 0..255. For IPv6, input format is eight fields, separated by colons. Each field consists of four hexadecimal characters. Value of each field is in range 0..FFFF. Leading zeroes can be omitted in a field. Multiple groups of 16 bits of zeroes can be compressed to :: and can appear once in address. Multiple groups of 16 bits of zeroes can be compressed to :: and can appear once in address.; length 2..39.";
      type string {
        length "2..39";
        pattern "(::|((([0-9A-Fa-f]{1,4}):){7}(([0-9A-Fa-f]{1,4})|:))|((([0-9A-Fa-f]{1,4}):){6}(:([0-9A-Fa-f]{1,4})|:))|((([0-9A-Fa-f]{1,4}):){5}(((:([0-9A-Fa-f]{1,4})){1,2})|:))|((([0-9A-Fa-f]{1,4}):){4}(((:([0-9A-Fa-f]{1,4})){1,3})|:))|((([0-9A-Fa-f]{1,4}):){3}(((:([0-9A-Fa-f]{1,4})){1,4})|:))|((([0-9A-Fa-f]{1,4}):){2}(((:([0-9A-Fa-f]{1,4})){1,5})|:))|((([0-9A-Fa-f]{1,4}):)(((:([0-9A-Fa-f]{1,4})){1,6})|:))|(:(:([0-9A-Fa-f]{1,4})){1,7})|((25[0-5]|(2[0-4]|1{0,1}[0-9]){0,1}[0-9])\\.){3}(25[0-5]|(2[0-4]|1{0,1}[0-9]){0,1}[0-9]))";
      }
    }
  }
  grouping TermPointToGNBCUUP-attributes {
    leaf-list availabilityStatus {
      description "The availability status. It contains details about operationalState..";
      type AvailStatus;
      min-elements 0;
    }
    leaf gNBCUUPId {
      description "Central Unit User Plane (CUUP) identity within gNodeB..";
      type int64;
      config false;
    }
    leaf gNBCUUPName {
      description "Central Unit User Plane (CUUP) name..";
      type string;
      config false;
    }
    leaf operationalState {
      description "The operational state..";
      type enumeration {
        enum DISABLED;
        enum ENABLED;
      }
      config false;
    }
    leaf termPointToGNBCUUPId {
      description "The value component of the RDN..";
      type string;
      mandatory true;
    }
    leaf usedIpAddress {
      description "Destination address used in underlying connection. Contains address of latest successful E1 setup. IP address can be an IPv4 or an IPv6 address..";
      type string;
      config false;
    }
  }
  grouping TermPointToGNBDU-attributes {
    leaf-list availabilityStatus {
      description "The availability status. It contains details about operational state..";
      type AvailStatus;
      min-elements 0;
    }
    leaf gNBDUId {
      description "Distributed Unit (DU) Identity within the gNodeB.; range 0..68719476735.";
      type eytypes:int64_range_0-68719476735;
      config false;
    }
    leaf gNBDUName {
      description "Distributed Unit (DU) name.; length 1..150.";
      type string {
        length "1..150";
      }
      config false;
    }
    leaf operationalState {
      description "The operational state..";
      type enumeration {
        enum DISABLED;
        enum ENABLED;
      }
      config false;
    }
    leaf pwsBroadcastStarted {
      description "Whether PWS service is started toward gNodeB-DU instance based on requested time. This attribute considers possible multiple messages and all cells in DU. NRCellDU::pwsBroadcastOngoing defines exact value for each cell..";
      type boolean;
      config false;
    }
    leaf termPointToGNBDUId {
      description "The value component of the RDN..";
      type string;
      mandatory true;
    }
    leaf usedIpAddress {
      description "Destination address used in underlying SCTP association. Contains address of latest successful F1-C setup. IP address can be an IPv4 or an IPv6 address..";
      type string;
      config false;
    }
  }
  grouping TermPointToGNodeB-attributes {
    leaf administrativeState {
      description "The administrative state. If set to SHUTTINGDOWN, the state is immediately brought to LOCKED..";
      type enumeration {
        enum LOCKED;
        enum UNLOCKED;
        enum SHUTTINGDOWN;
      }
    }
    leaf-list availabilityStatus {
      description "The availability status. It contains details about operationalState..";
      type AvailStatus;
      min-elements 0;
    }
    leaf ipsecEpAddress {
      description "Outer IP address of Xn neighbor. Non-empty if direct IPsec VPN connection is to be established.; length 2..39.";
      type string {
        length "2..39";
      }
      config false;
    }
    leaf ipv4Address {
      description "IPv4 address of peer gNodeB. Four fields, separated by dots. Each field consists of up to three digits. Value of each field is in range 0..255. This attribute can be overridden by system if GNBCUCPFunction::xnIpAddrViaNgActive is true.; length 7..15; Default value: 0.0.0.0.";
      type ietfinet:ipv4-address;
      default "0.0.0.0";
    }
    leaf ipv6Address {
      description "IPv6 address of peer gNodeB. Eight fields, separated by colons. Each field consists of up to four hexadecimal characters. Value of each field is in range 0..FFFF. Leading zeroes can be omitted in a field, and multiple groups of 16 bits of zeroes can be compressed to :: The :: can appear only once in an address. This attribute can be overridden by system if GNBCUCPFunction::xnIpAddrViaNgActive is true.; length 2..39; Default value: ::.";
      type ietfinet:ipv6-address;
      default "::";
    }
    leaf operationalState {
      description "The operational state..";
      type enumeration {
        enum DISABLED;
        enum ENABLED;
      }
      config false;
    }
    leaf termPointToGNodeBId {
      description "The value component of the RDN..";
      type string;
      mandatory true;
    }
    leaf upIpAddress {
      description "Inner IP address of Xn neighbor. Non-empty if direct IPsec VPN connection is to be established.; length 2..39.";
      type string {
        length "2..39";
      }
      config false;
    }
    leaf usedIpAddress {
      description "Destination address used in underlying SCTP association..";
      type string;
      config false;
    }
    list usedPLMNId {
      config false;
      description "PLMNId used in underlying SCTP association. Used to select SctpEndPoint of Xn-C in local IP address selection for SCTP association..";
      uses PLMNId-struct;
    }
  }
  grouping TimeSchedulingGroup-attributes {
    leaf-list reservedBy {
      description "Contains a list of MO instances that reserve this MO instance..";
      type string;
      min-elements 0;
    }
    leaf timeSchedulingGroupId {
      description "The value component of the RDN..";
      type string;
      mandatory true;
    }
    leaf userLabel {
      description "Label for free use..";
      type string;
    }
  }
  grouping TimeSchedulingWindow-attributes {
    leaf-list daysOfWeek {
      description "Days when time window is applicable..";
      type DayOfWeekOnly;
      min-elements 1;
      max-elements 7;
    }
    leaf epBoosterCellProfileRef {
      description "Reference to an instance of EpBoosterCellProfile MO. If empty, no Booster Carrier Sleep is used for this MO instance..";
      type string;
    }
    leaf startTime {
      description "Time of day when time window starts. Value ranges from 00:00 to 23:58.; length 5..5; Default value: 00:00.";
      type string {
        length "5";
        pattern "([01][0-9]|2[0-3]):([0-5][0-9])";
      }
      default "00:00";
    }
    leaf stopTime {
      description "Time of day when time window ends. Value ranges from 00:01 to 23:59.; length 5..5; Default value: 06:00.";
      type string {
        length "5";
        pattern "([01][0-9]|2[0-3]):([0-5][0-9])";
      }
      default "06:00";
    }
    leaf timeSchedulingWindowId {
      description "The value component of the RDN..";
      type string;
      mandatory true;
    }
    leaf userLabel {
      description "Label for free use..";
      type string;
    }
  }
  grouping TnlAssociation-attributes {
    leaf activeForNonUe {
      description "Whether this TNL association is preferred for non-UE associated signaling from gNodeB..";
      type boolean;
      config false;
    }
    leaf operationalState {
      description "The operational state..";
      type enumeration {
        enum DISABLED;
        enum ENABLED;
      }
      config false;
    }
    leaf-list remoteIpAddress {
      description "List of AMF IP addresses of this TNL association..";
      type string {
        length "2..39";
      }
      min-elements 1;
      max-elements 2;
    }
    leaf remotePortNumber {
      description "AMF port number of this TNL association.; range 1..65535.";
      type ietfinet:port-number;
      config false;
    }
    leaf tnlAssociationId {
      description "The value component of the RDN..";
      type string;
      mandatory true;
    }
    leaf usage {
      description "Usage of this TNL association. TNL association can be used for UE-associated signaling, for non-UE associated signaling or for both UE-associated and non-UE associated signaling..";
      type enumeration {
        enum BOTH;
        enum UE;
        enum NON_UE;
      }
      config false;
    }
    leaf weightFactor {
      description "Weight factor for TNL association, as set by AMF. Weight factor is used for selecting a TNL association for UE initial NGAP message.; range 0..255.";
      type eytypes:int32_range_0-255;
      config false;
    }
  }
  grouping TrafficOffload-attributes {
    leaf trafficOffloadId {
      description "The value component of the RDN..";
      type string;
      mandatory true;
    }
  }
  grouping TrafficSteering-attributes {
    leaf bwtishoB1ToB2DepHEnabled {
      description "Whether deprecation handling for rsrpPCellCandidateB1 in TrStSaCellProfileUeCfg is enabled. Whether deprecation handling for rsrpPCellCandidateB1 in TrStSaCellProfileUeCfg and for rsrpPCellCandidateB1Offset in TrStSaEUtranFreqRelProfileUeCfg is enabled. If true, deprecation handling as below apply: - At create of TrStSaCellProfileUeCfg instance: Set rsrpPCellCandidateB2.threshold1 to -29 Copy rsrpPCellCandidateB1.hysteresis to rsrpPCellCandidateB2.hysteresis Copy rsrpPCellCandidateB1.threshold to rsrpPCellCandidateB2.threshold2EUtra Copy rsrpPCellCandidateB1.timeToTrigger to rsrpPCellCandidateB2.timeToTrigger - At update of rsrpPCellCandidateB1 corresponding update of replacing rsrpPCellCandidateB2 is done as described below: Copy rsrpPCellCandidateB1.hysteresis to rsrpPCellCandidateB2.hysteresis Copy rsrpPCellCandidateB1.threshold to rsrpPCellCandidateB2.threshold2EUtra Copy rsrpPCellCandidateB1.timeToTrigger to rsrpPCellCandidateB2.timeToTrigger - At create of TrStSaEUtranFreqRelProfileUeCfg instance: Copy rsrpPCellCandidateB1Offset to rsrpPCellCandidateB2Offsets.threshold2EUtraOffset Set rsrpPCellCandidateB2Offsets.threshold1Offset to 0 - At update of rsrpPCellCandidateB1Offset corresponding update of replacing rsrpPCellCandidateB2Offsets is done as described below: Copy rsrpPCellCandidateB1Offset to rsrpPCellCandidateB2Offsets.threshold2EUtraOffset If false, no deprecation handling is applied for rsrpPCellCandidateB1 and rsrpPCellCandidateB1Offset. Node always uses rsrpPCellCandidateB2 configured in TrStSaCellProfileUeCfg instance. Updating rsrpPCellCandidateB2 never updates deprecated rsrpPCellCandidateB1. Node always uses rsrpPCellCandidateB2Offsets configured in TrStSaEUtranFreqRelProfileUeCfg instance. Updating rsrpPCellCandidateB2Offsets never updates deprecated rsrpPCellCandidateB1Offset. Disabling deprecation handling prevents rsrpPCellCandidateB2 in TrStSaEUtranFreqRelPro MO class from being overwritten by deprecation handling for rsrpPCellCandidateB1. Disabling deprecation handling prevents rsrpPCellCandidateB2Offsets in TrStSaEUtranFreqRelProfileUeCfg MO class from being overwritten by deprecation handling for rsrpPCellCandidateB1Offset. Set to false when using management system where rsrpPCellCandidateB2 in TrStSaCellProfileUeCfg MO class and rsrpPCellCandidateB2Offsets in TrStSaEUtranFreqRelProfileUeCfg MO class are visible.; Default value: true.";
      type boolean;
      default "true";
    }
    leaf dlCellLoadAware {
      description "Whether downlink cell load is considered when selecting cells. Only applicable if license for NR Advanced Multi-Layer Coordination is present and feature is active. Only applicable to Low-Band and Mid-Band cells.; Default value: false.";
      type boolean;
      default "false";
    }
    leaf trafficSteeringId {
      description "The value component of the RDN..";
      type string;
      mandatory true;
    }
    leaf ulCellLoadAwareEnabled {
      description "Whether uplink cell load is considered when selecting cells. Only applicable if licenses for both following features are present and features are active: - Uplink-Aware Advanced Multi-Layer Coordination - NR Advanced Multi-Layer Coordination Only applicable to Low-Band and Mid-Band cells.; Default value: false.";
      type boolean;
      default "false";
    }
    leaf userLabel {
      description "Label for free use..";
      type string;
    }
  }
  grouping TrStPSCellNrFreqRelProfile-attributes {
    leaf-list reservedBy {
      description "Contains a list of MO instances that reserve this MO instance..";
      type string;
      min-elements 0;
    }
    leaf trStPSCellNrFreqRelProfileId {
      description "The value component of the RDN..";
      type string;
      mandatory true;
    }
    leaf ueConfGroupType {
      description "UE configuration group type. UE configuration group type that is applied in contained TrStPSCellNrFreqRelProfileUeCfg instances..";
      type enumeration {
        enum UE_MOBILITY_GROUP;
        enum UE_SERVICE_GROUP;
        enum UE_ADMISSION_GROUP;
      }
    }
    leaf userLabel {
      description "Label for free use..";
      type string;
    }
  }
  grouping TrStPSCellNrFreqRelProfileUeCfg-attributes {
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf rsrpCandidateA5Thr2Offset {
      description "RSRP A5 measurement threshold2 offset when searching for higher priority PSCell candidate. Used in PSCell Change to Higher Priority feature.; range -100..100; Default value: 0.";
      type eytypes:int32_range_-100-100;
      default "0";
      units "dB";
    }
    leaf rsrqCandidateA5Thr2Offset {
      description "RSRQ A5 measurement threshold2 offset when searching for higher priority PSCell candidate. Used in PSCell Change to Higher Priority feature.; range -100..100; Default value: 0.";
      type eytypes:int32_range_-100-100;
      default "0";
      units "dB";
    }
    leaf sinrCandidateA5Thr2Offset {
      description "SINR A5 measurement threshold2 offset when searching for higher priority PSCell candidate. Used in PSCell Change to Higher Priority feature.; range -100..100; Default value: 0.";
      type eytypes:int32_range_-100-100;
      default "0";
      units "dB";
    }
    leaf trStPSCellNrFreqRelProfileUeCfgId {
      description "The value component of the RDN..";
      type string;
      mandatory true;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 16;
    }
    leaf-list ueGroupList {
      description "UE group list. List of UE group identifiers. If empty, MO instance matches all UE group identifiers..";
      type eytypes:int32_range_1-255;
      ordered-by user;
      min-elements 0;
      max-elements 32;
    }
    leaf userLabel {
      description "Label for free use..";
      type string;
    }
  }
  grouping TrStPSCellProfile-attributes {
    leaf-list reservedBy {
      description "Contains a list of MO instances that reserve this MO instance..";
      type string;
      min-elements 0;
    }
    leaf trStPSCellProfileId {
      description "The value component of the RDN..";
      type string;
      mandatory true;
    }
    leaf ueConfGroupType {
      description "UE configuration group type. UE configuration group type that is applied in contained TrStPSCellProfileUeCfg instances..";
      type enumeration {
        enum UE_MOBILITY_GROUP;
        enum UE_SERVICE_GROUP;
        enum UE_ADMISSION_GROUP;
      }
    }
    leaf userLabel {
      description "Label for free use..";
      type string;
    }
  }
  grouping TrStPSCellProfileUeCfg-attributes {
    leaf candidateA5TriggerQuantity {
      description "Measurement trigger quantity used when searching for higher priority PSCell candidate..";
      type enumeration {
        enum RSRP;
        enum RSRQ;
        enum SINR_FALLBACK_RSRP;
        enum SINR_FALLBACK_RSRQ;
      }
    }
    leaf hiPrioAllowedForDistUeEnabled {
      description "Whether PSCell Change to Higher Priority is allowed when EN-DC distribution model is applied. If true, PSCell Change to Higher Priority is allowed.; Default value: false.";
      type boolean;
      default "false";
    }
    leaf hiPrioDetInactiveTime {
      description "Time period between periods of active measurements on higher priority cells.; range 500..300000; Default value: 30000.";
      type int32 {
        range "500..300000";
      }
      default "30000";
      units "ms";
    }
    leaf hiPrioDetMeasurementTime {
      description "Time period when measurements on higher priority cells are active.; range 500..120000; Default value: 5000.";
      type int32 {
        range "500..120000";
      }
      default "5000";
      units "ms";
    }
    leaf hiPrioDetStartTime {
      description "Initial delay before starting A5 measurements for higher priority cells.; range 10..10000; Default value: 2000.";
      type int32 {
        range "10..10000";
      }
      default "2000";
      units "ms";
    }
    leaf maxReportCells {
      description "Maximum number of non-serving cells included in measurement report. Only applicable to event A5.; range 1..8; Default value: 1.";
      type eytypes:int32_range_1-8;
      default "1";
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    list rsrpCandidateA5 {
      key "id";
      leaf id {
        type uint32;
        description "Synthetic key for struct attribute.";
      }
      description "RSRP A5 measurement report criteria when searching for higher priority PSCell candidate..";
      uses ReportConfigA5NoThr1Rsrp-struct;
    }
    leaf rsrpCandidateA5AddTargEval {
      description "Additional target evaluation of other reported quantity. Applicable when searching for for higher priority PSCell candidate with trigger quantity RSRP. Other reported quantity SINR is evaluated towards threshold value defined by following formula: threshold2 in sinrCandidateA5 + hysteresis in sinrCandidateA5 + TrStPSCellNrFreqRelProfileUeCfg::sinrCandidateA5Thr2Offset Other reported quantity RSRQ is evaluated towards threshold value defined by following formula: threshold2 in rsrqCandidateA5 + hysteresis in rsrqCandidateA5 + TrStPSCellNrFreqRelProfileUeCfg::rsrqCandidateA5Thr2Offset.";
      type enumeration {
        enum NONE;
        enum RSRQ;
        enum SINR_FALLBACK_RSRQ;
        enum SINR_NO_FALLBACK_RSRQ;
      }
    }
    list rsrqCandidateA5 {
      key "id";
      leaf id {
        type uint32;
        description "Synthetic key for struct attribute.";
      }
      description "RSRQ A5 measurement report criteria when searching for higher priority PSCell candidate..";
      uses ReportConfigA5NoThr1Rsrq-struct;
    }
    leaf rsrqCandidateA5AddTargEval {
      description "Additional target evaluation of other reported quantity. Applicable when searching for for higher priority PSCell candidate with trigger quantity RSRQ. Other reported quantity RSRP is evaluated towards threshold value defined by following formula: threshold2 in rsrpCandidateA5 + hysteresis in rsrpCandidateA5 + TrStPSCellNrFreqRelProfileUeCfg::rsrpCandidateA5Thr2Offset - NRCellRelation::cellIndividualOffsetNR.";
      type enumeration {
        enum NONE;
        enum RSRP;
      }
    }
    list sinrCandidateA5 {
      key "id";
      leaf id {
        type uint32;
        description "Synthetic key for struct attribute.";
      }
      description "SINR A5 measurement report criteria when searching for higher priority PSCell candidate..";
      uses ReportConfigA5NoThr1Sinr-struct;
    }
    leaf sinrCandidateA5AddTargEval {
      description "Additional target evaluation of other reported quantity. Applicable when searching for for higher priority PSCell candidate with trigger quantity SINR. Other reported quantity RSRP is evaluated towards threshold value defined by following formula: threshold2 in rsrpCandidateA5 + hysteresis in rsrpCandidateA5 + TrStPSCellNrFreqRelProfileUeCfg::rsrpCandidateA5Thr2Offset - NRCellRelation::cellIndividualOffsetNR Other reported quantity RSRQ is evaluated towards threshold value defined by following formula: threshold2 in rsrqCandidateA5 + hysteresis in rsrqCandidateA5 + TrStPSCellNrFreqRelProfileUeCfg::rsrqCandidateA5Thr2Offset.";
      type enumeration {
        enum NONE;
        enum RSRP;
        enum RSRQ;
        enum RSRP_AND_RSRQ;
      }
    }
    leaf trStPSCellProfileUeCfgId {
      description "The value component of the RDN..";
      type string;
      mandatory true;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 16;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping TrStSaCellProfile-attributes {
    leaf dataAwareMobDlLowThpDuration {
      description "Minimum duration for UE to experience low downlink throughput. Used for throughput monitoring in NR Data-Aware Mobility feature.; range 1..10; Default value: 1.";
      type int32 {
        range "1..10";
      }
      default "1";
      units "s";
    }
    leaf dataAwareMobDlThpFilterCoeff {
      description "Filter coefficient used for downlink throughput monitoring. Used for throughput monitoring in NR Data-Aware Mobility feature.; range 0..95; Default value: 60.";
      type eytypes:int32_range_0-95;
      default "60";
    }
    leaf dataAwareMobDlThpFilterTime {
      description "Minimum valid time of downlink throughput samples. Used for throughput monitoring in NR Data-Aware Mobility feature.; range 0..1000; Default value: 200.";
      type eytypes:int32_range_0-1000;
      default "200";
      units "ms";
    }
    leaf dataAwareMobUlLowThpDuration {
      description "Minimum duration for UE to experience low uplink throughput. Used for throughput monitoring in NR Data-Aware Mobility feature.; range 1..10; Default value: 1.";
      type int32 {
        range "1..10";
      }
      default "1";
      units "s";
    }
    leaf dataAwareMobUlThpFilterCoeff {
      description "Filter coefficient used for uplink throughput monitoring. Used for throughput monitoring in NR Data-Aware Mobility feature.; range 0..95; Default value: 60.";
      type eytypes:int32_range_0-95;
      default "60";
    }
    leaf dataAwareMobUlThpFilterTime {
      description "Minimum valid time of uplink throughput samples. Used for throughput monitoring in NR Data-Aware Mobility feature.; range 0..1000; Default value: 200.";
      type eytypes:int32_range_0-1000;
      default "200";
      units "ms";
    }
    leaf-list reservedBy {
      description "Contains a list of MO instances that reserve this MO instance..";
      type string;
      min-elements 0;
    }
    leaf trStSaCellProfileId {
      description "The value component of the RDN..";
      type string;
      mandatory true;
    }
    leaf ueConfGroupType {
      description "UE configuration group type. UE configuration group type that is applied in contained TrStSaCellProfileUeCfg instances..";
      type enumeration {
        enum UE_MOBILITY_GROUP;
        enum UE_SERVICE_GROUP;
        enum UE_ADMISSION_GROUP;
      }
    }
    leaf userLabel {
      description "Label for free use..";
      type string;
    }
  }
  grouping TrStSaCellProfileUeCfg-attributes {
    leaf actionAtRelease {
      description "Traffic steering action at UE release. If mlcEnabled is false, value CA_CONF does not take effect. It is handled as DISABLED. Value RANDOM_REDIRECT is applicable to High-Band cells. Not supported for Low-Band or Mid-Band cells..";
      type enumeration {
        enum DISABLED;
        enum CA_CONF;
        enum PRIORITY_LIST;
        enum CRP_MLC_CONDITIONAL;
        enum RANDOM_REDIRECT;
      }
    }
    leaf aggregatedBwThreshold {
      description "Aggregated bandwidth threshold. Used in bandwidth-triggered inter-system handover function to decide if inter-system handover to E-UTRAN shall be triggered. If aggregated downlink bandwidth (MHz) of current serving NR cell(s) in coverage is lower than or equal to threshold inter-system handover to E-UTRAN might be triggereded. Downlink bandwidth per serving cell corresponds to value of NRSectorCarrier::bSChannelBwDL under GNBDUFunction instance.; range 1..1000; Default value: 10.";
      type int32 {
        range "1..1000";
      }
      default "10";
      units "MHz";
    }
    leaf bwTrigISHoEnabled {
      description "Whether bandwidth-triggered inter-system handover is enabled for NR cell.; Default value: false.";
      type boolean;
      default "false";
    }
    leaf bwTrigISHoTriggerQuantity {
      description "Measurement trigger quantity used when searching for E-UTRAN PCell candidate. Used in function Bandwidth-Triggered Inter-System Handover and in feature NR Data-Aware Mobility..";
      type enumeration {
        enum RSRP;
        enum RSRQ;
        enum SINR_FALLBACK_RSRP;
        enum SINR_FALLBACK_RSRQ;
      }
    }
    leaf capAwarePCellSelEnabled {
      description "Whether multi-layer coordination is enabled for NR cell.; Default value: false; Takes effect: Next usage; Status info: Since 23.Q2. Replaced by mlcEnabled. Planned to be removed..";
      type boolean;
      status deprecated;
      default "false";
      reference "Takes effect: Next usage.";
    }
    leaf criterionBetterUeConfig {
      description "Criterion for better UE configuration. Defines a better UE configuration candidate relative to the current UE configuration. Expressed as percentage better estimated throughput based on the configured bandwidth of respective UE configuration. For NR Advanced Multi-Layer Coordination feature and Uplink-Aware Advanced Multi-Layer Coordination feature, cell load is also used when calculating estimated throughput.; range 1..100; Default value: 100.";
      type eytypes:int32_range_1-100;
      default "100";
      units "percent";
    }
    leaf criterionDlAbsoluteOffset {
      description "Absolute offset criterion in downlink for better UE configuration. Defines a better UE configuration candidate than current UE configuration. Expressed as an absolute offset above current estimated downlink cell weight for current UE configuration.; Default value: 5.";
      type int32 {
        range "0 | 5..100";
      }
      default "5";
      units "Mbps";
    }
    leaf criterionUlAbsoluteOffset {
      description "Absolute offset criterion in uplink for better UE configuration. Defines a better UE configuration candidate than current UE configuration. Expressed as an absolute offset above current estimated uplink cell weight for current UE configuration.; range 0..100; Default value: 2.";
      type int32 {
        range "0..100";
      }
      default "2";
      units "Mbps";
    }
    leaf dataAwareMobDlPktAgeThr {
      description "Threshold for age of packets in RLC SDU buffer. Used for buffer monitoring in NR Data-Aware Mobility feature. If 0, age buffer monitoring is disabled.; Default value: 0.";
      type int32 {
        range "0 | 10..500";
      }
      default "0";
      units "ms";
    }
    leaf dataAwareMobDlPktVolThr {
      description "Threshold for volume of packets in RLC SDU buffer. Used for buffer monitoring in NR Data-Aware Mobility feature. If 0, volume buffer monitoring is disabled.; Default value: 0.";
      type int32 {
        range "0 | 10..30000";
      }
      default "0";
      units "kB";
    }
    leaf dataAwareMobLowDlThpThr {
      description "Threshold for low downlink throughput. Used for throughput monitoring in NR Data-Aware Mobility feature. If 0, downlink throughput monitoring is disabled.; Default value: 0.";
      type int32 {
        range "0 | 500..10000";
      }
      default "0";
      units "kbps";
    }
    leaf dataAwareMobLowUlThpThr {
      description "Threshold for low uplink throughput. Used for throughput monitoring in NR Data-Aware Mobility feature. If 0, uplink throughput monitoring is disabled.; Default value: 0.";
      type int32 {
        range "0 | 500..3000";
      }
      default "0";
      units "kbps";
    }
    leaf dlCellLoadAware {
      description "Whether downlink cell load is considered when selecting cells. Only applicable if license for Advanced Multi-Layer Coordination is present and feature is active. Only applicable to Low-Band and Mid-Band cells..";
      type boolean;
    }
    list freqPrioListEUtran {
      key "id";
      leaf id {
        type uint32;
        description "Synthetic key for struct sequence entry.";
      }
      min-elements 0;
      max-elements 8;
      uses EUtranFreqPrio-struct;
    }
    list freqPrioListNR {
      key "id";
      leaf id {
        type uint32;
        description "Synthetic key for struct sequence entry.";
      }
      min-elements 0;
      max-elements 8;
      uses NRFreqPrio-struct;
    }
    leaf maxReportCells {
      description "Maximum number of non-serving cells included in measurement report. Only applicable to event A5 and event B2.; range 1..8; Default value: 1.";
      type eytypes:int32_range_1-8;
      default "1";
    }
    leaf mlcAllowedCellSetChangeAction {
      description "Allowed cell set change action. Used by Multi-Layer Coordination, Dynamic Cell Set Change during Mobility, NR Advanced Multi-Layer Coordination, and Uplink-Aware Advanced Multi-Layer Coordination..";
      type enumeration {
        enum HANDOVER;
        enum SCELL_RESELECTION;
        enum HO_AND_SCELL_RESELECTION;
      }
    }
    leaf mlcEnabled {
      description "Whether multi-layer coordination is enabled for NR cell at UE Setup and RRC Resume. Used by Multi-Layer Coordination, Dynamic Cell Set Change during Mobility, NR Advanced Multi-Layer Coordination, and Uplink-Aware Advanced Multi-Layer Coordination.; Default value: false.";
      type boolean;
      default "false";
    }
    leaf mlcPeriodicEnabled {
      description "Whether periodic multi-layer coordination evaluations are enabled for NR cell. Periodicity is defined by mlcPeriodicInterval. Used by Dynamic Cell Set Change during Mobility.; Default value: false.";
      type boolean;
      default "false";
    }
    leaf mlcPeriodicInterval {
      description "Time between multi-layer coordination evaluations.; range 5..1000; Default value: 15.";
      type int32 {
        range "5..1000";
      }
      default "15";
      units "s";
    }
    leaf mlcTriggerQuantity {
      description "Measurement trigger quantity used when searching for PCell and SCell candidates. Used in Multi-Layer Coordination, Dynamic Cell Set Change during Mobility, NR Advanced Multi-Layer Coordination, and Uplink-Aware Advanced Multi-Layer Coordination..";
      type enumeration {
        enum RSRP;
        enum RSRQ;
        enum SINR_FALLBACK_RSRP;
        enum SINR_FALLBACK_RSRQ;
      }
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    list rsrpPCellCandidate {
      key "id";
      leaf id {
        type uint32;
        description "Synthetic key for struct attribute.";
      }
      description "RSRP measurement report criteria when searching for NR PCell candidate. Struct member threshold2 must be higher than or equal to rsrpSCellCandidate.threshold2. Used in Multi-Layer Coordination, Dynamic Cell Set Change during Mobility, NR Advanced Multi-Layer Coordination, and Uplink-Aware Advanced Multi-Layer Coordination..";
      uses ReportConfigA5NoThr1Rsrp-struct;
    }
    leaf rsrpPCellCandidateAddTargEval {
      description "Additional target evaluation of other reported quantity. Applicable when searching for NR PCell candidate with A5 event with trigger quantity RSRP. Other reported quantity SINR is evaluated towards threshold value defined by following formula: threshold2 in sinrPCellCandidate + hysteresis in sinrPCellCandidate + TrStSaNrFreqRelProfileUeCfg::sinrPCellCandidateOffset Other reported quantity RSRQ is evaluated towards threshold value defined by following formula: threshold2 in rsrqPCellCandidate + hysteresis in rsrqPCellCandidate + TrStSaNrFreqRelProfileUeCfg::rsrqPCellCandidateOffset Used in Multi-Layer Coordination, Dynamic Cell Set Change during Mobility, NR Advanced Multi-Layer Coordination, and Uplink-Aware Advanced Multi-Layer Coordination..";
      type enumeration {
        enum NONE;
        enum RSRQ;
        enum SINR_FALLBACK_RSRQ;
        enum SINR_NO_FALLBACK_RSRQ;
      }
    }
    list rsrpPCellCandidateB1 {
      key "id";
      leaf id {
        type uint32;
        description "Synthetic key for struct attribute.";
      }
      description "RSRP measurement report criteria that define minimum RSRP value for E-UTRAN PCell candidate. Used in bandwidth-triggered inter-system handover function.; Takes effect: Next usage; Status info: Since 24.Q2. Replaced by rsrpPCellCandidateB2. Planned to be removed.; Specification: 3GPP TS 38.331.";
      uses ReportConfigB1Rsrp-struct;
    }
    list rsrpPCellCandidateB2 {
      key "id";
      leaf id {
        type uint32;
        description "Synthetic key for struct attribute.";
      }
      description "RSRP measurement report criteria when searching for E-UTRAN PCell candidate. Used in bandwidth-triggered inter-system handover function..";
      uses ReportConfigB2Rsrp-struct;
    }
    leaf rsrpPCellCandidateB2AddTargEval {
      description "Additional target evaluation of other reported quantity. Applicable when searching for E-UTRAN PCell candidate with B2 event with trigger quantity RSRP. Other reported quantity SINR is evaluated towards threshold value defined by: threshold2EUtra in sinrPCellCandidateB2 + hysteresis in sinrPCellCandidateB2 + threshold2EUtraOffset in TrStSaEUtranFreqRelProfileUeCfg::sinrPCellCandidateB2Offsets. Other reported quantity RSRQ is evaluated towards threshold value defined by: threshold2EUtra in rsrqPCellCandidateB2 + hysteresis in rsrqPCellCandidateB2 + threshold2EUtraOffset in TrStSaEUtranFreqRelProfileUeCfg::rsrqPCellCandidateB2Offsets. Used in bandwidth-triggered inter-system handover function..";
      type enumeration {
        enum NONE;
        enum RSRQ;
        enum SINR_FALLBACK_RSRQ;
        enum SINR_NO_FALLBACK_RSRQ;
      }
    }
    list rsrpPCellCandidateB2PcOffset {
      key "id";
      leaf id {
        type uint32;
        description "Synthetic key for struct sequence entry.";
      }
      min-elements 0;
      max-elements 3;
      uses ReportConfigB2NoThr2RsrpPcOffset-struct;
    }
    list rsrpPCellCandidatePcOffset {
      key "id";
      leaf id {
        type uint32;
        description "Synthetic key for struct sequence entry.";
      }
      min-elements 0;
      max-elements 3;
      uses ReportConfigA5NoThr1RsrpPcOffset-struct;
    }
    list rsrpSCellCandidate {
      key "id";
      leaf id {
        type uint32;
        description "Synthetic key for struct attribute.";
      }
      description "RSRP measurement report criteria when searching for NR SCell candidate. Struct member threshold2 must be lower than or equal to rsrpPCellCandidate.threshold2. Used in Multi-Layer Coordination, Dynamic Cell Set Change during Mobility, NR Advanced Multi-Layer Coordination, and Uplink-Aware Advanced Multi-Layer Coordination..";
      uses ReportConfigA5NoThr1Rsrp-struct;
    }
    list rsrqPCellCandidate {
      key "id";
      leaf id {
        type uint32;
        description "Synthetic key for struct attribute.";
      }
      description "RSRQ measurement report criteria when searching for NR PCell candidate. Struct member threshold2 must be higher than or equal to rsrqSCellCandidate.threshold2. Used in Multi-Layer Coordination, Dynamic Cell Set Change during Mobility, NR Advanced Multi-Layer Coordination, and Uplink-Aware Advanced Multi-Layer Coordination..";
      uses ReportConfigA5NoThr1Rsrq-struct;
    }
    leaf rsrqPCellCandidateAddTargEval {
      description "Additional target evaluation of other reported quantity. Applicable when searching for NR PCell candidate with A5 event with trigger quantity RSRQ. Other reported quantity RSRP is evaluated towards threshold value defined by following formula: threshold2 in rsrpPCellCandidate + hysteresis in rsrpPCellCandidate + TrStSaNrFreqRelProfileUeCfg::rsrpPCellCandidateOffset + threshold2Offset in rsrpPCellCandidatePcOffset based on power class of the UE - NRCellRelation::cellIndividualOffsetNR Used in Multi-Layer Coordination, Dynamic Cell Set Change during Mobility, NR Advanced Multi-Layer Coordination, and Uplink-Aware Advanced Multi-Layer Coordination..";
      type enumeration {
        enum NONE;
        enum RSRP;
      }
    }
    list rsrqPCellCandidateB2 {
      key "id";
      leaf id {
        type uint32;
        description "Synthetic key for struct attribute.";
      }
      description "RSRQ measurement report criteria when searching for E-UTRAN PCell candidate. Used in bandwidth-triggered inter-system handover function..";
      uses ReportConfigB2Rsrq-struct;
    }
    leaf rsrqPCellCandidateB2AddTargEval {
      description "Additional target evaluation of other reported quantity. Applicable when searching for E-UTRAN PCell candidate with B2 event with trigger quantity RSRQ. Other reported quantity RSRP is evaluated towards threshold value defined by: threshold2EUtra in rsrpPCellCandidateB2 + hysteresis in rsrpPCellCandidateB2 + threshold2EUtraOffset in TrStSaEUtranFreqRelProfileUeCfg::rsrpPCellCandidateB2Offsets. - EUtranCellRelation::cellIndividualOffset Used in bandwidth-triggered inter-system handover function..";
      type enumeration {
        enum NONE;
        enum RSRP;
      }
    }
    list rsrqSCellCandidate {
      key "id";
      leaf id {
        type uint32;
        description "Synthetic key for struct attribute.";
      }
      description "RSRQ measurement report criteria when searching for NR SCell candidate. Struct member threshold2 must be lower than or equal to rsrqPCellCandidate.threshold2. Used in Multi-Layer Coordination, Dynamic Cell Set Change during Mobility, NR Advanced Multi-Layer Coordination, and Uplink-Aware Advanced Multi-Layer Coordination..";
      uses ReportConfigA5NoThr1Rsrq-struct;
    }
    list sinrPCellCandidate {
      key "id";
      leaf id {
        type uint32;
        description "Synthetic key for struct attribute.";
      }
      description "SINR measurement report criteria when searching for NR PCell candidate. Struct member threshold2 must be higher than or equal to sinrSCellCandidate.threshold2. Used in Multi-Layer Coordination, Dynamic Cell Set Change during Mobility, NR Advanced Multi-Layer Coordination, and Uplink-Aware Advanced Multi-Layer Coordination..";
      uses ReportConfigA5NoThr1Sinr-struct;
    }
    leaf sinrPCellCandidateAddTargEval {
      description "Additional target evaluation of other reported quantity. Applicable when searching for NR PCell candidate with A5 event with trigger quantity SINR. Other reported quantity RSRP is evaluated towards threshold value defined by following formula: threshold2 in rsrpPCellCandidate + hysteresis in rsrpPCellCandidate + TrStSaNrFreqRelProfileUeCfg::rsrpPCellCandidateOffset + threshold2Offset in rsrpPCellCandidatePcOffset based on power class of the UE - NRCellRelation::cellIndividualOffsetNR Other reported quantity RSRQ is evaluated towards threshold value defined by following formula: threshold2 in rsrqPCellCandidate + hysteresis in rsrqPCellCandidate + TrStSaNrFreqRelProfileUeCfg::rsrqPCellCandidateOffset Used in Multi-Layer Coordination, Dynamic Cell Set Change during Mobility, NR Advanced Multi-Layer Coordination, and Uplink-Aware Advanced Multi-Layer Coordination..";
      type enumeration {
        enum NONE;
        enum RSRP;
        enum RSRQ;
        enum RSRP_AND_RSRQ;
      }
    }
    list sinrPCellCandidateB2 {
      key "id";
      leaf id {
        type uint32;
        description "Synthetic key for struct attribute.";
      }
      description "SINR measurement report criteria when searching for E-UTRAN PCell candidate. Used in bandwidth-triggered inter-system handover function..";
      uses ReportConfigB2Sinr-struct;
    }
    leaf sinrPCellCandidateB2AddTargEval {
      description "Additional target evaluation of other reported quantity. Applicable when searching for E-UTRAN PCell candidate with B2 event with trigger quantity SINR. Other reported quantity RSRP is evaluated towards threshold value defined by: threshold2EUtra in rsrpPCellCandidateB2 + hysteresis in rsrpPCellCandidateB2 + threshold2EUtraOffset in TrStSaEUtranFreqRelProfileUeCfg::rsrpPCellCandidateB2Offsets. - EUtranCellRelation::cellIndividualOffset Other reported quantity RSRQ is evaluated towards threshold value defined by: threshold2EUtra in rsrqPCellCandidateB2 + hysteresis in rsrqPCellCandidateB2 + threshold2EUtraOffset in TrStSaEUtranFreqRelProfileUeCfg::rsrqPCellCandidateB2Offsets. Used in bandwidth-triggered inter-system handover function..";
      type enumeration {
        enum NONE;
        enum RSRP;
        enum RSRQ;
        enum RSRP_AND_RSRQ;
      }
    }
    list sinrSCellCandidate {
      key "id";
      leaf id {
        type uint32;
        description "Synthetic key for struct attribute.";
      }
      description "SINR measurement report criteria when searching for NR SCell candidate. Struct member threshold2 must be lower than or equal to sinrPCellCandidate.threshold2. Used in Multi-Layer Coordination, Dynamic Cell Set Change during Mobility, NR Advanced Multi-Layer Coordination, and Uplink-Aware Advanced Multi-Layer Coordination..";
      uses ReportConfigA5NoThr1Sinr-struct;
    }
    leaf t320 {
      description "Validity time for cell reselection priority information provided by dedicated signaling. Used by UE for traffic steering at UE release.; Default value: 30.";
      type int32 {
        range "5 | 10 | 20 | 30 | 60 | 120 | 180";
      }
      default "30";
      units "minute";
    }
    leaf trStSaCellProfileUeCfgId {
      description "The value component of the RDN..";
      type string;
      mandatory true;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 16;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping TrStSaEUtranFreqRelProfile-attributes {
    leaf-list reservedBy {
      description "Contains a list of MO instances that reserve this MO instance..";
      type string;
      min-elements 0;
    }
    leaf trStSaEUtranFreqRelProfileId {
      description "The value component of the RDN..";
      type string;
      mandatory true;
    }
    leaf ueConfGroupType {
      description "UE configuration group type. UE configuration group type that is applied in contained TrStSaEUtranFreqRelProfileUeCfg instances..";
      type enumeration {
        enum UE_MOBILITY_GROUP;
        enum UE_SERVICE_GROUP;
        enum UE_ADMISSION_GROUP;
      }
    }
    leaf userLabel {
      description "Label for free use..";
      type string;
    }
  }
  grouping TrStSaEUtranFreqRelProfileUeCfg-attributes {
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf rsrpPCellCandidateB1Offset {
      description "RSRP measurement threshold offset that defines minimum RSRP value for E-UTRAN PCell candidate. Used in combination with TrStSaCellProfileUeCfg::rsrpPCellCandidateB1 in bandwidth-triggered inter-system handover function.; range -100..100; Default value: 0; Takes effect: Next usage; Status info: Since 24.Q2. Replaced by rsrpPCellCandidateB2Offsets. Planned to be removed..";
      type eytypes:int32_range_-100-100;
      status deprecated;
      default "0";
      units "dB";
      reference "Takes effect: Next usage.";
    }
    list rsrpPCellCandidateB2Offsets {
      key "id";
      leaf id {
        type uint32;
        description "Synthetic key for struct attribute.";
      }
      description "Downlink RSRP B2 measurement offsets when searching for E-UTRAN PCell candidate. Used in bandwidth-triggered inter-system handover function..";
      uses ReportConfigB2RsrpOffsets-struct;
    }
    list rsrqPCellCandidateB2Offsets {
      key "id";
      leaf id {
        type uint32;
        description "Synthetic key for struct attribute.";
      }
      description "Downlink RSRQ B2 measurement offsets when searching for E-UTRAN PCell candidate. Used in bandwidth-triggered inter-system handover function..";
      uses ReportConfigB2RsrqOffsets-struct;
    }
    list sinrPCellCandidateB2Offsets {
      key "id";
      leaf id {
        type uint32;
        description "Synthetic key for struct attribute.";
      }
      description "Downlink SINR B2 measurement offsets when searching for E-UTRAN PCell candidate. Used in bandwidth-triggered inter-system handover function..";
      uses ReportConfigB2SinrOffsets-struct;
    }
    leaf trStSaEUtranFreqRelProfileUeCfgId {
      description "The value component of the RDN..";
      type string;
      mandatory true;
    }
    leaf-list ueConfGroupList {
      description "UE configuration group list. List of UE configuration group identifiers. If empty, MO instance matches all UE configuration group identifiers. Attribute ueConfGroupType in parent MO instance defines the applied UE configuration group type..";
      type eytypes:int32_range_1-255;
      ordered-by user;
      min-elements 0;
      max-elements 16;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping TrStSaNrFreqRelProfile-attributes {
    leaf-list reservedBy {
      description "Contains a list of MO instances that reserve this MO instance..";
      type string;
      min-elements 0;
    }
    leaf trStSaNrFreqRelProfileId {
      description "The value component of the RDN..";
      type string;
      mandatory true;
    }
    leaf ueConfGroupType {
      description "UE configuration group type. UE configuration group type that is applied in contained TrStSaNrFreqRelProfileUeCfg instances..";
      type enumeration {
        enum UE_MOBILITY_GROUP;
        enum UE_SERVICE_GROUP;
        enum UE_ADMISSION_GROUP;
      }
    }
    leaf userLabel {
      description "Label for free use..";
      type string;
    }
  }
  grouping TrStSaNrFreqRelProfileUeCfg-attributes {
    leaf hoToPrioritizedCell {
      description "Whether to prioritize HO to reported neighboring cell over best candidate cell identified by MLC. If true, handover to a reported neighboring cell is prioritized over handover to cell identified as best candidate by Multi-Layer Coordination (MLC). Relevant for small cell interworking.; Default value: false.";
      type boolean;
      default "false";
    }
    leaf pCellAllowed {
      description "Whether traffic steering is allowed to choose PCell candidates on NR frequency. NR frequency defined by NR frequency relation.; Default value: false.";
      type boolean;
      default "false";
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf rsrpPCellCandidateOffset {
      description "RSRP A5 measurement threshold2 offset when searching for NR PCell candidate. Used in combination with TrStSaCellProfileUeCfg::rsrpPCellCandidate in Multi-Layer Coordination, Dynamic Cell Set Change during Mobility, NR Advanced Multi-Layer Coordination, and Uplink-Aware Advanced Multi-Layer Coordination.; range -100..100; Default value: 0.";
      type eytypes:int32_range_-100-100;
      default "0";
      units "dB";
    }
    leaf rsrpSCellCandidateOffset {
      description "RSRP A5 measurement threshold2 offset when searching for NR SCell candidate. Used in combination with TrStSaCellProfileUeCfg::rsrpSCellCandidate in Multi-Layer Coordination, Dynamic Cell Set Change during Mobility, NR Advanced Multi-Layer Coordination, and Uplink-Aware Advanced Multi-Layer Coordination.; range -100..100; Default value: 0.";
      type eytypes:int32_range_-100-100;
      default "0";
      units "dB";
    }
    leaf rsrpUl2lCoverageThrOffset {
      description "NR frequency relation-specific downlink RSRP measurement threshold offset value. Threshold offset used for detecting uplink two layer coverage in NR PCell based on downlink RSRP measurements. Only applicable to Low-Band and Mid-Band cells.; range -100..100; Default value: 0.";
      type eytypes:int32_range_-100-100;
      default "0";
      units "dB";
    }
    leaf rsrqPCellCandidateOffset {
      description "RSRQ A5 measurement threshold2 offset when searching for NR PCell candidate. Used in combination with TrStSaCellProfileUeCfg::rsrqPCellCandidate in Multi-Layer Coordination, Dynamic Cell Set Change during Mobility, NR Advanced Multi-Layer Coordination, and Uplink-Aware Advanced Multi-Layer Coordination.; range -100..100; Default value: 0.";
      type eytypes:int32_range_-100-100;
      default "0";
      units "dB";
    }
    leaf rsrqSCellCandidateOffset {
      description "RSRQ A5 measurement threshold2 offset when searching for NR SCell candidate. Used in combination with TrStSaCellProfileUeCfg::rsrqSCellCandidate in Multi-Layer Coordination, Dynamic Cell Set Change during Mobility, NR Advanced Multi-Layer Coordination, and Uplink-Aware Advanced Multi-Layer Coordination.; range -100..100; Default value: 0.";
      type eytypes:int32_range_-100-100;
      default "0";
      units "dB";
    }
    leaf sinrPCellCandidateOffset {
      description "SINR A5 measurement threshold2 offset when searching for NR PCell candidate. Used in combination with TrStSaCellProfileUeCfg::sinrPCellCandidate in Multi-Layer Coordination, Dynamic Cell Set Change during Mobility, NR Advanced Multi-Layer Coordination, and Uplink-Aware Advanced Multi-Layer Coordination.; range -100..100; Default value: 0.";
      type eytypes:int32_range_-100-100;
      default "0";
      units "dB";
    }
    leaf sinrSCellCandidateOffset {
      description "SINR A5 measurement threshold2 offset when searching for NR SCell candidate. Used in combination with TrStSaCellProfileUeCfg::sinrSCellCandidate in Multi-Layer Coordination, Dynamic Cell Set Change during Mobility, NR Advanced Multi-Layer Coordination, and Uplink-Aware Advanced Multi-Layer Coordination.; range -100..100; Default value: 0.";
      type eytypes:int32_range_-100-100;
      default "0";
      units "dB";
    }
    leaf trStSaNrFreqRelProfileUeCfgId {
      description "The value component of the RDN..";
      type string;
      mandatory true;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 16;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping Uac-attributes {
    leaf uacId {
      description "The value component of the RDN..";
      type string;
      mandatory true;
    }
  }
  grouping UacProfile-attributes {
    leaf barringEnabled {
      description "Whether barring is enabled in NR Unified Access Control.; Default value: false.";
      type boolean;
      default "false";
    }
    leaf-list reservedBy {
      description "Contains a list of MO instances that reserve this MO instance..";
      type string;
      min-elements 0;
    }
    leaf uacProfileId {
      description "The value component of the RDN..";
      type string;
      mandatory true;
    }
  }
  grouping UaiProfile-attributes {
    leaf uaiProfileId {
      description "The value component of the RDN..";
      type string;
      mandatory true;
    }
    leaf ueConfGroupType {
      description "UE configuration group type. UE configuration group type that is applied in contained UaiProfileUeCfg instances..";
      type enumeration {
        enum UE_MOBILITY_GROUP;
        enum UE_SERVICE_GROUP;
        enum UE_ADMISSION_GROUP;
      }
    }
  }
  grouping UaiProfileUeCfg-attributes {
    leaf overheatingAssistanceConfig {
      description "Whether UE is configured to provide overheating assistance information. If true, overheating assistance config is sent to UEs with overheating indication capabilities in RRCReconfiguration messages.; Default value: false.";
      type boolean;
      default "false";
    }
    leaf overheatingIndProhibitTimer {
      description "Overheating indication prohibit timer for overheating assistance information reporting (T345).; Default value: 20.";
      type int32 {
        range "0 | 5 | 10 | 20 | 50 | 100 | 200 | 300 | 600 | 900 | 1200 | 3000 | 6000";
      }
      default "20";
      units "s";
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf releasePrefConfig {
      description "Whether UE is configured to inform gNodeB about the UE preference to leave RRC_CONNECTED state. If true, release preference configuration is sent in RRCReconfiguration message, if UE has release preference indication capabilities.; Default value: false.";
      type boolean;
      default "false";
    }
    leaf releasePrefOverride {
      description "Whether preference set by operator overrides preferredRRC-State in UEAssistanceInformation. If NO_PREFERENCE, preferredRRC-State in UE assistance information is not changed, otherwise preference set by operator overrides preferredRRC-State in UE assistance information..";
      type enumeration {
        enum IDLE;
        enum INACTIVE;
        enum NO_PREFERENCE;
      }
    }
    leaf releasePrefProhibitTimer {
      description "Prohibit timer for release preference assistance information reporting (T346f)..";
      type enumeration {
        enum S0;
        enum S0DOT5;
        enum S1;
        enum S2;
        enum S3;
        enum S4;
        enum S5;
        enum S6;
        enum S7;
        enum S8;
        enum S9;
        enum S10;
        enum S20;
        enum S30;
        enum INFINITY;
      }
    }
    leaf uaiProfileUeCfgId {
      description "The value component of the RDN..";
      type string;
      mandatory true;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 16;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping UcmCellProfile-attributes {
    leaf-list reservedBy {
      description "Contains a list of MO instances that reserve this MO instance..";
      type string;
      min-elements 0;
    }
    leaf ucmCellProfileId {
      description "The value component of the RDN..";
      type string;
      mandatory true;
    }
    leaf ucmCellTargetIntensity {
      description "Target intensity of UE coverage measurements per hour for cell.; range 1..100; Default value: 10.";
      type eytypes:int32_range_1-100-3;
      default "10";
    }
    leaf ucmEnabled {
      description "Whether UE coverage measurement is enabled in NR cell.; Default value: false.";
      type boolean;
      default "false";
    }
    leaf ucmSelectionProbability {
      description "Probability for inactive UE to be selected for UE coverage measurements.; range 1..100; Default value: 100.";
      type eytypes:int32_range_1-100;
      default "100";
      units "percent";
    }
    leaf ueConfGroupType {
      description "UE configuration group type. UE configuration group type that is applied in contained UcmCellProfileUeCfg instances..";
      type enumeration {
        enum UE_MOBILITY_GROUP;
        enum UE_SERVICE_GROUP;
        enum UE_ADMISSION_GROUP;
      }
    }
    leaf userLabel {
      description "Label for free use..";
      type string;
    }
  }
  grouping UcmCellProfileUeCfg-attributes {
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf ucmCellProfileUeCfgId {
      description "The value component of the RDN..";
      type string;
      mandatory true;
    }
    leaf ucmMaxFreqLayerToMeas {
      description "Maximum number of NR and E-UTRAN frequencies for concurrent UE coverage measurement per UE. If 0, no measurements are configured.; range 0..16; Default value: 7.";
      type eytypes:int32_range_0-16;
      default "7";
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping UcmEUtranFreqRelProfile-attributes {
    list reportConfigPeriodicalEutran {
      key "id";
      leaf id {
        type uint32;
        description "Synthetic key for struct attribute.";
      }
      description "Report configuration setting for periodical UE coverage measurements..";
      uses ReportConfigPeriodicalEUtran-struct;
    }
    leaf-list reservedBy {
      description "Contains a list of MO instances that reserve this MO instance..";
      type string;
      min-elements 0;
    }
    leaf ucmEUtranFreqRelProfileId {
      description "The value component of the RDN..";
      type string;
      mandatory true;
    }
    leaf ucmTargetFactor {
      description "Multiplication factor to calculate target intensity of UE coverage measurements per hour. UE coverage measurement intensity is multiplied by this factor. If 0, no measurements are configured.; range 0..36; Default value: 1.";
      type int32 {
        range "0..36";
      }
      default "1";
    }
  }
  grouping UcmNrFreqRelProfile-attributes {
    list reportConfigPeriodical {
      key "id";
      leaf id {
        type uint32;
        description "Synthetic key for struct attribute.";
      }
      description "Report configuration setting for periodical UE coverage measurements. Struct member reportInterval can only be MS_120, MS_240, MS_480 or MS_640. Struct member reportAmount can only be R1, R2 or R4..";
      uses ReportConfigPeriodical-struct;
    }
    leaf-list reservedBy {
      description "Contains a list of MO instances that reserve this MO instance..";
      type string;
      min-elements 0;
    }
    leaf ucmNrFreqRelProfileId {
      description "The value component of the RDN..";
      type string;
      mandatory true;
    }
    leaf ucmTargetFactor {
      description "Multiplication factor to calculate target intensity of UE coverage measurements per hour. UE coverage measurement intensity is multiplied with this factor. If 0, no measurements are configured.; range 0..36; Default value: 1.";
      type int32 {
        range "0..36";
      }
      default "1";
    }
  }
  grouping UeAdmissionGroupDefinition-attributes {
    leaf chipsetRef {
      description "Reference to an instance of Chipsets MO. Special <Value> \"ref\" for <Variable> chipset in selectionCriteria represents chipset <ValueList> defined via this reference. If empty, represented chipset <ValueList> is empty..";
      type string;
    }
    leaf imeiSvRef {
      description "Reference to an instance of ImeiSvs MO. Special <Value> \"ref\" for <Variable> imeisv in selectionCriteria represents imeisv <ValueList> defined via this reference. If empty, represented imeisv <ValueList> is empty..";
      type string;
    }
    leaf selectionCriteria {
      description "UE admission group selection criteria. Defines selection criteria that UE needs to fulfill to belong to UE admission group instance. If selection criteria evaluates to True, UE fulfills UE admission group instance. If selection criteria evaluates to False or Unknown, UE does not fulfill UE admission group instance. If selection criteria evaluates to True for more than one UE admission group instance, UE belongs to UE admission group instance with highest setting of ueAdmissionGroupPriority. Syntax: ====== The syntax of selection criteria is defined using Backus-Naur form. <SelectionCriteria> ::= <ParentExpressionList> | \"\" <ParentExpressionList> ::= <ParentExpressionList> <AndOr> < ParentExpressionList> | <Not>? \"(\" <ParentExpressionList> \")\" | <ExpressionList> | <FlowExpressionList> <FlowExpressionList> ::= <FlowExpressionList> <AndOr> <FlowExpressionList> | <Not>? <FlowExpression> <FlowExpression> ::= \"[\"<ExpressionList>\"]\" <ExpressionList> ::= <ExpressionList> <AndOr> <ExpressionList> | <Not>? \"(\" <ExpressionList> \")\" | <Not>? <VariableExpression> <VariableExpression> ::= <Variable> <RelationalOperator> <Value> | <Variable> \"==\" \"{\" <ValueList> \"}\" <ValueList> ::= <Value> \",\" <ValueList> | <Value> <Variable> ::= \"5qi\" | \"arp\" | \"cgrole\" | \"chipset\" | \"imeisv\" | \"imeisvn\" | \"imeitac\" | \"pagingPrio\" | \"pCellOnlyUe\" | \"plmn\" | \"qci\" | \"redCapUe\" | \"rfsp\" | \"rrcEstResCause\" | \"snssai\" | \"spid\" | \"voNrUe\" <AndOr> ::= \"&&\" | \"||\" <Not> ::= \"!\" <RelationalOperator> ::= \"==\" | \"!=\" | \"<\" | \"<=\" | \">=\" | \">\" A list of possible values can be specified in the form <Variable> == {<value1>, <value2>, ... , <valueN>}. This statement is equivalent to writing (<Variable> == <value1> || <Variable> == <value2> || ... || <Variable> == <valueN>). Up to 4 <FlowExpression> can be defined in <SelectionCriteria>. Whitespaces are allowed in the string for improved readability and are removed prior to evaluation. Question mark (?) means zero or one occurrence. For example, <Not>? makes <Not> optional. Syntax is case sensitive. Semantic: ======== Selection criteria evaluation is defined by the following semantic rules. If empty or set to empty string \"\", selection criteria always evaluates to True. Selection criteria evaluation is done per UE with the current applicable UE <Variable> values as input. List of UE <Variable> values that are applicable to NR standalone and EN-DC, respectively, is defined in Variable Definitions section below. Selection criteria for a UE is evaluated separately for each flow using applicable flow-dependent <Variable> together with rest of applicable UE <Variable>. For UE in NR standalone flow-dependent <Variable> 5qi, arp, and snssai are applicable. For UE in EN-DC flow-dependent <Variable> qci, and arp are applicable. Selection criteria evaluates to True if any of the flows evaluates to True. If UE does not have a flow, flow-dependent <Variable> values are evaluated as unknown variable values. If selection criteria shall match combination of flow-dependent <Variable>, then <FlowExpression> and <FlowExpressionList> must be used. Note: An <ExpressionList> defined as <VariableExpression> && <VariableExpression>, for which both <VariableExpression> relate to flow-dependent <Variable>, needs special attention. Example: <ExpressionList> = \"5qi==5 && 5qi==9\" always evaluate to False for UE in NR standalone even if UE has one flow with 5qi=5 and one flow with 5qi=9. Example: <ExpressionList> = \"5qi>=7 && 5qi<=11\" will evaluate to True for UE in NR standalone if UE has any flow with 5qi between 7 and 11. <FlowExpression> is defined as \"[\"<ExpressionList>\"]\" and indicates that an <ExpressionList> is evaluated per QoS flow independent of other <ExpressionList>. Example: <FlowExpressionList> = \"[5qi==1] && [5qi==5]\" evaluates to True for UE in NR standalone if UE has any flow with 5qi=1 and any flow with 5qi=5. In the example, [5qi==1] must match one flow, and [5qi==5] must match one flow. <VariableExpression> evaluates to Unknown if <Variable> is not known or if the <Variable> value is not valid. <VariableExpression> evaluates to True or False if <Variable> value is known and valid. <Value> \"ref\" is a special <Value> of <Variable> representing <ValueList> defined via corresponding reference attribute. For <Variable> chipset, and imeisv, corresponding reference attribute is chipsetRef, and imeiSvRef respectively. If reference attribute is empty, represented <ValueList> is empty. The logical operators <AndOr> and <Not> apply three way logic as defined below: F=False; T=True; U=Unknown A=Evaluation result of <ExpressionList> or <VariableExpression> B=Evaluation result of <ExpressionList> or <VariableExpression> NOT operator: A !A ----------------- F T U U T F AND operator: A B A && B ------------------- F F F F T F F U F T F F T T T T U U U F F U T U U U U OR operator: A B A || B ------------------ F F F F T T F U U T F T T T T T U T U F U U T T U U U Variable Definitions: ================= Allowed <Value> and <RelationalOperator> depend on <Variable> with limitations given below. 5qi: 5G QoS Identifier (3GPP TS 23.501). Applicable to NR standalone. Operator: ==, !=, <=, >=, <, and >. Value: Integer in range 0..255 given in decimal. arp: Priority Level part of the Allocation and Retention Priority (3GPP TS 38.413, 3GPP TS 36.423). Applicable to both NR standalone and EN-DC. Operator: ==, !=, <=, >=, <, and >. Value: Integer in range 1..15 given in decimal. cgrole: Cell group role. Applicable to both NR standalone and EN-DC. Operator: ==, and !=. Value: mcg or scg, where mcg is only applicable to NR standalone. chipset: Chipset identifier. Applicable to both NR standalone and EN-DC. Operator: ==, and !=. Value: String in format \"<vendor>.<variant>.<version>\" matched by regular expression \"(1[0-6]|[0-9])\\\\.(6[0-4]|[1-5]?[0-9])\\\\.(12[0-8]|1[01][0-9]|[1-9]?[0-9])\", or a string constant \"ref\". Description: Chipset identifier composed of three distinct elements: - vendor: 1-2 digit decimal number in range 0..16 - variant: 1-2 digit decimal number in range 0..64 - version: 1-3 digit decimal number in range 0..128 UEs that do not support chipset identifier reporting are represented internally as 0.0.0. Example values: 0.0.0, 1.1.1, 1.2.3, 16.10.100, 16.64.128, ref. imeisv: International Mobile Station Equipment Identity Software Version. Applicable to both NR standalone and EN-DC. Operator: ==, and !=. Value: String in format \"<TAC><SNR><SVN>\" matched by regular expression \"[0-9]{10}[0-9fF]{4}[0-9]{2}\", or string constant \"ref\". Description: IMEISV composed of three distinct elements: - TAC (Type Allocation Code): 8 digit decimal number - SNR (or SN, Serial Number): 2 digit decimal number + 4 digit hexa-decimal number, last four digits are automatically masked with 0xFFFF to match with masked IMEISV - SVN (Software Version Number): 2 digit decimal number Example values: 1234567890123456, 1234567890FFFF12, 1234567890ffff12, ref. imeitac: Type Allocation Code (TAC) part of imeisv. Applicable to both NR standalone and EN-DC. Operator: ==, !=, <=, >=, <, and >. Value: 8 digit decimal number. imeisvn: Software Version Number (SVN) part of imeisv. Applicable to both NR standalone and EN-DC. Operator: ==, !=, <=, >=, <, and >. Value: 2 digit decimal number. pagingPrio: Paging Priority (3GPP TS 23.501). Applicable to NR standalone. Operator: ==, !=, <=, >=, <, and > Value: Integer in range 1..8 given in decimal. Description: Paging priority value received in NGAP Paging message. The received value is valid in UE grouping framework when performing UE group evaluation during time specified by UeGroupSelection::validityTimePagingPrio. pCellOnlyUe: Low-Band and Mid-Band PCell-only capability. Indicates whether the UE is not capable of carrier aggregation in Low-Band or Mid-Band. Only applicable when performing UE group evaluation in NR standalone Master Node. Operator: ==, and !=. Value: Integer in range 0..1 given in decimal, where 0 means false and 1 means true. Only applicable if license for Flexible UE Grouping for Limited Capability UEs is present and feature is active. plmn: Public Land and Mobile Network identifier. Applicable to both NR standalone and EN-DC. Operator: ==, and !=. Value: A string matched by regular expression \"[02-79][0-9][0-9]-[0-9][0-9][0-9]?\". Example values: 070-007, 070-07, 234-56. qci: QoSClass Identifier (3GPP TS 23.401). Applicable to EN-DC. Operator: ==, !=, <=, >=, <, and >. Value: Integer in range 0..255 given in decimal. redCapUe: Reduced Capabilities UE indicator. Applicable to NR standalone. Operator: ==, and !=. Value: Integer in range 0..1 given in decimal, where 0 means false and 1 means true. Description: RedCap UE identification received via LCID in MSG3 (see 3GPP TS 38.331). rfsp: Index to RAT/Frequency Selection Priority (3GPP TS 23.501). Applicable to NR standalone. Operator: ==, !=, <=, >=, <, and >. Value: Integer in range 1..256 given in decimal. rrcEstResCause: RRC establishment cause or RRC resume cause. Applicable to NR standalone. Operator: ==, and !=. Value: One of emergency, highPriorityAccess, mt-Access, mo-Signaling, mo-Data, mo-VoiceCall, mo-VideoCall, mo-SMS, mps-PriorityAccess, or mcs-PriorityAccess. Description: Establishment cause value received in RRC Setup Request message or resume cause received in RRC Resume Request message (see 3GPP TS 38.331). The received establishment cause or resume cause is valid in UE grouping framework when performing UE group evaluation during time specified by corresponding validity time attribute value in MO class UeGroupSelection. snssai: Single Network Slice Selection Assistance Information (3GPP TS 23.003). Applicable to NR standalone. Operator: ==, !=, <=, >=, <, and >. Value: input option 1: String in format \"<SST><SD>\" matched by regular expression [0][x][0-9a-fA-F]{8} (8 digit hexa-decimal number). Value: input option 2: Integer in range 0x0..0xffffffff given in hexadecimal. Description: S-NSSAI is composed of two distinct elements: - SST (Slice/Service Type): 2 digit hexa-decimal number - SD (Slice Differentiator): 6 digit hexa-decimal number The SD field has a reserved value \"no SD value associated with the SST\" defined as hexadecimal FFFFFF/ffffff. Example values, input option 1: - 0x050000EE (SST=0x05,SD=0x0000EE) - 0x2effffff (SST=0x2e,SD=0xffffff // no SD associated with the SST) Example values, input option 2: - 0x1 (SST=0x00,SD=0x000001) - 0x50000EE (SST=0x05,SD=0x0000EE) - 0x150000EE (SST=0x15,SD=0x0000EE) spid: Subscriber Profile ID for RAT/Frequency Priority (3GPP TS 36.300). Applicable to EN-DC. Operator: ==, !=, <=, >=, <, and >. Value: Integer in range 1..256 given in decimal. voNrUe: Low-Band and Mid-Band VoNR capability. Only applicable when performing UE group evaluation in NR standalone Master Node. Operator: ==, and !=. Value: Integer in range 0..1 given in decimal, where 0 means false and 1 means true. Operator Precedence Order: ======================= The logical and relation operators are evaluated according to the precedence order listed below. --------------------------------------------- 1 (highest precedence) < Less than <= Less than or equal > Greater than >= Greater than or equal == Equal != Not equal ------------------------------------------- 2 ! (Not) --------------------------------------------- 3 && (And) --------------------------------------------- 4 (lowest precedence) || (Or) --------------------------------------------- The NOT operator \"!\" negates the following <ParentExpressionList>, <VariableExpression>, <FlowExpression> or an <ExpressionList> encapsulated in parenthesis. Therefore, expression !a==b && c==d is equivalent to ((!(a==b)) && (c==d)) and different from !(a==b && c==d). Expression !a==b and !(a==b) are equivalent. Since AND operator \"&&\" has higher precedence than OR operator \"||\", a<b || a<c && c<d is equivalent to (a<b || (a<c && c<d)). Surround expression list including OR operator with parenthesis to force OR operator to be evaluated before AND operators outside of the expression list, for example (a<b || a<c) && c<d. Examples: ========= Simple one valued expressions: plmn == 234-56 spid == 1 cgrole == mcg arp > 3 snssai == 0xfedcba98 rrcEstResCause == mo-VoiceCall imeisv == 1234567890FFFF12 imeisv == ref //Special <value> ref represents <ValueList> defined via imeiSvRef. chipset == ref chipset == 1.1.1 //Matches all UEs with chipset identifier: vendor = 1, variant = 1 and version = 1. chipset == 0.0.0 //Matches all UEs that do not support chipset identifier reporting. Value list expressions: spid == {8,9,10,1,155} !plmn == {234-56, 434-567} chipset == {1.1.1, 1.1.2, 1.1.3, ref} //Matches all UEs with chipset identifier: vendor = 1, variant = 1 and version = 1, 2 or 3, or the corresponding vendor, variant and version defined via chipsetRef. imeisv == {1234567890FFFF12, ref, 1234567890FFFF13} //Matches all UEs with imeisv: TAC = 12345678, SNR = 90FFFF and SVN = 12 or 13, or the corresponding TAC, SN and SVN defined via imeiSvRef. Equivalent expressions using ||: (spid == 8 || spid == 9 || spid == 10 || spid == 1 || spid == 155) //Equals to spid == {8, 9, 10, 1, 155}. !(plmn == 234-56 || plmn == 434-567) //Equals to !plmn == {234-56, 434-567}. imeisv == ref || imeisv == 1234567890FFFF12|| imeisv == 1234567890FFFF13 //Equals to imeisv == {ref, 1234567890FFFF12, 1234567890FFFF13}. chipset == 1.1.1 || chipset == ref || chipset == 1.1.2 // Equals to chipset == {1.1.1, ref, 1.1.2}. Negative expressions: !5qi==1 //Matches flows with 5qi not equal to 1. 5qi!=1 //Matches flows with 5qi not equal to 1. Negative <FlowExpressions> that produce same result: [!5qi==1] //Matches flows with 5qi not equal to 1. [5qi!=1] //Matches flows with 5qi not equal to 1. <FlowExpressionList> negative expressions: !([5qi==1]) //Matches UEs that do not have flows with 5qi 1. ![5qi==1] //Matches UEs that do not have flows with 5qi 1. Mixed examples: spid == 1 && cgrole == mcg !(spid != 1 || cgrole != mcg) (spid == 8 || spid == 9 || spid == 10 || spid == 1 || spid == 155) && (plmn == 234-56 || plmn == 434-567) Precedence given by \"()\" and sequence alter the evaluation order and result: [5qi==1] && chipset==ref || imeisv==ref && [5qi==5] //Equals to ([5qi==1] && chipset==ref) || (imeisv==ref && [5qi==5]) [5qi==1] && (chipset==ref || imeisv==ref) && [5qi==5] ([5qi==1] && chipset==ref || imeisv==ref) && [5qi==5] [5qi==1] && (chipset==ref || imeisv==ref && [5qi==5]) chipset==ref || [5qi==1] && [5qi==5] && imeisv==ref Examples of selection criteria that shall be avoided since they will always be evaluated to False. <FlowExpression> can be used in these cases. 5qi==5 && 5qi==9 snssai==0x15000000 && snssai==0x17000000 arp==5 && arp==10 qci==5 && qci==9 Example of selection criteria for UE variable snssai: snssai>=15000000 && snssai<=15FFFFFF //Matches UE which has a flow with S-NSSAI SST part equal to 15 regardless of value of S-NSSAI SD part. snssai==15FFFFFF //Matches UE which has a flow with S-NSSAI SST part equal to 15 and S-NSSAI SD part value equal to FFFFFF, meaning no SD value associated with the SST. Flow expressions combined with UE variables: plmn == 234-56 && [5qi==1] && [5qi==9] //Matches UE which has plmn equal to 234-56, any QoS flow with 5qi equal to 1, and any QoS flow with 5qi equal to 9. chipset==1.5.32 && [5qi==9] && ![5qi==1] //Matches UE which has chipset identifier equal to 1.5.32, any QoS flow with 5qi equal to 9, and no QoS flow with 5qi equal to 1. [5qi==1 && snssai == 0xfedcba98] || ([5qi==2] && [snssai == 0xfedcba77]) //Matches UE which has any QoS flow with 5qi equal to 1 and snssai equal to 0xfedcba98, or has any QoS flow with 5qi equal to 2 and snssai equal to 0xfedcba77. voNrUe==1 && chipset==1.1.1 && [5qi==1] //Matches UEs with Low-Band and Mid-Band VoNR capability using chipset 1.1.1, and have an ongoing flow 5qi.; length 1..1000.";
      type string {
        length "1..1000";
      }
    }
    leaf ueAdmissionGroupDefinitionId {
      description "The value component of the RDN..";
      type string;
      mandatory true;
    }
    leaf ueAdmissionGroupId {
      description "UE admission group identifier. Must be unique among UE admission groups.; range 1..255.";
      type eytypes:int32_range_1-255;
      mandatory true;
    }
    leaf ueAdmissionGroupPriority {
      description "Relative priority among UE admission groups. Must be unique among UE admission groups. If UE fulfills selection criteria for more than one UE admission group, UE admission group with the highest priority is selected. Higher value gives higher priority.; range 1..65535.";
      type eytypes:int32_range_1-65535;
      mandatory true;
    }
    leaf userLabel {
      description "Label for free use..";
      type string;
    }
  }
  grouping UeCC-attributes {
    leaf ueCCId {
      description "The value component of the RDN..";
      type string;
      mandatory true;
    }
  }
  grouping UeCovMeas-attributes {
    leaf ueCovMeasId {
      description "The value component of the RDN..";
      type string;
      mandatory true;
    }
    leaf userLabel {
      description "Label for free use..";
      type string;
    }
  }
  grouping UeGroupSelection-attributes {
    leaf ueGroupSelectionId {
      description "The value component of the RDN..";
      type string;
      mandatory true;
    }
    leaf validityTimeEmergencyCause {
      description "Validity time of RRC establishment cause or resume cause emergency. Defines for how long time the IE establishmentCause with value emergency, received in RRCSetupRequest message, or the IE resumeCause with value emergency, received in RRCResumeRequest message, is valid when performing UE group evaluation.; range 1..36000; Default value: 6.";
      type int32 {
        range "1..36000";
      }
      default "6";
      units "s";
    }
    leaf validityTimeHighPrioAccCause {
      description "Validity time of RRC establishment cause or resume cause high priority access. Defines for how long time the IE establishmentCause with value high priority access, received in RRCSetupRequest message, or the IE resumeCause with value high priority access, received in RRCResumeRequest message, is valid when performing UE group evaluation.; range 1..15; Default value: 6.";
      type eytypes:int32_range_1-15;
      default "6";
      units "s";
    }
    leaf validityTimeMcsPrioAccCause {
      description "Validity time of RRC establishment cause or resume cause MCS priority access. Defines for how long time the IE establishmentCause with value mission critical services priority access, received in RRCSetupRequest message, or the IE resumeCause with value mission critical services priority access, received in RRCResumeRequest message, is valid when performing UE group evaluation.; range 1..15; Default value: 6.";
      type eytypes:int32_range_1-15;
      default "6";
      units "s";
    }
    leaf validityTimeMoDataCause {
      description "Validity time of RRC establishment cause or resume cause mobile originating data. Defines for how long time the IE establishmentCause with value mobile originating data, received in RRCSetupRequest message, or the IE resumeCause with value mobile originating data, received in RRCResumeRequest message, is valid when performing UE group evaluation.; range 1..15; Default value: 6.";
      type eytypes:int32_range_1-15;
      default "6";
      units "s";
    }
    leaf validityTimeMoSignallingCause {
      description "Validity time of RRC establishment cause or resume cause mobile originating signaling. Defines for how long time the IE establishmentCause with value mobile originating signaling, received in RRCSetupRequest message, or the IE resumeCause with value mobile originating signaling, received in RRCResumeRequest message, is valid when performing UE group evaluation.; range 1..15; Default value: 6.";
      type eytypes:int32_range_1-15;
      default "6";
      units "s";
    }
    leaf validityTimeMoSmsCause {
      description "Validity time of RRC establishment cause or resume cause mobile originating SMS. Defines for how long time the IE establishmentCause with value mobile originating short message service, received in RRCSetupRequest message, or the IE resumeCause with value mobile originating short message service, received in RRCResumeRequest message, is valid when performing UE group evaluation.; range 1..15; Default value: 6.";
      type eytypes:int32_range_1-15;
      default "6";
      units "s";
    }
    leaf validityTimeMoVideoCallCause {
      description "Validity time of RRC establishment cause or resume cause mobile originating video call. Defines for how long time the IE establishmentCause with value mobile originating video call, received in RRCSetupRequest message, or the IE resumeCause with value mobile originating video call, received in RRCResumeRequest message, is valid when performing UE group evaluation.; range 1..15; Default value: 6.";
      type eytypes:int32_range_1-15;
      default "6";
      units "s";
    }
    leaf validityTimeMoVoiceCallCause {
      description "Validity time of RRC establishment cause or resume cause mobile originating voice call. Defines for how long time the IE establishmentCause with value mobile originating voice call, received in RRCSetupRequest message, or the IE resumeCause with value mobile originating voice call, received in RRCResumeRequest message, is valid when performing UE group evaluation.; range 1..15; Default value: 6.";
      type eytypes:int32_range_1-15;
      default "6";
      units "s";
    }
    leaf validityTimeMpsPrioAccCause {
      description "Validity time of RRC establishment cause or resume cause MPS priority access. Defines for how long time the IE establishmentCause with value multimedia priority service priority access, received in RRCSetupRequest message, or the IE resumeCause with value multimedia priority service priority access, received in RRCResumeRequest message, is valid when performing UE group evaluation.; range 1..15; Default value: 6.";
      type eytypes:int32_range_1-15;
      default "6";
      units "s";
    }
    leaf validityTimeMtAccessCause {
      description "Validity time of RRC establishment cause or resume cause mobile terminating access. Defines for how long time the IE establishmentCause with value mobile terminating access, received in RRCSetupRequest message, or the IE resumeCause with value mobile terminating access, received in RRCResumeRequest message, is valid when performing UE group evaluation.; range 1..15; Default value: 6.";
      type eytypes:int32_range_1-15;
      default "6";
      units "s";
    }
    leaf validityTimePagingPrio {
      description "Validity time of Paging Priority. Defines how long IE Paging Priority, received in NGAP paging message, is valid when performing UE group evaluation.; range 1..15; Default value: 6.";
      type eytypes:int32_range_1-15;
      default "6";
      units "s";
    }
  }
  grouping UeGroupSelectionProfile-attributes {
    leaf chipsetRef {
      description "Reference to an instance of Chipsets MO. Special <Value> \"ref\" for <Variable> chipset in selectionCriteria represents chipset <ValueList> defined via this reference. If empty, represented chipset <ValueList> is empty..";
      type string;
    }
    leaf imeiSvRef {
      description "Reference to an instance of ImeiSvs MO. Special <Value> \"ref\" for <Variable> imeisv in selectionCriteria represents imeisv <ValueList> defined via this reference. If empty, represented imeisv <ValueList> is empty..";
      type string;
    }
    leaf selectionCriteria {
      description "UE group selection criteria. Defines selection criteria that UE needs to fulfill to belong to UE group instance. If selection criteria evaluates to True, UE fulfills UE group instance. If selection criteria evaluates to False or Unknown, UE does not fulfill UE group instance. If selection criteria evaluates to True for more than one UE group instance, UE belongs to UE group instance with highest setting of ueGroupPriority. Syntax: ====== The syntax of selection criteria is defined using Backus-Naur form. <SelectionCriteria> ::= <ParentExpressionList> | \"\" <ParentExpressionList> ::= <ParentExpressionList> <AndOr> < ParentExpressionList> | <Not>? \"(\" <ParentExpressionList> \")\" | <ExpressionList> | <FlowExpressionList> <FlowExpressionList> ::= <FlowExpressionList> <AndOr> <FlowExpressionList> | <Not>? <FlowExpression> <FlowExpression> ::= \"[\"<ExpressionList>\"]\" <ExpressionList> ::= <ExpressionList> <AndOr> <ExpressionList> | <Not>? \"(\" <ExpressionList> \")\" | <Not>? <VariableExpression> <VariableExpression> ::= <Variable> <RelationalOperator> <Value> | <Variable> \"==\" \"{\" <ValueList> \"}\" <ValueList> ::= <Value> \",\" <ValueList> | <Value> <Variable> ::= \"5qi\" | \"arp\" | \"cgrole\" | \"chipset\" | \"imeisv\" | \"imeisvn\" | \"imeitac\" | \"pagingPrio\" | \"pCellOnlyUe\" | \"plmn\" | \"qci\" | \"redCapUe\" | \"rfsp\" | \"rrcEstResCause\" | \"snssai\" | \"spid\" | \"voNrUe\" <AndOr> ::= \"&&\" | \"||\" <Not> ::= \"!\" <RelationalOperator> ::= \"==\" | \"!=\" | \"<\" | \"<=\" | \">=\" | \">\" A list of possible values can be specified in the form <Variable> == {<value1>, <value2>, ... , <valueN>}. This statement is equivalent to writing (<Variable> == <value1> || <Variable> == <value2> || ... || <Variable> == <valueN>). Up to 4 <FlowExpression> can be defined in <SelectionCriteria>. Whitespaces are allowed in the string for improved readability and are removed prior to evaluation. Question mark (?) means zero or one occurrence. For example, <Not>? makes <Not> optional. Syntax is case sensitive. Semantic: ======== Selection criteria evaluation is defined by the following semantic rules. If empty or set to empty string \"\", selection criteria always evaluates to True. Selection criteria evaluation is done per UE with the current applicable UE <Variable> values as input. List of UE <Variable> values that are applicable to NR standalone and EN-DC, respectively, is defined in Variable Definitions section below. Selection criteria for a UE is evaluated separately for each flow using applicable flow-dependent <Variable> together with rest of applicable UE <Variable>. For UE in NR standalone flow-dependent <Variable> 5qi, arp, and snssai are applicable. For UE in EN-DC flow-dependent <Variable> qci, and arp are applicable. Selection criteria evaluates to True if any of the flows evaluates to True. If UE does not have a flow, flow-dependent <Variable> values are evaluated as unknown variable values. If selection criteria shall match combination of flow-dependent <Variable>, then <FlowExpression> and <FlowExpressionList> must be used. Note: An <ExpressionList> defined as <VariableExpression> && <VariableExpression>, for which both <VariableExpression> relate to flow-dependent <Variable>, needs special attention. Example: <ExpressionList> = \"5qi==5 && 5qi==9\" always evaluate to False for UE in NR standalone even if UE has one flow with 5qi=5 and one flow with 5qi=9. Example: <ExpressionList> = \"5qi>=7 && 5qi<=11\" will evaluate to True for UE in NR standalone if UE has any flow with 5qi between 7 and 11. <FlowExpression> is defined as \"[\"<ExpressionList>\"]\" and indicates that an <ExpressionList> is evaluated per QoS flow independent of other <ExpressionList>. Example: <FlowExpressionList> = \"[5qi==1] && [5qi==5]\" evaluates to True for UE in NR standalone if UE has any flow with 5qi=1 and any flow with 5qi=5. In the example, [5qi==1] must match one flow, and [5qi==5] must match one flow. <VariableExpression> evaluates to Unknown if <Variable> is not known or if the <Variable> value is not valid. <VariableExpression> evaluates to True or False if <Variable> value is known and valid. <Value> \"ref\" is a special <Value> of <Variable> representing <ValueList> defined via corresponding reference attribute. For <Variable> chipset, and imeisv, corresponding reference attribute is chipsetRef, and imeiSvRef respectively. If reference attribute is empty, represented <ValueList> is empty. The logical operators <AndOr> and <Not> apply three way logic as defined below: F=False; T=True; U=Unknown A=Evaluation result of <ExpressionList> or <VariableExpression> B=Evaluation result of <ExpressionList> or <VariableExpression> NOT operator: A !A ----------------- F T U U T F AND operator: A B A && B ------------------- F F F F T F F U F T F F T T T T U U U F F U T U U U U OR operator: A B A || B ------------------ F F F F T T F U U T F T T T T T U T U F U U T T U U U Variable Definitions: ================= Allowed <Value> and <RelationalOperator> depend on <Variable> with limitations given below. 5qi: 5G QoS Identifier (3GPP TS 23.501). Applicable to NR standalone. Operator: ==, !=, <=, >=, <, and >. Value: Integer in range 0..255 given in decimal. arp: Priority Level part of the Allocation and Retention Priority (3GPP TS 38.413, 3GPP TS 36.423). Applicable to both NR standalone and EN-DC. Operator: ==, !=, <=, >=, <, and >. Value: Integer in range 1..15 given in decimal. cgrole: Cell group role. Applicable to both NR standalone and EN-DC. Operator: ==, and !=. Value: mcg or scg, where mcg is only applicable to NR standalone. chipset: Chipset identifier. Applicable to both NR standalone and EN-DC. Operator: ==, and !=. Value: String in format \"<vendor>.<variant>.<version>\" matched by regular expression \"(1[0-6]|[0-9])\\\\.(6[0-4]|[1-5]?[0-9])\\\\.(12[0-8]|1[01][0-9]|[1-9]?[0-9])\", or a string constant \"ref\". Description: Chipset identifier composed of three distinct elements: - vendor: 1-2 digit decimal number in range 0..16 - variant: 1-2 digit decimal number in range 0..64 - version: 1-3 digit decimal number in range 0..128 UEs that do not support chipset identifier reporting are represented internally as 0.0.0. Example values: 0.0.0, 1.1.1, 1.2.3, 16.10.100, 16.64.128, ref. imeisv: International Mobile Station Equipment Identity Software Version. Applicable to both NR standalone and EN-DC. Operator: ==, and !=. Value: String in format \"<TAC><SNR><SVN>\" matched by regular expression \"[0-9]{10}[0-9fF]{4}[0-9]{2}\", or string constant \"ref\". Description: IMEISV composed of three distinct elements: - TAC (Type Allocation Code): 8 digit decimal number - SNR (or SN, Serial Number): 2 digit decimal number + 4 digit hexa-decimal number, last four digits are automatically masked with 0xFFFF to match with masked IMEISV - SVN (Software Version Number): 2 digit decimal number Example values: 1234567890123456, 1234567890FFFF12, 1234567890ffff12, ref. imeitac: Type Allocation Code (TAC) part of imeisv. Applicable to both NR standalone and EN-DC. Operator: ==, !=, <=, >=, <, and >. Value: 8 digit decimal number. imeisvn: Software Version Number (SVN) part of imeisv. Applicable to both NR standalone and EN-DC. Operator: ==, !=, <=, >=, <, and >. Value: 2 digit decimal number. pagingPrio: Paging Priority (3GPP TS 23.501). Applicable to NR standalone. Operator: ==, !=, <=, >=, <, and > Value: Integer in range 1..8 given in decimal. Description: Paging priority value received in NGAP Paging message. The received value is valid in UE grouping framework when performing UE group evaluation during time specified by UeGroupSelection::validityTimePagingPrio. pCellOnlyUe: Low-Band and Mid-Band PCell-only capability. Indicates whether the UE is not capable of carrier aggregation in Low-Band or Mid-Band. Only applicable when performing UE group evaluation in NR standalone Master Node. Operator: ==, and !=. Value: Integer in range 0..1 given in decimal, where 0 means false and 1 means true. Only applicable if license for Flexible UE Grouping for Limited Capability UEs is present and feature is active. plmn: Public Land and Mobile Network identifier. Applicable to both NR standalone and EN-DC. Operator: ==, and !=. Value: A string matched by regular expression \"[02-79][0-9][0-9]-[0-9][0-9][0-9]?\". Example values: 070-007, 070-07, 234-56. qci: QoSClass Identifier (3GPP TS 23.401). Applicable to EN-DC. Operator: ==, !=, <=, >=, <, and >. Value: Integer in range 0..255 given in decimal. redCapUe: Reduced Capabilities UE indicator. Applicable to NR standalone. Operator: ==, and !=. Value: Integer in range 0..1 given in decimal, where 0 means false and 1 means true. Description: RedCap UE identification received via LCID in MSG3 (see 3GPP TS 38.331). rfsp: Index to RAT/Frequency Selection Priority (3GPP TS 23.501). Applicable to NR standalone. Operator: ==, !=, <=, >=, <, and >. Value: Integer in range 1..256 given in decimal. rrcEstResCause: RRC establishment cause or RRC resume cause. Applicable to NR standalone. Operator: ==, and !=. Value: One of emergency, highPriorityAccess, mt-Access, mo-Signaling, mo-Data, mo-VoiceCall, mo-VideoCall, mo-SMS, mps-PriorityAccess, or mcs-PriorityAccess. Description: Establishment cause value received in RRC Setup Request message or resume cause received in RRC Resume Request message (see 3GPP TS 38.331). The received establishment cause or resume cause is valid in UE grouping framework when performing UE group evaluation during time specified by corresponding validity time attribute value in MO class UeGroupSelection. snssai: Single Network Slice Selection Assistance Information (3GPP TS 23.003). Applicable to NR standalone. Operator: ==, !=, <=, >=, <, and >. Value: input option 1: String in format \"<SST><SD>\" matched by regular expression [0][x][0-9a-fA-F]{8} (8 digit hexa-decimal number). Value: input option 2: Integer in range 0x0..0xffffffff given in hexadecimal. Description: S-NSSAI is composed of two distinct elements: - SST (Slice/Service Type): 2 digit hexa-decimal number - SD (Slice Differentiator): 6 digit hexa-decimal number The SD field has a reserved value \"no SD value associated with the SST\" defined as hexadecimal FFFFFF/ffffff. Example values, input option 1: - 0x050000EE (SST=0x05,SD=0x0000EE) - 0x2effffff (SST=0x2e,SD=0xffffff // no SD associated with the SST) Example values, input option 2: - 0x1 (SST=0x00,SD=0x000001) - 0x50000EE (SST=0x05,SD=0x0000EE) - 0x150000EE (SST=0x15,SD=0x0000EE) spid: Subscriber Profile ID for RAT/Frequency Priority (3GPP TS 36.300). Applicable to EN-DC. Operator: ==, !=, <=, >=, <, and >. Value: Integer in range 1..256 given in decimal. voNrUe: Low-Band and Mid-Band VoNR capability. Only applicable when performing UE group evaluation in NR standalone Master Node. Operator: ==, and !=. Value: Integer in range 0..1 given in decimal, where 0 means false and 1 means true. Operator Precedence Order: ======================= The logical and relation operators are evaluated according to the precedence order listed below. --------------------------------------------- 1 (highest precedence) < Less than <= Less than or equal > Greater than >= Greater than or equal == Equal != Not equal ------------------------------------------- 2 ! (Not) --------------------------------------------- 3 && (And) --------------------------------------------- 4 (lowest precedence) || (Or) --------------------------------------------- The NOT operator \"!\" negates the following <ParentExpressionList>, <VariableExpression>, <FlowExpression> or an <ExpressionList> encapsulated in parenthesis. Therefore, expression !a==b && c==d is equivalent to ((!(a==b)) && (c==d)) and different from !(a==b && c==d). Expression !a==b and !(a==b) are equivalent. Since AND operator \"&&\" has higher precedence than OR operator \"||\", a<b || a<c && c<d is equivalent to (a<b || (a<c && c<d)). Surround expression list including OR operator with parenthesis to force OR operator to be evaluated before AND operators outside of the expression list, for example (a<b || a<c) && c<d. Examples: ========= Simple one valued expressions: plmn == 234-56 spid == 1 cgrole == mcg arp > 3 snssai == 0xfedcba98 rrcEstResCause == mo-VoiceCall imeisv == 1234567890FFFF12 imeisv == ref //Special <value> ref represents <ValueList> defined via imeiSvRef. chipset == ref chipset == 1.1.1 //Matches all UEs with chipset identifier: vendor = 1, variant = 1 and version = 1. chipset == 0.0.0 //Matches all UEs that do not support chipset identifier reporting. Value list expressions: spid == {8,9,10,1,155} !plmn == {234-56, 434-567} chipset == {1.1.1, 1.1.2, 1.1.3, ref} //Matches all UEs with chipset identifier: vendor = 1, variant = 1 and version = 1, 2 or 3, or the corresponding vendor, variant and version defined via chipsetRef. imeisv == {1234567890FFFF12, ref, 1234567890FFFF13} //Matches all UEs with imeisv: TAC = 12345678, SNR = 90FFFF and SVN = 12 or 13, or the corresponding TAC, SN and SVN defined via imeiSvRef. Equivalent expressions using ||: (spid == 8 || spid == 9 || spid == 10 || spid == 1 || spid == 155) //Equals to spid == {8, 9, 10, 1, 155}. !(plmn == 234-56 || plmn == 434-567) //Equals to !plmn == {234-56, 434-567}. imeisv == ref || imeisv == 1234567890FFFF12|| imeisv == 1234567890FFFF13 //Equals to imeisv == {ref, 1234567890FFFF12, 1234567890FFFF13}. chipset == 1.1.1 || chipset == ref || chipset == 1.1.2 // Equals to chipset == {1.1.1, ref, 1.1.2}. Negative expressions: !5qi==1 //Matches flows with 5qi not equal to 1. 5qi!=1 //Matches flows with 5qi not equal to 1. Negative <FlowExpressions> that produce same result: [!5qi==1] //Matches flows with 5qi not equal to 1. [5qi!=1] //Matches flows with 5qi not equal to 1. <FlowExpressionList> negative expressions: !([5qi==1]) //Matches UEs that do not have flows with 5qi 1. ![5qi==1] //Matches UEs that do not have flows with 5qi 1. Mixed examples: spid == 1 && cgrole == mcg !(spid != 1 || cgrole != mcg) (spid == 8 || spid == 9 || spid == 10 || spid == 1 || spid == 155) && (plmn == 234-56 || plmn == 434-567) Precedence given by \"()\" and sequence alter the evaluation order and result: [5qi==1] && chipset==ref || imeisv==ref && [5qi==5] //Equals to ([5qi==1] && chipset==ref) || (imeisv==ref && [5qi==5]) [5qi==1] && (chipset==ref || imeisv==ref) && [5qi==5] ([5qi==1] && chipset==ref || imeisv==ref) && [5qi==5] [5qi==1] && (chipset==ref || imeisv==ref && [5qi==5]) chipset==ref || [5qi==1] && [5qi==5] && imeisv==ref Examples of selection criteria that shall be avoided since they will always be evaluated to False. <FlowExpression> can be used in these cases. 5qi==5 && 5qi==9 snssai==0x15000000 && snssai==0x17000000 arp==5 && arp==10 qci==5 && qci==9 Example of selection criteria for UE variable snssai: snssai>=15000000 && snssai<=15FFFFFF //Matches UE which has a flow with S-NSSAI SST part equal to 15 regardless of value of S-NSSAI SD part. snssai==15FFFFFF //Matches UE which has a flow with S-NSSAI SST part equal to 15 and S-NSSAI SD part value equal to FFFFFF, meaning no SD value associated with the SST. Flow expressions combined with UE variables: plmn == 234-56 && [5qi==1] && [5qi==9] //Matches UE which has plmn equal to 234-56, any QoS flow with 5qi equal to 1, and any QoS flow with 5qi equal to 9. chipset==1.5.32 && [5qi==9] && ![5qi==1] //Matches UE which has chipset identifier equal to 1.5.32, any QoS flow with 5qi equal to 9, and no QoS flow with 5qi equal to 1. [5qi==1 && snssai == 0xfedcba98] || ([5qi==2] && [snssai == 0xfedcba77]) //Matches UE which has any QoS flow with 5qi equal to 1 and snssai equal to 0xfedcba98, or has any QoS flow with 5qi equal to 2 and snssai equal to 0xfedcba77. voNrUe==1 && chipset==1.1.1 && [5qi==1] //Matches UEs with Low-Band and Mid-Band VoNR capability using chipset 1.1.1, and have an ongoing flow 5qi.; length 1..1000.";
      type string {
        length "1..1000";
      }
    }
    leaf selectionProbability {
      description "Selection probability for AB testing. Probability for UE to be selected into this UeGroup after fulfilling all selection conditions according to the configured selectionCriteria.; range 0..100; Default value: 100.";
      type eytypes:int32_range_0-100;
      default "100";
      units "percent";
    }
    leaf ueGroupId {
      description "UE group identifier.; range 1..255.";
      type eytypes:int32_range_1-255;
      mandatory true;
    }
    leaf ueGroupPriority {
      description "Relative priority among UE groups. If UE fulfills more than one UeGroupSelectionProfile, UeGroupSelectionProfile with the highest relative priority is applied. Higher value gives higher priority.; range 1..65535.";
      type eytypes:int32_range_1-65535;
      mandatory true;
    }
    leaf ueGroupSelectionProfileId {
      description "The value component of the RDN..";
      type string;
      mandatory true;
    }
    leaf userLabel {
      description "Label for free use..";
      type string;
    }
  }
  grouping UeMC-attributes {
    leaf ueConfGroupType {
      description "UE configuration group type. UE configuration group type that is applied in contained UeMCUeCfg instances..";
      type enumeration {
        enum UE_MOBILITY_GROUP;
        enum UE_SERVICE_GROUP;
        enum UE_ADMISSION_GROUP;
      }
    }
    leaf ueMCId {
      description "The value component of the RDN..";
      type string;
      mandatory true;
    }
    leaf userLabel {
      description "Label for free use..";
      type string;
    }
  }
  grouping UeMCCellProfile-attributes {
    leaf connModeUeAllowedToBarredCell {
      description "Whether UE in RRC Connected Mode is allowed to access cell in BARRED state. If true, UE in RRC Connected Mode can access cell in BARRED state, also valid for EN-DC UE.; Default value: true.";
      type boolean;
      default "true";
    }
    leaf filterCoefficientEUtraRsrp {
      description "Layer 3 average filter coefficient for RSRP measurements on E-UTRA frequencies. Layer 3 average filter coefficient that is applied in UE performing RSRP measurements on E-UTRA frequencies.; Default value: 4.";
      type int32 {
        range "0..9 | 11 | 13 | 15 | 17 | 19";
      }
      default "4";
    }
    leaf filterCoefficientEUtraRsrq {
      description "Layer 3 average filter coefficient for RSRQ measurements on E-UTRA frequencies. Layer 3 average filter coefficient that is applied in UE performing RSRQ measurements on E-UTRA frequencies.; Default value: 11.";
      type int32 {
        range "0..9 | 11 | 13 | 15 | 17 | 19";
      }
      default "11";
    }
    leaf filterCoefficientEUtraSinr {
      description "Layer 3 average filter coefficient for SINR measurements on E-UTRA frequencies. Layer 3 average filter coefficient that is applied in UE performing SINR measurements on E-UTRA frequencies.; Default value: 4.";
      type int32 {
        range "0..9 | 11 | 13 | 15 | 17 | 19";
      }
      default "4";
    }
    leaf filterCoefficientNrRsrpHigh {
      description "Layer 3 average filter coefficient for RSRP measurements on NR frequencies. Layer 3 average filter coefficient that is applied in UE performing RSRP measurements on NR frequencies. Filter coefficient for measurement of NR frequencies with ARFCN-ValueNR value higher than ARFCN-ValueNR defined by freqClassificationThreshold.; Default value: 4.";
      type int32 {
        range "0..9 | 11 | 13 | 15 | 17 | 19";
      }
      default "4";
    }
    leaf filterCoefficientNrRsrpLow {
      description "Layer 3 average filter coefficient for RSRP measurements on NR frequencies. Layer 3 average filter coefficient that is applied in UE performing RSRP measurements on NR frequencies. Filter coefficient for measurement of NR frequencies with ARFCN-ValueNR value lower than or equal to ARFCN-ValueNR defined by freqClassificationThreshold.; Default value: 4.";
      type int32 {
        range "0..9 | 11 | 13 | 15 | 17 | 19";
      }
      default "4";
    }
    leaf filterCoefficientNrRsrqHigh {
      description "Layer 3 average filter coefficient for RSRQ measurements on NR frequencies. Layer 3 average filter coefficient that is applied in UE performing RSRQ measurements on NR frequencies. Filter coefficient for measurement of NR frequencies with ARFCN-ValueNR value higher than ARFCN-ValueNR defined by freqClassificationThreshold.; Default value: 11.";
      type int32 {
        range "0..9 | 11 | 13 | 15 | 17 | 19";
      }
      default "11";
    }
    leaf filterCoefficientNrRsrqLow {
      description "Layer 3 average filter coefficient for RSRQ measurements on NR frequencies. Layer 3 average filter coefficient that is applied in UE performing RSRQ measurements on NR frequencies. Filter coefficient for measurement of NR frequencies with ARFCN-ValueNR value lower than or equal to ARFCN-ValueNR defined by freqClassificationThreshold.; Default value: 11.";
      type int32 {
        range "0..9 | 11 | 13 | 15 | 17 | 19";
      }
      default "11";
    }
    leaf filterCoefficientNrSinrHigh {
      description "Layer 3 average filter coefficient for SINR measurements on NR frequencies. Layer 3 average filter coefficient that is applied in UE performing SINR measurements on NR frequencies. Filter coefficient for measurement of NR frequencies with ARFCN-ValueNR value higher than ARFCN-ValueNR defined by freqClassificationThreshold.; Default value: 4.";
      type int32 {
        range "0..9 | 11 | 13 | 15 | 17 | 19";
      }
      default "4";
    }
    leaf filterCoefficientNrSinrLow {
      description "Layer 3 average filter coefficient for SINR measurements on NR frequencies. Layer 3 average filter coefficient that is applied in UE performing SINR measurements on NR frequencies. Filter coefficient for measurement of NR frequencies with ARFCN-ValueNR value lower than or equal to ARFCN-ValueNR defined by freqClassificationThreshold.; Default value: 4.";
      type int32 {
        range "0..9 | 11 | 13 | 15 | 17 | 19";
      }
      default "4";
    }
    leaf freqClassificationThreshold {
      description "Frequency classification threshold. Threshold is provided as ARFCN-ValueNR value and defines which filter coefficients that are used by UE when measuring on NR frequencies.; range 0..3279164; Default value: 3279163.";
      type int32 {
        range "0..3279164";
      }
      default "3279163";
    }
    leaf noOfInvIntraFreqTrigPCSearch {
      description "Number of invalid mobility targets needed to trigger PCell candidates search. Configuration of number of better intra-frequency PCell measurement reports for invalid mobility targets needed to trigger PCell candidates search outside PCell search zone.; range 1..3; Default value: 1.";
      type int32 {
        range "1..3";
      }
      default "1";
    }
    leaf prohibitCellTrigMob {
      description "Whether prohibited cell triggered mobility is enabled. If not DISABLED, configure measurements for searching PCell candidates on other frequencies in following cases: - UE is outside of PCell search zone and number of reported better intra-frequency PCell measurements for invalid mobility targets has reached noOfInvIntraFTrigPCSearch. - Inter-gNB intra-frequency handover is rejected by target cell. For ENABLED_EUTRAN_ONLY, E-UTRAN frequency measurements are configured for PCell candidates search. For ENABLED_ALL, both NR and E-UTRAN frequency measurements are configured for PCell candidates search..";
      type enumeration {
        enum DISABLED;
        enum ENABLED_EUTRAN_ONLY;
        enum ENABLED_ALL;
      }
    }
    leaf-list reservedBy {
      description "Contains a list of MO instances that reserve this MO instance..";
      type string;
      min-elements 0;
    }
    leaf sMeasure {
      description "RSRP measurement threshold when UE is required to perform measurements on non-serving cells. Corresponds to RRC parameter s-MeasureConfig and choice ssb-RSRP. If empty or 1000, threshold is not used. Value -29 corresponds to special value of ssb-RSRP = infinity.; Default value: -29.";
      type int32 {
        range "-156..-29 | 1000";
      }
      default "-29";
      units "dBm";
    }
    leaf ueConfGroupType {
      description "UE configuration group type. UE configuration group type that is applied in contained UeMCCellProfileUeCfg instances..";
      type enumeration {
        enum UE_MOBILITY_GROUP;
        enum UE_SERVICE_GROUP;
        enum UE_ADMISSION_GROUP;
      }
    }
    leaf ueMCCellProfileId {
      description "The value component of the RDN..";
      type string;
      mandatory true;
    }
    leaf userLabel {
      description "Label for free use..";
      type string;
    }
  }
  grouping UeMCCellProfileUeCfg-attributes {
    leaf checkUlQualityIncomingHo {
      description "Whether uplink quality evaluation is enabled at inter-frequency incoming handover.; Default value: false.";
      type boolean;
      default "false";
    }
    leaf connModeUeAllowedToResCell {
      description "Whether UE in RRC Connected Mode is allowed to access cell in RESERVED state. If true, UE in RRC Connected Mode can access cell in RESERVED state, also valid for EN-DC UE.; Default value: true.";
      type boolean;
      default "true";
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf ueMCCellProfileUeCfgId {
      description "The value component of the RDN..";
      type string;
      mandatory true;
    }
    leaf ulQualityThreshIncomingHo {
      description "Threshold value for uplink radio quality in target cell at inter-frequency incoming handover. Below this threshold, target cell uplink quality is considered critical for UE and incoming handover is rejected. Only applicable if checkUlQualityIncomingHo is true.; range -150..500; Default value: 70.";
      type int32 {
        range "-150..500";
      }
      default "70";
      units "dB";
    }
  }
  grouping UeMCEUtranFreqRelProfile-attributes {
    leaf blindRwrAllowed {
      description "Whether this frequency relation is used as blind release with redirect candidate. Applied at blind release with redirect triggered by poor coverage or when UE fails capability check. If true for more than one E-UTRAN frequency relation, frequency relation with lowest ARFCN is used. If false for all E-UTRAN frequency relations, UE will be released to idle without redirection..";
      type boolean;
    }
    leaf connModeAllowedPCell {
      description "Whether placing PCell on E-UTRAN frequency defined by E-UTRAN frequency relation is allowed. Applies to UEs that use cell as PCell for poor coverage triggered handover or blind release with redirect to this cell. Blind release with redirect can be triggered by poor coverage or when UE fails capability check..";
      type boolean;
    }
    leaf connModePrioPCell {
      description "Connected mode PCell priority for E-UTRAN frequency relation. Applies to UEs that use cell as PCell. Used to decide preference on which E-UTRAN frequency to place PCell in connected mode. 0 means frequency relation with lowest priority. 7 means frequency relation with highest priority. Applicable only when connModeAllowedPCell attribute is true.; range 0..7.";
      type eytypes:int32_range_0-7;
    }
    leaf-list reservedBy {
      description "Contains a list of MO instances that reserve this MO instance..";
      type string;
      min-elements 0;
    }
    leaf ueConfGroupType {
      description "UE configuration group type. UE configuration group type that is applied in contained UeMCEUtranFreqRelProfileUeCfg instances..";
      type enumeration {
        enum UE_MOBILITY_GROUP;
        enum UE_SERVICE_GROUP;
        enum UE_ADMISSION_GROUP;
      }
    }
    leaf ueMCEUtranFreqRelProfileId {
      description "The value component of the RDN..";
      type string;
      mandatory true;
    }
    leaf userLabel {
      description "Label for free use..";
      type string;
    }
  }
  grouping UeMCEUtranFreqRelProfileUeCfg-attributes {
    leaf blindRwrAllowed {
      description "Whether this frequency relation is used as blind release with redirect candidate. Applied at blind release with redirect triggered by poor coverage or when UE fails capability check. If true for more than one E-UTRAN frequency relation, frequency relation with lowest ARFCN is used. If false for all E-UTRAN frequency relations, UE will be released to idle without redirection.; Default value: false.";
      type boolean;
      default "false";
    }
    leaf connModeAllowedPCell {
      description "Whether placing PCell on E-UTRAN frequency defined by E-UTRAN frequency relation is allowed. Applies to UEs that use cell as PCell for poor coverage triggered handover or blind release with redirect to this cell. Blind release with redirect can be triggered by poor coverage or when UE fails capability check.; Default value: false.";
      type boolean;
      default "false";
    }
    leaf connModePrioPCell {
      description "Connected mode PCell priority for E-UTRAN frequency relation. Applies to UEs that use cell as PCell. Used to decide preference on which E-UTRAN frequency to place PCell in connected mode. 0 means frequency relation with lowest priority. 7 means frequency relation with highest priority. Applicable only when connModeAllowedPCell is true.; range 0..7; Default value: 7.";
      type eytypes:int32_range_0-7;
      default "7";
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf ueMCEUtranFreqRelProfileUeCfgId {
      description "The value component of the RDN..";
      type string;
      mandatory true;
    }
    leaf userLabel {
      description "Label for free use..";
      type string;
    }
  }
  grouping UeMCNrFreqRelProfile-attributes {
    leaf connModeAllowedPCell {
      description "Whether it is allowed to place PCell on NR frequency defined by NR frequency relation. Applies to UEs that use cell as PCell..";
      type boolean;
    }
    leaf connModePrioPCell {
      description "Connected mode PCell priority for NR frequency relation. Applies to UEs that use cell as PCell. Used to decide preference on which NR frequency to place PCell in connected mode. 0 means frequency relation with lowest priority. 7 means frequency relation with highest priority. Applicable only when connModeAllowedPCell attribute is true.; range 0..7.";
      type eytypes:int32_range_0-7;
    }
    leaf-list reservedBy {
      description "Contains a list of MO instances that reserve this MO instance..";
      type string;
      min-elements 0;
    }
    leaf ueConfGroupType {
      description "UE configuration group type. UE configuration group type that is applied in contained UeMCNrFreqRelProfileUeCfg instances..";
      type enumeration {
        enum UE_MOBILITY_GROUP;
        enum UE_SERVICE_GROUP;
        enum UE_ADMISSION_GROUP;
      }
    }
    leaf ueMCNrFreqRelProfileId {
      description "The value component of the RDN..";
      type string;
      mandatory true;
    }
    leaf userLabel {
      description "Label for free use..";
      type string;
    }
  }
  grouping UeMCNrFreqRelProfileUeCfg-attributes {
    leaf connModeAllowedPCell {
      description "Whether it is allowed to place PCell on NR frequency defined by NR frequency relation. Applies to UEs that use cell as PCell.; Default value: false.";
      type boolean;
      default "false";
    }
    leaf connModeAllowedPSCell {
      description "Whether PSCell can be placed on NR frequency defined by NR frequency relation. Applies to UEs that use this cell as PSCell in EN-DC.; Default value: false.";
      type boolean;
      default "false";
    }
    leaf connModePrioPCell {
      description "Connected mode PCell priority for NR frequency relation. Applies to UEs that use cell as PCell. Used to decide preference on which NR frequency to place PCell in connected mode. 0 means frequency relation with lowest priority. 7 means frequency relation with highest priority. Applicable only when connModeAllowedPCell is true.; range 0..7; Default value: 7.";
      type eytypes:int32_range_0-7;
      default "7";
    }
    leaf connModePrioPSCell {
      description "Connected mode PSCell priority for NR frequency relation. Applies to UEs that use this cell as PSCell in EN-DC. Used to decide preference on which NR frequency to place PSCell in connected mode. 0 means frequency relation with lowest priority. 7 means frequency relation with highest priority. Applicable only when connModeAllowedPSCell is true.; range 0..7; Default value: 7.";
      type eytypes:int32_range_0-7;
      default "7";
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf ueMCNrFreqRelProfileUeCfgId {
      description "The value component of the RDN..";
      type string;
      mandatory true;
    }
    leaf userLabel {
      description "Label for free use..";
      type string;
    }
  }
  grouping UeMCUeCfg-attributes {
    leaf maxNrInterFreqMeasEndc {
      description "Maximum number of NR inter-frequency measurements in NR EN-DC. Maximum number of NR inter-frequency measurements that gNodeB allows simultaneously for UE in NR EN-DC.; range 10..32; Default value: 10.";
      type eytypes:int32_range_10-32;
      default "10";
    }
    leaf maxNrInterFreqMeasSa {
      description "Maximum number of NR inter-frequency measurements in NR standalone. Maximum number of inter-frequency measurements that gNodeB allows simultaneously for UE in NR standalone.; range 10..32; Default value: 10.";
      type eytypes:int32_range_10-32;
      default "10";
    }
    leaf maxNrIratMeasSa {
      description "Maximum number of NR IRAT measurements in NR standalone. Maximum number of NR IRAT (FDD and/or TDD E-UTRAN) measurements that gNodeB allows simultaneously for UE in NR standalone.; range 10..32; Default value: 10.";
      type eytypes:int32_range_10-32;
      default "10";
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf ueMCUeCfgId {
      description "The value component of the RDN..";
      type string;
      mandatory true;
    }
    leaf userLabel {
      description "Label for free use..";
      type string;
    }
  }
  grouping UeMobilityGroupDefinition-attributes {
    leaf chipsetRef {
      description "Reference to an instance of Chipsets MO. Special <Value> \"ref\" for <Variable> chipset in selectionCriteria represents chipset <ValueList> defined via this reference. If empty, represented chipset <ValueList> is empty..";
      type string;
    }
    leaf imeiSvRef {
      description "Reference to an instance of ImeiSvs MO. Special <Value> \"ref\" for <Variable> imeisv in selectionCriteria represents imeisv <ValueList> defined via this reference. If empty, represented imeisv <ValueList> is empty..";
      type string;
    }
    leaf selectionCriteria {
      description "UE mobility group selection criteria. Defines selection criteria that UE needs to fulfill to belong to UE mobility group instance. If selection criteria evaluates to True, UE fulfills UE mobility group instance. If selection criteria evaluates to False or Unknown, UE does not fulfill UE mobility group instance. If selection criteria evaluates to True for more than one UE mobility group instance, UE belongs to UE mobility group instance with highest setting of ueMobilityGroupPriority. Syntax: ====== The syntax of selection criteria is defined using Backus-Naur form. <SelectionCriteria> ::= <ParentExpressionList> | \"\" <ParentExpressionList> ::= <ParentExpressionList> <AndOr> < ParentExpressionList> | <Not>? \"(\" <ParentExpressionList> \")\" | <ExpressionList> | <FlowExpressionList> <FlowExpressionList> ::= <FlowExpressionList> <AndOr> <FlowExpressionList> | <Not>? <FlowExpression> <FlowExpression> ::= \"[\"<ExpressionList>\"]\" <ExpressionList> ::= <ExpressionList> <AndOr> <ExpressionList> | <Not>? \"(\" <ExpressionList> \")\" | <Not>? <VariableExpression> <VariableExpression> ::= <Variable> <RelationalOperator> <Value> | <Variable> \"==\" \"{\" <ValueList> \"}\" <ValueList> ::= <Value> \",\" <ValueList> | <Value> <Variable> ::= \"5qi\" | \"arp\" | \"cgrole\" | \"chipset\" | \"imeisv\" | \"imeisvn\" | \"imeitac\" | \"pagingPrio\" | \"pCellOnlyUe\" | \" \"plmn\" | \"qci\" | \"redCapUe\" | \"rfsp\" | \"rrcEstResCause\" | \"snssai\" | \"spid\" | \"voNrUe\" <AndOr> ::= \"&&\" | \"||\" <Not> ::= \"!\" <RelationalOperator> ::= \"==\" | \"!=\" | \"<\" | \"<=\" | \">=\" | \">\" A list of possible values can be specified in the form <Variable> == {<value1>, <value2>, ... , <valueN>}. This statement is equivalent to writing (<Variable> == <value1> || <Variable> == <value2> || ... || <Variable> == <valueN>). Up to 4 <FlowExpression> can be defined in <SelectionCriteria>. Whitespaces are allowed in the string for improved readability and are removed prior to evaluation. Question mark (?) means zero or one occurrence. For example, <Not>? makes <Not> optional. Syntax is case sensitive. Semantic: ======== Selection criteria evaluation is defined by the following semantic rules. If empty or set to empty string \"\", selection criteria always evaluates to True. Selection criteria evaluation is done per UE with the current applicable UE <Variable> values as input. List of UE <Variable> values that are applicable to NR standalone and EN-DC, respectively, is defined in Variable Definitions section below. Selection criteria for a UE is evaluated separately for each flow using applicable flow-dependent <Variable> together with rest of applicable UE <Variable>. For UE in NR standalone flow-dependent <Variable> 5qi, arp, and snssai are applicable. For UE in EN-DC flow-dependent <Variable> qci, and arp are applicable. Selection criteria evaluates to True if any of the flows evaluates to True. If UE does not have a flow, flow-dependent <Variable> values are evaluated as unknown variable values. If selection criteria shall match combination of flow-dependent <Variable>, then <FlowExpression> and <FlowExpressionList> must be used. Note: An <ExpressionList> defined as <VariableExpression> && <VariableExpression>, for which both <VariableExpression> relate to flow-dependent <Variable>, needs special attention. Example: <ExpressionList> = \"5qi==5 && 5qi==9\" always evaluate to False for UE in NR standalone even if UE has one flow with 5qi=5 and one flow with 5qi=9. Example: <ExpressionList> = \"5qi>=7 && 5qi<=11\" will evaluate to True for UE in NR standalone if UE has any flow with 5qi between 7 and 11. <FlowExpression> is defined as \"[\"<ExpressionList>\"]\" and indicates that an <ExpressionList> is evaluated per QoS flow independent of other <ExpressionList>. Example: <FlowExpressionList> = \"[5qi==1] && [5qi==5]\" evaluates to True for UE in NR standalone if UE has any flow with 5qi=1 and any flow with 5qi=5. In the example, [5qi==1] must match one flow, and [5qi==5] must match one flow. <VariableExpression> evaluates to Unknown if <Variable> is not known or if the <Variable> value is not valid. <VariableExpression> evaluates to True or False if <Variable> value is known and valid. <Value> \"ref\" is a special <Value> of <Variable> representing <ValueList> defined via corresponding reference attribute. For <Variable> chipset, and imeisv, corresponding reference attribute is chipsetRef, and imeiSvRef respectively. If reference attribute is empty, represented <ValueList> is empty. The logical operators <AndOr> and <Not> apply three way logic as defined below: F=False; T=True; U=Unknown A=Evaluation result of <ExpressionList> or <VariableExpression> B=Evaluation result of <ExpressionList> or <VariableExpression> NOT operator: A !A ----------------- F T U U T F AND operator: A B A && B ------------------- F F F F T F F U F T F F T T T T U U U F F U T U U U U OR operator: A B A || B ------------------ F F F F T T F U U T F T T T T T U T U F U U T T U U U Variable Definitions: ================= Allowed <Value> and <RelationalOperator> depend on <Variable> with limitations given below. 5qi: 5G QoS Identifier (3GPP TS 23.501). Applicable to NR standalone. Operator: ==, !=, <=, >=, <, and >. Value: Integer in range 0..255 given in decimal. arp: Priority Level part of the Allocation and Retention Priority (3GPP TS 38.413, 3GPP TS 36.423). Applicable to both NR standalone and EN-DC. Operator: ==, !=, <=, >=, <, and >. Value: Integer in range 1..15 given in decimal. cgrole: Cell group role. Applicable to both NR standalone and EN-DC. Operator: ==, and !=. Value: mcg or scg, where mcg is only applicable to NR standalone. chipset: Chipset identifier. Applicable to both NR standalone and EN-DC. Operator: ==, and !=. Value: String in format \"<vendor>.<variant>.<version>\" matched by regular expression \"(1[0-6]|[0-9])\\\\.(6[0-4]|[1-5]?[0-9])\\\\.(12[0-8]|1[01][0-9]|[1-9]?[0-9])\", or a string constant \"ref\". Description: Chipset identifier composed of three distinct elements: - vendor: 1-2 digit decimal number in range 0..16 - variant: 1-2 digit decimal number in range 0..64 - version: 1-3 digit decimal number in range 0..128 UEs that do not support chipset identifier reporting are represented internally as 0.0.0. Example values: 0.0.0, 1.1.1, 1.2.3, 16.10.100, 16.64.128, ref. imeisv: International Mobile Station Equipment Identity Software Version. Applicable to both NR standalone and EN-DC. Operator: ==, and !=. Value: String in format \"<TAC><SNR><SVN>\" matched by regular expression \"[0-9]{10}[0-9fF]{4}[0-9]{2}\", or string constant \"ref\". Description: IMEISV composed of three distinct elements: - TAC (Type Allocation Code): 8 digit decimal number - SNR (or SN, Serial Number): 2 digit decimal number + 4 digit hexa-decimal number, last four digits are automatically masked with 0xFFFF to match with masked IMEISV - SVN (Software Version Number): 2 digit decimal number Example values: 1234567890123456, 1234567890FFFF12, 1234567890ffff12, ref. imeitac: Type Allocation Code (TAC) part of imeisv. Applicable to both NR standalone and EN-DC. Operator: ==, !=, <=, >=, <, and >. Value: 8 digit decimal number. imeisvn: Software Version Number (SVN) part of imeisv. Applicable to both NR standalone and EN-DC. Operator: ==, !=, <=, >=, <, and >. Value: 2 digit decimal number. pagingPrio: Paging Priority (3GPP TS 23.501). Applicable to NR standalone. Operator: ==, !=, <=, >=, <, and > Value: Integer in range 1..8 given in decimal. Description: Paging priority value received in NGAP Paging message. The received value is valid in UE grouping framework when performing UE group evaluation during time specified by UeGroupSelection::validityTimePagingPrio. pCellOnlyUe: Low-Band and Mid-Band PCell-only capability. Indicates whether the UE is not capable of carrier aggregation in Low-Band or Mid-Band. Only applicable when performing UE group evaluation in NR standalone Master Node. Operator: ==, and !=. Value: Integer in range 0..1 given in decimal, where 0 means false and 1 means true. Only applicable if license for Flexible UE Grouping for Limited Capability UEs is present and feature is active. plmn: Public Land and Mobile Network identifier. Applicable to both NR standalone and EN-DC. Operator: ==, and !=. Value: A string matched by regular expression \"[02-79][0-9][0-9]-[0-9][0-9][0-9]?\". Example values: 070-007, 070-07, 234-56. qci: QoSClass Identifier (3GPP TS 23.401). Applicable to EN-DC. Operator: ==, !=, <=, >=, <, and >. Value: Integer in range 0..255 given in decimal. redCapUe: Reduced Capabilities UE indicator. Applicable to NR standalone. Operator: ==, and !=. Value: Integer in range 0..1 given in decimal, where 0 means false and 1 means true. Description: RedCap UE identification received via LCID in MSG3 (see 3GPP TS 38.331). rfsp: Index to RAT/Frequency Selection Priority (3GPP TS 23.501). Applicable to NR standalone. Operator: ==, !=, <=, >=, <, and >. Value: Integer in range 1..256 given in decimal. rrcEstResCause: RRC establishment cause or RRC resume cause. Applicable to NR standalone. Operator: ==, and !=. Value: One of emergency, highPriorityAccess, mt-Access, mo-Signaling, mo-Data, mo-VoiceCall, mo-VideoCall, mo-SMS, mps-PriorityAccess, or mcs-PriorityAccess. Description: Establishment cause value received in RRC Setup Request message or resume cause received in RRC Resume Request message (see 3GPP TS 38.331). The received establishment cause or resume cause is valid in UE grouping framework when performing UE group evaluation during time specified by corresponding validity time attribute value in MO class UeGroupSelection. snssai: Single Network Slice Selection Assistance Information (3GPP TS 23.003). Applicable to NR standalone. Operator: ==, !=, <=, >=, <, and >. Value: input option 1: String in format \"<SST><SD>\" matched by regular expression [0][x][0-9a-fA-F]{8} (8 digit hexa-decimal number). Value: input option 2: Integer in range 0x0..0xffffffff given in hexadecimal. Description: S-NSSAI is composed of two distinct elements: - SST (Slice/Service Type): 2 digit hexa-decimal number - SD (Slice Differentiator): 6 digit hexa-decimal number The SD field has a reserved value \"no SD value associated with the SST\" defined as hexadecimal FFFFFF/ffffff. Example values, input option 1: - 0x050000EE (SST=0x05,SD=0x0000EE) - 0x2effffff (SST=0x2e,SD=0xffffff // no SD associated with the SST) Example values, input option 2: - 0x1 (SST=0x00,SD=0x000001) - 0x50000EE (SST=0x05,SD=0x0000EE) - 0x150000EE (SST=0x15,SD=0x0000EE) spid: Subscriber Profile ID for RAT/Frequency Priority (3GPP TS 36.300). Applicable to EN-DC. Operator: ==, !=, <=, >=, <, and >. Value: Integer in range 1..256 given in decimal. voNrUe: Low-Band and Mid-Band VoNR capability. Only applicable when performing UE group evaluation in NR standalone Master Node. Operator: ==, and !=. Value: Integer in range 0..1 given in decimal, where 0 means false and 1 means true. Operator Precedence Order: ======================= The logical and relation operators are evaluated according to the precedence order listed below. --------------------------------------------- 1 (highest precedence) < Less than <= Less than or equal > Greater than >= Greater than or equal == Equal != Not equal ------------------------------------------- 2 ! (Not) --------------------------------------------- 3 && (And) --------------------------------------------- 4 (lowest precedence) || (Or) --------------------------------------------- The NOT operator \"!\" negates the following <ParentExpressionList>, <VariableExpression>, <FlowExpression> or an <ExpressionList> encapsulated in parenthesis. Therefore, expression !a==b && c==d is equivalent to ((!(a==b)) && (c==d)) and different from !(a==b && c==d). Expression !a==b and !(a==b) are equivalent. Since AND operator \"&&\" has higher precedence than OR operator \"||\", a<b || a<c && c<d is equivalent to (a<b || (a<c && c<d)). Surround expression list including OR operator with parenthesis to force OR operator to be evaluated before AND operators outside of the expression list, for example (a<b || a<c) && c<d. Examples: ========= Simple one valued expressions: plmn == 234-56 spid == 1 cgrole == mcg arp > 3 snssai == 0xfedcba98 rrcEstResCause == mo-VoiceCall imeisv == 1234567890FFFF12 imeisv == ref //Special <value> ref represents <ValueList> defined via imeiSvRef. chipset == ref chipset == 1.1.1 //Matches all UEs with chipset identifier: vendor = 1, variant = 1 and version = 1. chipset == 0.0.0 //Matches all UEs that do not support chipset identifier reporting. Value list expressions: spid == {8,9,10,1,155} !plmn == {234-56, 434-567} chipset == {1.1.1, 1.1.2, 1.1.3, ref} //Matches all UEs with chipset identifier: vendor = 1, variant = 1 and version = 1, 2 or 3, or the corresponding vendor, variant and version defined via chipsetRef. imeisv == {1234567890FFFF12, ref, 1234567890FFFF13} //Matches all UEs with imeisv: TAC = 12345678, SNR = 90FFFF and SVN = 12 or 13, or the corresponding TAC, SN and SVN defined via imeiSvRef. Equivalent expressions using ||: (spid == 8 || spid == 9 || spid == 10 || spid == 1 || spid == 155) //Equals to spid == {8, 9, 10, 1, 155}. !(plmn == 234-56 || plmn == 434-567) //Equals to !plmn == {234-56, 434-567}. imeisv == ref || imeisv == 1234567890FFFF12|| imeisv == 1234567890FFFF13 //Equals to imeisv == {ref, 1234567890FFFF12, 1234567890FFFF13}. chipset == 1.1.1 || chipset == ref || chipset == 1.1.2 // Equals to chipset == {1.1.1, ref, 1.1.2}. Negative expressions: !5qi==1 //Matches flows with 5qi not equal to 1. 5qi!=1 //Matches flows with 5qi not equal to 1. Negative <FlowExpressions> that produce same result: [!5qi==1] //Matches flows with 5qi not equal to 1. [5qi!=1] //Matches flows with 5qi not equal to 1. <FlowExpressionList> negative expressions: !([5qi==1]) //Matches UEs that do not have flows with 5qi 1. ![5qi==1] //Matches UEs that do not have flows with 5qi 1. Mixed examples: spid == 1 && cgrole == mcg !(spid != 1 || cgrole != mcg) (spid == 8 || spid == 9 || spid == 10 || spid == 1 || spid == 155) && (plmn == 234-56 || plmn == 434-567) Precedence given by \"()\" and sequence alter the evaluation order and result: [5qi==1] && chipset==ref || imeisv==ref && [5qi==5] //Equals to ([5qi==1] && chipset==ref) || (imeisv==ref && [5qi==5]) [5qi==1] && (chipset==ref || imeisv==ref) && [5qi==5] ([5qi==1] && chipset==ref || imeisv==ref) && [5qi==5] [5qi==1] && (chipset==ref || imeisv==ref && [5qi==5]) chipset==ref || [5qi==1] && [5qi==5] && imeisv==ref Examples of selection criteria that shall be avoided since they will always be evaluated to False. <FlowExpression> can be used in these cases. 5qi==5 && 5qi==9 snssai==0x15000000 && snssai==0x17000000 arp==5 && arp==10 qci==5 && qci==9 Example of selection criteria for UE variable snssai: snssai>=15000000 && snssai<=15FFFFFF //Matches UE which has a flow with S-NSSAI SST part equal to 15 regardless of value of S-NSSAI SD part. snssai==15FFFFFF //Matches UE which has a flow with S-NSSAI SST part equal to 15 and S-NSSAI SD part value equal to FFFFFF, meaning no SD value associated with the SST. Flow expressions combined with UE variables: plmn == 234-56 && [5qi==1] && [5qi==9] //Matches UE which has plmn equal to 234-56, any QoS flow with 5qi equal to 1, and any QoS flow with 5qi equal to 9. chipset==1.5.32 && [5qi==9] && ![5qi==1] //Matches UE which has chipset identifier equal to 1.5.32, any QoS flow with 5qi equal to 9, and no QoS flow with 5qi equal to 1. [5qi==1 && snssai == 0xfedcba98] || ([5qi==2] && [snssai == 0xfedcba77]) //Matches UE which has any QoS flow with 5qi equal to 1 and snssai equal to 0xfedcba98, or has any QoS flow with 5qi equal to 2 and snssai equal to 0xfedcba77. voNrUe==1 && chipset==1.1.1 && [5qi==1] //Matches UEs with Low-Band and Mid-Band VoNR capability using chipset 1.1.1, and have an ongoing flow 5qi.; length 1..1000.";
      type string {
        length "1..1000";
      }
    }
    leaf ueMobilityGroupDefinitionId {
      description "The value component of the RDN..";
      type string;
      mandatory true;
    }
    leaf ueMobilityGroupId {
      description "UE mobility group identifier.; range 1..255.";
      type eytypes:int32_range_1-255;
      mandatory true;
    }
    leaf ueMobilityGroupPriority {
      description "Relative priority among UE mobility groups. If UE fulfills selection criteria for more than one UE mobility group, UE mobility group with the highest priority is selected. Higher value gives higher priority.; range 1..65535.";
      type eytypes:int32_range_1-65535;
      mandatory true;
    }
    leaf userLabel {
      description "Label for free use..";
      type string;
    }
  }
  grouping UeNoDrb-attributes {
    leaf ueNoDrbId {
      description "The value component of the RDN..";
      type string;
      mandatory true;
    }
  }
  grouping UeNoDrbPCellProfile-attributes {
    leaf-list reservedBy {
      description "Contains a list of MO instances that reserve this MO instance..";
      type string;
      min-elements 0;
    }
    leaf ueConfGroupType {
      description "UE configuration group type. UE configuration group type that is applied in contained UeNoDrbPCellProfileUeCfg instances..";
      type enumeration {
        enum UE_MOBILITY_GROUP;
        enum UE_SERVICE_GROUP;
        enum UE_ADMISSION_GROUP;
      }
    }
    leaf ueNoDrbPCellProfileId {
      description "The value component of the RDN..";
      type string;
      mandatory true;
    }
    leaf userLabel {
      description "Label for free use..";
      type string;
    }
  }
  grouping UeNoDrbPCellProfileUeCfg-attributes {
    leaf posUeWoPduSessionEnabled {
      description "Whether UE positioning is enabled for UE without PDU session. Only applicable if license for Positioning of UEs without PDU Session is present and feature is active. Only applicable to Low-Band and Mid-Band cells.; Default value: false.";
      type boolean;
      default "false";
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    list rsrpBetterPCell {
      key "id";
      leaf id {
        type uint32;
        description "Synthetic key for struct attribute.";
      }
      description "Downlink RSRP measurement report criteria when searching for better PCell..";
      uses ReportConfigA3Rsrp-struct;
    }
    leaf rsrpBetterPCellEnabled {
      description "Whether RSRP measurement for detecting better PCell is enabled. RSRP measurement criteria for detecting better PCell is defined by rsrpBetterPCell.; Default value: false.";
      type boolean;
      default "false";
    }
    list rsrpCritical {
      key "id";
      leaf id {
        type uint32;
        description "Synthetic key for struct attribute.";
      }
      description "RSRP measurement report criteria for detecting critical coverage..";
      uses ReportConfigA2Rsrp-struct;
    }
    leaf rsrpCriticalEnabled {
      description "Whether RSRP measurement for detecting critical coverage is enabled. RSRP measurement criteria for detecting critical coverage is defined by rsrpCritical.; Default value: false.";
      type boolean;
      default "false";
    }
    list rsrpCriticalPcOffset {
      key "id";
      leaf id {
        type uint32;
        description "Synthetic key for struct sequence entry.";
      }
      min-elements 0;
      max-elements 3;
      uses ReportConfigA1A2RsrpPcOffset-struct;
    }
    list rsrqCritical {
      key "id";
      leaf id {
        type uint32;
        description "Synthetic key for struct attribute.";
      }
      description "RSRQ measurement report criteria for detecting critical coverage..";
      uses ReportConfigA2Rsrq-struct;
    }
    leaf rsrqCriticalEnabled {
      description "Whether RSRQ measurement for detecting critical coverage is enabled. RSRQ measurement criteria for detecting critical coverage is defined by rsrqCritical.; Default value: false.";
      type boolean;
      default "false";
    }
    list sinrCritical {
      key "id";
      leaf id {
        type uint32;
        description "Synthetic key for struct attribute.";
      }
      description "SINR measurement report criteria for detecting critical coverage. Applicable for UEs supporting SINR..";
      uses ReportConfigA2Sinr-struct;
    }
    leaf sinrCriticalEnabled {
      description "Whether SINR measurement for detecting critical coverage is enabled. SINR measurement criteria for detecting critical coverage is defined by sinrCritical.; Default value: false.";
      type boolean;
      default "false";
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf ueNoDrbPCellProfileUeCfgId {
      description "The value component of the RDN..";
      type string;
      mandatory true;
    }
    leaf userLabel {
      description "Label for free use..";
      type string;
    }
  }
  grouping UeServiceGroupDefinition-attributes {
    leaf chipsetRef {
      description "Reference to an instance of Chipsets MO. Special <Value> \"ref\" for <Variable> chipset in selectionCriteria represents chipset <ValueList> defined via this reference. If empty, represented chipset <ValueList> is empty..";
      type string;
    }
    leaf imeiSvRef {
      description "Reference to an instance of ImeiSvs MO. Special <Value> \"ref\" for <Variable> imeisv in selectionCriteria represents imeisv <ValueList> defined via this reference. If empty, represented imeisv <ValueList> is empty..";
      type string;
    }
    leaf selectionCriteria {
      description "UE service group selection criteria. Defines selection criteria that UE needs to fulfill to belong to the UE service group instance. If selection criteria evaluates to True, UE fulfills UE service group instance. If selection criteria evaluates to False or Unknown, UE does not fulfill UE service group instance. If selection criteria evaluates to True for more than one UE service group instance, UE belongs to the UE service group instance with highest setting of ueServiceGroupPriority. Syntax: ====== The syntax of selection criteria is defined using Backus-Naur form. <SelectionCriteria> ::= <ParentExpressionList> | \"\" <ParentExpressionList> ::= <ParentExpressionList> <AndOr> < ParentExpressionList> | <Not>? \"(\" <ParentExpressionList> \")\" | <ExpressionList> | <FlowExpressionList> <FlowExpressionList> ::= <FlowExpressionList> <AndOr> <FlowExpressionList> | <Not>? <FlowExpression> <FlowExpression> ::= \"[\"<ExpressionList>\"]\" <ExpressionList> ::= <ExpressionList> <AndOr> <ExpressionList> | <Not>? \"(\" <ExpressionList> \")\" | <Not>? <VariableExpression> <VariableExpression> ::= <Variable> <RelationalOperator> <Value> | <Variable> \"==\" \"{\" <ValueList> \"}\" <ValueList> ::= <Value> \",\" <ValueList> | <Value> <Variable> ::= \"5qi\" | \"arp\" | \"cgrole\" | \"chipset\" | \"imeisv\" | \"imeisvn\" | \"imeitac\" | \"pagingPrio\" | \"pCellOnlyUe\" | \"plmn\" | \"qci\" | \"redCapUe\" | \"rfsp\" | \"rrcEstResCause\" | \"snssai\" | \"spid\" | \"voNrUe\" <AndOr> ::= \"&&\" | \"||\" <Not> ::= \"!\" <RelationalOperator> ::= \"==\" | \"!=\" | \"<\" | \"<=\" | \">=\" | \">\" A list of possible values can be specified in the form <Variable> == {<value1>, <value2>, ... , <valueN>}. This statement is equivalent to writing (<Variable> == <value1> || <Variable> == <value2> || ... || <Variable> == <valueN>). Up to 4 <FlowExpression> can be defined in <SelectionCriteria>. Whitespaces are allowed in the string for improved readability and are removed prior to evaluation. Question mark (?) means zero or one occurrence. For example, <Not>? makes <Not> optional. Syntax is case sensitive. Semantic: ======== Selection criteria evaluation is defined by the following semantic rules. If empty or set to empty string \"\", selection criteria always evaluates to True. Selection criteria evaluation is done per UE with the current applicable UE <Variable> values as input. List of UE <Variable> values that are applicable to NR standalone and EN-DC, respectively, is defined in Variable Definitions section below. Selection criteria for a UE is evaluated separately for each flow using applicable flow-dependent <Variable> together with rest of applicable UE <Variable>. For UE in NR standalone flow-dependent <Variable> 5qi, arp, and snssai are applicable. For UE in EN-DC flow-dependent <Variable> qci, and arp are applicable. Selection criteria evaluates to True if any of the flows evaluates to True. If UE does not have a flow, flow-dependent <Variable> values are evaluated as unknown variable values. If selection criteria shall match combination of flow-dependent <Variable>, then <FlowExpression> and <FlowExpressionList> must be used. Note: An <ExpressionList> defined as <VariableExpression> && <VariableExpression>, for which both <VariableExpression> relate to flow-dependent <Variable>, needs special attention. Example: <ExpressionList> = \"5qi==5 && 5qi==9\" always evaluate to False for UE in NR standalone even if UE has one flow with 5qi=5 and one flow with 5qi=9. Example: <ExpressionList> = \"5qi>=7 && 5qi<=11\" will evaluate to True for UE in NR standalone if UE has any flow with 5qi between 7 and 11. <FlowExpression> is defined as \"[\"<ExpressionList>\"]\" and indicates that an <ExpressionList> is evaluated per QoS flow independent of other <ExpressionList>. Example: <FlowExpressionList> = \"[5qi==1] && [5qi==5]\" evaluates to True for UE in NR standalone if UE has any flow with 5qi=1 and any flow with 5qi=5. In the example, [5qi==1] must match one flow, and [5qi==5] must match one flow. <VariableExpression> evaluates to Unknown if <Variable> is not known or if the <Variable> value is not valid. <VariableExpression> evaluates to True or False if <Variable> value is known and valid. <Value> \"ref\" is a special <Value> of <Variable> representing <ValueList> defined via corresponding reference attribute. For <Variable> chipset, and imeisv, corresponding reference attribute is chipsetRef, and imeiSvRef respectively. If reference attribute is empty, represented <ValueList> is empty. The logical operators <AndOr> and <Not> apply three way logic as defined below: F=False; T=True; U=Unknown A=Evaluation result of <ExpressionList> or <VariableExpression> B=Evaluation result of <ExpressionList> or <VariableExpression> NOT operator: A !A ----------------- F T U U T F AND operator: A B A && B ------------------- F F F F T F F U F T F F T T T T U U U F F U T U U U U OR operator: A B A || B ------------------ F F F F T T F U U T F T T T T T U T U F U U T T U U U Variable Definitions: ================= Allowed <Value> and <RelationalOperator> depend on <Variable> with limitations given below. 5qi: 5G QoS Identifier (3GPP TS 23.501). Applicable to NR standalone. Operator: ==, !=, <=, >=, <, and >. Value: Integer in range 0..255 given in decimal. arp: Priority Level part of the Allocation and Retention Priority (3GPP TS 38.413, 3GPP TS 36.423). Applicable to both NR standalone and EN-DC. Operator: ==, !=, <=, >=, <, and >. Value: Integer in range 1..15 given in decimal. cgrole: Cell group role. Applicable to both NR standalone and EN-DC. Operator: ==, and !=. Value: mcg or scg, where mcg is only applicable to NR standalone. chipset: Chipset identifier. Applicable to both NR standalone and EN-DC. Operator: ==, and !=. Value: String in format \"<vendor>.<variant>.<version>\" matched by regular expression \"(1[0-6]|[0-9])\\\\.(6[0-4]|[1-5]?[0-9])\\\\.(12[0-8]|1[01][0-9]|[1-9]?[0-9])\", or a string constant \"ref\". Description: Chipset identifier composed of three distinct elements: - vendor: 1-2 digit decimal number in range 0..16 - variant: 1-2 digit decimal number in range 0..64 - version: 1-3 digit decimal number in range 0..128 UEs that do not support chipset identifier reporting are represented internally as 0.0.0. Example values: 0.0.0, 1.1.1, 1.2.3, 16.10.100, 16.64.128, ref. imeisv: International Mobile Station Equipment Identity Software Version. Applicable to both NR standalone and EN-DC. Operator: ==, and !=. Value: String in format \"<TAC><SNR><SVN>\" matched by regular expression \"[0-9]{10}[0-9fF]{4}[0-9]{2}\", or string constant \"ref\". Description: IMEISV composed of three distinct elements: - TAC (Type Allocation Code): 8 digit decimal number - SNR (or SN, Serial Number): 2 digit decimal number + 4 digit hexa-decimal number, last four digits are automatically masked with 0xFFFF to match with masked IMEISV - SVN (Software Version Number): 2 digit decimal number Example values: 1234567890123456, 1234567890FFFF12, 1234567890ffff12, ref. imeitac: Type Allocation Code (TAC) part of imeisv. Applicable to both NR standalone and EN-DC. Operator: ==, !=, <=, >=, <, and >. Value: 8 digit decimal number. imeisvn: Software Version Number (SVN) part of imeisv. Applicable to both NR standalone and EN-DC. Operator: ==, !=, <=, >=, <, and >. Value: 2 digit decimal number. pagingPrio: Paging Priority (3GPP TS 23.501). Applicable to NR standalone. Operator: ==, !=, <=, >=, <, and > Value: Integer in range 1..8 given in decimal. Description: Paging priority value received in NGAP Paging message. The received value is valid in UE grouping framework when performing UE group evaluation during time specified by UeGroupSelection::validityTimePagingPrio. plmn: Public Land and Mobile Network identifier. Applicable to both NR standalone and EN-DC. Operator: ==, and !=. Value: A string matched by regular expression \"[02-79][0-9][0-9]-[0-9][0-9][0-9]?\". Example values: 070-007, 070-07, 234-56. qci: QoSClass Identifier (3GPP TS 23.401). Applicable to EN-DC. Operator: ==, !=, <=, >=, <, and >. Value: Integer in range 0..255 given in decimal. redCapUe: Reduced Capabilities UE indicator. Applicable to NR standalone. Operator: ==, and !=. Value: Integer in range 0..1 given in decimal, where 0 means false and 1 means true. Description: RedCap UE identification received via LCID in MSG3 (see 3GPP TS 38.331). pCellOnlyUe: Low-Band and Mid-Band PCell-only capability. Indicates whether the UE is not capable of carrier aggregation in Low-Band or Mid-Band. Only applicable when performing UE group evaluation in NR standalone Master Node. Operator: ==, and !=. Value: Integer in range 0..1 given in decimal, where 0 means false and 1 means true. Only applicable if license for Flexible UE Grouping for Limited Capability UEs is present and feature is active. rfsp: Index to RAT/Frequency Selection Priority (3GPP TS 23.501). Applicable to NR standalone. Operator: ==, !=, <=, >=, <, and >. Value: Integer in range 1..256 given in decimal. rrcEstResCause: RRC establishment cause or RRC resume cause. Applicable to NR standalone. Operator: ==, and !=. Value: One of emergency, highPriorityAccess, mt-Access, mo-Signaling, mo-Data, mo-VoiceCall, mo-VideoCall, mo-SMS, mps-PriorityAccess, or mcs-PriorityAccess. Description: Establishment cause value received in RRC Setup Request message or resume cause received in RRC Resume Request message (see 3GPP TS 38.331). The received establishment cause or resume cause is valid in UE grouping framework when performing UE group evaluation during time specified by corresponding validity time attribute value in MO class UeGroupSelection. snssai: Single Network Slice Selection Assistance Information (3GPP TS 23.003). Applicable to NR standalone. Operator: ==, !=, <=, >=, <, and >. Value: input option 1: String in format \"<SST><SD>\" matched by regular expression [0][x][0-9a-fA-F]{8} (8 digit hexa-decimal number). Value: input option 2: Integer in range 0x0..0xffffffff given in hexadecimal. Description: S-NSSAI is composed of two distinct elements: - SST (Slice/Service Type): 2 digit hexa-decimal number - SD (Slice Differentiator): 6 digit hexa-decimal number The SD field has a reserved value \"no SD value associated with the SST\" defined as hexadecimal FFFFFF/ffffff. Example values, input option 1: - 0x050000EE (SST=0x05,SD=0x0000EE) - 0x2effffff (SST=0x2e,SD=0xffffff // no SD associated with the SST) Example values, input option 2: - 0x1 (SST=0x00,SD=0x000001) - 0x50000EE (SST=0x05,SD=0x0000EE) - 0x150000EE (SST=0x15,SD=0x0000EE) spid: Subscriber Profile ID for RAT/Frequency Priority (3GPP TS 36.300). Applicable to EN-DC. Operator: ==, !=, <=, >=, <, and >. Value: Integer in range 1..256 given in decimal. voNrUe: Low-Band and Mid-Band VoNR capability. Only applicable when performing UE group evaluation in NR standalone Master Node. Operator: ==, and !=. Value: Integer in range 0..1 given in decimal, where 0 means false and 1 means true. Operator Precedence Order: ======================= The logical and relation operators are evaluated according to the precedence order listed below. --------------------------------------------- 1 (highest precedence) < Less than <= Less than or equal > Greater than >= Greater than or equal == Equal != Not equal ------------------------------------------- 2 ! (Not) --------------------------------------------- 3 && (And) --------------------------------------------- 4 (lowest precedence) || (Or) --------------------------------------------- The NOT operator \"!\" negates the following <ParentExpressionList>, <VariableExpression>, <FlowExpression> or an <ExpressionList> encapsulated in parenthesis. Therefore, expression !a==b && c==d is equivalent to ((!(a==b)) && (c==d)) and different from !(a==b && c==d). Expression !a==b and !(a==b) are equivalent. Since AND operator \"&&\" has higher precedence than OR operator \"||\", a<b || a<c && c<d is equivalent to (a<b || (a<c && c<d)). Surround expression list including OR operator with parenthesis to force OR operator to be evaluated before AND operators outside of the expression list, for example (a<b || a<c) && c<d. Examples: ========= Simple one valued expressions: plmn == 234-56 spid == 1 cgrole == mcg arp > 3 snssai == 0xfedcba98 rrcEstResCause == mo-VoiceCall imeisv == 1234567890FFFF12 imeisv == ref //Special <value> ref represents <ValueList> defined via imeiSvRef. chipset == ref chipset == 1.1.1 //Matches all UEs with chipset identifier: vendor = 1, variant = 1 and version = 1. chipset == 0.0.0 //Matches all UEs that do not support chipset identifier reporting. Value list expressions: spid == {8,9,10,1,155} !plmn == {234-56, 434-567} chipset == {1.1.1, 1.1.2, 1.1.3, ref} //Matches all UEs with chipset identifier: vendor = 1, variant = 1 and version = 1, 2 or 3, or the corresponding vendor, variant and version defined via chipsetRef. imeisv == {1234567890FFFF12, ref, 1234567890FFFF13} //Matches all UEs with imeisv: TAC = 12345678, SNR = 90FFFF and SVN = 12 or 13, or the corresponding TAC, SN and SVN defined via imeiSvRef. Equivalent expressions using ||: (spid == 8 || spid == 9 || spid == 10 || spid == 1 || spid == 155) //Equals to spid == {8, 9, 10, 1, 155}. !(plmn == 234-56 || plmn == 434-567) //Equals to !plmn == {234-56, 434-567}. imeisv == ref || imeisv == 1234567890FFFF12|| imeisv == 1234567890FFFF13 //Equals to imeisv == {ref, 1234567890FFFF12, 1234567890FFFF13}. chipset == 1.1.1 || chipset == ref || chipset == 1.1.2 // Equals to chipset == {1.1.1, ref, 1.1.2}. Negative expressions: !5qi==1 //Matches flows with 5qi not equal to 1. 5qi!=1 //Matches flows with 5qi not equal to 1. Negative <FlowExpressions> that produce same result: [!5qi==1] //Matches flows with 5qi not equal to 1. [5qi!=1] //Matches flows with 5qi not equal to 1. <FlowExpressionList> negative expressions: !([5qi==1]) //Matches UEs that do not have flows with 5qi 1. ![5qi==1] //Matches UEs that do not have flows with 5qi 1. Mixed examples: spid == 1 && cgrole == mcg !(spid != 1 || cgrole != mcg) (spid == 8 || spid == 9 || spid == 10 || spid == 1 || spid == 155) && (plmn == 234-56 || plmn == 434-567) Precedence given by \"()\" and sequence alter the evaluation order and result: [5qi==1] && chipset==ref || imeisv==ref && [5qi==5] //Equals to ([5qi==1] && chipset==ref) || (imeisv==ref && [5qi==5]) [5qi==1] && (chipset==ref || imeisv==ref) && [5qi==5] ([5qi==1] && chipset==ref || imeisv==ref) && [5qi==5] [5qi==1] && (chipset==ref || imeisv==ref && [5qi==5]) chipset==ref || [5qi==1] && [5qi==5] && imeisv==ref Examples of selection criteria that shall be avoided since they will always be evaluated to False. <FlowExpression> can be used in these cases. 5qi==5 && 5qi==9 snssai==0x15000000 && snssai==0x17000000 arp==5 && arp==10 qci==5 && qci==9 Example of selection criteria for UE variable snssai: snssai>=15000000 && snssai<=15FFFFFF //Matches UE which has a flow with S-NSSAI SST part equal to 15 regardless of value of S-NSSAI SD part. snssai==15FFFFFF //Matches UE which has a flow with S-NSSAI SST part equal to 15 and S-NSSAI SD part value equal to FFFFFF, meaning no SD value associated with the SST. Flow expressions combined with UE variables: plmn == 234-56 && [5qi==1] && [5qi==9] //Matches UE which has plmn equal to 234-56, any QoS flow with 5qi equal to 1, and any QoS flow with 5qi equal to 9. chipset==1.5.32 && [5qi==9] && ![5qi==1] //Matches UE which has chipset identifier equal to 1.5.32, any QoS flow with 5qi equal to 9, and no QoS flow with 5qi equal to 1. [5qi==1 && snssai == 0xfedcba98] || ([5qi==2] && [snssai == 0xfedcba77]) //Matches UE which has any QoS flow with 5qi equal to 1 and snssai equal to 0xfedcba98, or has any QoS flow with 5qi equal to 2 and snssai equal to 0xfedcba77. voNrUe==1 && chipset==1.1.1 && [5qi==1] //Matches UEs with Low-Band and Mid-Band VoNR capability using chipset 1.1.1, and have an ongoing flow 5qi.; length 1..1000.";
      type string {
        length "1..1000";
      }
    }
    leaf ueServiceGroupDefinitionId {
      description "The value component of the RDN..";
      type string;
      mandatory true;
    }
    leaf ueServiceGroupId {
      description "UE service group identifier.; range 1..255.";
      type eytypes:int32_range_1-255;
      mandatory true;
    }
    leaf ueServiceGroupPriority {
      description "Relative priority among UE service groups. If UE fulfills selection criteria for more than one UE service group, UE service group with the highest priority is selected. Higher value gives higher priority.; range 1..65535.";
      type eytypes:int32_range_1-65535;
      mandatory true;
    }
    leaf userLabel {
      description "Label for free use..";
      type string;
    }
  }
  grouping UeUlResMon-attributes {
    leaf ueUlResMonId {
      description "The value component of the RDN..";
      type string;
      mandatory true;
    }
  }
  grouping UlBufferMonCfg-attributes {
    leaf-list reservedBy {
      description "Contains a list of MO instances that reserve this MO instance..";
      type string;
      min-elements 0;
    }
    leaf ulBsVolThresh {
      description "Buffer size threshold for uplink data volume for each LCG in BSR. If 0, uplink volume buffer monitoring is disabled.; Default value: 0.";
      type int32 {
        range "0 | 10..20 | 22..23 | 25..26 | 28 | 30 | 32 | 34 | 36 | 38 | 40 | 43 | 46 | 49 | 52 | 55 | 59 | 62 | 66 | 71 | 75 | 80 | 85 | 91 | 97 | 103 | 110 | 117 | 124 | 132 | 141 | 150 | 160 | 170 | 181 | 193 | 205 | 218 | 233 | 248 | 264 | 281 | 299 | 318 | 339 | 361 | 384 | 409 | 436 | 464 | 494 | 526 | 560 | 597 | 635 | 677 | 720 | 767 | 817 | 870 | 926 | 987 | 1051 | 1119 | 1191 | 1269 | 1351 | 1439 | 1532 | 1631 | 1737 | 1850 | 1970 | 2098 | 2234 | 2379 | 2533 | 2698 | 2873 | 3059 | 3258 | 3469 | 3694 | 3934 | 4189 | 4461 | 4751 | 5059 | 5387 | 5737 | 6109 | 6506 | 6928 | 7378 | 7857 | 8367 | 8910 | 9488 | 10104 | 10760 | 11458 | 12202 | 12994 | 13838 | 14736 | 15692 | 16711 | 17795 | 18951 | 20181 | 21491 | 22885 | 24371 | 25953 | 27638 | 29431 | 31342 | 33376 | 35543 | 37850 | 40307 | 42923 | 45709 | 48676 | 51836 | 55200 | 58784 | 62599 | 66663 | 70990 | 75598 | 80505 | 85730 | 91295 | 97221 | 103532 | 110252 | 117409 | 125030 | 133146 | 141789 | 150992 | 160793 | 171231 | 182345 | 194182 | 206786 | 220209 | 234503 | 249725 | 265935 | 283197 | 301579 | 321155 | 342002 | 364202 | 387842 | 413018 | 439827 | 468377 | 498780 | 531156 | 565634 | 602350 | 641449 | 683087 | 727427 | 774645 | 824928 | 878475 | 935498 | 996222 | 1060888 | 1129752 | 1203085 | 1281179 | 1364342 | 1452903 | 1547213 | 1647644 | 1754595 | 1868488 | 1989774 | 2118933 | 2256475 | 2402946 | 2558924 | 2725027 | 2901912 | 3090279 | 3290873 | 3504487 | 3731968 | 3974215 | 4232186 | 4506902 | 4799451 | 5110989 | 5442750 | 5796046 | 6172275 | 6572925 | 6999582 | 7453933 | 7937777 | 8453028 | 9001725 | 9586039 | 10208280 | 10870913 | 11576557 | 12328006 | 13128233 | 13980403 | 14887889 | 15854280 | 16883401 | 17979324 | 19146385 | 20389201 | 21712690 | 23122088 | 24622972 | 26221280 | 27923336 | 29735875 | 31666069 | 33721553 | 35910462 | 38241455 | 40723756 | 43367187 | 46182206 | 49179951 | 52372284 | 55771835 | 59392055 | 63247269 | 67352729 | 71724679 | 76380419 | 81338368";
      }
      default "0";
      units "byte";
    }
    leaf ulBufferMonCfgId {
      description "The value component of the RDN..";
      type string;
      mandatory true;
    }
  }
  grouping UlDataSplit-attributes {
    leaf-list reservedBy {
      description "Contains a list of MO instances that reserve this MO instance..";
      type string;
      min-elements 0;
    }
    leaf ueConfGroupType {
      description "UE configuration group type. UE configuration group type that is applied in contained UlDataSplitUeCfg instances..";
      type enumeration {
        enum UE_MOBILITY_GROUP;
        enum UE_SERVICE_GROUP;
        enum UE_ADMISSION_GROUP;
      }
    }
    leaf ulDataSplitId {
      description "The value component of the RDN..";
      type string;
      mandatory true;
    }
    leaf userLabel {
      description "Label for free use..";
      type string;
    }
  }
  grouping UlDataSplitUeCfg-attributes {
    leaf initialUlPrimaryPathMode {
      description "Uplink primary path mode for initial configuration at dual connectivity setup. Applicable to both EN-DC and NR-DC. Uplink primary path is configured as follows at setup of secondary node-terminated split DRB. SCG in following cases: - value is SCG. - value is COVERAGE_BASED and PSCell uplink quality level is above sum of UlCgSwitchCfg::ulScgLowQualThresh and UlCgSwitchCfg::ulScgLowQualHyst. - value is COVERAGE_BASED and PSCell RSRP level is above InitialCgUeCfg::ulScgInitialLowRsrpThresh. - value is COVERAGE_BASED and PSCell uplink quality and PSCell RSRP are not available. MCG in following cases: - value is MCG. - value is COVERAGE_BASED and PSCell uplink quality level is below UlCgSwitchCfg::ulScgLowQualThresh. - value is COVERAGE_BASED and PSCell RSRP level is below InitialCgUeCfg::ulScgInitialLowRsrpThresh. Value COVERAGE_BASED is only applicable if license for Service-Adaptive Uplink User Plane Profile feature is present and feature is active. Otherwise, COVERAGE_BASED is handled as SCG..";
      type enumeration {
        enum MCG;
        enum COVERAGE_BASED;
        enum SCG;
      }
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf ulDataSplitThreshMcg {
      description "Buffer threshold for uplink PDCP split when primary path is MCG. Buffer level where capable UE instances can split data on both main and secondary leg when primary path is MCG. A capable UE is a UE with dual connectivity supporting split DRB with uplink on both MCG and SCG. This UE can submit uplink PDCP PDUs to both primary RLC entity and secondary RLC entity if total amount of PDCP and RLC data volume for initial transmission in two associated RLC entities is equal or greater than used threshold. Following settings are possible: - If empty, value according to ulDataSplitThreshScg is used. - If 0, uplink PDCP split is always active for capable UE instances. - If -1, used threshold is infinity meaning that PDCP split is not allowed even for capable UE instances. - Value -1 is recommended when DcUlCfg::ulPrimaryPathMode is set to SCG, UlCgSwitchCfg::ulCgSwitchMode is not DISABLED and a low value is set for UlCgSwitchCfg::ulScgLowQualThresh. - Values 0 to 1600 are only recommended for operators for temporary testing purposes. If UlDataSplitUeCfg=Base instance under UlDataSplit=Default_nrdc instance is created automatically, value is -1. Applicable to capable EN-DC and NR-DC UEs. Only applicable if license for LTE-NR Uplink Aggregation is present and feature is active..";
      type int32 {
        range "-1..0 | 100 | 200 | 400 | 800 | 1600 | 3200 | 6400 | 12800 | 25600 | 51200 | 102400 | 204800 | 409600 | 819200 | 1228800 | 1638400 | 2457600 | 3276800 | 4096000 | 4915200 | 5734400 | 6553600";
      }
      units "Byte";
    }
    leaf ulDataSplitThreshScg {
      description "Buffer threshold for uplink PDCP split when primary path is SCG and RSRP or uplink quality is good. Buffer level where capable UE instances can split data on both MCG and SCG when primary path is SCG and PSCell uplink quality or PSCell RSRP level is good, or PSCell uplink quality and PSCell RSRP are not available. A capable UE is a UE with dual connectivity supporting split DRB with uplink on both MCG and SCG. This UE can submit uplink PDCP PDUs to both primary RLC entity and secondary RLC entity if total amount of PDCP and RLC data volume for initial transmission in two associated RLC entities is equal or greater than used threshold. PSCell quality is considered good when PSCell quality level is above the sum of UlCgSwitchCfg::ulScgLowQualThresh and UlCgSwitchCfg::ulScgLowQualHyst. PSCell RSRP is considered good when target PSCell RSRP level is above InitialCgUeCfg::ulScgInitialLowRsrpThresh. If 0, uplink PDCP split is always active for capable UE instances. If -1, used threshold is infinity meaning that PDCP split is not allowed even for capable UE instances. If UlDataSplitUeCfg=Base instance under UlDataSplit=Default_nrdc instance is created automatically, value is -1. Applicable to capable EN-DC and NR-DC UE instances. Only applicable if license for LTE-NR Uplink Aggregation is present and feature is active.; Default value: 51200.";
      type int32 {
        range "-1..0 | 100 | 200 | 400 | 800 | 1600 | 3200 | 6400 | 12800 | 25600 | 51200 | 102400 | 204800 | 409600 | 819200 | 1228800 | 1638400 | 2457600 | 3276800 | 4096000 | 4915200 | 5734400 | 6553600";
      }
      default "51200";
      units "Byte";
    }
    leaf ulDataSplitThreshScgLow {
      description "Buffer threshold for uplink PDCP split when primary path is SCG and RSRP or uplink quality is low. Buffer level where capable UE instances can split data on both main and secondary leg when primary path is SCG and PSCell uplink quality or PSCell RSRP level is low. A capable UE is a UE with dual connectivity supporting split DRB with uplink on both MCG and SCG. This UE can submit uplink PDCP PDUs to both primary RLC entity and secondary RLC entity if total amount of PDCP and RLC data volume for initial transmission in two associated RLC entities is equal or greater than used threshold. PSCell quality is considered low when PSCell quality level is below UlCgSwitchCfg::ulScgLowQualThresh. PSCell RSRP is considered low when target PSCell RSRP level is below InitialCgUeCfg::ulScgInitialLowRsrpThresh. If 0, uplink PDCP split is always active for capable UE instances. If -1, used threshold is infinity meaning that PDCP split is not allowed even for capable UE instances. Applicable to capable EN-DC and NR-DC UE instances. Only applicable if license for following features are present and features are active: - LTE-NR Uplink Aggregation. - Service-Adaptive Uplink User Plane Profile. If license for Service-Adaptive Uplink User Plane Profile is not present or feature is not active, value of ulDataSplitThreshScg is used.; Default value: 3200.";
      type int32 {
        range "-1..0 | 100 | 200 | 400 | 800 | 1600 | 3200 | 6400 | 12800 | 25600 | 51200 | 102400 | 204800 | 409600 | 819200 | 1228800 | 1638400 | 2457600 | 3276800 | 4096000 | 4915200 | 5734400 | 6553600";
      }
      default "3200";
      units "Byte";
    }
    leaf ulDataSplitUeCfgId {
      description "The value component of the RDN..";
      type string;
      mandatory true;
    }
    leaf userLabel {
      description "Label for free use..";
      type string;
    }
  }
  grouping UlQualMcpcMeasCfg-attributes {
    leaf-list reservedBy {
      description "Contains a list of MO instances that reserve this MO instance..";
      type string;
      min-elements 0;
    }
    list ulQualCritical {
      key "id";
      leaf id {
        type uint32;
        description "Synthetic key for struct attribute.";
      }
      description "Configuration of critical uplink radio quality measurement for SpCell. Used for Mobility Control at Poor Coverage (MCPC)..";
      uses UlQualMcpcCritical-struct;
    }
    leaf ulQualMcpcMeasCfgId {
      description "The value component of the RDN..";
      type string;
      mandatory true;
    }
    list ulQualSearchZone {
      key "id";
      leaf id {
        type uint32;
        description "Synthetic key for struct attribute.";
      }
      description "Configuration of search zone uplink radio quality measurement for SpCell. Used for Mobility Control at Poor Coverage (MCPC)..";
      uses UlQualMcpcSearchZone-struct;
    }
    leaf userLabel {
      description "Label for free use..";
      type string;
    }
  }
}
