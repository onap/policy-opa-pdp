module ericsson-plug-in-module-radio {
  yang-version 1.1;
  namespace "urn:com:ericsson:ecim:ReqPlugInModule";
  prefix pimodrdo;
  import ericsson-equip-radio {
    prefix equiprdo;
  }
  import ericsson-field-replaceable-unit-radio {
    prefix frurdo;
  }
  import ericsson-managed-element {
    prefix emael;
  }
  description "Auto-generated from Ericsson CPI MOM XML 15554-lza7016014_33-v1uenfk.xml\n<p>.</p>";
  revision "2026-03-29" {
    description "Ericsson G3G4, version: CXP2020502/2-R32C08";
  }

  augment "/emael:ManagedElement/equiprdo:Equipment/frurdo:FieldReplaceableUnit" {
    list PlugInModule {
      description "Additional definitions from MOM:min/max-elements:0/unbounded;root;systemCreated; This MO represents a module that is inserted into a unit that has a modular building practise.";
      key "plugInModuleId";
      leaf plugInModuleId {
        type leafref {
          path "../attributes/plugInModuleId";
        }
      }
      container attributes {
      uses PlugInModule-attributes;
      }
    }
  }
  typedef AdmState {
    description "Administrative state of a resource.";
    type enumeration {
      enum LOCKED {
        description "The resource is administratively prohibited from performing services for its users.";
      }
      enum UNLOCKED {
        description "The resource is administratively permitted to perform services for its users. This is independent of its inherent operability.";
      }
      enum SHUTTINGDOWN {
        description "Use of the resource is administratively permitted to existing instances of use only. While the system remains in the shutting down state the manager may at any time cause the managed object to revert to the locked state.";
      }
    }
  }
  typedef ApcIndicatorStatus {
    description "Possible states for green, yellow and red indicators. Since the semantics of the different indicator states depend on the color of the indicator, the semantics is described as part of the corresponding indicator status attribute description.";
    type enumeration {
      enum NOT_APPLICABLE {
        description "The indicator is not supported.";
      }
      enum NOT_AVAILABLE {
        description "The indicator state is currently not available.";
      }
      enum OFF {
        description "The indicator is off.";
      }
      enum STEADY_ON {
        description "The indicator is on continuously.";
      }
      enum SLOW_BLINK {
        description "The indicator blinks slowly.";
      }
      enum FAST_BLINK {
        description "The indicator blinks quickly.";
      }
      enum DOUBLE_FLASH_AND_STEADY_ON {
        description "The indicator blinks twice and is then on for a short time. This cycle is then repeated.";
      }
      enum DOUBLE_FLASH_AND_OFF {
        description "The indicator blinks twice and is then off for a short time. This cycle is then repeated.";
      }
    }
  }
  typedef AvailStatus {
    description "The availability status is used to qualify the operational state. It indicates why the operational state has changed its value.";
    type enumeration {
      enum IN_TEST {
        description "The resource is undergoing a test procedure. If the administrative state is locked or shutting down, normal users are prevented from using the resource.";
      }
      enum FAILED {
        description "The resource has an internal fault that prevents it from operating.";
      }
      enum POWER_OFF {
        description "The resource requires power to be applied and is not powered on.";
      }
      enum OFF_LINE {
        description "The resource requires a routine operation to be performed. This routine operation is to place the resource online and make it available for use. The operation may be manual or automatic, or both. The operational state is disabled.";
      }
      enum OFF_DUTY {
        description "The resource has been made inactive by an internal control process.";
      }
      enum DEPENDENCY {
        description "The resource cannot operate because some other resource on which it depends is unavailable.";
      }
      enum DEGRADED {
        description "The service available from the resource is degraded in some respect.";
      }
      enum NOT_INSTALLED {
        description "The resource represented by the managed object is not present, or is incomplete.";
      }
      enum LOG_FULL {
        description "Indicates a log full condition. The semantics are defined in CCITT Rec. X.735 | ISO/IEC 10164-6.";
      }
      enum DEPENDENCY_LOCKED {
        description "The administrative state of a resource that this resource depends on is locked. Alternatively, the availability status of the other resource is dependency locked.";
      }
      enum DEPENDENCY_FAILED {
        description "The availability status of a resource that this resource depends on is failed or dependency failed.";
      }
      enum DEPENDENCY_SHUTTINGDOWN {
        description "The administrative state of a resource that this resource depends on is shutting down. Alternatively, the availability status of the other resource is dependency shutting down.";
      }
      enum DEPENDENCY_RECOVERY {
        description "Resource that this resource depends on is undergoing a recovery procedure.";
      }
      enum DEPENDENCY_HOLDING {
        description "Resource cannot operate because some other resource on which it depends is currently unavailable. The situation is expected to be resolved. Actions to facilitate dependency resolution may be ongoing.";
      }
    }
  }
  typedef OperState {
    description "Operational states of a resource.";
    type enumeration {
      enum DISABLED {
        description "The resource is totally inoperable.";
      }
      enum ENABLED {
        description "The resource is partially or fully operable.";
      }
    }
  }
  grouping ApcProductData-struct {
    description ".";
    leaf productionDate {
      description "length 5..8.";
      type string {
        length "5..8";
      }
    }
    leaf productName {
      description "length 1..32.";
      type string {
        length "1..32";
      }
    }
    leaf productNumber {
      description "length 1..24.";
      type string {
        length "1..24";
      }
    }
    leaf productRevision {
      description "length 1..7.";
      type string {
        length "1..7";
      }
    }
    leaf serialNumber {
      description "length 1..13.";
      type string {
        length "1..13";
      }
    }
  }
  grouping PlugInModule-attributes {
    leaf plugInModuleId {
      description "The value component of the RDN..";
      type string;
      mandatory true;
    }
    leaf faultIndicator {
      description "The fault status of the module as shown by the optical fault indicator on the module. Valid values: • NOT_APPLICABLE = This indicator is not supported. • NOT_AVAILABLE = The indicator state is currently not available. • OFF = No HW fault. • STEADY_ON = HW Fault..";
      type enumeration {
        enum NOT_APPLICABLE;
        enum NOT_AVAILABLE;
        enum OFF;
        enum STEADY_ON;
        enum SLOW_BLINK;
        enum FAST_BLINK;
        enum DOUBLE_FLASH_AND_STEADY_ON;
        enum DOUBLE_FLASH_AND_OFF;
      }
      config false;
    }
    leaf-list availabilityStatus {
      description "The availability status. It contains details about operationalState..";
      type AvailStatus;
      min-elements 0;
    }
    leaf operationalState {
      description "Defines the operational state..";
      type enumeration {
        enum DISABLED;
        enum ENABLED;
      }
      config false;
    }
    leaf moduleType {
      description "A description or identifier of the type of plugin module.; length 0..128.";
      type string {
        length "0..128";
      }
      mandatory true;
    }
    leaf administrativeState {
      description "Defines the administrative state. If set to SHUTTINGDOWN, the state is immediately brought to LOCKED..";
      type enumeration {
        enum LOCKED;
        enum UNLOCKED;
        enum SHUTTINGDOWN;
      }
    }
    list productData {
      config false;
      description "Product data of installed unit. If corresponding HHW unit is not installed, struct contains empty strings..";
      uses ApcProductData-struct;
    }
  }
}
