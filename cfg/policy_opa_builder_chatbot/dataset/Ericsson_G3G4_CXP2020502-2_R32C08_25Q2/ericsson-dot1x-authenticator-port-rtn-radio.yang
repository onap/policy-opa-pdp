module ericsson-dot1x-authenticator-port-rtn-radio {
  yang-version 1.1;
  namespace "urn:com:ericsson:ecim:RtnDot1xAuthenticatorPort";
  prefix dot1xaptrdo;
  import ericsson-l2-eth-port-rtn-radio {
    prefix l2ethptrdo;
  }
  import ericsson-managed-element {
    prefix emael;
  }
  description "Auto-generated from Ericsson CPI MOM XML 15554-lza7016014_33-v1uenfk.xml\nRtnDot1xAuthenticatorPort.";
  revision "2026-03-29" {
    description "Ericsson G3G4, version: CXP2020502/2-R32C08";
  }

  augment "/emael:ManagedElement/emael:Transport/l2ethptrdo:EthernetPort" {
    list Dot1xAuthenticatorPort {
      description "Additional definitions from MOM:min/max-elements:0/1;root; Represents IEEE 802.1X authenticator.";
      key "dot1xAuthenticatorPortId";
      leaf dot1xAuthenticatorPortId {
        type leafref {
          path "../attributes/dot1xAuthenticatorPortId";
        }
      }
      container attributes {
      uses Dot1xAuthenticatorPort-attributes;
      }
    }
  }
  typedef AvailStatus {
    description "The availability status is used to qualify the operational state. It indicates why the operational state has changed its value.";
    type enumeration {
      enum IN_TEST {
        description "The resource is undergoing a test procedure. If the administrative state is locked or shutting down then normal users are precluded from using the resource.";
      }
      enum FAILED {
        description "The resource has an internal fault that prevents it from operating.";
      }
      enum POWER_OFF {
        description "The resource requires power to be applied and is not powered on.";
      }
      enum OFF_LINE {
        description "The resource requires a routine operation to be performed. This routine operation is to place the resource online and make it available for use. The operation may be manual or automatic, or both. The operational state is disabled.";
      }
      enum OFF_DUTY {
        description "The resource has been made inactive by an internal control process.";
      }
      enum DEPENDENCY {
        description "The resource cannot operate because some other resource on which it depends is unavailable.";
      }
      enum DEGRADED {
        description "The service available from the resource is degraded in some respect.";
      }
      enum NOT_INSTALLED {
        description "The resource represented by the managed object is not present, or is incomplete.";
      }
      enum LOG_FULL {
        description "This indicates a log full condition.";
      }
      enum DEPENDENCY_LOCKED {
        description "The administrative state of a resource that this resource depends on is locked. or the availability status of the other resource is dependency locked.";
      }
      enum DEPENDENCY_FAILED {
        description "The availability status of a resource that this resource depends on is failed or dependency failed.";
      }
      enum DEPENDENCY_SHUTTINGDOWN {
        description "The administrative state of a resource that this resource depends on is shutting down. or the availability status of the other resource is dependency shutting down.";
      }
    }
  }
  typedef Dot1xStatusType {
    description "Port dot1x status.";
    type enumeration {
      enum UNAUTHORIZED {
        description "Port is not authorized. Traffic disabled.";
      }
      enum AUTHORIZED {
        description "Port is authorized. Traffic enabled.";
      }
    }
  }
  typedef OperState {
    description "The operational states of a resource.";
    type enumeration {
      enum DISABLED {
        description "The resource is totally inoperable.";
      }
      enum ENABLED {
        description "The resource is partially or fully operable.";
      }
    }
  }
  grouping Dot1xAuthenticatorPort-attributes {
    leaf authenticationServer {
      description "Reference to AuthenticationServer MO to reach authentication server..";
      type string;
      mandatory true;
    }
    leaf-list availabilityStatus {
      description "The availability status. It contains details about operationalState..";
      type AvailStatus;
      min-elements 0;
    }
    leaf dot1xAuthenticatorPortId {
      description "The value component of the RDN..";
      type string;
      mandatory true;
    }
    leaf dot1xStatus {
      description "Port dot1x status..";
      type enumeration {
        enum UNAUTHORIZED;
        enum AUTHORIZED;
      }
      config false;
    }
    leaf operationalState {
      description "The operational state..";
      type enumeration {
        enum DISABLED;
        enum ENABLED;
      }
      config false;
    }
    leaf reAuthPeriod {
      description "Interval between periodic authentication of connected supplicant. If set to 0, reauthentication is disabled.; Default value: 0.";
      type uint32 {
        range "0 | 300..7200";
      }
      default "0";
      units "s";
    }
    leaf userLabel {
      description "Label for free use.; length 1..128.";
      type string {
        length "1..128";
      }
    }
  }
}
