module ericsson-eup-radio {
  yang-version 1.1;
  namespace "urn:com:ericsson:ecim:ReqExternalUp";
  prefix euprdo;
  import ericsson-rmesupport-radio {
    prefix rmesuppo;
  }
  import ericsson-eum-radio {
    prefix eumrdo;
  }
  import ericsson-managed-element {
    prefix emael;
  }
  description "Auto-generated from Ericsson CPI MOM XML 15554-lza7016014_33-v1uenfk.xml\nFW upgrade package for external HW.";
  revision "2026-03-29" {
    description "Ericsson G3G4, version: CXP2020502/2-R32C08";
  }

  augment "/emael:ManagedElement/rmesuppo:NodeSupport/eumrdo:ExternalUpManager" {
    list ExternalUp {
      description "Additional definitions from MOM:min/max-elements:0/unbounded;root; Controls change process of software configuration of external hardware unit. An instance of ExternalUp represents a specific change of software configuration from existing one to new one identified by administrativeData attribute. When ExternalUp MO is created, firmware is downloaded to node. Created automatically when triggered by createExternalUp action on ExternalUpManager MO. Deleted automatically when triggered by removeExternalUp action on ExternalUpManager MO. The RDNs of these MOs are ExternalUP=1, 2, 3, and so on.";
      key "externalUpId";
      leaf externalUpId {
        type leafref {
          path "../attributes/externalUpId";
        }
      }
      container attributes {
      uses ExternalUp-attributes;
      }
    }
  }
  typedef ExternalUpStatus {
    description "Current status of upgrade performed using this ExternalUp MO.";
    type enumeration {
      enum INIT_IN_PROGRESS {
        description "ExternalUp MO initialization is in progress.";
      }
      enum INIT_FAILED {
        description "ExternalUp MO initialization fails.";
      }
      enum INIT_COMPLETED {
        description "ExternalUp MO initialization is completed successfully.";
      }
      enum TRANSFER_FILE_IN_PROGRESS {
        description "Firmware transfer to target hardware is in progress.";
      }
      enum TRANSFER_FILE_COMPLETED {
        description "Firmware transfer to target hardware is completed successfully.";
      }
      enum TRANSFER_FILE_PARTIALLY_COMPLETED {
        description "Firmware transfer to target hardware is completed but fails for some units.";
      }
      enum TRANSFER_FILE_FAILED {
        description "Firmware transfer to target hardware fails.";
      }
      enum ACTIVATION_IN_PROGRESS {
        description "Firmware activation is in progress.";
      }
      enum ACTIVATION_COMPLETED {
        description "Firmware activation is completed successfully.";
      }
      enum ACTIVATION_PARTIALLY_COMPLETED {
        description "Firmware activation is completed but fails for some units.";
      }
      enum ACTIVATION_FAILED {
        description "Firmware activation fails.";
      }
    }
  }
  grouping AdministrativeData-struct {
    description "Product identification of software version activated when upgrade is completed.";
    leaf revision {
      type string;
    }
    leaf name {
      type string;
    }
    leaf vendor {
      type string;
    }
  }
  grouping ExternalUpUnitStatus-struct {
    description "Upgrade status of every hardware unit that is upgraded using this ExternalUp MO.";
    leaf unitStatus {
      type enumeration {
        enum INIT_IN_PROGRESS;
        enum INIT_FAILED;
        enum INIT_COMPLETED;
        enum TRANSFER_FILE_IN_PROGRESS;
        enum TRANSFER_FILE_COMPLETED;
        enum TRANSFER_FILE_PARTIALLY_COMPLETED;
        enum TRANSFER_FILE_FAILED;
        enum ACTIVATION_IN_PROGRESS;
        enum ACTIVATION_COMPLETED;
        enum ACTIVATION_PARTIALLY_COMPLETED;
        enum ACTIVATION_FAILED;
      }
    }
    leaf statusMessage {
      type string;
    }
    leaf upgradeTargetRef {
      type string;
    }
    leaf timeActionCompleted {
      type string;
    }
    leaf timeActionStarted {
      type string;
    }
    leaf timeOfLastStatusUpdate {
      type string;
    }
    leaf progressPercentage {
      description "range 0..100.";
      type uint8 {
        range "0..100";
      }
    }
  }
  grouping ExternalUp-attributes {
    leaf externalUpId {
      description "The value component of the RDN..";
      type string;
      mandatory true;
    }
    list administrativeData {
      config false;
      description "Product identification of software version activated when upgrade is completed..";
      uses AdministrativeData-struct;
    }
    leaf cumulativeUpgradeStatus {
      description "Current status of upgrade performed using this ExternalUp MO..";
      type enumeration {
        enum INIT_IN_PROGRESS;
        enum INIT_FAILED;
        enum INIT_COMPLETED;
        enum TRANSFER_FILE_IN_PROGRESS;
        enum TRANSFER_FILE_COMPLETED;
        enum TRANSFER_FILE_PARTIALLY_COMPLETED;
        enum TRANSFER_FILE_FAILED;
        enum ACTIVATION_IN_PROGRESS;
        enum ACTIVATION_COMPLETED;
        enum ACTIVATION_PARTIALLY_COMPLETED;
        enum ACTIVATION_FAILED;
      }
      config false;
    }
    list unitUpgradeStatus {
      config false;
      min-elements 0;
      uses ExternalUpUnitStatus-struct;
    }
    leaf-list upgradeTargetRef {
      description "References to SupportUnit MOs that are to be upgraded using this ExternalUp MO..";
      type string;
      min-elements 0;
    }
    leaf userLabel {
      description "Label for free use.; length 1..128.";
      type string {
        length "1..128";
      }
    }
  }
}
