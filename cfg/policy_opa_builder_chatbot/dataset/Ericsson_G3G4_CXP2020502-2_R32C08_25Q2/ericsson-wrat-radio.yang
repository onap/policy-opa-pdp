module ericsson-wrat-radio {
  yang-version 1.1;
  namespace "urn:com:ericsson:ecim:Wrat";
  prefix wrat;
  import ietf-inet-types {
    prefix ietfinet;
  }
  import ericsson-yang-types {
    prefix eytypes;
  }
  import ericsson-managed-element {
    prefix emael;
  }
  description "Auto-generated from Ericsson CPI MOM XML 15554-lza7016014_33-v1uenfk.xml\nThe WRAT MOM";
  revision "2026-03-29" {
    description "Ericsson G3G4, version: CXP2020502/2-R32C08";
  }

  augment "/emael:ManagedElement" {
    list NodeBFunction {
      description "Additional definitions from MOM:min/max-elements:0/1;root; This MO models the radio network resources in a Node B application (WCDMA).";
      key "nodeBFunctionId";
      leaf nodeBFunctionId {
        type leafref {
          path "../attributes/nodeBFunctionId";
        }
      }
      container attributes {
      uses NodeBFunction-attributes;
      }
    }
  }

  augment "/emael:ManagedElement/wrat:NodeBFunction/wrat:Iub" {
    list NbapCommon {
      description "Additional definitions from MOM:min/max-elements:0/1; This MO models the Node B Application Part for common procedures.";
      key "nbapCommonId";
      leaf nbapCommonId {
        type leafref {
          path "../attributes/nbapCommonId";
        }
      }
      container attributes {
      uses NbapCommon-attributes;
      }
    }
  }

  augment "/emael:ManagedElement/wrat:NodeBFunction/wrat:Iub" {
    list NbapDedicated {
      description "Additional definitions from MOM:min/max-elements:0/1; This MO models the Node B Application Part for dedicated procedures.";
      key "nbapDedicatedId";
      leaf nbapDedicatedId {
        type leafref {
          path "../attributes/nbapDedicatedId";
        }
      }
      container attributes {
      uses NbapDedicated-attributes;
      }
    }
  }

  augment "/emael:ManagedElement/wrat:NodeBFunction/wrat:Iub" {
    list IubDataStreams {
      description "Additional definitions from MOM:min/max-elements:0/1; This MO models all Iub data streams between the RNC and the Node B for common as well as for dedicated channels.";
      key "iubDataStreamsId";
      leaf iubDataStreamsId {
        type leafref {
          path "../attributes/iubDataStreamsId";
        }
      }
      container attributes {
      uses IubDataStreams-attributes;
      }
    }
  }

  augment "/emael:ManagedElement/wrat:NodeBFunction" {
    list Iub {
      description "Additional definitions from MOM:min/max-elements:0/1; This MO models the Iub interface. Iub is the interface between a Node B and the associated RNC.";
      key "iubId";
      leaf iubId {
        type leafref {
          path "../attributes/iubId";
        }
      }
      container attributes {
      uses Iub-attributes;
      }
    }
  }

  augment "/emael:ManagedElement/wrat:NodeBFunction" {
    list NodeBLocalCellGroup {
      description "Additional definitions from MOM:min/max-elements:0/8; This MO models a group of Node B Local Cells that share common baseband equipment cluster. Within the Node B Local Cell Group you can do softer handover.";
      key "nodeBLocalCellGroupId";
      leaf nodeBLocalCellGroupId {
        type leafref {
          path "../attributes/nodeBLocalCellGroupId";
        }
      }
      container attributes {
      uses NodeBLocalCellGroup-attributes;
      }
    }
  }

  augment "/emael:ManagedElement/wrat:NodeBFunction" {
    list CommunicationContexts {
      description "Additional definitions from MOM:min/max-elements:1/1;systemCreated; This MO models all communication contexts in a Node B. A communication context is a concept that describes all connections between one UE and the network. The RDN of this MO is CommunicationContexts=1.";
      key "communicationContextsId";
      leaf communicationContextsId {
        type leafref {
          path "../attributes/communicationContextsId";
        }
      }
      container attributes {
      uses CommunicationContexts-attributes;
      }
    }
  }

  augment "/emael:ManagedElement/wrat:NodeBFunction" {
    list DlPowerSharing {
      description "Additional definitions from MOM:min/max-elements:0/unbounded;systemCreated; This MO models the HSDPA Mixed Mode Dynamic Power Sharing of a PA. The RDN of this MO is DlPowerSharing=n. Persistent: Yes";
      key "dlPowerSharingId";
      leaf dlPowerSharingId {
        type leafref {
          path "../attributes/dlPowerSharingId";
        }
      }
      container attributes {
      uses DlPowerSharing-attributes;
      }
    }
  }

  augment "/emael:ManagedElement/wrat:NodeBFunction/wrat:NodeBLocalCellGroup/wrat:NodeBLocalCell" {
    list HsDschResources {
      description "Additional definitions from MOM:min/max-elements:0/1;systemCreated; This MO models the High-Speed Downlink Shared Channel resources. They are set up through Iub. The RDN of this MO is HsDschResources=1. Persistent: No";
      key "hsDschResourcesId";
      leaf hsDschResourcesId {
        type leafref {
          path "../attributes/hsDschResourcesId";
        }
      }
      container attributes {
      uses HsDschResources-attributes;
      }
    }
  }

  augment "/emael:ManagedElement/wrat:NodeBFunction/wrat:NodeBLocalCellGroup/wrat:NodeBLocalCell" {
    list RadioLinks {
      description "Additional definitions from MOM:min/max-elements:1/1;systemCreated; This MO models all radio links on one Node B Local Cell. The RDN of this MO is RadioLinks=1.";
      key "radioLinksId";
      leaf radioLinksId {
        type leafref {
          path "../attributes/radioLinksId";
        }
      }
      container attributes {
      uses RadioLinks-attributes;
      }
    }
  }

  augment "/emael:ManagedElement/wrat:NodeBFunction/wrat:NodeBLocalCellGroup/wrat:NodeBLocalCell" {
    list CellResources {
      description "Additional definitions from MOM:min/max-elements:0/1;systemCreated; This MO models all basic physical and transport channels related to a Node B Local Cell. Basic physical channels: PCPICH, SCPICH, PSCH, SSCH and PCCPCH. Transport channels: BCH. The RDN of this MO is CellResources=1. Persistent: No";
      key "cellResourcesId";
      leaf cellResourcesId {
        type leafref {
          path "../attributes/cellResourcesId";
        }
      }
      container attributes {
      uses CellResources-attributes;
      }
    }
  }

  augment "/emael:ManagedElement/wrat:NodeBFunction/wrat:NodeBLocalCellGroup/wrat:NodeBLocalCell" {
    list NodeBSectorCarrier {
      description "Additional definitions from MOM:min/max-elements:0/6; This MO models a carrier frequency that is broadcast in a sector.";
      key "nodeBSectorCarrierId";
      leaf nodeBSectorCarrierId {
        type leafref {
          path "../attributes/nodeBSectorCarrierId";
        }
      }
      container attributes {
      uses NodeBSectorCarrier-attributes;
      }
    }
  }

  augment "/emael:ManagedElement/wrat:NodeBFunction/wrat:NodeBLocalCellGroup/wrat:NodeBLocalCell" {
    list CommonChannelResourcesDl {
      description "Additional definitions from MOM:min/max-elements:0/1;systemCreated; This MO models all physical and transport channels related to the downlink common channels. Physical channels: SCCPCH, PICH and AICH. Transport channel: FACH and PCH. The RDN of this MO is CommonChannelResourcesDl=1. Persistent: No";
      key "commonChannelResourcesDlId";
      leaf commonChannelResourcesDlId {
        type leafref {
          path "../attributes/commonChannelResourcesDlId";
        }
      }
      container attributes {
      uses CommonChannelResourcesDl-attributes;
      }
    }
  }

  augment "/emael:ManagedElement/wrat:NodeBFunction/wrat:NodeBLocalCellGroup/wrat:NodeBLocalCell" {
    list EDchResourcesCell {
      description "Additional definitions from MOM:min/max-elements:0/1;systemCreated; This MO models the Enhanced Uplink Shared Channel resources related to a Node B Local Cell. They are set up through Iub. The RDN of this MO is EDchResourcesCell=1. Persistent: No";
      key "eDchResourcesCellId";
      leaf eDchResourcesCellId {
        type leafref {
          path "../attributes/eDchResourcesCellId";
        }
      }
      container attributes {
      uses EDchResourcesCell-attributes;
      }
    }
  }

  augment "/emael:ManagedElement/wrat:NodeBFunction/wrat:NodeBLocalCellGroup" {
    list NodeBLocalCell {
      description "Additional definitions from MOM:min/max-elements:0/18; This MO models a local cell, that is the equipment and resources in a Node B needed to support an UTRAN cell. Precondition: This MO can not be deleted if it has not administrativeState=LOCKED.";
      key "nodeBLocalCellId";
      leaf nodeBLocalCellId {
        type leafref {
          path "../attributes/nodeBLocalCellId";
        }
      }
      container attributes {
      uses NodeBLocalCell-attributes;
      }
    }
  }

  augment "/emael:ManagedElement/wrat:NodeBFunction/wrat:NodeBLocalCellGroup/wrat:NodeBLocalCell/wrat:NodeBSectorCarrier" {
    list CommonChannelResourcesUl {
      description "Additional definitions from MOM:min/max-elements:0/1;systemCreated; This MO models all physical and transport channels related to the uplink common channels. Physical channels: PRACH. Transport channel: RACH. The RDN of this MO is CommonChannelResourcesUl=1. Persistent: No";
      key "commonChannelResourcesUlId";
      leaf commonChannelResourcesUlId {
        type leafref {
          path "../attributes/commonChannelResourcesUlId";
        }
      }
      container attributes {
      uses CommonChannelResourcesUl-attributes;
      }
    }
  }

  augment "/emael:ManagedElement/wrat:NodeBFunction/wrat:NodeBLocalCellGroup/wrat:NodeBLocalCell/wrat:NodeBSectorCarrier" {
    list EDchResources {
      description "Additional definitions from MOM:min/max-elements:0/1;systemCreated; This MO models the Enhanced Uplink Shared Channel resources. They are set up through Iub. The RDN of this MO is EDchResources=1. Persistent: No";
      key "eDchResourcesId";
      leaf eDchResourcesId {
        type leafref {
          path "../attributes/eDchResourcesId";
        }
      }
      container attributes {
      uses EDchResources-attributes;
      }
    }
  }
  typedef AdmState {
    description "Administrative state of a resource.";
    type enumeration {
      enum LOCKED {
        description "The resource is administratively prohibited from performing services for its users.";
      }
      enum UNLOCKED {
        description "The resource is administratively permitted to perform services for its users. This is independent of its inherent operability.";
      }
      enum SHUTTINGDOWN {
        description "Use of the resource is administratively permitted to existing instances of use only. While the system remains in the shutting down state the manager may at any time cause the managed object to revert to the locked state.";
      }
    }
  }
  typedef AdvCellSupAction {
    description "Recovery action performed when Advanced Cell Supervision feature detects a sleeping cell.";
    type enumeration {
      enum NO_ACTION {
        description "No recovery action is initiated.";
      }
      enum CELL_RESTART {
        description "Cell restart is initiated automatically, that is, a cell is deleted and then setup again.";
      }
    }
  }
  typedef AvailStatus {
    description "The availability status is used to qualify the operational state. It indicates why the operational state has changed its value.";
    type enumeration {
      enum IN_TEST {
        description "The resource is undergoing a test procedure. If the administrative state is locked or shutting down, normal users are prevented from using the resource.";
      }
      enum FAILED {
        description "The resource has an internal fault that prevents it from operating.";
      }
      enum POWER_OFF {
        description "The resource requires power to be applied and is not powered on.";
      }
      enum OFF_LINE {
        description "The resource requires a routine operation to be performed. This routine operation is to place the resource online and make it available for use. The operation may be manual or automatic, or both. The operational state is disabled.";
      }
      enum OFF_DUTY {
        description "The resource has been made inactive by an internal control process.";
      }
      enum DEPENDENCY {
        description "The resource cannot operate because some other resource on which it depends is unavailable.";
      }
      enum DEGRADED {
        description "The service available from the resource is degraded in some respect.";
      }
      enum NOT_INSTALLED {
        description "The resource represented by the managed object is not present, or is incomplete.";
      }
      enum LOG_FULL {
        description "Indicates a log full condition. The semantics are defined in CCITT Rec. X.735 | ISO/IEC 10164-6.";
      }
      enum DEPENDENCY_LOCKED {
        description "The administrative state of a resource that this resource depends on is locked. or the availability status of the other resource is dependency locked.";
      }
      enum DEPENDENCY_FAILED {
        description "The availability status of a resource that this resource depends on is failed or dependency failed.";
      }
      enum DEPENDENCY_SHUTTINGDOWN {
        description "The administrative state of a resource that this resource depends on is shutting down. or the availability status of the other resource is dependency shutting down.";
      }
      enum DEPENDENCY_RECOVERY {
        description "The availability status of the other resource is dependency recovery.";
      }
    }
  }
  typedef BbPowerSavingMode {
    description "Status of Baseband power saving mode.";
    type enumeration {
      enum NOT_SUPPORTED {
        description "Not supported by Baseband hardware.";
      }
      enum IN_POWER_SAVING {
        description "Baseband in power saving mode.";
      }
      enum OUT_OF_POWER_SAVING {
        description "Baseband not in power saving mode.";
      }
    }
  }
  typedef BsctInnerLoopDlpcStatus {
    description "Whether the inner loop DL power control for DPCH is active or not.";
    type enumeration {
      enum INACTIVE {
      }
      enum ACTIVE {
      }
    }
  }
  typedef BsctMode {
    description "Whether NodeB is in Normal or Base Station Conformance Testing operation mode.";
    type enumeration {
      enum NORMAL {
      }
      enum BASE_STATION_CONFORMANCE_TEST {
      }
    }
  }
  typedef BsctState {
    description "Whether Base Station Conformance Testing is started or not.";
    type enumeration {
      enum STOPPED {
      }
      enum STARTED {
      }
      enum NOT_APPLICABLE {
      }
    }
  }
  typedef BsctTestModel {
    description "Possible Base Station Conformance Testing models.";
    type enumeration {
      enum TEST_MODEL_1 {
      }
      enum TEST_MODEL_2 {
      }
      enum TEST_MODEL_3 {
      }
      enum TEST_MODEL_4 {
      }
      enum TEST_MODEL_5 {
      }
      enum TEST_MODEL_6 {
      }
      enum NOT_APPLICABLE {
      }
    }
  }
  typedef BsctTpcDlStepSize {
    description "FDD transmission power control DL Step Size. Unit: 0.1 dB";
    type enumeration {
      enum _5 {
      }
      enum _10 {
      }
      enum _15 {
      }
      enum _20 {
      }
    }
  }
  typedef CarrierAirRateTypeSelector {
    description "Indicates possible status values of a corresponding AirRateType Selector attribute.";
    type enumeration {
      enum ACKNOWLEDGED {
      }
      enum TRANSMITTED {
      }
    }
  }
  typedef CarrierQueueSelectAlgorithm {
    type enumeration {
      enum ROUND_ROBIN {
      }
      enum PROPORTIONAL_FAIR_MEDIUM {
      }
      enum PROPORTIONAL_FAIR_HIGH {
      }
      enum PROPORTIONAL_FAIR_LOW {
      }
      enum MAXIMUM_CQI {
      }
      enum EQUAL_RATE {
      }
    }
  }
  typedef CombinedCellConfiguration {
    description "Defines which combined cell deployment is used.";
    type enumeration {
      enum COMBINED_CELL_NORMAL {
        description "Legacy combined cell is used.";
      }
      enum COMBINED_CELL_INDOOR {
        description "The indoor deployment combined cell is used.";
      }
    }
  }
  typedef CpcCapability {
    description "Whether the local cell is CPC capable or not.";
    type enumeration {
      enum CPC_NON_CAPABLE {
      }
      enum CPC_CAPABLE {
      }
    }
  }
  typedef EulMcCapability {
    description "Defines if this local cell is EUL Multi-Carrier capable or not.";
    type enumeration {
      enum EUL_MC_NON_CAPABLE {
      }
      enum EUL_MC_CAPABLE {
      }
    }
  }
  typedef FeatCtrlState {
    description "Possible states set by operator for licensed or unlicensed feature.";
    type enumeration {
      enum OFF {
        description "Operator does not allow usage of the feature.";
      }
      enum ON {
        description "Operator allows usage of the feature.";
      }
    }
  }
  typedef Hsdpa3McCapability {
    description "Defines if the cell is 3x multi carrier capable or not.";
    type enumeration {
      enum HSDPA_3MC_CAPABLE {
      }
      enum HSDPA_3MC_NON_CAPABLE {
      }
    }
  }
  typedef HsdpaDb3McCapability {
    description "Defines if the cell is dual band 3x multi carrier capable or not.";
    type enumeration {
      enum HSDPA_DB_3MC_CAPABLE {
      }
      enum HSDPA_DB_3MC_NON_CAPABLE {
      }
    }
  }
  typedef HsdpaDbMcCapability {
    description "Defines if the cell is dual band multi carrier capable or not.";
    type enumeration {
      enum HSDPA_DB_MC_NON_CAPABLE {
      }
      enum HSDPA_DB_MC_CAPABLE {
      }
    }
  }
  typedef HsdpaMcCapability {
    description "Defines if the Cell is multi carrier capable or not.";
    type enumeration {
      enum HSDPA_MC_NON_CAPABLE {
      }
      enum HSDPA_MC_CAPABLE {
      }
    }
  }
  typedef HsdpaMmPowerSharingCapability {
    description "Defines if the Cell is capable of HSDPA Mixed Mode Dynamic Power Sharing or not.";
    type enumeration {
      enum HSDPA_MM_POWER_SHARING_NON_CAPABLE {
      }
      enum HSDPA_MM_POWER_SHARING_CAPABLE {
      }
    }
  }
  typedef HsdpaPowerSharingCapability {
    description "Defines if the Cell is capable of HSDPA dynamic power sharing or not.";
    type enumeration {
      enum HSDPA_POWER_SHARING_NON_CAPABLE {
      }
      enum HSDPA_POWER_SHARING_CAPABLE {
      }
    }
  }
  typedef IpOptimizedHsTnSettingsStatus {
    description "Possible status set by operator for IP Optimized HSDPA TN Settings.";
    type enumeration {
      enum OFF {
        description "IP Optimized HSDPA TN Settings is off when low bandwidth IP links are used.";
      }
      enum ON {
        description "IP Optimized HSDPA TN Settings is on when high bandwidth IP links are used, for example the bandwidth is no less than 20 Mbps.";
      }
    }
  }
  typedef NbirAutoSelectAlgorithm {
    description "Automatically selected Narrowband Interference Rejection algorithm.";
    type enumeration {
      enum NBIR_OFF {
      }
      enum GENERIC_NBIR {
      }
      enum ADAPTIVE_NOTCH_NBIR {
      }
      enum NOT_APPLICABLE {
      }
    }
  }
  typedef NbirSelectAlgorithm {
    description "Selects which Narrowband Interference Rejection algorithm to use.";
    type enumeration {
      enum GENERIC_NBIR {
      }
      enum ADAPTIVE_NOTCH_NBIR {
      }
      enum FIXED_NOTCH_NBIR {
      }
      enum AUTO_GENERIC_ADAPTIVE_NBIR {
      }
      enum AUTO_GENERIC_ADAPTIVE_OFF_NBIR {
      }
    }
  }
  typedef NewSteHsAllocStatus {
    description "The status of the optimal HS allocation based on the feature Load-based Steered HS Allocation.";
    type enumeration {
      enum NOT_APPLICABLE {
        description "Feature Load-based Steered HS Allocation is deactivated.";
      }
      enum NEW_STE_HS_ALLOC_NOT_READY {
        description "Optimal HS core allocation is not ready.";
      }
      enum NEW_STE_HS_ALLOC_READY {
        description "Optimal HS core allocation is ready.";
      }
    }
  }
  typedef NoiseFloorAlgorithm {
    description "Indicates which noise floor algoritmh should be used.";
    type enumeration {
      enum SLIDING_WINDOW_NOISE_FLOOR {
      }
      enum RECURSIVE_NOISE_FLOOR {
      }
    }
  }
  typedef OperState {
    description "Operational states of a resource.";
    type enumeration {
      enum DISABLED {
        description "The resource is totally inoperable.";
      }
      enum ENABLED {
        description "The resource is partially or fully operable.";
      }
    }
  }
  typedef SchFlowControlState {
    description "Defines whether flow control is activated (on) or deactivated (off).";
    type enumeration {
      enum OFF {
        description "Flow control is deactivated.";
      }
      enum ON {
        description "Flow control is activated.";
      }
    }
  }
  typedef SectorLatHemisphere {
    description "The latitude hemisphere for the Sector.";
    type enumeration {
      enum NORTH {
      }
      enum SOUTH {
      }
    }
  }
  typedef UsageState {
    description "The usage state describes the usage of a resource. The allowed values are defined by ITU-T X.731.";
    type enumeration {
      enum IDLE {
        description "The resource is not currently in use. Defined by ITU-T X.731";
      }
      enum ACTIVE {
        description "The resource is in use and it has sufficient spare operating capacity. Spare operating capacity to provide for additional users simultaneously. Defined by ITU-T X.731";
      }
      enum BUSY {
        description "The resource is in use, but it has no spare operating capacity. Spare operating capacity to provide for additional users at this instant. Defined by ITU-T X.731";
      }
    }
  }
  grouping CeCapacitiesDl-struct {
    description "Downlink channel element capacities.";
    leaf dlAvailableCe {
      description "range 0..65535.";
      type uint16 {
        range "0..65535";
      }
      units "CE";
    }
    leaf dlStaticCe {
      description "range 0..65535.";
      type uint16 {
        range "0..65535";
      }
      units "CE";
    }
    leaf dlStaticCeMaxLimit {
      description "range 0..65535.";
      type uint16 {
        range "0..65535";
      }
      units "CE";
    }
  }
  grouping CeCapacitiesTotalUl-struct {
    description "Total uplink channel element capacities.";
    leaf totalUlCe {
      description "range 0..65535.";
      type uint16 {
        range "0..65535";
      }
      units "CE";
    }
    leaf totalUlCeAvailable {
      description "range 0..65535.";
      type uint16 {
        range "0..65535";
      }
      units "CE";
    }
    leaf totalUlCeMaxLimit {
      description "range 0..65535.";
      type uint16 {
        range "0..65535";
      }
      units "CE";
    }
  }
  grouping CeCapacitiesUl-struct {
    description "Uplink channel element capacities.";
    leaf ulStaticCe {
      description "range 0..65535.";
      type uint16 {
        range "0..65535";
      }
      units "CE";
    }
    leaf ulAvailableCe {
      description "range 0..65535.";
      type uint16 {
        range "0..65535";
      }
      units "CE";
    }
    leaf ulStaticCeLimit {
      description "range 0..65535.";
      type uint16 {
        range "0..65535";
      }
      units "CE";
    }
  }
  grouping HsPdschCodeCapacities-struct {
    description "HS-PDSCH code capacity with BB HWAC limit..";
    leaf hsPdschCodesMaxLimit {
      description "range 0..720.";
      type uint16 {
        range "0..720";
      }
    }
    leaf hsPdschCodesAvailable {
      description "range 0..720.";
      type uint16 {
        range "0..720";
      }
    }
  }
  grouping CellResources-attributes {
    leaf cellResourcesId {
      description "The value component of the RDN..";
      type string;
      mandatory true;
    }
    leaf-list availabilityStatus {
      description "The availability status. It contains details about operationalState..";
      type AvailStatus;
      min-elements 0;
    }
    leaf operationalState {
      description "Defines the operational state..";
      type enumeration {
        enum DISABLED;
        enum ENABLED;
      }
      config false;
    }
    leaf numOfBch {
      description "Current number of BCHs (Broadcast CHannels) in the cell. The BCH is a fixed rate point to multi point downlink channel, used to convey system information in the whole coverage area of the cell.; range 0..1.";
      type eytypes:int16_range_0-1;
      config false;
    }
    leaf numOfPccpch {
      description "Current number of PCCPCHs (Primary Common Control Physical CHannel) in the cell. This downlink physical channel carries the transport channel BCH.; range 0..1.";
      type eytypes:int16_range_0-1;
      config false;
    }
    leaf numOfPcpich {
      description "Current number of PCPICHs (Primary Common Pilot CHannel) in the cell. This is a fixed rate downlink physical channel that carries a predefined symbol sequence. PCPICH is used as phase reference for other downlink physical channels. No transport channel is carried on PCPICH.; range 0..1.";
      type eytypes:int16_range_0-1;
      config false;
    }
    leaf numOfPsch {
      description "Current number of PSCHs (Primary Synchronization CHannel) in the cell. This is a downlink physical channel used to find the scrambling code of the cell. The PSCH transmits the Primary Synchronization Code, which is the same for every cell in the system and known by each UE. It is sent simultaneously with the transmission on the SSCH. No transport channel is carried on PSCH.; range 0..1.";
      type eytypes:int16_range_0-1;
      config false;
    }
    leaf numOfScpich {
      description "Current number of SCPICHs (Secondary Common Pilot CHannel) in the cell. This is a fixed rate downlink physical channel that carries a predefined symbol sequence. SCPICH is used as phase reference for other downlink physical channels on a second antenna branch in certain MIMO configurations. No transport channel is carried on SCPICH.; range 0..1.";
      type eytypes:int16_range_0-1;
      config false;
    }
    leaf numOfSsch {
      description "Current number of SSCHs (Secondary Synchronization CHannel) in the cell. This is a downlink physical channel used to find the scrambling code of the cell. SSCH transmits a sequence of 15 codes, simultaneously with transmission on the PSCH. By identifying the sequence the UE can derive the primary scrambling code of the cell. No transport channel is carried on SSCH.; range 0..1.";
      type eytypes:int16_range_0-1;
      config false;
    }
  }
  grouping CommonChannelResourcesDl-attributes {
    leaf commonChannelResourcesDlId {
      description "The value component of the RDN..";
      type string;
      mandatory true;
    }
    leaf-list availabilityStatus {
      description "The availability status. It contains details about operationalState..";
      type AvailStatus;
      min-elements 0;
    }
    leaf operationalState {
      description "Defines the operational state..";
      type enumeration {
        enum DISABLED;
        enum ENABLED;
      }
      config false;
    }
    leaf numOfAich {
      description "Current number of AICHs (Acquisition Indication CHannel) in the cell. AICH is a fixed rate downlink physical channel that carries the acquisition indications for reception of preambles on RACH. No transport channel is carried on AICH.; range 0..1.";
      type eytypes:int16_range_0-1;
      config false;
    }
    leaf numOfFach {
      description "Current number of FACHs (Forward Access link CHannel) in the cell. FACH is a downlink common transport channel is used by the network to send messages to a specific UE when no dedicated channels have been established.; range 0..2.";
      type int16 {
        range "0..2";
      }
      config false;
    }
    leaf numOfPch {
      description "Current number of PCHs (Paging CHannel) in the cell. PCH is a downlink common control channel used by the network to broadcast paging messages to find a UE when no dedicated channels have been established.; range 0..1.";
      type eytypes:int16_range_0-1;
      config false;
    }
    leaf numOfPich {
      description "Current number of PICHs (Paging Indication CHannel) in the cell. PICH is a downlink physical channel used to notify UEs that they must listen for paging messages on the PCH. No transport channel is carried on PICH.; range 0..1.";
      type eytypes:int16_range_0-1;
      config false;
    }
    leaf numOfSccpch {
      description "Current number of SCCPCHs (Secondary Common Control Physical CHannel) in the cell. SCCPCH is a downlink physical channel that carries the transport channels FACH or PCH.; range 0..2.";
      type int16 {
        range "0..2";
      }
      config false;
    }
    leaf pmNoOfTfc2OnFach1 {
      description "Number of frames of format TFC2 on FACH1. This counter, together with pmNoOfTfc1OnFach1 and pmNoOfTfc3OnFach2, can be used to calculate the average transmitted output power on FACH..";
      type uint64;
      config false;
    }
    leaf pmNoOfTfc3OnFach2 {
      description "Number of frames of format TFC3 on FACH2. This counter, together with pmNoOfTfc1OnFach1 and pmNoOfTfc2OnFach1, can be used to calculate the average transmitted output power on FACH..";
      type uint64;
      config false;
    }
    leaf pmAichPositiveMessages {
      description "This is a peg counter counting the number of positive Acquisition Indicator (AI) messages sent on the Acquisition Indicator CHannel (AICH), per granularity period..";
      type uint64;
      config false;
    }
    leaf pmNoOfTfc1OnFach1 {
      description "Number of frames of format TFC1 on FACH1. This counter, together with pmNoOfTfc2OnFach1 and pmNoOfTfc3OnFach2, can be used to calculate the average transmitted output power on FACH..";
      type uint64;
      config false;
    }
    leaf pmAichNegativeMessages {
      description "This is a peg counter counting the number of negative Acquisition Indicator (AI) messages sent on the Acquisition Indicator CHannel (AICH), per granularity period..";
      type uint64;
      config false;
    }
    leaf pmAichPositiveMessagesEulFach {
      description "Number of positive Acquisition Indicator messages sent on AICH for EUL FACH assigned signatures..";
      type uint64;
      config false;
    }
    leaf-list pmAichNegativeMessagesEulFach {
      description "Number of negative Acquisition Indicator messages sent on AICH for EUL FACH assigned signatures. Bins: [0]: The C-EDCH resource (selected by the preamble signature) is occupied. [1]: The C-EDCH resource (selected by the preamble signature) is free, but lacks HW decoder..";
      type uint64;
      max-elements 2;
    }
  }
  grouping CommonChannelResourcesUl-attributes {
    leaf commonChannelResourcesUlId {
      description "The value component of the RDN..";
      type string;
      mandatory true;
    }
    leaf-list availabilityStatus {
      description "The availability status. It contains details about operationalState..";
      type AvailStatus;
      min-elements 0;
    }
    leaf operationalState {
      description "Defines the operational state..";
      type enumeration {
        enum DISABLED;
        enum ENABLED;
      }
      config false;
    }
    leaf numOfPrach {
      description "Current number of PRACHs (Physical Random Access CHannel) in the cell. PRACH is an uplink physical channel used to carry RACH.; range 0..1.";
      type eytypes:int16_range_0-1;
      config false;
    }
    leaf numOfRach {
      description "Current number of RACHs (Random Access CHannel) in the cell. RACH is an uplink common control channel used by any UE to send messages to the network when no dedicated channels have been established.; range 0..1.";
      type eytypes:int16_range_0-1;
      config false;
    }
    leaf pmPrachPropagationDelayMax {
      description "Maximum propagation delay within the cell (i.e. from the cell range to the antenna) in number of chips (0..2562)..";
      type int64;
      config false;
    }
    leaf-list pmAccessIntensityEulFach {
      description "Number of EUL_FACH accesses during a sampling period. Bins: [0]: Number of sampling periods with 0 accesses [1]: Number of sampling periods with 1 access [2]: Number of sampling periods with 2 accesses ... [25]: Number of sampling periods with 25 accesses [26]: Number of sampling periods with more than 25 accesses.";
      type uint64;
      max-elements 27;
    }
    leaf-list pmPrachPropagationDelay {
      description "Propagation delay between UEs and the antenna for a cell, as percentage of the maximum propagation delay within the cell (indicated by the counter pmPrachPropagationDelayMax). Bins: [0]: 0 (not used) [1]: Number of samples less than 1 % [2]: Number of samples in range [1..2[ % ... [10]: Number of samples in range [9..10[ % [11]: Number of samples in range [10..12[ % [12]: Number of samples in range [12..14[ % ... [20]: Number of samples in range [28..30[ % [21]: Number of samples in range [30..33[ % [22]: Number of samples in range [33..36[ % ... [30]: Number of samples in range [57..60[ % [31]: Number of samples in range [60..64[ % [32]: Number of samples in range [64..68[ % ... [40]: Number of samples greater than or equal to 96 %.";
      type uint64;
      max-elements 41;
    }
    leaf pmPrachSuccReceivedBlocks {
      description "The number of successfully received transport blocks during a granularity period..";
      type uint64;
      config false;
    }
    leaf-list pmAccessIntensityRach {
      description "Number of RACH accesses during a sampling period. Bins: [0]: Number of sampling periods with 0 accesses [1]: Number of sampling periods with 1 access [2]: Number of sampling periods with 2 accesses ... [25]: Number of sampling periods with 25 accesses [26]: Number of sampling periods with more than 25 accesses.";
      type uint64;
      max-elements 27;
    }
    leaf-list pmPrachReceivedPreambleSir {
      description "The signal to interference ratio (SIR) of all access attempts (above the preamble threshold) except false detection (noise) on RACH. Bins: [0]: Number of sampled values less than -25 dB [1]: Number of sampled values in range [-25..-24[ dB [2]: Number of sampled values in range [-24..-23[ dB ... [25]: Number of sampled values in range [-1..0[ dB [26]: Number of sampled values greater than or equal to 0.";
      type uint64;
      max-elements 27;
    }
    leaf pmPrachUnsuccReceivedBlocks {
      description "The number of unsuccessfully received transport blocks during a granularity period..";
      type uint64;
      config false;
    }
    leaf pmPrachNoPreambleFalseDetection {
      description "The number of false detections owing to noise on RACH..";
      type uint64;
      config false;
    }
  }
  grouping CommunicationContexts-attributes {
    leaf communicationContextsId {
      description "The value component of the RDN..";
      type string;
      mandatory true;
    }
    leaf noOfCommunicationContexts {
      description "Total number of Communication Contexts allocated in the Node B.; range 0..9999.";
      type int16 {
        range "0..9999";
      }
      config false;
    }
  }
  grouping DlPowerSharing-attributes {
    leaf dlPowerSharingId {
      description "The value component of the RDN..";
      type string;
      mandatory true;
    }
    leaf extraPowerHsdpaMixedMode {
      description "Maximum borrowed power from other standards on the PA referenced by rfBranchTxRef.; range 0..160; Default value: 160.";
      type int16 {
        range "0..160";
      }
      default "160";
      units "W";
    }
    leaf rfBranchTxRef {
      description "Refers to RF branch instance corresponding to shared PA..";
      type string;
      config false;
    }
    leaf-list nodeBLocalCellRef {
      description "List of NodeBLocalCell MOs using rfBranchTxRef as TX branch and with NodeBLocalCell::featCtrlHsdpaMmPowerSharing = ON..";
      type string;
      min-elements 0;
      max-elements 4;
    }
    leaf pmNoOfPowLimSlots {
      description "The number of power-limited slots during a granularity period..";
      type uint64;
      config false;
    }
  }
  grouping EDchResources-attributes {
    leaf eDchResourcesId {
      description "The value component of the RDN..";
      type string;
      mandatory true;
    }
    leaf-list availabilityStatus {
      description "The availability status. It contains details about operationalState..";
      type AvailStatus;
      min-elements 0;
    }
    leaf operationalState {
      description "Defines the operational state..";
      type enumeration {
        enum DISABLED;
        enum ENABLED;
      }
      config false;
    }
    leaf pmSumNackedBitsCellEulFach {
      description "Counter for the total amount of nacked data received after HARQ process on MAC-i level for all EUL FACH 10 ms TTI users in a cell. Unit 1 kilobit..";
      type uint64;
      config false;
    }
    leaf pmNoAllowedEul {
      description "Number of times uplink interference is above load threshold for E-DCH traffic, causing stop of E-DCH traffic..";
      type uint64;
      config false;
    }
    leaf-list pmLDch {
      description "The measured uplink Uu load of a cell for users configured with only Release 99 DCH on the uplink. Load contributions from DPDCH, DPCCH and HS-DPCCH are included. The sampled value is a load factor and is unitless with range 0..1, where 0 means no load and 1 is maximum possible load. Bins: [0]: Number of samples in range [0..0.02[ [1]: Number of samples in range [0.02..0.04[ ... [49]: Number of samples in range [0.98..1].";
      type uint64;
      max-elements 50;
    }
    leaf pmCapacityAllocAttServEDchUsers {
      description "Number of attempts to allocate resources for new Serving E-DCH user. If the corresponding carrier is part of a cell using more than one carrier, its value is undefined. Deprecated: Since 17.Q2. Replaced by EDchResourcesCell::pmCapacityAllocAttServEDchUsers.; MOM flags: noNotification.";
      type uint64;
      config false;
      status deprecated;
    }
    leaf-list pmGrantReductionReasonEul {
      description "Number of grant reductions made by EUL Scheduler due to different reasons. Count for each reason is given by a separate bin. Bins: [0]: TN Congestion -- Incremented every time a grant reduction is triggered due to a TCI (TNL Congestion Indication) received by the scheduler. [1]: Uu Congestion Serving -- Incremented every time an absolute grant overload action is taken due insufficient scheduling headroom. [2]: Uu Congestion Non-serving -- Incremented every time a relative grant overload action is taken due insufficient scheduling headroom. [3]: HW Congestion -- Incremented every time an overload action is taken due insufficient UL HW. [4]: Low usage happy -- Incremented every time a happy user's grant is reduced due to consistently low usage of the granted rate. [5]: Low usage unhappy -- Incremented every time an unhappy user's grant is reduced due to consistently low usage of the granted rate. [6]: Not used -- Always reported as 0. [7]: Inactivity at high grant -- Incremented when a user with a high grant is reduced to the minimum UL HW allocation due to data inactivity on the UL. [8]: Rescheduling -- Incremented every time a user's rate is reduced due to rescheduling in the scheduler..";
      type uint64;
      max-elements 9;
    }
    leaf pmNoActive2msFramesEul {
      description "Sum of used 2 ms frames (TTI) that receive E-DCH data in a cell during a granularity period for all E-DCH users, excluding frames that are not decoded due to lack of hardware. Note that this counter also includes TTIs for TD Scheduled users. An E-DCH user may belong to several cells or sector carriers (in case of a cell using more than one carrier) at the same time. If so is the case the user will be counted in each of these cells or sector carriers (in case of a cell using more than one carrier)..";
      type uint64;
      config false;
    }
    leaf-list pmCapacityOfServEDchUsers {
      description "Distribution of number of Serving E-DCH users, as percentages of licensed limit visible in pmCapacityLimitServEDchUsers. If the corresponding carrier is part of a cell using more than one carrier, all values are undefined. Bins: [0]: Number of sampled values in range [0..20[ % [1]: Number of sampled values in range [20..40[ % [2]: Number of sampled values in range [40..50[ % [3]: Number of sampled values in range [50..60[ % [4]: Number of sampled values in range [60..70[ % [5]: Number of sampled values in range [70..80[ % [6]: Number of sampled values in range [80..85[ % [7]: Number of sampled values in range [85..90[ % [8]: Number of sampled values in range [90..95[ % [9]: Number of sampled values >= 95%. Deprecated: Since 17.Q2. Replaced by EDchResourcesCell::pmCapacityOfServEDchUsers.; MOM flags: noNotification.";
      type uint64;
      max-elements 10;
    }
    leaf pmSumAckedBitsCellEulTti10 {
      description "Counter for the total amount of acked data received in kbits after HARQ process on MAC-e/MAC-i level for all 10 ms TTI users in a cell. Note that k = 1000. An E-DCH user may belong to several cells or sector carriers (in case of a cell using more than one carrier) at the same time. If so is the case the user will be counted in each of these cells or sector carriers (in case of a cell using more than one carrier)..";
      type uint64;
      config false;
    }
    leaf-list pmTotalRotCoverage {
      description "Counter per cell for the total Rise over Thermal (RoT) (including all uplink traffic and external interference) that affects the coverage. Bins: [0]: Number of samples less than 0.5 dB [1]: Number of samples in range [0.5..1.0[ dB [2]: Number of samples in range [1.0..1.5[ dB ... [49]: Number of samples in range [24.5..25[ dB [50]: Number of samples greater than or equal to 25 dB.";
      type uint64;
      max-elements 51;
    }
    leaf pmNoActive2msFramesEulTd {
      description "Sum of used 2 ms frames (TTI) for TD-scheduled E-DCH users. TD-scheduled E-DCH users which receive scheduled or non-scheduled E-DCH data in the frame, in a cell during a granularity period..";
      type uint64;
      config false;
    }
    leaf pmSumAckedBitsCellEulTti2Td {
      description "Total amount of acked data received in kbits after HARQ process. Received data is on MAC-e/MAC-i level for all TD-scheduled users in a cell. Note that k = 1000..";
      type uint64;
      config false;
    }
    leaf pmNoUlUuLoadLimitEul {
      description "Counter for the number of times a scheduling decision is taken to increase the Uu rate of an E-DCH user and there is a need to decrease the Uu rate for another E-DCH user owing to UL Uu load limitations..";
      type uint64;
      config false;
    }
    leaf-list pmEdchThpGlim {
      description "Number of times that throughput for grant limited EUL users was in range during ROP. In case of PSI or combined cell configuration, E-DCH users can belong to several sector carriers. If so, user is counted in each of these sector carriers(cell portion level). Bins: [0]: Number of samples in range [0] kbps [1]: Number of samples in range ]0..25[ kbps [2]: Number of samples in range [25..50[ kbps [3]: Number of samples in range [50..100[ kbps [4]: Number of samples in range [100..200[ kbps ... [12]: Number of samples in range [900..1000[ kbps [13]: Number of samples in range [1000..1200[ kbps [14]: Number of samples in range [1200..1400[ kbps ... [17]: Number of samples in range [1800..2000[ kbps [18]: Number of samples in range [2000..2500[ kbps [19]: Number of samples in range [2500..3000[ kbps ... [23]: Number of samples in range [4500..5000[ kbps [24]: Number of samples in range [5000..6000[ kbps [25]: Number of samples in range [6000..7000[ kbps [26]: Number of samples in range [7000..8000[ kbps [27]: Number of samples in range [8000..9000[ kbps [28]: Number of samples in range [9000..10000[ kbps [29]: Number of samples in range [10000..11000[ kbps [30]: Number of samples in range [11000..12000[ kbps [31]: Number of samples greater than or equal to 12000 kbps.";
      type uint32;
      max-elements 32;
    }
    leaf pmNoActive2msIntervalsEulNonGlim {
      description "The total amount of 2ms intervals in a cell in which the transmission of one or more E-DCH frames are detected for non-grant-limited users. In case of PSI or combined cell configuration, E-DCH users can belong to several sector carriers. If so, user is counted in each of these sector carriers(cell portion level)..";
      type uint32;
      config false;
    }
    leaf pmNoActive2msIntervalsEulTti2 {
      description "Counter for the total amount of 2 ms intervals in a cell in which the transmission of one or more E-DCH frames has been detected, excluding frames that are not decoded due to lack of hardware to decode the frame. An E-DCH user may belong to several cells or sector carriers at the same time. If so is the case the user will be counted in each of these cells or sector carriers..";
      type uint64;
      config false;
    }
    leaf-list pmBurstLengthEulFach {
      description "Total number of bits acked (MAC level) in an EUL FACH access. This counter only applies to DCCH/DTCH transmissions and not to CCCH transmissions. Bins: [0]: [1..500[ bits [1]: [500..1000[ bits [2]: [1000..1500[ bits ... [30]: [15000-15500[ bits [31]: >= 15500 bits.";
      type uint64;
      max-elements 32;
    }
    leaf pmSumAckedBitsCellEulGlim {
      description "Total received acked data in a cell for grant-limited 2ms and 10ms TTI users in the following conditions: - after HARQ process on MAC-e/MAC-i level - grant-limited user existed in a sampling interval (100 ms by default) Given in kbits. In case of PSI or combined cell configuration, E-DCH users can belong to several sector carriers. If so, user is counted in each of these sector carriers(cell portion level)..";
      type uint64;
      config false;
    }
    leaf pmSumAckedBitsCellEulFach {
      description "Counter for the total amount of acked data received after HARQ process on MAC-i level for all EUL FACH 10 ms TTI users in a cell. Unit 1 kilobit..";
      type uint64;
      config false;
    }
    leaf-list pmLCEdch {
      description "The C-EDCH Uu load estimate in a cell. Includes component from E-DPDCH, E-DPCCH and DPCCH for EUL FACH users in the cell, but not that from the HS-DPCCH. The sampled value is a load factor and is unitless with range 0..1, where 0 means no load and 1 is infinite load. Bins: [0]: Number of samples in range [0..0.02[ [1]: Number of samples in range [0.02..0.04[ ... [49]: Number of samples in range [0.98..1].";
      type uint64;
      max-elements 50;
    }
    leaf pmNoActive10msIntervalsEulTti10 {
      description "Counter for the total amount of 10 ms intervals in a cell in which the transmission of one or more E-DCH frames has been detected, excluding frames that are not decoded due to lack of hardware to decode the frame. An E-DCH user may belong to several cells or sector carriers at the same time. If so is the case the user will be counted in each of these cells or sector carriers..";
      type uint64;
      config false;
    }
    leaf-list pmOwnUuLoad {
      description "Counter per cell for the power-controlled noise rise caused by the intra-cell interference that affects the Uu load. Bins: [0]: Number of samples in range [0..0.2[ dB [1]: Number of samples in range [0.2..0.4[ dB ... [49]: Number of samples in range [9.8..10[ dB [50]: Number of samples greater than or equal to 10 dB.";
      type uint64;
      max-elements 51;
    }
    leaf-list pmEdchThpAppLim {
      description "Number of times that throughput for low utilization EUL users was in range during ROP. In case of PSI or combined cell configuration, E-DCH users can belong to several sector carriers. If so, user is counted in each of these sector carriers(cell portion level). Bins: [0]: Number of samples in range [0] kbps [1]: Number of samples in range ]0..25[ kbps [2]: Number of samples in range [25..50[ kbps [3]: Number of samples in range [50..100[ kbps [4]: Number of samples in range [100..200[ kbps ... [12]: Number of samples in range [900..1000[ kbps [13]: Number of samples in range [1000..1200[ kbps [14]: Number of samples in range [1200..1400[ kbps ... [17]: Number of samples in range [1800..2000[ kbps [18]: Number of samples in range [2000..2500[ kbps [19]: Number of samples in range [2500..3000[ kbps ... [23]: Number of samples in range [4500..5000[ kbps [24]: Number of samples in range [5000..6000[ kbps [25]: Number of samples in range [6000..7000[ kbps [26]: Number of samples in range [7000..8000[ kbps [27]: Number of samples in range [8000..9000[ kbps [28]: Number of samples in range [9000..10000[ kbps [29]: Number of samples in range [10000..11000[ kbps [30]: Number of samples in range [11000..12000[ kbps [31]: Number of samples greater than or equal to 12000 kbps.";
      type uint32;
      max-elements 32;
    }
    leaf-list pmFirstDecodedFrameEulFach {
      description "Frame number when E-DPDCH data is first correctly decoded. Bins: [0]: Correct data in 1st expected frame [1]: Correct data in 2nd expected frame [2]: Correct data in 3rd expected frame ... [11]: Correct data in 12th expected frame [12]: Correct data after 12th expected frame.";
      type uint64;
      max-elements 13;
    }
    leaf pmSumAckedBitsCellEulNonGlim {
      description "Total received acked data in a cell for non-grant-limited 2ms and 10ms TTI users in the following conditions: - after HARQ process on MAC-e/MAC-i level - non-grant-limited user existed in a sampling interval (100 ms by default) Given in kbits. In case of PSI or combined cell configuration, E-DCH users can belong to several sector carriers. If so, user is counted in each of these sector carriers(cell portion level)..";
      type uint64;
      config false;
    }
    leaf-list pmLEDchTot {
      description "The measured uplink Uu load of a cell that is caused by users configured with an E-DCH. Load contributions from E-DPDCH (both scheduled and not scheduled), E-DPCCH, DPCCH, and DPDCH (if one is configured) are included, but not that from the HS-DPCCH. The sampled value is a load factor and is unitless with range 0..1, where 0 means no load and 1 is maximum possible load. Bins: [0]: Number of samples in range [0..0.02[ [1]: Number of samples in range [0.02..0.04[ ... [48]: Number of samples in range [0.96..0.98[ [49]: Number of samples in range [0.98..1].";
      type uint64;
      max-elements 50;
    }
    leaf pmNoActive10msFramesEulFach {
      description "Indicated the number of used 10ms frames (TTI) in which data is received in C-EDCH for all EUL-FACH users..";
      type uint64;
      config false;
    }
    leaf pmSumNackedBitsCellEulTti2Td {
      description "Total amount of nacked data received in kbits after HARQ process. Received data is on MAC-e/MAC-i level for all TD-scheduled users in a cell. Excludes data that is NACKed due to lack of hardware to decode the frame. Note that k = 1000..";
      type uint64;
      config false;
    }
    leaf-list pmNoUsersCEdchEul {
      description "Number of simultaneous EUL FACH users. Increased bin is the number of simultaneous C-EDCH resources being allocated in the carrier at that moment. The pmNoUsersCEdchEul counter will be updated in the carrier with best signal in pre-amble detection, if the corresponding carrier is part of a cell using more than one carrier. Bins: [0]: No resources in use [1]: 1 resource in use ... [32]: 32 resources in use.";
      type uint64;
      max-elements 33;
    }
    leaf pmNoActive2msIntervalsEulGlim {
      description "The total amount of 2ms intervals in a cell in which the transmission of one or more E-DCH frames are detected for grant limited users. In case of PSI or combined cell configuration, E-DCH users can belong to several sector carriers. If so, user is counted in each of these sector carriers(cell portion level)..";
      type uint32;
      config false;
    }
    leaf pmSamplesCapacityServEDchUsers {
      description "Number of samples in pmSumCapacityServEDchUsers. pmSamplesCapacityServEDchUsers = pmSamplesCapacityServEDchUsers + 1, whenever pmSumCapacityServEDchUsers is updated. If the corresponding carrier is part of a cell using more than one carrier, its value is undefined. Deprecated: Since 17.Q2. Replaced by EDchResourcesCell::pmSamplesCapacityServEDchUsers.; MOM flags: noNotification.";
      type uint64;
      config false;
      status deprecated;
    }
    leaf pmSumCapacityServEDchUsers {
      description "Sum of sample values recorded during ROP for number of Serving E-DCH users. If the corresponding carrier is part of a cell using more than one carrier, its value is undefined. Deprecated: Since 17.Q2. Replaced by EDchResourcesCell::pmSumCapacityServEDchUsers.; MOM flags: noNotification.";
      type uint64;
      config false;
      status deprecated;
    }
    leaf pmSumNackedBitsCellEulTti10 {
      description "Counter for the total amount of nacked data received in kbits after HARQ process on MAC-e/MAC-i level for all 10 ms TTI users in a cell, excluding data that is NACKed due to lack of hardware to decode the frame. Note that k = 1000. An E-DCH user may belong to several cells or sector carriers (in case of a cell using more than one carrier) at the same time. If so is the case the user will be counted in each of these cells or sector carriers (in case of a cell using more than one carrier)..";
      type uint64;
      config false;
    }
    leaf-list pmLOther {
      description "The estimated distribution of the Uplink load caused by inter-cell and external interferers. The sampled value is a load factor and is unitless with range 0..1, where 0 means no load and 1 is maximum possible load. Bins: [0]: Number of samples in range [0..0.02[ [1]: Number of samples in range [0.02..0.04[ ... [48]: Number of samples in range [0.96..0.98[ [49]: Number of samples in range [0.98..1].";
      type uint64;
      max-elements 50;
    }
    leaf-list pmCommonChPowerEul {
      description "Total DL power used for the E-AGCH, E-RGCH and E-HICH in the cell. If the corresponding carrier is part of a cell using more than one carrier, all values are undefined. Bins: [0]: Number of samples in range [0..1[ dBm [1]: Number of samples in range [1..2[ dBm ... [39]: Number of samples in range [39..40[ dBm [40]: Number of samples greater than or equal to 40 dBm. Deprecated: Since 17.Q2. Replaced by EDchResourcesCell::pmCommonChPowerEul.; MOM flags: noNotification.";
      type uint16;
      max-elements 41;
    }
    leaf-list pmNoSchEdchEul {
      description "The total number of simultaneous scheduled E-DCH users having a rate greater than 0 kbits/s. Bins: [0]: Number of samples in range [0..1[ E-DCH user [1]: Number of samples in range [1..2[ E-DCH users ... [9]: Number of samples in range [9..10[ E-DCH users [10]: Number of samples in range [10..15[ E-DCH users [11]: Number of samples in range [15..20[ E-DCH users [12]: Number of samples in range [20..25[ E-DCH users [13]: Number of samples in range [25..30[ E-DCH users [14]: Number of samples in range [30..40[ E-DCH users [15]: Number of samples in range [40..50[ E-DCH users ... [19]: Number of samples in range [80..90[ E-DCH users [20]: Number of samples greater than or equal to 90 E-DCH users.";
      type uint64;
      max-elements 21;
    }
    leaf-list pmWaitingTimeEul {
      description "The waiting time for an E-DCH user from when a rate increase request is received when the scheduled grant = 0 to when a scheduled grant greater than 0 is sent to the UE with an absolute grant. Bins: [0]: Number of samples in range [0..10[ ms [1]: Number of samples in range [10..20[ ms ... [9]: Number of samples in range [90..100[ ms [10]: Number of samples in range [100..200[ ms ... [18]: Number of samples in range [900..1000[ ms [19]: Number of samples in range [1000..2000[ ms ... [27]: Number of samples in range [9000..10 000[ ms [28]: Number of samples greater than or equal to 10 000 ms.";
      type uint64;
      max-elements 29;
    }
    leaf pmSumAckedBitsCellEulTti2 {
      description "Counter for the total amount of acked data received in kbits after HARQ process on MAC-e/MAC-i level for all 2 ms TTI users in a cell. Note that k = 1000. An E-DCH user may belong to several cells or sector carriers (in case of a cell using more than one carrier) at the same time. If so is the case the user will be counted in each of these cells or sector carriers (in case of a cell using more than one carrier)..";
      type uint64;
      config false;
    }
    leaf pmNoActive2msIntervalsEul {
      description "Counter for the total amount of 2 ms intervals in a cell in which the transmission of one or more E-DCH frames has been detected, excluding frames that are not decoded due to lack of hardware to decode the frame. An E-DCH user may belong to several cells or sector carriers at the same time. If so is the case the user will be counted in each of these cells or sector carriers..";
      type uint64;
      config false;
    }
    leaf-list pmTotRateGrantedEul {
      description "Total granted Uu rate. Counter for the total granted Uu rate for all E-DCH users including soft/softer handover by the scheduler per cell. Bins: [0]: Number of samples in range [0..100[ kbits/s [1]: Number of samples in range [100..200[ kbits/s ... [59]: Number of samples in range [5900..6000[ kbits/s [60]: Number of samples greater than or equal to 6000 kbits/s.";
      type uint64;
      max-elements 61;
    }
    leaf-list pmEdchThpNonGlim {
      description "Number of times that throughput for non-grant limited EUL users was in range during ROP. In case of PSI or combined cell configuration, E-DCH users can belong to several sector carriers. If so, user is counted in each of these sector carriers(cell portion level). Bins: [0]: Number of samples in range [0] kbps [1]: Number of samples in range ]0..25[ kbps [2]: Number of samples in range [25..50[ kbps [3]: Number of samples in range [50..100[ kbps [4]: Number of samples in range [100..200[ kbps ... [12]: Number of samples in range [900..1000[ kbps [13]: Number of samples in range [1000..1200[ kbps [14]: Number of samples in range [1200..1400[ kbps ... [17]: Number of samples in range [1800..2000[ kbps [18]: Number of samples in range [2000..2500[ kbps [19]: Number of samples in range [2500..3000[ kbps ... [23]: Number of samples in range [4500..5000[ kbps [24]: Number of samples in range [5000..6000[ kbps [25]: Number of samples in range [6000..7000[ kbps [26]: Number of samples in range [7000..8000[ kbps [27]: Number of samples in range [8000..9000[ kbps [28]: Number of samples in range [9000..10000[ kbps [29]: Number of samples in range [10000..11000[ kbps [30]: Number of samples in range [11000..12000[ kbps [31]: Number of samples greater than or equal to 12000 kbps.";
      type uint32;
      max-elements 32;
    }
    leaf pmNoActive10msIntervalsEulFach {
      description "Counter for the total amount of 10 ms intervals in a cell in which the transmission of one or more E-DCH frames has been detected for EUL FACH users..";
      type uint64;
      config false;
    }
    leaf pmNoActive10msFramesEul {
      description "Sum of used 10 ms frames (TTI) that receive E-DCH data in a cell during a granularity period for all E-DCH users, excluding frames that are not decoded due to lack of hardware. An E-DCH user may belong to several cells or sector carriers (in case of a cell using more than one carrier) at the same time. If so is the case the user will be counted in each of these cells or sector carriers (in case of a cell using more than one carrier)..";
      type uint64;
      config false;
    }
    leaf-list pmCEdchReleaseCause {
      description "The C-EDCH release cause. Bins: [0]: UL Synch never achieved (post verification procedure failed, timer expired). Note that this counter has 2 contributions that cannot be distinguished, that is, unsuccessful accesses and false preamble detections. [1]: UL Synch Achieved but no data could be decoded. [2]: SI(TEBS=0) received for CCCH. [3]: SI(TEBS=0) received for DCCH/DTCH. [4]: CCCH timeout. [5]: DTCH/DCCH timeout (AG=INACTIVE sent). [6]: RL failure. [7]: Up-switch attempt. [8]: Up-switch timeout..";
      type uint64;
      max-elements 9;
    }
    leaf pmSumNackedBitsCellEulTti2 {
      description "Counter for the total amount of nacked data received in kbits after HARQ process on MAC-e/MAC-i level for all 2 ms TTI users in a cell, excluding data that is NACKed due to lack of hardware to decode the frame. Note that k = 1000. Note also that this counter also includes kbits for TD Scheduled users. An E-DCH user may belong to several cells or sector carriers (in case of a cell using more than one carrier) at the same time. If so is the case the user will be counted in each of these cells or sector carriers (in case of a cell using more than one carrier)..";
      type uint64;
      config false;
    }
    leaf pmCapacityAllocRejServEDchUsers {
      description "Number of rejected attempts to allocate resources for new Serving E-DCH user (related to pmCapacityLimitServEDchUser). If the corresponding carrier is part of a cell using more than one carrier, its value is undefined. Deprecated: Since 17.Q2. Replaced by EDchResourcesCell::pmCapacityAllocRejServEDchUsers.; MOM flags: noNotification.";
      type uint64;
      config false;
      status deprecated;
    }
    leaf-list pmNoSchEdchEulTd {
      description "Total number of simultaneous TD scheduled E-DCH users in a cell during a granularity period. Bins: [0]: Number of samples where there is no TD-scheduled user. [1]: Number of samples where there is only one user TD-scheduled. User can use all-HARQ-process grant because no other user shares TD schedule, or it can use one or more HARQ-process grants after other TD users removed. [2]: Number of samples where there are two TD users in TD Schedule, each with one or more HARQ-process grants. [3]: Number of samples where there are three TD users in TD Schedule, each with one or more HARQ-process grants. ... [8]: Number of samples where there are eight TD users in TD Schedule, each with one or more HARQ-process grants..";
      type uint64;
      max-elements 9;
    }
    leaf pmEulFachHarqTransmFailure {
      description "Number of HARQ failures for EUL FACH traffic..";
      type uint64;
      config false;
    }
    leaf pmCapacityLimitServEDchUsers {
      description "Licensed limit for number of Serving E-DCH users in the cell. License key value if valid license key, else default value of NodeBLocalCell::maxNumEulUsers if invalid/missing license key, else max value of NodeBLocalCell::maxNumEulUsers if emergency unlock is active. If the corresponding carrier is part of a cell using more than one carrier, its value is undefined. Deprecated: Since 17.Q2. Replaced by EDchResourcesCell::pmCapacityLimitServEDchUsers.; MOM flags: noNotification.";
      type int64;
      config false;
      status deprecated;
    }
    leaf-list pmNoiseFloorHighRes {
      description "The distribution of estimated thermal noise level. The estimated thermal noise level is used in Rise over Thermal (RoT) calculations when NodeBSectorCarrier::eulNoiseFloorLock is not set. It is limited to be at least -110 dBm. Bins: [0]: Number of samples less than -110.0 dBm [1]: Number of samples in range [-110.0..-109.75[ dBm [2]: Number of samples in range [-109.75..-109.5[ dBm ... [200]: Number of samples in range [-60.25..-60[ dBm [201]: Number of samples greater than or equal to -60 dBm.";
      type uint64;
      max-elements 202;
    }
    leaf-list pmEulFachHarqTransm {
      description "Number of HARQ transmissions attempted until correct reception. Bins: [0]: E-TFCI acked at first transmission [1]: E-TFCI acked after 1 re-transmission [2]: E-TFCI acked after 2 re-transmissions [3]: E-TFCI acked after 3 or more re-transmissions.";
      type uint64;
      max-elements 4;
    }
    leaf-list pmLMaxEDch {
      description "The total uplink Uu load headroom for a cell available to users configured with an E-DCH. The system aims to secure that total load from E-DCH users for this cell (see pmLEDchTot for a description) does not exceed the total uplink Uu load headroom. The sampled value is a load factor and is unitless with range 0..1, where 0 means no load and 1 is maximum possible load. Bins: [0]: Number of samples in range [0..0.02[ [1]: Number of samples in range [0.02..0.04[ ... [48]: Number of samples in range [0.96..0.98[ [49]: Number of samples in range [0.98..1].";
      type uint64;
      max-elements 50;
    }
  }
  grouping EDchResourcesCell-attributes {
    leaf eDchResourcesCellId {
      description "The value component of the RDN..";
      type string;
      mandatory true;
    }
    leaf pmAllocRejEdchRlEul {
      description "Number of rejected attempts to allocate E-DCH radio links in EUL scheduler. Includes number of removed E-DCH radio links due EUL user setup, when limit is reached of total number of E-DCH radio links in baseband pool..";
      type uint64;
      config false;
    }
    leaf-list pmCapacityOfServEDchUsers {
      description "Distribution of number of Serving E-DCH users, as percentages of licensed limit visible in pmCapacityLimitServEDchUsers. Bins: [0]: Number of sampled values in range [0..20[ % [1]: Number of sampled values in range [20..40[ % [2]: Number of sampled values in range [40..50[ % [3]: Number of sampled values in range [50..60[ % [4]: Number of sampled values in range [60..70[ % [5]: Number of sampled values in range [70..80[ % [6]: Number of sampled values in range [80..85[ % [7]: Number of sampled values in range [85..90[ % [8]: Number of sampled values in range [90..95[ % [9]: Number of sampled values >= 95%.";
      type uint64;
      max-elements 10;
    }
    leaf-list pmCommonChPowerEul {
      description "Total DL power used for the E-AGCH, E-RGCH and E-HICH in the cell. Bins: [0]: Number of samples in range [0..1[ dBm [1]: Number of samples in range [1..2[ dBm ... [39]: Number of samples in range [39..40[ dBm [40]: Number of samples greater than or equal to 40 dBm.";
      type uint16;
      max-elements 41;
    }
    leaf pmCapacityAllocRejServEDchUsers {
      description "Number of rejected attempts to allocate resources for new Serving E-DCH user (related to pmCapacityLimitServEDchUser)..";
      type uint64;
      config false;
    }
    leaf pmCapacityAllocAttServEDchUsers {
      description "Number of attempts to allocate resources for new Serving E-DCH user. If the corresponding carrier is part of a cell using more than one carrier, its value is undefined.";
      type uint64;
      config false;
    }
    leaf pmSamplesCapacityServEDchUsers {
      description "Number of samples in pmSumCapacityServEDchUsers. pmSamplesCapacityServEDchUsers = pmSamplesCapacityServEDchUsers + 1, whenever pmSumCapacityServEDchUsers is updated..";
      type uint64;
      config false;
    }
    leaf pmCapacityLimitServEDchUsers {
      description "Licensed limit for number of Serving E-DCH users in the cell. License key value if valid license key, else default value of NodeBLocalCell::maxNumEulUsers if invalid/missing license key, else max value of NodeBLocalCell::maxNumEulUsers if emergency unlock is active..";
      type int64;
      config false;
    }
    leaf pmSumCapacityServEDchUsers {
      description "Sum of sample values recorded during ROP for number of Serving E-DCH users..";
      type uint64;
      config false;
    }
  }
  grouping HsDschResources-attributes {
    leaf hsDschResourcesId {
      description "The value component of the RDN..";
      type string;
      mandatory true;
    }
    leaf-list availabilityStatus {
      description "The availability status. It contains details about operationalState..";
      type AvailStatus;
      min-elements 0;
    }
    leaf operationalState {
      description "Defines the operational state..";
      type enumeration {
        enum DISABLED;
        enum ENABLED;
      }
      config false;
    }
    leaf maxAvailMixedModeExtraPower {
      description "Maximum value of available extra power borrowed from other RAT(s). Undefined value: -1 Unit: 0.1 W.";
      type int32;
      config false;
    }
    leaf pmSumNonEmptyUserBuffersPqSpi15 {
      description "Number of PQs with data in the buffer for each 2 ms subframe. Only PQs with scheduling priority class 15 and belonging to UEs units configured to use cell as serving HS-DSCH cell are considered. The counter reflects the PQ perspective..";
      type uint32;
      config false;
    }
    leaf pmSumAckedBits3McPqSpi11 {
      description "Total amount of acknowledged MAC-hs/ehs data to UEs using any cell as serving HS-DSCH cell in 3MC mode. Only acknowledged data originating from a PQ with scheduling priority class 11 is considered. The counter reflects the PQ perspective. Unit: 1 kilobit..";
      type uint32;
      config false;
    }
    leaf-list pmDelayDistributionSpi00 {
      description "Measurement to observe the distribution of the scheduling delay for scheduling priority class 00 on each subframe on those priority queue(s) selected for transmission. Bins: [0]: Number of delays in [0..10[ % [1]: Number of delays in [10..20[ % ... [9]: Number of delays in [90..100[ % [10]: Number of delays greater than or equal to 100%.";
      type uint32;
      max-elements 11;
    }
    leaf pmSumAckedBitsSpi14 {
      description "Total amount of acknowledged data sent on MAC-hs level per scheduling priority class 14. The counter does not consider whether or not the transmitted data originates from an MC-PQ. The counter reflects the cell perspective. Unit: 1 kilobit..";
      type uint32;
      config false;
    }
    leaf-list pmDelayDistributionSpi07 {
      description "Measurement to observe the distribution of the scheduling delay for scheduling priority class 07 on each subframe on those priority queue(s) selected for transmission. Bins: [0]: Number of delays in [0..10[ % [1]: Number of delays in [10..20[ % ... [9]: Number of delays in [90..100[ % [10]: Number of delays greater than or equal to 100%.";
      type uint32;
      max-elements 11;
    }
    leaf-list pmTransmittedCarrierPowerWNonHs {
      description "The transmitted carrier power for all non high-speed codes in the cell, as a percentage of the maximum power (indicated by the counter NodeBLocalCell::pmTransmittedCarrierPowerWLimit). Bins: [0]: Number of sampled values in range [0..2[ % [1]: Number of sampled values in range [2..4[ % [2]: Number of sampled values in range [4..6[ % ... [49]: Number of sampled values in range [98..100] %.";
      type uint64;
      max-elements 50;
    }
    leaf pmNackReceived {
      description "Number of occasions when NACK is received, not counting repetitions of NACK transmissions. The counter does not consider whether or not the transmitted data originates from an MC-PQ. The counter does not consider ACK/NACKs corresponding to HS-SCCH orders. The counter reflects the cell perspective..";
      type uint32;
      config false;
    }
    leaf pmSumTransmittedBitsSpi01 {
      description "Measurement to observe the total amount of data, in kbits, sent on MAC-hs level per scheduling priority class 01. The counter does not consider whether or not the transmitted data originates from an MC-PQ. The counter reflects the cell perspective..";
      type uint32;
      config false;
    }
    leaf-list pmSamplesSumAckedBitsRlim {
      description "Distribution states how many sample values pmSumAckedBitsRlim is incremented. Ranges: [0] : Number of increments of pmSumAckedBitsRlim[0] [1] : Number of increments of pmSumAckedBitsRlim[1] ... [30] : Number of increments of pmSumAckedBitsRlim[30].";
      type uint16;
      max-elements 31;
    }
    leaf pmSumNoOfUsersSpi02 {
      description "Counts the total number of users for scheduling priority class 02 selected for each 2 ms subframe that is transmitted in the cell. For an MC-PQ only the counter in the serving HS-DSCH cell (of the UE to which the MC-PQ belongs) is updated. However, the aggregated measurement, based on all cells where the MC-PQ may be served, is considered when that counter is updated. The counter reflects the PQ perspective..";
      type uint32;
      config false;
    }
    leaf pmSumAckedBitsMcPqSpi08 {
      description "Total amount of acknowledged MAC-hs/ehs data to UEs using any cell as serving HS-DSCH cell in MC mode. Only acknowledged data originating from a PQ with scheduling priority class 08 is considered. The counter reflects the PQ perspective. Unit: 1 kilobit..";
      type uint32;
      config false;
    }
    leaf pmAqmBasedDiscardSpi15 {
      description "Number of discards performed by the AQM feature for all Priority Queues (PQs) for Scheduling Priority Indicator (SPI) 15..";
      type uint32;
      config false;
    }
    leaf-list pmDelayDistributionSpi11 {
      description "Measurement to observe the distribution of the scheduling delay for scheduling priority class 11 on each subframe on those priority queue(s) selected for transmission. Bins: [0]: Number of delays in [0..10[ % [1]: Number of delays in [10..20[ % ... [9]: Number of delays in [90..100[ % [10]: Number of delays greater than or equal to 100%.";
      type uint32;
      max-elements 11;
    }
    leaf-list pmSumTransmissions {
      description "Distribution over CQI, of total number of transmissions to UE units configured to use cell, including retransmissions, on MAC-hs or MAC-ehs level until acknowledgement is received. CQI value used to index distribution is one reported by UE units and applicable during initial transmission. For non-64QAM-capable UE units, CQI value is mapped down to align with CQI reporting for 64QAM-capable UE units, as further described for PDF range 26...30. Ranges: [0] : Number of transmissions for reported CQI=0 at initial transmission [1] : Number of transmissions for reported CQI=1 at initial transmission ... [25] : Number of transmissions for reported CQI=25 at initial transmission [26] : Number of transmissions for reported CQI=26 for 64QAM-capable UE units, or reported CQI=26 and 27 for non-64QAM-capable UE units, at initial transmission [27] : Number of transmissions for reported CQI=27 for 64QAM-capable UE units, or reported CQI=28 and 29 for non-64QAM-capable UE units, at initial transmission [28] : Number of transmissions for reported CQI=28 for 64QAM-capable UE units, or reported CQI=30 for non-64QAM-capable UE units, at initial transmission [29] : Number of transmissions for reported CQI=29 at initial transmission for 64QAM-capable UE units (not used for non-64QAM-capable UE units) [30] : Number of transmissions for reported CQI=30 at initial transmission for 64QAM-capable UE units (not used for non-64QAM-capable UE units).";
      type uint16;
      max-elements 31;
    }
    leaf-list pmDelayDistributionSpi08 {
      description "Measurement to observe the distribution of the scheduling delay for scheduling priority class 08 on each subframe on those priority queue(s) selected for transmission. Bins: [0]: Number of delays in [0..10[ % [1]: Number of delays in [10..20[ % ... [9]: Number of delays in [90..100[ % [10]: Number of delays greater than or equal to 100%.";
      type uint32;
      max-elements 11;
    }
    leaf pmAqmBasedDiscardSpi10 {
      description "Number of discards performed by the AQM feature for all Priority Queues (PQs) for Scheduling Priority Indicator (SPI) 10..";
      type uint32;
      config false;
    }
    leaf pmSumNonEmptyUserBuffers3McPqSpi03 {
      description "Number of PQs with data in the buffer for each 2 ms subframe. Only PQs with scheduling priority class 03 and belonging to UEs units configured to use cell as serving HS-DSCH cell in 3MC mode are considered. The counter reflects the PQ perspective..";
      type uint32;
      config false;
    }
    leaf pmSumAckedBitsSpi08 {
      description "Total amount of acknowledged data sent on MAC-hs level per scheduling priority class 08. The counter does not consider whether or not the transmitted data originates from an MC-PQ. The counter reflects the cell perspective. Unit: 1 kilobit..";
      type uint32;
      config false;
    }
    leaf pmSumTransmittedBitsSpi13 {
      description "Measurement to observe the total amount of data, in kbits, sent on MAC-hs level per scheduling priority class 13. The counter does not consider whether or not the transmitted data originates from an MC-PQ. The counter reflects the cell perspective..";
      type uint32;
      config false;
    }
    leaf pmSumNonEmptyUserBuffersMcPqSpi04 {
      description "Number of PQs with data in the buffer for each 2 ms subframe. Only PQs with scheduling priority class 04 and belonging to UEs units configured to use cell as serving HS-DSCH cell in MC mode are considered. The counter reflects the PQ perspective..";
      type uint32;
      config false;
    }
    leaf pmNoActiveSubFramesSpi09 {
      description "Sum of active 2 ms subframes for scheduling priority class 09..";
      type uint32;
      config false;
    }
    leaf pmAvailableMixedModeExtraPowerLimit {
      description "Indicates the maximum value of available extra power borrowed from other RAT(s) Unit: 0.1 W.";
      type int32;
      config false;
    }
    leaf pmSumAckedBits3McPqSpi14 {
      description "Total amount of acknowledged MAC-hs/ehs data to UEs using any cell as serving HS-DSCH cell in 3MC mode. Only acknowledged data originating from a PQ with scheduling priority class 14 is considered. The counter reflects the PQ perspective. Unit: 1 kilobit..";
      type uint32;
      config false;
    }
    leaf pmSumCapacityHsPdschCodes {
      description "Aggregation of all sample values within the ROP for number of available HS-PDSCH codes..";
      type uint64;
      config false;
    }
    leaf pmNoActiveSubFramesSpi08 {
      description "Sum of active 2 ms subframes for scheduling priority class 08..";
      type uint32;
      config false;
    }
    leaf pmNoActiveSubFramesSpi06 {
      description "Sum of active 2 ms subframes for scheduling priority class 06..";
      type uint32;
      config false;
    }
    leaf pmSum3McPriUes {
      description "Number of UEs configured to use cell as primary serving HS-DSCH cell in 3 MC mode. Consequently, only UEs in 3 MC mode are considered by the counter. The counter is the aggregate of sample values taken every 100 ms. The counter reflects the cell perspective..";
      type uint32;
      config false;
    }
    leaf pmSumNonEmptyUserBuffersSpi09 {
      description "Number of user buffers for scheduling priority class 09 with data in buffer for each 2 ms subframes. The counter reflects the cell perspective..";
      type uint32;
      config false;
    }
    leaf pmAqmBasedDiscardSpi04 {
      description "Number of discards performed by the AQM feature for all Priority Queues (PQs) for Scheduling Priority Indicator (SPI) 04..";
      type uint32;
      config false;
    }
    leaf-list pmAckQpsk {
      description "Number of received ACKs for a specified transport block size (TBS) with QPSK. The number of successful HARQ transmissions are counted on the MAC-hs layer. The counter does not consider whether or not the transmitted data originates from an MC-PQ. The counter does not consider ACK/NACKs corresponding to HS-SCCH orders. The counter reflects the cell perspective. Bins: [0]: Number of ACKs for transport block with size [0..1000[ bits [1]: Number of ACKs for transport block with size [1000..2000[ bits [2]: Number of ACKs for transport block with size [2000..3000[ bits ... [28]: Number of ACKs for transport block with size [28000..29000[ bits [29]: Number of ACKs for transport block with size [29000..30000[ bits.";
      type uint32;
      max-elements 30;
    }
    leaf pmSumCapacityHsDschUsers {
      description "Aggregate of all sample values (measurement_value) recorded within the granularity period for number of HS-DSCH users..";
      type uint64;
      config false;
    }
    leaf pmNoInactiveRequiredSubFramesSpi03 {
      description "Number of subframes in which no data with scheduling priority class 03 is transmitted although there is user data to be sent in the validated PQ. This user data is either waiting for first transmission, or data waiting for transmission (NACK is received or no ACK/NACK). If a subframe goes without scheduling priority class 03, that is, just carrying other scheduling priority classes or going totally empty, then the counter is stepped. If the buffer of an MC-PQ is emptied, due to prior scheduling in another cell in the same subframe, and no other buffer in the cell contains data the counter is not incremented. The counter reflects the cell perspective..";
      type uint16;
      config false;
    }
    leaf pmSumNonEmptyUserBuffers3McPqSpi01 {
      description "Number of PQs with data in the buffer for each 2 ms subframe. Only PQs with scheduling priority class 01 and belonging to UEs units configured to use cell as serving HS-DSCH cell in 3MC mode are considered. The counter reflects the PQ perspective..";
      type uint32;
      config false;
    }
    leaf pmSumAckedBitsMcPqSpi10 {
      description "Total amount of acknowledged MAC-hs/ehs data to UEs using any cell as serving HS-DSCH cell in MC mode. Only acknowledged data originating from a PQ with scheduling priority class 10 is considered. The counter reflects the PQ perspective. Unit: 1 kilobit..";
      type uint32;
      config false;
    }
    leaf pmSumNonEmptyUserBuffersPqSpi12 {
      description "Number of PQs with data in the buffer for each 2 ms subframe. Only PQs with scheduling priority class 12 and belonging to UEs units configured to use cell as serving HS-DSCH cell are considered. The counter reflects the PQ perspective..";
      type uint32;
      config false;
    }
    leaf pmSumNoOfUsersSpi09 {
      description "Counts the total number of users for scheduling priority class 09 selected for each 2 ms subframe that is transmitted in the cell. For an MC-PQ only the counter in the serving HS-DSCH cell (of the UE to which the MC-PQ belongs) is updated. However, the aggregated measurement, based on all cells where the MC-PQ may be served, is considered when that counter is updated. The counter reflects the PQ perspective..";
      type uint32;
      config false;
    }
    leaf pmSumAckedBitsMcPqSpi12 {
      description "Total amount of acknowledged MAC-hs/ehs data to UEs using any cell as serving HS-DSCH cell in MC mode. Only acknowledged data originating from a PQ with scheduling priority class 12 is considered. The counter reflects the PQ perspective. Unit: 1 kilobit..";
      type uint32;
      config false;
    }
    leaf pmSumNonEmptyUserBuffers {
      description "Number of user buffers with data in the buffer for each 2 ms subframe..";
      type uint32;
      config false;
    }
    leaf pmSumDelaySpi07 {
      description "Sum of delay of transmitted data before it is scheduled for scheduling priority class 07. Counter unit: 1 ms..";
      type uint32;
      config false;
    }
    leaf pmSumNonEmptyUserBuffersPqSpi11 {
      description "Number of PQs with data in the buffer for each 2 ms subframe. Only PQs with scheduling priority class 11 and belonging to UEs units configured to use cell as serving HS-DSCH cell are considered. The counter reflects the PQ perspective..";
      type uint32;
      config false;
    }
    leaf pmSumNonEmptyUserBuffers3McPqSpi08 {
      description "Number of PQs with data in the buffer for each 2 ms subframe. Only PQs with scheduling priority class 08 and belonging to UEs units configured to use cell as serving HS-DSCH cell in 3MC mode are considered. The counter reflects the PQ perspective..";
      type uint32;
      config false;
    }
    leaf pmSumAckedBits3McPqSpi08 {
      description "Total amount of acknowledged MAC-hs/ehs data to UEs using any cell as serving HS-DSCH cell in 3MC mode. Only acknowledged data originating from a PQ with scheduling priority class 08 is considered. The counter reflects the PQ perspective. Unit: 1 kilobit..";
      type uint32;
      config false;
    }
    leaf pmSumAckedBits3McPqSpi06 {
      description "Total amount of acknowledged MAC-hs/ehs data to UEs using any cell as serving HS-DSCH cell in 3MC mode. Only acknowledged data originating from a PQ with scheduling priority class 06 is considered. The counter reflects the PQ perspective. Unit: 1 kilobit..";
      type uint32;
      config false;
    }
    leaf pmSumNonEmptyUserBuffersPqSpi05 {
      description "Number of PQs with data in the buffer for each 2 ms subframe. Only PQs with scheduling priority class 05 and belonging to UEs units configured to use cell as serving HS-DSCH cell are considered. The counter reflects the PQ perspective..";
      type uint32;
      config false;
    }
    leaf-list pmReportedCqi64Qam {
      description "The UE reported CQI received for a 64 QAM enabled HS-DSCH. Note that it is the true (unadjusted) CQI that is counted for 64 QAM enabled HS-DSCHs. Bins: [0]: Number of reported CQI with value 0 [1]: Number of reported CQI with value 1 ... [30]: Number of reported CQI with value 30 [31]: Number of reported CQI with invalid value.";
      type uint32;
      max-elements 32;
    }
    leaf pmSumDelaySpi01 {
      description "Sum of delay of transmitted data before it is scheduled for scheduling priority class 01. Counter unit: 1 ms..";
      type uint32;
      config false;
    }
    leaf-list pmSumAckedBits {
      description "Distribution over CQI, of total amount of acknowledged data sent on MAC-hs or MAC-ehs level to UE units configured to use cell. CQI value used to index distribution is one reported by UE units and applicable during initial transmission. For non-64QAM-capable UE units, CQI value is mapped down to align with CQI reporting for 64QAM-capable UE units, as further described for PDF range 26...30. Ranges: [0] : Sum of acknowledged data sent for reported CQI=0 at initial transmission [1] : Sum of acknowledged data sent for reported CQI=1 at initial transmission ... [25] : Sum of acknowledged data sent for reported CQI=25 at initial transmission [26] : Sum of acknowledged data sent for reported CQI=26 for 64QAM-capable UE units, or reported CQI=26 and 27 for non-64QAM-capable UE units, at initial transmission [27] : Sum of acknowledged data sent for reported CQI=27 for 64QAM-capable UE units, or reported CQI=28 and 29 for non-64QAM-capable UE units, at initial transmission [28] : Sum of acknowledged data sent for reported CQI=28 for 64QAM-capable UE units, or reported CQI=30 for non-64QAM-capable UE units, at initial transmission [29] : Sum of acknowledged data sent for reported CQI=29 at initial transmission for 64QAM-capable UE units (not used for non-64QAM-capable UE units) [30] : Sum of acknowledged data sent for reported CQI=30 at initial transmission for 64QAM-capable UE units (not used for non-64QAM-capable UE units).";
      type uint32;
      max-elements 31;
    }
    leaf pmSumNonEmptyUserBuffersMcPqSpi11 {
      description "Number of PQs with data in the buffer for each 2 ms subframe. Only PQs with scheduling priority class 11 and belonging to UEs units configured to use cell as serving HS-DSCH cell in MC mode are considered. The counter reflects the PQ perspective..";
      type uint32;
      config false;
    }
    leaf pmSumNonEmptyUserBuffersSpi15 {
      description "Number of user buffers for scheduling priority class 15 with data in buffer for each 2 ms subframes. The counter reflects the cell perspective..";
      type uint32;
      config false;
    }
    leaf pmSumAckedBitsMcPqSpi03 {
      description "Total amount of acknowledged MAC-hs/ehs data to UEs using any cell as serving HS-DSCH cell in MC mode. Only acknowledged data originating from a PQ with scheduling priority class 03 is considered. The counter reflects the PQ perspective. Unit: 1 kilobit..";
      type uint32;
      config false;
    }
    leaf pmSumNoOfUsersSpi04 {
      description "Counts the total number of users for scheduling priority class 04 selected for each 2 ms subframe that is transmitted in the cell. For an MC-PQ only the counter in the serving HS-DSCH cell (of the UE to which the MC-PQ belongs) is updated. However, the aggregated measurement, based on all cells where the MC-PQ may be served, is considered when that counter is updated. The counter reflects the PQ perspective..";
      type uint32;
      config false;
    }
    leaf-list pmSumAckedBitsUsersRlim {
      description "Distribution over number of multiplexed UE units for each 2ms TTI, of total amount of acknowledged data sent on MAC-hs or MAC-ehs level to UE units configured to use cell, under resource limited conditions. Scheduling decision is defined to be resource-limited if transport block size is limited only by available codes or power, or both. In addition, condition is not fulfilled if any retransmissions or transmissions to UE units configured in MIMO or HS-FACH mode occur among multiplexed UE units. Ranges: [0] : Sum of acknowledged data sent in 2ms TTIs with 2 multiplexed UE units [1] : Sum of acknowledged data sent in 2ms TTIs with 3 multiplexed UE units [2] : Sum of acknowledged data sent in 2ms TTIs with 4 multiplexed UE units.";
      type uint32;
      max-elements 3;
    }
    leaf pmSumAckedBitsMcPqSpi04 {
      description "Total amount of acknowledged MAC-hs/ehs data to UEs using any cell as serving HS-DSCH cell in MC mode. Only acknowledged data originating from a PQ with scheduling priority class 04 is considered. The counter reflects the PQ perspective. Unit: 1 kilobit..";
      type uint32;
      config false;
    }
    leaf pmIubBasedDiscardFrameLossUserSpi09 {
      description "Number of Iub discards on all Priority Queues (PQs), that experienced the frame loss due to Iub congestion, for Scheduling Priority Indicator (SPI) 09..";
      type uint32;
      config false;
    }
    leaf pmCapacityAllocAttHsPdschCodes {
      description "Number of attempts to allocate HS-PDSCH codes. Attempts to allocate HS-DSCH codes can be done in the following cases: - When RNC sets up or releases HS-PDSCH codes. If codes are released by the RNC, they might be allocated by RBS dynamically if dynamic code allocation is active. - Fluctuating R99 traffic with dynamic code allocation active might increase the counter. If increased R99 traffic cause a code collision in the code tree for one cell, then dynamically allocated HS-PDSCH codes are released and used for R99 traffic instead. Later when the R99 traffic is released, then the codes will be dynamically allocated again and thus increase the counter..";
      type uint64;
      config false;
    }
    leaf pmSumNonEmptyUserBuffers3McPqSpi05 {
      description "Number of PQs with data in the buffer for each 2 ms subframe. Only PQs with scheduling priority class 05 and belonging to UEs units configured to use cell as serving HS-DSCH cell in 3MC mode are considered. The counter reflects the PQ perspective..";
      type uint32;
      config false;
    }
    leaf-list pmUsedExtraPowerWHs {
      description "Distribution of total used extra HS power borrowed from other WCDMA cells or other RAT(s) cells. Presented as percentage of maximum power visible in NodeBSectorCarrier::pmTransmittedCarrierPowerWLimit. Bins: [0]: Number of sampled values in range [0..2[ % [1]: Number of sampled values in range [2..4[ % [2]: Number of sampled values in range [4..6[ % ... [49]: Number of sampled values is greater or equal to 98 %.";
      type uint32;
      max-elements 50;
    }
    leaf pmSumNonEmptyUserBuffersMcPqSpi10 {
      description "Number of PQs with data in the buffer for each 2 ms subframe. Only PQs with scheduling priority class 10 and belonging to UEs units configured to use cell as serving HS-DSCH cell in MC mode are considered. The counter reflects the PQ perspective..";
      type uint32;
      config false;
    }
    leaf pmSumNoOfUsersSpi11 {
      description "Counts the total number of users for scheduling priority class 11 selected for each 2 ms subframe that is transmitted in the cell. For an MC-PQ only the counter in the serving HS-DSCH cell (of the UE to which the MC-PQ belongs) is updated. However, the aggregated measurement, based on all cells where the MC-PQ may be served, is considered when that counter is updated. The counter reflects the PQ perspective..";
      type uint32;
      config false;
    }
    leaf-list pmSumOfHsUsedPwrHsFach {
      description "The distribution of transmitted carrier power used for HS-FACH (HS-PDSCH + HS-SCCH). Bins: [0]: Number of samples with values less than 0 dBm or no transmission [1]: Number of samples in range [0..0.5[ dBm [2]: Number of samples in range [0.5..1[ dBm ... [101]: Number of samples in range [50..50.5[ dBm [102]: Number of samples >= 50.5 dBm.";
      type uint16;
      max-elements 103;
    }
    leaf pmSumNonEmptyUserBuffers3McPqSpi14 {
      description "Number of PQs with data in the buffer for each 2 ms subframe. Only PQs with scheduling priority class 14 and belonging to UEs units configured to use cell as serving HS-DSCH cell in 3MC mode are considered. The counter reflects the PQ perspective..";
      type uint32;
      config false;
    }
    leaf-list pmDelayDistributionSpi06 {
      description "Measurement to observe the distribution of the scheduling delay for scheduling priority class 06 on each subframe on those priority queue(s) selected for transmission. Bins: [0]: Number of delays in [0..10[ % [1]: Number of delays in [10..20[ % ... [9]: Number of delays in [90..100[ % [10]: Number of delays greater than or equal to 100%.";
      type uint32;
      max-elements 11;
    }
    leaf pmAqmBasedDiscardSpi13 {
      description "Number of discards performed by the AQM feature for all Priority Queues (PQs) for Scheduling Priority Indicator (SPI) 13..";
      type uint32;
      config false;
    }
    leaf pmNoActiveSubFramesSpi11 {
      description "Sum of active 2 ms subframes for scheduling priority class 11..";
      type uint32;
      config false;
    }
    leaf pmNoActiveSubFramesSpi04 {
      description "Sum of active 2 ms subframes for scheduling priority class 04..";
      type uint32;
      config false;
    }
    leaf pmSumMcPriUes {
      description "Number of UEs configured to use cell as primary serving HS-DSCH cell in MC mode. Consequently, only UEs in MC mode are considered by the counter. The counter is the aggregate of sample values taken every 100 ms. The counter reflects the cell perspective..";
      type uint32;
      config false;
    }
    leaf pmSumNonEmptyUserBuffersPqSpi03 {
      description "Number of PQs with data in the buffer for each 2 ms subframe. Only PQs with scheduling priority class 03 and belonging to UEs units configured to use cell as serving HS-DSCH cell are considered. The counter reflects the PQ perspective..";
      type uint32;
      config false;
    }
    leaf pmNoActiveSubFramesSpi07 {
      description "Sum of active 2 ms subframes for scheduling priority class 07..";
      type uint32;
      config false;
    }
    leaf pmSumNonEmptyUserBuffers3McPqSpi04 {
      description "Number of PQs with data in the buffer for each 2 ms subframe. Only PQs with scheduling priority class 04 and belonging to UEs units configured to use cell as serving HS-DSCH cell in 3MC mode are considered. The counter reflects the PQ perspective..";
      type uint32;
      config false;
    }
    leaf pmIubBasedDiscardFrameLossUserSpi03 {
      description "Number of Iub discards on all Priority Queues (PQs), that experienced the frame loss due to Iub congestion, for Scheduling Priority Indicator (SPI) 03..";
      type uint32;
      config false;
    }
    leaf-list pmUsedExtraMixedModePowerWHs {
      description "Distribution of used extra HS power borrowed from other RAT(s). Presented as percentage of maximum power visible in NodeBSectorCarrier::pmTransmittedCarrierPowerWLimit. Bins: [0]: Number of sampled values in range [0..2[ % [1]: Number of sampled values in range [2..4[ % [2]: Number of sampled values in range [4..6[ % ... [49]: Number of sampled values is greater or equal to 98 %.";
      type uint32;
      max-elements 50;
    }
    leaf pmSumTransmittedBitsSpi11 {
      description "Measurement to observe the total amount of data, in kbits, sent on MAC-hs level per scheduling priority class 11. The counter does not consider whether or not the transmitted data originates from an MC-PQ. The counter reflects the cell perspective..";
      type uint32;
      config false;
    }
    leaf pmSumNonEmptyUserBuffersSpi00 {
      description "Number of user buffers for scheduling priority class 00 with data in buffer for each 2 ms subframes. The counter reflects the cell perspective..";
      type uint32;
      config false;
    }
    leaf pmSumDelaySpi11 {
      description "Sum of delay of transmitted data before it is scheduled for scheduling priority class 11. Counter unit: 1 ms..";
      type uint32;
      config false;
    }
    leaf pmSumNonEmptyUserBuffersMcPqSpi13 {
      description "Number of PQs with data in the buffer for each 2 ms subframe. Only PQs with scheduling priority class 13 and belonging to UEs units configured to use cell as serving HS-DSCH cell in MC mode are considered. The counter reflects the PQ perspective..";
      type uint32;
      config false;
    }
    leaf pmSumBlockedTransmissions {
      description "Counts number of 2ms TTIs where UE units are blocked. UE unit is considered blocked in TTI if it is not scheduled to transmit any data even though it has data available in its queues. Incremented each 2ms TTI, by one for each UE unit with data available in its queues, that is not scheduled for data transmission..";
      type uint32;
      config false;
    }
    leaf pmNoInactiveRequiredSubFrames {
      description "The number of subframes in which no data is transmitted although there is user data to be sent in the validated PQ. This user data is either waiting for first transmission, or data waiting for transmission (NACK is received or no ACK/NACK). If the buffer of an MC-PQ is emptied, due to prior scheduling in another cell in the same subframe, and no other buffer in the cell contains data the counter is not incremented. The counter reflects the cell perspective. The counter is per cell and per subframe, meaning increments with max 1 per subframe. A \"subframe\" is a 2 ms TTI for HS-DSCH..";
      type uint16;
      config false;
    }
    leaf pmSumAckedBitsPqSpi04 {
      description "Total amount of acknowledged MAC-hs/ehs data to UEs using any cell as serving HS-DSCH cell. Only acknowledged data originating from a PQ with scheduling priority class 04 is considered. The counter reflects the PQ perspective. Unit: 1 kilobit..";
      type uint32;
      config false;
    }
    leaf pmNoActiveSubFramesSpi14 {
      description "Sum of active 2 ms subframes for scheduling priority class 14..";
      type uint32;
      config false;
    }
    leaf pmSumNonEmptyUserBuffersMcPqSpi07 {
      description "Number of PQs with data in the buffer for each 2 ms subframe. Only PQs with scheduling priority class 07 and belonging to UEs units configured to use cell as serving HS-DSCH cell in MC mode are considered. The counter reflects the PQ perspective..";
      type uint32;
      config false;
    }
    leaf-list pmTransmittedCarrierPowerWHs {
      description "Measurement to observe the distribution of transmitted carrier power for all codes used for transmission of HSDPA channels including HS-PDSCH, HS-SCCH, HS-FACH, E-AGCH, E-RGCH and E-HICH, as a percentage of the maximum power (indicated by the counter NodeBLocalCell::pmTransmittedCarrierPowerWLimit). Bins: [0]: Number of sampled values in range [0..2[ % [1]: Number of sampled values in range [2..4[ % [2]: Number of sampled values in range [4..6[ % ... [99]: Number of sampled values in range [198..200] %.";
      type uint64;
      max-elements 100;
    }
    leaf pmIubBasedDiscardFrameLossUserSpi11 {
      description "Number of Iub discards on all Priority Queues (PQs), that experienced the frame loss due to Iub congestion, for Scheduling Priority Indicator (SPI) 11..";
      type uint32;
      config false;
    }
    leaf pmAqmBasedDiscardSpi07 {
      description "Number of discards performed by the AQM feature for all Priority Queues (PQs) for Scheduling Priority Indicator (SPI) 07..";
      type uint32;
      config false;
    }
    leaf pmSumAckedBits3McPqSpi02 {
      description "Total amount of acknowledged MAC-hs/ehs data to UEs using any cell as serving HS-DSCH cell in 3MC mode. Only acknowledged data originating from a PQ with scheduling priority class 02 is considered. The counter reflects the PQ perspective. Unit: 1 kilobit..";
      type uint32;
      config false;
    }
    leaf pmIubBasedDiscardFrameLossUserSpi13 {
      description "Number of Iub discards on all Priority Queues (PQs), that experienced the frame loss due to Iub congestion, for Scheduling Priority Indicator (SPI) 13..";
      type uint32;
      config false;
    }
    leaf pmSumDelaySpi05 {
      description "Sum of delay of transmitted data before it is scheduled for scheduling priority class 05. Counter unit: 1 ms..";
      type uint32;
      config false;
    }
    leaf pmSumNonEmptyUserBuffersSpi02 {
      description "Number of user buffers for scheduling priority class 02 with data in buffer for each 2 ms subframes. The counter reflects the cell perspective..";
      type uint32;
      config false;
    }
    leaf pmSumAckedBitsMcPqSpi06 {
      description "Total amount of acknowledged MAC-hs/ehs data to UEs using any cell as serving HS-DSCH cell in MC mode. Only acknowledged data originating from a PQ with scheduling priority class 06 is considered. The counter reflects the PQ perspective. Unit: 1 kilobit..";
      type uint32;
      config false;
    }
    leaf pmSumJitterSpi15 {
      description "Sum of delay jitter of transmitted data before it is scheduled for scheduling priority class 15. The jitter delay is defined as a time difference between current delay and the previous one. Counter unit: 1 ms..";
      type uint32;
      config false;
    }
    leaf pmAllocRejHwHsDschUsers {
      description "Number of rejected attempts to allocate resources for new HS-DSCH user because of lack of HS resource capacity..";
      type uint64;
      config false;
    }
    leaf pmNoInactiveRequiredSubFramesSpi08 {
      description "Number of subframes in which no data with scheduling priority class 08 is transmitted although there is user data to be sent in the validated PQ. This user data is either waiting for first transmission, or data waiting for transmission (NACK is received or no ACK/NACK). If a subframe goes without scheduling priority class 08, that is, just carrying other scheduling priority classes or going totally empty, then the counter is stepped. If the buffer of an MC-PQ is emptied, due to prior scheduling in another cell in the same subframe, and no other buffer in the cell contains data the counter is not incremented. The counter reflects the cell perspective..";
      type uint16;
      config false;
    }
    leaf pmSumDelaySpi13 {
      description "Sum of delay of transmitted data before it is scheduled for scheduling priority class 13. Counter unit: 1 ms..";
      type uint32;
      config false;
    }
    leaf pmSumNonEmptyUserBuffersPqSpi02 {
      description "Number of PQs with data in the buffer for each 2 ms subframe. Only PQs with scheduling priority class 02 and belonging to UEs units configured to use cell as serving HS-DSCH cell are considered. The counter reflects the PQ perspective..";
      type uint32;
      config false;
    }
    leaf-list pmSumTransmissionsRlim {
      description "Distribution over CQI, of total number of transmissions to UE units configured to use cell, including retransmissions, on MAC-hs or MAC-ehs level until acknowledgement is received, under resource-limited conditions. Scheduling decision is defined to be resource-limited if transport block size is limited only by available codes or power, or both. In addition, only one single UE unit must be scheduled for data transmission in 2ms TTI. CQI value used to index distribution is one reported by UE units and applicable during initial transmission. For non-64QAM-capable UE units, CQI value is mapped down to align with CQI reporting for 64QAM-capable UE units, as further described for PDF range 26...30. Ranges: [0] : Number of transmissions for reported CQI=0 at initial transmission [1] : Number of transmissions for reported CQI=1 at initial transmission ... [25] : Number of transmissions for reported CQI=25 at initial transmission [26] : Number of transmissions for reported CQI=26 for 64QAM-capable UE units, or reported CQI=26 and 27 for non-64QAM-capable UE units, at initial transmission [27] : Number of transmissions for reported CQI=27 for 64QAM-capable UE units, or reported CQI=28 and 29 for non-64QAM-capable UE units, at initial transmission [28] : Number of transmissions for reported CQI=28 for 64QAM-capable UE units, or reported CQI=30 for non-64QAM-capable UE units, at initial transmission [29] : Number of transmissions for reported CQI=29 at initial transmission for 64QAM-capable UE units (not used for non-64QAM-capable UE units) [30] : Number of transmissions for reported CQI=30 at initial transmission for 64QAM-capable UE units (not used for non-64QAM-capable UE units).";
      type uint16;
      max-elements 31;
    }
    leaf pmSumJitterSpi14 {
      description "Sum of delay jitter of transmitted data before it is scheduled for scheduling priority class 14. The jitter delay is defined as a time difference between current delay and the previous one. Counter unit: 1 ms..";
      type uint32;
      config false;
    }
    leaf pmSumNonEmptyUserBuffersSpi14 {
      description "Number of user buffers for scheduling priority class 14 with data in buffer for each 2 ms subframes. The counter reflects the cell perspective..";
      type uint32;
      config false;
    }
    leaf-list pmSumOfHsScchUsedPwr {
      description "HS-SCCH transmitted power for each cell. Includes HS-SCCH power used for HS-FACH. If more than one HS-SCCH code is used, registered value is the sum of individual values. Bins: [0]: Number of samples with values lower than 0 dBm or 'no transmission' [1]: Number of samples in range [0..0.5[ dBm [2]: Number of samples in range [0.5..1[ dBm ... [101]: Number of samples in range [50..50.5[ dBm [102]: Number of samples greater than or equal to 50.5 dBm.";
      type uint16;
      max-elements 103;
    }
    leaf pmSumAckedBitsSpi04 {
      description "Total amount of acknowledged data sent on MAC-hs level per scheduling priority class 04. The counter does not consider whether or not the transmitted data originates from an MC-PQ. The counter reflects the cell perspective. Unit: 1 kilobit..";
      type uint32;
      config false;
    }
    leaf pmSumAckedBits3McPqSpi00 {
      description "Total amount of acknowledged MAC-hs/ehs data to UEs using any cell as serving HS-DSCH cell in 3MC mode. Only acknowledged data originating from a PQ with scheduling priority class 00 is considered. The counter reflects the PQ perspective. Unit: 1 kilobit..";
      type uint32;
      config false;
    }
    leaf-list pmUsedHsPdschCodes {
      description "The distribution of the HS-PDSCH code utilization, as the number of HS-PDSCH codes used by the scheduler. Also includes codes used for HS-FACH. Bins: [0]: 0 codes [1]: 1 code [2]: 2 codes [3]: 3 codes [4]: 4 codes [5]: 5 codes [6]: 6 codes [7]: 7 codes [8]: 8 codes [9]: 9 codes [10]: 10 codes [11]: 11 codes [12]: 12 codes [13]: 13 codes [14]: 14 codes [15]: 15 codes.";
      type uint32;
      max-elements 16;
    }
    leaf pmNoInactiveRequiredSubFramesSpi12 {
      description "Number of subframes in which no data with scheduling priority class 12 is transmitted although there is user data to be sent in the validated PQ. This user data is either waiting for first transmission, or data waiting for transmission (NACK is received or no ACK/NACK). If a subframe goes without scheduling priority class 12, that is, just carrying other scheduling priority classes or going totally empty, then the counter is stepped. If the buffer of an MC-PQ is emptied, due to prior scheduling in another cell in the same subframe, and no other buffer in the cell contains data the counter is not incremented. The counter reflects the cell perspective..";
      type uint16;
      config false;
    }
    leaf pmSumNoOfUsersSpi13 {
      description "Counts the total number of users for scheduling priority class 13 selected for each 2 ms subframe that is transmitted in the cell. For an MC-PQ only the counter in the serving HS-DSCH cell (of the UE to which the MC-PQ belongs) is updated. However, the aggregated measurement, based on all cells where the MC-PQ may be served, is considered when that counter is updated. The counter reflects the PQ perspective..";
      type uint32;
      config false;
    }
    leaf pmSumJitterSpi10 {
      description "Sum of delay jitter of transmitted data before it is scheduled for scheduling priority class 10. The jitter delay is defined as a time difference between current delay and the previous one. Counter unit: 1 ms..";
      type uint32;
      config false;
    }
    leaf pmSumAckedBitsPqSpi14 {
      description "Total amount of acknowledged MAC-hs/ehs data to UEs using any cell as serving HS-DSCH cell. Only acknowledged data originating from a PQ with scheduling priority class 14 is considered. The counter reflects the PQ perspective. Unit: 1 kilobit..";
      type uint32;
      config false;
    }
    leaf pmSumNonEmptyUserBuffersSpi13 {
      description "Number of user buffers for scheduling priority class 13 with data in buffer for each 2 ms subframes. The counter reflects the cell perspective..";
      type uint32;
      config false;
    }
    leaf pmSumSqrCapacityHsPdschCodes {
      description "Aggregate of the squares of the sample values in pmSumCapacityHsPdschCodes. That is, pmSumSqrCapacityHsPdschCodes = pmSumSqrCapacityHsPdschCodes + sqr(measurement_value)..";
      type uint64;
      config false;
    }
    leaf-list pmSumOfHsUsedPwr {
      description "The distribution of transmitted power for HS (HS-FACH as well as HS traffic on CELL_DCH). Bins: [0]: Number of samples with values less than 0 dBm or no transmission [1]: Number of samples in range [0..0.5[ dBm [2]: Number of samples in range [0.5..1[ dBm ... [101]: Number of samples in range [50..50.5[ dBm [102]: Number of samples greater than or equal to 50.5 dBm.";
      type uint16;
      max-elements 103;
    }
    leaf pmSumTransmittedBitsSpi00 {
      description "Measurement to observe the total amount of data, in kbits, sent on MAC-hs level per scheduling priority class 00. The counter does not consider whether or not the transmitted data originates from an MC-PQ. The counter reflects the cell perspective..";
      type uint32;
      config false;
    }
    leaf-list pmAck16Qam {
      description "Number of received ACKs for a specified transport block size (TBS) with 16 QAM. The number of successful HARQ transmissions are counted on the MAC-hs layer. The counter does not consider whether or not the transmitted data originates from an MC-PQ. The counter does not consider ACK/NACKs corresponding to HS-SCCH orders. The counter reflects the cell perspective. Bins: [0]: Number of ACKs for transport block with size [0..1000[ bits [1]: Number of ACKs for transport block with size [1000..2000[ bits [2]: Number of ACKs for transport block with size [2000..3000[ bits ... [28]: Number of ACKs for transport block with size [28000..29000[ bits [29]: Number of ACKs for transport block with size [29000..30000[ bits.";
      type uint32;
      max-elements 30;
    }
    leaf pmSumNonEmptyUserBuffersSpi05 {
      description "Number of user buffers for scheduling priority class 05 with data in buffer for each 2 ms subframes. The counter reflects the cell perspective..";
      type uint32;
      config false;
    }
    leaf pmSumAckedBitsPqSpi01 {
      description "Total amount of acknowledged MAC-hs/ehs data to UEs using any cell as serving HS-DSCH cell. Only acknowledged data originating from a PQ with scheduling priority class 01 is considered. The counter reflects the PQ perspective. Unit: 1 kilobit..";
      type uint32;
      config false;
    }
    leaf pmSumAckedBitsPqSpi15 {
      description "Total amount of acknowledged MAC-hs/ehs data to UEs using any cell as serving HS-DSCH cell. Only acknowledged data originating from a PQ with scheduling priority class 15 is considered. The counter reflects the PQ perspective. Unit: 1 kilobit..";
      type uint32;
      config false;
    }
    leaf pmIubBasedDiscardFrameLossUserSpi06 {
      description "Number of Iub discards on all Priority Queues (PQs), that experienced the frame loss due to Iub congestion, for Scheduling Priority Indicator (SPI) 06..";
      type uint32;
      config false;
    }
    leaf pmSumAckedBitsPqSpi05 {
      description "Total amount of acknowledged MAC-hs/ehs data to UEs using any cell as serving HS-DSCH cell. Only acknowledged data originating from a PQ with scheduling priority class 05 is considered. The counter reflects the PQ perspective. Unit: 1 kilobit..";
      type uint32;
      config false;
    }
    leaf pmSumJitterSpi12 {
      description "Sum of delay jitter of transmitted data before it is scheduled for scheduling priority class 12. The jitter delay is defined as a time difference between current delay and the previous one. Counter unit: 1 ms..";
      type uint32;
      config false;
    }
    leaf-list pmCapacityOfHsPdschCodes {
      description "Distribution of HS-PDSCH codes allocated (including HS-PDSCH codes allocated by the RNC). Values are expressed as percentage of the license controlled level visible in pmCapacityLimitHsPdschCodes. The number of allocated HS-PDSCH code can be reduced below the license limit by non-HS traffic. This means that number of allocated HS-PDSCH codes may not reach 100%. When feature Dynamic Code Allocation is inoperable, HS-PDSCH Codes are only allocated by the RNC. Bins: [0]: Number of sampled values in range [0..20[ % [1]: Number of sampled values in range [20..40[ % [2]: Number of sampled values in range [40..50[ % [3]: Number of sampled values in range [50..60[ % [4]: Number of sampled values in range [60..70[ % [5]: Number of sampled values in range [70..80[ % [6]: Number of sampled values in range [80..85[ % [7]: Number of sampled values in range [85..90[ % [8]: Number of sampled values in range [90..95[ % [9]: Number of sampled values >= 95%.";
      type uint64;
      max-elements 10;
    }
    leaf pmSumAckedBitsPqSpi08 {
      description "Total amount of acknowledged MAC-hs/ehs data to UEs using any cell as serving HS-DSCH cell. Only acknowledged data originating from a PQ with scheduling priority class 08 is considered. The counter reflects the PQ perspective. Unit: 1 kilobit..";
      type uint32;
      config false;
    }
    leaf pmSumTransmittedBitsSpi14 {
      description "Measurement to observe the total amount of data, in kbits, sent on MAC-hs level per scheduling priority class 14. The counter does not consider whether or not the transmitted data originates from an MC-PQ. The counter reflects the cell perspective..";
      type uint32;
      config false;
    }
    leaf pmSumNonEmptyUserBuffersMcPqSpi15 {
      description "Number of PQs with data in the buffer for each 2 ms subframe. Only PQs with scheduling priority class 15 and belonging to UEs units configured to use cell as serving HS-DSCH cell in MC mode are considered. The counter reflects the PQ perspective..";
      type uint32;
      config false;
    }
    leaf pmNoActiveSubFramesSpi03 {
      description "Sum of active 2 ms subframes for scheduling priority class 03..";
      type uint32;
      config false;
    }
    leaf pmSumTransmittedBitsSpi12 {
      description "Measurement to observe the total amount of data, in kbits, sent on MAC-hs level per scheduling priority class 12. The counter does not consider whether or not the transmitted data originates from an MC-PQ. The counter reflects the cell perspective..";
      type uint32;
      config false;
    }
    leaf pmAqmBasedDiscardSpi05 {
      description "Number of discards performed by the AQM feature for all Priority Queues (PQs) for Scheduling Priority Indicator (SPI) 05..";
      type uint32;
      config false;
    }
    leaf pmSumJitterSpi00 {
      description "Sum of delay jitter of transmitted data before it is scheduled for scheduling priority class 00. The jitter delay is defined as a time difference between current delay and the previous one. Counter unit: 1 ms..";
      type uint32;
      config false;
    }
    leaf-list pmDelayDistributionSpi01 {
      description "Measurement to observe the distribution of the scheduling delay for scheduling priority class 01 on each subframe on those priority queue(s) selected for transmission. Bins: [0]: Number of delays in [0..10[ % [1]: Number of delays in [10..20[ % ... [9]: Number of delays in [90..100[ % [10]: Number of delays greater than or equal to 100%.";
      type uint32;
      max-elements 11;
    }
    leaf pmSumAckedBitsPqSpi10 {
      description "Total amount of acknowledged MAC-hs/ehs data to UEs using any cell as serving HS-DSCH cell. Only acknowledged data originating from a PQ with scheduling priority class 10 is considered. The counter reflects the PQ perspective. Unit: 1 kilobit..";
      type uint32;
      config false;
    }
    leaf pmSumAckedBitsSpi15 {
      description "Total amount of acknowledged data sent on MAC-hs level per scheduling priority class 15. The counter does not consider whether or not the transmitted data originates from an MC-PQ. The counter reflects the cell perspective. Unit: 1 kilobit..";
      type uint32;
      config false;
    }
    leaf pmSumAckedBits3McPqSpi04 {
      description "Total amount of acknowledged MAC-hs/ehs data to UEs using any cell as serving HS-DSCH cell in 3MC mode. Only acknowledged data originating from a PQ with scheduling priority class 04 is considered. The counter reflects the PQ perspective. Unit: 1 kilobit..";
      type uint32;
      config false;
    }
    leaf-list pmDelayDistributionSpi10 {
      description "Measurement to observe the distribution of the scheduling delay for scheduling priority class 10 on each subframe on those priority queue(s) selected for transmission. Bins: [0]: Number of delays in [0..10[ % [1]: Number of delays in [10..20[ % ... [9]: Number of delays in [90..100[ % [10]: Number of delays greater than or equal to 100%.";
      type uint32;
      max-elements 11;
    }
    leaf pmNoInactiveRequiredSubFramesSpi13 {
      description "Number of subframes in which no data with scheduling priority class 13 is transmitted although there is user data to be sent in the validated PQ. This user data is either waiting for first transmission, or data waiting for transmission (NACK is received or no ACK/NACK). If a subframe goes without scheduling priority class 13, that is, just carrying other scheduling priority classes or going totally empty, then the counter is stepped. If the buffer of an MC-PQ is emptied, due to prior scheduling in another cell in the same subframe, and no other buffer in the cell contains data the counter is not incremented. The counter reflects the cell perspective..";
      type uint16;
      config false;
    }
    leaf pmAckReceived {
      description "Number of occasions when ACK is received, not counting repetitions of ACK transmissions. The counter does not consider whether or not the transmitted data originates from an MC-PQ. The counter does not consider ACK/NACKs corresponding to HS-SCCH orders. The counter reflects the cell perspective..";
      type uint32;
      config false;
    }
    leaf pmSumAckedBitsMcPqSpi11 {
      description "Total amount of acknowledged MAC-hs/ehs data to UEs using any cell as serving HS-DSCH cell in MC mode. Only acknowledged data originating from a PQ with scheduling priority class 11 is considered. The counter reflects the PQ perspective. Unit: 1 kilobit..";
      type uint32;
      config false;
    }
    leaf pmSumAckedBitsPqSpi12 {
      description "Total amount of acknowledged MAC-hs/ehs data to UEs using any cell as serving HS-DSCH cell. Only acknowledged data originating from a PQ with scheduling priority class 12 is considered. The counter reflects the PQ perspective. Unit: 1 kilobit..";
      type uint32;
      config false;
    }
    leaf pmNoInactiveRequiredSubFramesSpi11 {
      description "Number of subframes in which no data with scheduling priority class 11 is transmitted although there is user data to be sent in the validated PQ. This user data is either waiting for first transmission, or data waiting for transmission (NACK is received or no ACK/NACK). If a subframe goes without scheduling priority class 11, that is, just carrying other scheduling priority classes or going totally empty, then the counter is stepped. If the buffer of an MC-PQ is emptied, due to prior scheduling in another cell in the same subframe, and no other buffer in the cell contains data the counter is not incremented. The counter reflects the cell perspective..";
      type uint16;
      config false;
    }
    leaf-list pmDelayDistributionSpi03 {
      description "Measurement to observe the distribution of the scheduling delay for scheduling priority class 03 on each subframe on those priority queue(s) selected for transmission. Bins: [0]: Number of delays in [0..10[ % [1]: Number of delays in [10..20[ % ... [9]: Number of delays in [90..100[ % [10]: Number of delays greater than or equal to 100%.";
      type uint32;
      max-elements 11;
    }
    leaf pmIubBasedDiscardFrameLossUserSpi01 {
      description "Number of Iub discards on all Priority Queues (PQs), that experienced the frame loss due to Iub congestion, for Scheduling Priority Indicator (SPI) 01..";
      type uint32;
      config false;
    }
    leaf pmNoActiveSubFramesSpi01 {
      description "Sum of active 2 ms subframes for scheduling priority class 01..";
      type uint32;
      config false;
    }
    leaf-list pmUsedHsPdschCodesHsFach {
      description "The distribution of the HS-PDSCH code utilization, as the number of HS-PDSCH codes used by the scheduler for HS-FACH. Bins: [0]: 0 codes [1]: 1 code [2]: 2 codes [3]: 3 codes [4]: 4 codes [5]: 5 codes [6]: 6 codes [7]: 7 codes [8]: 8 codes [9]: 9 codes [10]: 10 codes [11]: 11 codes [12]: 12 codes [13]: 13 codes [14]: 14 codes [15]: 15 codes.";
      type uint32;
      max-elements 16;
    }
    leaf pmSumAckedBitsPqSpi00 {
      description "Total amount of acknowledged MAC-hs/ehs data to UEs using any cell as serving HS-DSCH cell. Only acknowledged data originating from a PQ with scheduling priority class 00 is considered. The counter reflects the PQ perspective. Unit: 1 kilobit..";
      type uint32;
      config false;
    }
    leaf pmSumNonEmptyUserBuffersMcPqSpi05 {
      description "Number of PQs with data in the buffer for each 2 ms subframe. Only PQs with scheduling priority class 05 and belonging to UEs units configured to use cell as serving HS-DSCH cell in MC mode are considered. The counter reflects the PQ perspective..";
      type uint32;
      config false;
    }
    leaf pmSumAckedBitsPqSpi09 {
      description "Total amount of acknowledged MAC-hs/ehs data to UEs using any cell as serving HS-DSCH cell. Only acknowledged data originating from a PQ with scheduling priority class 09 is considered. The counter reflects the PQ perspective. Unit: 1 kilobit..";
      type uint32;
      config false;
    }
    leaf pmCapacityAllocAttHsDschUsers {
      description "Number of attempts to allocate resources for new HS-DSCH user..";
      type uint64;
      config false;
    }
    leaf pmSumNoOfUsersSpi12 {
      description "Counts the total number of users for scheduling priority class 12 selected for each 2 ms subframe that is transmitted in the cell. For an MC-PQ only the counter in the serving HS-DSCH cell (of the UE to which the MC-PQ belongs) is updated. However, the aggregated measurement, based on all cells where the MC-PQ may be served, is considered when that counter is updated. The counter reflects the PQ perspective..";
      type uint32;
      config false;
    }
    leaf pmSamplesCapacityHsDschUsers {
      description "Number of samples in pmSumCapacityHsDschUsers (that is, pmSamplesCapacityHsDschUsers = pmSamplesCapacityHsDschUsers + 1, whenever pmSumCapacityHsDschUsers is to be updated)..";
      type uint64;
      config false;
    }
    leaf-list pmUsedCqi {
      description "Adjusted CQI, used to calculate transport format when user transmits on the HS-DSCH. This counter is only relevant for the UE units not using MIMO or 64 QAM. No corresponding counter exists for the UE units using MIMO or 64 QAM. The counter reflects the cell perspective. Bins: [0]: Number of samples with CQI value 0 [1]: Number of samples with CQI value 1 ... [30]: Number of samples with CQI value 30 [31]: Invalid (not used).";
      type uint16;
      max-elements 32;
    }
    leaf pmNoInactiveRequiredSubFramesSpi07 {
      description "Number of subframes in which no data with scheduling priority class 07 is transmitted although there is user data to be sent in the validated PQ. This user data is either waiting for first transmission, or data waiting for transmission (NACK is received or no ACK/NACK). If a subframe goes without scheduling priority class 07, that is, just carrying other scheduling priority classes or going totally empty, then the counter is stepped. If the buffer of an MC-PQ is emptied, due to prior scheduling in another cell in the same subframe, and no other buffer in the cell contains data the counter is not incremented. The counter reflects the cell perspective..";
      type uint16;
      config false;
    }
    leaf-list pmNoOfHsUsersPerTtiHsFach {
      description "Number of HS-FACH users scheduled in the cell. HS-FACH user is UE in RRC state CELL_FACH on RNC level, using transport channel HS-DSCH and not FACH. Bins: [0]: Number of samples equal to 0 HS-FACH users [1]: Number of samples equal to 1 HS-FACH user [2]: Number of samples equal to 2 HS-FACH users [3]: Number of samples equal to 3 HS-FACH users [4]: Number of samples equal to 4 HS-FACH users.";
      type uint16;
      max-elements 5;
    }
    leaf pmSumAckedBitsSpi13 {
      description "Total amount of acknowledged data sent on MAC-hs level per scheduling priority class 13. The counter does not consider whether or not the transmitted data originates from an MC-PQ. The counter reflects the cell perspective. Unit: 1 kilobit..";
      type uint32;
      config false;
    }
    leaf pmAqmBasedDiscardSpi12 {
      description "Number of discards performed by the AQM feature for all Priority Queues (PQs) for Scheduling Priority Indicator (SPI) 12..";
      type uint32;
      config false;
    }
    leaf pmIubBasedDiscardFrameLossUserSpi00 {
      description "Number of Iub discards on all Priority Queues (PQs), that experienced the frame loss due to Iub congestion, for Scheduling Priority Indicator (SPI) 00..";
      type uint32;
      config false;
    }
    leaf pmSumAckedBitsMcPqSpi15 {
      description "Total amount of acknowledged MAC-hs/ehs data to UEs using any cell as serving HS-DSCH cell in MC mode. Only acknowledged data originating from a PQ with scheduling priority class 15 is considered. The counter reflects the PQ perspective. Unit: 1 kilobit..";
      type uint32;
      config false;
    }
    leaf pmAqmBasedDiscardSpi02 {
      description "Number of discards performed by the AQM feature for all Priority Queues (PQs) for Scheduling Priority Indicator (SPI) 02..";
      type uint32;
      config false;
    }
    leaf pmIubBasedDiscardFrameLossUserSpi10 {
      description "Number of Iub discards on all Priority Queues (PQs), that experienced the frame loss due to Iub congestion, for Scheduling Priority Indicator (SPI) 10..";
      type uint32;
      config false;
    }
    leaf pmSumNonEmptyUserBuffersMcPqSpi14 {
      description "Number of PQs with data in the buffer for each 2 ms subframe. Only PQs with scheduling priority class 14 and belonging to UEs units configured to use cell as serving HS-DSCH cell in MC mode are considered. The counter reflects the PQ perspective..";
      type uint32;
      config false;
    }
    leaf-list pmReportedCqi {
      description "CQI reported by the UE. It is the true (unadjusted) CQI that is counted. This counter is only relevant for UE units not using 64 QAM. Bins: [0]: Number of reported CQI with value 0 [1]: Number of reported CQI with value 1 ... [30]: Number of reported CQI with value 30 [31]: Number of reported CQI with invalid value.";
      type uint32;
      max-elements 32;
    }
    leaf pmSumJitterSpi04 {
      description "Sum of delay jitter of transmitted data before it is scheduled for scheduling priority class 04. The jitter delay is defined as a time difference between current delay and the previous one. Counter unit: 1 ms..";
      type uint32;
      config false;
    }
    leaf pmNoActiveSubFramesSpi05 {
      description "Sum of active 2 ms subframes for scheduling priority class 05..";
      type uint32;
      config false;
    }
    leaf-list pmAverageUserRate {
      description "The distribution of the average user rate among all users allocated to high-speed DSCH in the cell. The counter reports the acknowledged throughput for each Priority Queue (PQ) allocated to the cell. For an MC-PQ only the counter in the serving HS-DSCH cell (of the UE to which the MC PQ belongs) is updated. However, the aggregated measurement, based on all cells where the MC-PQ may be served, is considered when that counter is updated. The counter reflects the PQ perspective. Bins: [0]: Number of value samples = 0 (no data sent) [1]: Number of value samples in range ]0..8[ kbps [2]: Number of value samples in range [8..16[ kbps [3]: Number of value samples in range [16..32[ kbps [4]: Number of value samples in range [32..48[ kbps [5]: Number of value samples in range [48..64[ kbps [6]: Number of value samples in range [64..96[ kbps [7]: Number of value samples in range [96..128[ kbps [8]: Number of value samples in range [128..192[ kbps [9]: Number of value samples in range [192..256[ kbps [10]: Number of value samples in range [256..384[ kbps [11]: Number of value samples in range [384..512[ kbps [12]: Number of value samples in range [512..768[ kbps [13]: Number of value samples in range [768..1024[ kbps [14]: Number of value samples in range [1024..2048[ kbps [15]: Number of value samples in range [2048..3072[ kbps [16]: Number of value samples in range [3072..4096[ kbps [17]: Number of value samples in range [4096..7000[ kbps [18]: Number of value samples in range [7000..10000[ kbps [19]: Number of value samples in range [10000..14000[ kbps [20]: Number of value samples in range [14000..21000[ kbps [21]: Number of value samples in range [21000..28000[ kbps [22]: Number of value samples in range [28000..40000[ kbps [23]: Number of value samples in range [40000..60000[ kbps [24]: Number of value samples in range [60000..80000[ kbps [25]: Number of value samples in range [80000..100000[ kbps [26]: Number of value samples in range [100000..130000[ kbps [27]: Number of value samples greater than or equal to 130000 kbps.";
      type uint16;
      max-elements 28;
    }
    leaf pmSumNoOfUsersSpi14 {
      description "Counts the total number of users for scheduling priority class 14 selected for each 2 ms subframe that is transmitted in the cell. For an MC-PQ only the counter in the serving HS-DSCH cell (of the UE to which the MC-PQ belongs) is updated. However, the aggregated measurement, based on all cells where the MC-PQ may be served, is considered when that counter is updated. The counter reflects the PQ perspective..";
      type uint32;
      config false;
    }
    leaf-list pmDelayDistributionSpi14 {
      description "Measurement to observe the distribution of the scheduling delay for scheduling priority class 14 on each subframe on those priority queue(s) selected for transmission. Bins: [0]: Number of delays in [0..10[ % [1]: Number of delays in [10..20[ % ... [9]: Number of delays in [90..100[ % [10]: Number of delays greater than or equal to 100%.";
      type uint32;
      max-elements 11;
    }
    leaf pmSumAckedBitsMcPqSpi02 {
      description "Total amount of acknowledged MAC-hs/ehs data to UEs using any cell as serving HS-DSCH cell in MC mode. Only acknowledged data originating from a PQ with scheduling priority class 02 is considered. The counter reflects the PQ perspective. Unit: 1 kilobit..";
      type uint32;
      config false;
    }
    leaf pmSumNonEmptyUserBuffersSpi07 {
      description "Number of user buffers for scheduling priority class 07 with data in buffer for each 2 ms subframes. The counter reflects the cell perspective..";
      type uint32;
      config false;
    }
    leaf pmSumAckedBitsPqSpi13 {
      description "Total amount of acknowledged MAC-hs/ehs data to UEs using any cell as serving HS-DSCH cell. Only acknowledged data originating from a PQ with scheduling priority class 13 is considered. The counter reflects the PQ perspective. Unit: 1 kilobit..";
      type uint32;
      config false;
    }
    leaf pmSumDelaySpi09 {
      description "Sum of delay of transmitted data before it is scheduled for scheduling priority class 09. Counter unit: 1 ms..";
      type uint32;
      config false;
    }
    leaf pmSumAckedBitsSpi05 {
      description "Total amount of acknowledged data sent on MAC-hs level per scheduling priority class 05. The counter does not consider whether or not the transmitted data originates from an MC-PQ. The counter reflects the cell perspective. Unit: 1 kilobit..";
      type uint32;
      config false;
    }
    leaf pmSumNonEmptyUserBuffersSpi03 {
      description "Number of user buffers for scheduling priority class 03 with data in buffer for each 2 ms subframes. The counter reflects the cell perspective..";
      type uint32;
      config false;
    }
    leaf pmSumDelaySpi15 {
      description "Sum of delay of transmitted data before it is scheduled for scheduling priority class 15. Counter unit: 1 ms..";
      type uint32;
      config false;
    }
    leaf pmSumAckedBitsSpi09 {
      description "Total amount of acknowledged data sent on MAC-hs level per scheduling priority class 09. The counter does not consider whether or not the transmitted data originates from an MC-PQ. The counter reflects the cell perspective. Unit: 1 kilobit..";
      type uint32;
      config false;
    }
    leaf pmSumJitterSpi07 {
      description "Sum of delay jitter of transmitted data before it is scheduled for scheduling priority class 07. The jitter delay is defined as a time difference between current delay and the previous one. Counter unit: 1 ms..";
      type uint32;
      config false;
    }
    leaf pmIubBasedDiscardFrameLossUserSpi14 {
      description "Number of Iub discards on all Priority Queues (PQs), that experienced the frame loss due to Iub congestion, for Scheduling Priority Indicator (SPI) 14..";
      type uint32;
      config false;
    }
    leaf pmSumNonEmptyUserBuffersSpi08 {
      description "Number of user buffers for scheduling priority class 08 with data in buffer for each 2 ms subframes. The counter reflects the cell perspective..";
      type uint32;
      config false;
    }
    leaf pmSumAckedBitsSpi01 {
      description "Total amount of acknowledged data sent on MAC-hs level per scheduling priority class 01. The counter does not consider whether or not the transmitted data originates from an MC-PQ. The counter reflects the cell perspective. Unit: 1 kilobit..";
      type uint32;
      config false;
    }
    leaf pmSumAckedBitsSpi06 {
      description "Total amount of acknowledged data sent on MAC-hs level per scheduling priority class 06. The counter does not consider whether or not the transmitted data originates from an MC-PQ. The counter reflects the cell perspective. Unit: 1 kilobit..";
      type uint32;
      config false;
    }
    leaf pmSumJitterSpi09 {
      description "Sum of delay jitter of transmitted data before it is scheduled for scheduling priority class 09. The jitter delay is defined as a time difference between current delay and the previous one. Counter unit: 1 ms..";
      type uint32;
      config false;
    }
    leaf-list pmNoOfMcSecUsersPerTti {
      description "Distribution of number of UEs scheduled in each 2 ms subframe in the cell. Only UEs configured using cell as activated secondary serving HS-DSCH cell are considered. The counter reflects the cell perspective. Bins: [0]: Number of samples equal to 0 UEs [1]: Number of samples equal to 1 UE [2]: Number of samples equal to 2 UEs [3]: Number of samples equal to 3 UEs [4]: Number of samples equal to 4 UEs.";
      type uint32;
      max-elements 5;
    }
    leaf pmSumNonEmptyUserBuffers3McPqSpi10 {
      description "Number of PQs with data in the buffer for each 2 ms subframe. Only PQs with scheduling priority class 10 and belonging to UEs units configured to use cell as serving HS-DSCH cell in 3MC mode are considered. The counter reflects the PQ perspective..";
      type uint32;
      config false;
    }
    leaf pmSumDelaySpi04 {
      description "Sum of delay of transmitted data before it is scheduled for scheduling priority class 04. Counter unit: 1 ms..";
      type uint32;
      config false;
    }
    leaf pmSumAckedBitsPqSpi03 {
      description "Total amount of acknowledged MAC-hs/ehs data to UEs using any cell as serving HS-DSCH cell. Only acknowledged data originating from a PQ with scheduling priority class 03 is considered. The counter reflects the PQ perspective. Unit: 1 kilobit..";
      type uint32;
      config false;
    }
    leaf pmIubBasedDiscardFrameLossUserSpi07 {
      description "Number of Iub discards on all Priority Queues (PQs), that experienced the frame loss due to Iub congestion, for Scheduling Priority Indicator (SPI) 07..";
      type uint32;
      config false;
    }
    leaf pmSumNoOfUsersSpi05 {
      description "Counts the total number of users for scheduling priority class 05 selected for each 2 ms subframe that is transmitted in the cell. For an MC-PQ only the counter in the serving HS-DSCH cell (of the UE to which the MC-PQ belongs) is updated. However, the aggregated measurement, based on all cells where the MC-PQ may be served, is considered when that counter is updated. The counter reflects the PQ perspective..";
      type uint32;
      config false;
    }
    leaf pmIubBasedDiscardFrameLossUserSpi12 {
      description "Number of Iub discards on all Priority Queues (PQs), that experienced the frame loss due to Iub congestion, for Scheduling Priority Indicator (SPI) 12..";
      type uint32;
      config false;
    }
    leaf pmSumNonEmptyUserBuffersPqSpi08 {
      description "Number of PQs with data in the buffer for each 2 ms subframe. Only PQs with scheduling priority class 08 and belonging to UEs units configured to use cell as serving HS-DSCH cell are considered. The counter reflects the PQ perspective..";
      type uint32;
      config false;
    }
    leaf pmSumAckedBitsSpi12 {
      description "Total amount of acknowledged data sent on MAC-hs level per scheduling priority class 12. The counter does not consider whether or not the transmitted data originates from an MC-PQ. The counter reflects the cell perspective. Unit: 1 kilobit..";
      type uint32;
      config false;
    }
    leaf pmSumNonEmptyUserBuffers3McPqSpi13 {
      description "Number of PQs with data in the buffer for each 2 ms subframe. Only PQs with scheduling priority class 13 and belonging to UEs units configured to use cell as serving HS-DSCH cell in 3MC mode are considered. The counter reflects the PQ perspective..";
      type uint32;
      config false;
    }
    leaf pmSumNoOfUsersSpi01 {
      description "Counts the total number of users for scheduling priority class 01 selected for each 2 ms subframe that is transmitted in the cell. For an MC-PQ only the counter in the serving HS-DSCH cell (of the UE to which the MC-PQ belongs) is updated. However, the aggregated measurement, based on all cells where the MC-PQ may be served, is considered when that counter is updated. The counter reflects the PQ perspective..";
      type uint32;
      config false;
    }
    leaf pmSumTransmittedBitsSpi15 {
      description "Measurement to observe the total amount of data, in kbits, sent on MAC-hs level per scheduling priority class 15. The counter does not consider whether or not the transmitted data originates from an MC-PQ. The counter reflects the cell perspective..";
      type uint32;
      config false;
    }
    leaf pmSumDelaySpi10 {
      description "Sum of delay of transmitted data before it is scheduled for scheduling priority class 10. Counter unit: 1 ms..";
      type uint32;
      config false;
    }
    leaf pmSumNonEmptyUserBuffersMcPqSpi12 {
      description "Number of PQs with data in the buffer for each 2 ms subframe. Only PQs with scheduling priority class 12 and belonging to UEs units configured to use cell as serving HS-DSCH cell in MC mode are considered. The counter reflects the PQ perspective..";
      type uint32;
      config false;
    }
    leaf pmSumNonEmptyUserBuffers3McPqSpi15 {
      description "Number of PQs with data in the buffer for each 2 ms subframe. Only PQs with scheduling priority class 15 and belonging to UEs units configured to use cell as serving HS-DSCH cell in 3MC mode are considered. The counter reflects the PQ perspective..";
      type uint32;
      config false;
    }
    leaf pmNoInactiveRequiredSubFramesSpi00 {
      description "Number of subframes in which no data with scheduling priority class 00 is transmitted although there is user data to be sent in the validated PQ. This user data is either waiting for first transmission, or data waiting for transmission (NACK is received or no ACK/NACK). If a subframe goes without scheduling priority class 00, that is, just carrying other scheduling priority classes or going totally empty, then the counter is stepped. If the buffer of an MC-PQ is emptied, due to prior scheduling in another cell in the same subframe, and no other buffer in the cell contains data the counter is not incremented. The counter reflects the cell perspective..";
      type uint16;
      config false;
    }
    leaf pmSumJitterSpi13 {
      description "Sum of delay jitter of transmitted data before it is scheduled for scheduling priority class 13. The jitter delay is defined as a time difference between current delay and the previous one. Counter unit: 1 ms..";
      type uint32;
      config false;
    }
    leaf pmSumDelaySpi06 {
      description "Sum of delay of transmitted data before it is scheduled for scheduling priority class 06. Counter unit: 1 ms..";
      type uint32;
      config false;
    }
    leaf pmSumJitterSpi05 {
      description "Sum of delay jitter of transmitted data before it is scheduled for scheduling priority class 05. The jitter delay is defined as a time difference between current delay and the previous one. Counter unit: 1 ms..";
      type uint32;
      config false;
    }
    leaf pmSumNonEmptyUserBuffers3McPqSpi11 {
      description "Number of PQs with data in the buffer for each 2 ms subframe. Only PQs with scheduling priority class 11 and belonging to UEs units configured to use cell as serving HS-DSCH cell in 3MC mode are considered. The counter reflects the PQ perspective..";
      type uint32;
      config false;
    }
    leaf-list pmTransmittedCarrierPowerHs {
      description "Distribution of transmitted carrier power used for HSDPA. Bins: [0]: Number of sampled values lower than or equal to 0 dBm [1]: Number of sampled values in range ]0..1[ dBm [2]: Number of sampled values in range [1..2[ dBm ... [52]: Number of sampled values in range [51..52[ dBm [53]: Number of sampled values greater than or equal to 52 dBm.";
      type uint32;
      max-elements 54;
    }
    leaf-list pmRemainingResourceCheck {
      description "The reason why it is not possible to schedule another high-speed user. Bins: [0]: HS-SCCH code shortage [1]: HS-PDSCH code shortage [2]: HS-PDSCH power shortage.";
      type uint16;
      max-elements 3;
    }
    leaf pmSumNonEmptyUserBuffersSpi10 {
      description "Number of user buffers for scheduling priority class 10 with data in buffer for each 2 ms subframes. The counter reflects the cell perspective..";
      type uint32;
      config false;
    }
    leaf pmSumTransmittedBitsSpi05 {
      description "Measurement to observe the total amount of data, in kbits, sent on MAC-hs level per scheduling priority class 05. The counter does not consider whether or not the transmitted data originates from an MC-PQ. The counter reflects the cell perspective..";
      type uint32;
      config false;
    }
    leaf pmSumAckedBits3McPqSpi10 {
      description "Total amount of acknowledged MAC-hs/ehs data to UEs using any cell as serving HS-DSCH cell in 3MC mode. Only acknowledged data originating from a PQ with scheduling priority class 10 is considered. The counter reflects the PQ perspective. Unit: 1 kilobit..";
      type uint32;
      config false;
    }
    leaf pmSumAckedBitsMcPqSpi14 {
      description "Total amount of acknowledged MAC-hs/ehs data to UEs using any cell as serving HS-DSCH cell in MC mode. Only acknowledged data originating from a PQ with scheduling priority class 14 is considered. The counter reflects the PQ perspective. Unit: 1 kilobit..";
      type uint32;
      config false;
    }
    leaf pmIubBasedDiscardFrameLossUserSpi15 {
      description "Number of Iub discards on all Priority Queues (PQs), that experienced the frame loss due to Iub congestion, for Scheduling Priority Indicator (SPI) 15..";
      type uint32;
      config false;
    }
    leaf pmSumTransmittedBitsSpi04 {
      description "Measurement to observe the total amount of data, in kbits, sent on MAC-hs level per scheduling priority class 04. The counter does not consider whether or not the transmitted data originates from an MC-PQ. The counter reflects the cell perspective..";
      type uint32;
      config false;
    }
    leaf pmSumNonEmptyUserBuffersSpi04 {
      description "Number of user buffers for scheduling priority class 04 with data in buffer for each 2 ms subframes. The counter reflects the cell perspective..";
      type uint32;
      config false;
    }
    leaf pmCapacityAllocRejHsPdschCodes {
      description "Number of rejected attempts to allocate HS-PDSCH codes (related to pmCapacityLimitHsPdschCodes)..";
      type uint64;
      config false;
    }
    leaf-list pmUsedTbs16Qam {
      description "Number of used transport block size (TBS) with 16 QAM. A transport block is a HARQ data block (MAC-hs PDU). The number of HARQ transmissions and retransmissions on the MAC-hs layer are counted. The counter does not consider whether or not the transmitted data originates from an MC-PQ. The counter reflects the cell perspective. Bins: [0]: Number of used transport blocks with size [0..1000[ bits [1]: Number of used transport blocks with size [1000..2000[ bits [2]: Number of used transport blocks with size [2000..3000[ bits ... [29]: Number of used transport blocks with size [29000..30000[ bits.";
      type uint32;
      max-elements 30;
    }
    leaf pmNoActiveSubFramesSpi10 {
      description "Sum of active 2 ms subframes for scheduling priority class 10..";
      type uint32;
      config false;
    }
    leaf pmAqmBasedDiscardSpi09 {
      description "Number of discards performed by the AQM feature for all Priority Queues (PQs) for Scheduling Priority Indicator (SPI) 09..";
      type uint32;
      config false;
    }
    leaf pmSumAckedBitsSpi03 {
      description "Total amount of acknowledged data sent on MAC-hs level per scheduling priority class 03. The counter does not consider whether or not the transmitted data originates from an MC-PQ. The counter reflects the cell perspective. Unit: 1 kilobit..";
      type uint32;
      config false;
    }
    leaf pmSumAckedBitsSpi02 {
      description "Total amount of acknowledged data sent on MAC-hs level per scheduling priority class 02. The counter does not consider whether or not the transmitted data originates from an MC-PQ. The counter reflects the cell perspective. Unit: 1 kilobit..";
      type uint32;
      config false;
    }
    leaf pmSumNonEmptyUserBuffersSpi11 {
      description "Number of user buffers for scheduling priority class 11 with data in buffer for each 2 ms subframes. The counter reflects the cell perspective..";
      type uint32;
      config false;
    }
    leaf-list pmUsedTbsQpsk {
      description "Number of used transport block size (TBS) with QPSK. A transport block is a HARQ data block (MAC-hs PDU). The number of HARQ transmissions and retransmissions on the MAC-hs layer are counted. The counter does not consider whether or not the transmitted data originates from an MC-PQ. The counter reflects the cell perspective. Bins: [0]: Number of used transport blocks with size [0..1000[ bits [1]: Number of used transport blocks with size [1000..2000[ bits [2]: Number of used transport blocks with size [2000..3000[ bits ... [29]: Number of used transport blocks with size [29000..30000[ bits.";
      type uint32;
      max-elements 30;
    }
    leaf-list pmTransmittedCarrierPowerNonHs {
      description "The distribution of transmitted carrier power for all codes NOT used for HSDPA. Bins: [0]: Number of sampled values lower than or equal to 0 dBm [1]: Number of sampled values in range ]0..1[ dBm [2]: Number of sampled values in range [1..2[ dBm ... [50]: Number of sampled values in range [49..50[ dBm [51]: Number of sampled values greater than or equal to 50 dBm.";
      type uint32;
      max-elements 52;
    }
    leaf pmSumAckedBitsMcPqSpi09 {
      description "Total amount of acknowledged MAC-hs/ehs data to UEs using any cell as serving HS-DSCH cell in MC mode. Only acknowledged data originating from a PQ with scheduling priority class 09 is considered. The counter reflects the PQ perspective. Unit: 1 kilobit..";
      type uint32;
      config false;
    }
    leaf pmSumAckedBitsPqSpi07 {
      description "Total amount of acknowledged MAC-hs/ehs data to UEs using any cell as serving HS-DSCH cell. Only acknowledged data originating from a PQ with scheduling priority class 07 is considered. The counter reflects the PQ perspective. Unit: 1 kilobit..";
      type uint32;
      config false;
    }
    leaf pmIubBasedDiscardFrameLossUserSpi08 {
      description "Number of Iub discards on all Priority Queues (PQs), that experienced the frame loss due to Iub congestion, for Scheduling Priority Indicator (SPI) 08..";
      type uint32;
      config false;
    }
    leaf pmSumJitterSpi02 {
      description "Sum of delay jitter of transmitted data before it is scheduled for scheduling priority class 02. The jitter delay is defined as a time difference between current delay and the previous one. Counter unit: 1 ms..";
      type uint32;
      config false;
    }
    leaf pmSumNonEmptyUserBuffers3McPqSpi06 {
      description "Number of PQs with data in the buffer for each 2 ms subframe. Only PQs with scheduling priority class 06 and belonging to UEs units configured to use cell as serving HS-DSCH cell in 3MC mode are considered. The counter reflects the PQ perspective..";
      type uint32;
      config false;
    }
    leaf pmAqmBasedDiscardSpi11 {
      description "Number of discards performed by the AQM feature for all Priority Queues (PQs) for Scheduling Priority Indicator (SPI) 11..";
      type uint32;
      config false;
    }
    leaf pmSumNoOfUsersSpi03 {
      description "Counts the total number of users for scheduling priority class 03 selected for each 2 ms subframe that is transmitted in the cell. For an MC-PQ only the counter in the serving HS-DSCH cell (of the UE to which the MC-PQ belongs) is updated. However, the aggregated measurement, based on all cells where the MC-PQ may be served, is considered when that counter is updated. The counter reflects the PQ perspective..";
      type uint32;
      config false;
    }
    leaf pmSamplesCapacityHsPdschCodes {
      description "Number of samples in pmSumCapacityHsPdschCodes..";
      type uint64;
      config false;
    }
    leaf pmSumJitterSpi08 {
      description "Sum of delay jitter of transmitted data before it is scheduled for scheduling priority class 08. The jitter delay is defined as a time difference between current delay and the previous one. Counter unit: 1 ms..";
      type uint32;
      config false;
    }
    leaf-list pmDelayDistributionSpi15 {
      description "Measurement to observe the distribution of the scheduling delay for scheduling priority class 15 on each subframe on those priority queue(s) selected for transmission. Bins: [0]: Number of delays in [0..10[ % [1]: Number of delays in [10..20[ % ... [9]: Number of delays in [90..100[ % [10]: Number of delays greater than or equal to 100%.";
      type uint32;
      max-elements 11;
    }
    leaf pmSumAckedBitsMcPqSpi01 {
      description "Total amount of acknowledged MAC-hs/ehs data to UEs using any cell as serving HS-DSCH cell in MC mode. Only acknowledged data originating from a PQ with scheduling priority class 01 is considered. The counter reflects the PQ perspective. Unit: 1 kilobit..";
      type uint32;
      config false;
    }
    leaf pmSumNonEmptyUserBuffersMcPqSpi08 {
      description "Number of PQs with data in the buffer for each 2 ms subframe. Only PQs with scheduling priority class 08 and belonging to UEs units configured to use cell as serving HS-DSCH cell in MC mode are considered. The counter reflects the PQ perspective..";
      type uint32;
      config false;
    }
    leaf pmNoInactiveRequiredSubFramesSpi01 {
      description "Number of subframes in which no data with scheduling priority class 01 is transmitted although there is user data to be sent in the validated PQ. This user data is either waiting for first transmission, or data waiting for transmission (NACK is received or no ACK/NACK). If a subframe goes without scheduling priority class 01, that is, just carrying other scheduling priority classes or going totally empty, then the counter is stepped. If the buffer of an MC-PQ is emptied, due to prior scheduling in another cell in the same subframe, and no other buffer in the cell contains data the counter is not incremented. The counter reflects the cell perspective..";
      type uint16;
      config false;
    }
    leaf pmSumAckedBitsSpi10 {
      description "Total amount of acknowledged data sent on MAC-hs level per scheduling priority class 10. The counter does not consider whether or not the transmitted data originates from an MC-PQ. The counter reflects the cell perspective. Unit: 1 kilobit..";
      type uint32;
      config false;
    }
    leaf-list pmDelayDistributionSpi02 {
      description "Measurement to observe the distribution of the scheduling delay for scheduling priority class 02 on each subframe on those priority queue(s) selected for transmission. Bins: [0]: Number of delays in [0..10[ % [1]: Number of delays in [10..20[ % ... [9]: Number of delays in [90..100[ % [10]: Number of delays greater than or equal to 100%.";
      type uint32;
      max-elements 11;
    }
    leaf pmSumNonEmptyUserBuffersSpi12 {
      description "Number of user buffers for scheduling priority class 12 with data in buffer for each 2 ms subframes. The counter reflects the cell perspective..";
      type uint32;
      config false;
    }
    leaf-list pmDelayDistributionSpi13 {
      description "Measurement to observe the distribution of the scheduling delay for scheduling priority class 13 on each subframe on those priority queue(s) selected for transmission. Bins: [0]: Number of delays in [0..10[ % [1]: Number of delays in [10..20[ % ... [9]: Number of delays in [90..100[ % [10]: Number of delays greater than or equal to 100%.";
      type uint32;
      max-elements 11;
    }
    leaf-list pmDelayDistributionSpi04 {
      description "Measurement to observe the distribution of the scheduling delay for scheduling priority class 04 on each subframe on those priority queue(s) selected for transmission. Bins: [0]: Number of delays in [0..10[ % [1]: Number of delays in [10..20[ % ... [9]: Number of delays in [90..100[ % [10]: Number of delays greater than or equal to 100%.";
      type uint32;
      max-elements 11;
    }
    leaf-list pmDelayDistributionSpi05 {
      description "Measurement to observe the distribution of the scheduling delay for scheduling priority class 05 on each subframe on those priority queue(s) selected for transmission. Bins: [0]: Number of delays in [0..10[ % [1]: Number of delays in [10..20[ % ... [9]: Number of delays in [90..100[ % [10]: Number of delays greater than or equal to 100%.";
      type uint32;
      max-elements 11;
    }
    leaf pmIubBasedDiscardFrameLossUserSpi04 {
      description "Number of Iub discards on all Priority Queues (PQs), that experienced the frame loss due to Iub congestion, for Scheduling Priority Indicator (SPI) 04..";
      type uint32;
      config false;
    }
    leaf pmSumAckedBits3McPqSpi09 {
      description "Total amount of acknowledged MAC-hs/ehs data to UEs using any cell as serving HS-DSCH cell in 3MC mode. Only acknowledged data originating from a PQ with scheduling priority class 09 is considered. The counter reflects the PQ perspective. Unit: 1 kilobit..";
      type uint32;
      config false;
    }
    leaf pmSumAckedBitsPqSpi11 {
      description "Total amount of acknowledged MAC-hs/ehs data to UEs using any cell as serving HS-DSCH cell. Only acknowledged data originating from a PQ with scheduling priority class 11 is considered. The counter reflects the PQ perspective. Unit: 1 kilobit..";
      type uint32;
      config false;
    }
    leaf pmSumDelaySpi02 {
      description "Sum of delay of transmitted data before it is scheduled for scheduling priority class 02. Counter unit: 1 ms..";
      type uint32;
      config false;
    }
    leaf pmSumNonEmptyUserBuffersPqSpi10 {
      description "Number of PQs with data in the buffer for each 2 ms subframe. Only PQs with scheduling priority class 10 and belonging to UEs units configured to use cell as serving HS-DSCH cell are considered. The counter reflects the PQ perspective..";
      type uint32;
      config false;
    }
    leaf pmSumAckedBitsPqSpi06 {
      description "Total amount of acknowledged MAC-hs/ehs data to UEs using any cell as serving HS-DSCH cell. Only acknowledged data originating from a PQ with scheduling priority class 06 is considered. The counter reflects the PQ perspective. Unit: 1 kilobit..";
      type uint32;
      config false;
    }
    leaf pmSumNonEmptyUserBuffersMcPqSpi06 {
      description "Number of PQs with data in the buffer for each 2 ms subframe. Only PQs with scheduling priority class 06 and belonging to UEs units configured to use cell as serving HS-DSCH cell in MC mode are considered. The counter reflects the PQ perspective..";
      type uint32;
      config false;
    }
    leaf pmSumNoOfUsersSpi00 {
      description "Counts the total number of users for scheduling priority class 00 selected for each 2 ms subframe that is transmitted in the cell. For an MC-PQ only the counter in the serving HS-DSCH cell (of the UE to which the MC-PQ belongs) is updated. However, the aggregated measurement, based on all cells where the MC-PQ may be served, is considered when that counter is updated. The counter reflects the PQ perspective..";
      type uint32;
      config false;
    }
    leaf pmNoActiveSubFramesSpi02 {
      description "Sum of active 2 ms subframes for scheduling priority class 02..";
      type uint32;
      config false;
    }
    leaf pmIubBasedDiscardFrameLossUserSpi05 {
      description "Number of Iub discards on all Priority Queues (PQs), that experienced the frame loss due to Iub congestion, for Scheduling Priority Indicator (SPI) 05..";
      type uint32;
      config false;
    }
    leaf pmSampleScAndMcActUes {
      description "The aggregated number of sample values that pmSumScAndMcActUes has been updated with. The following counters are sampled simultaneously and therefore this counter is used to observe how many sample values each counter has been incremented with: * pmSumScAndMcActUes * pmSumMcSecActUes * pmSumMcSecDeactUes The counter reflects the cell perspective..";
      type uint16;
      config false;
    }
    leaf pmSumNoOfUsersSpi15 {
      description "Counts the total number of users for scheduling priority class 15 selected for each 2 ms subframe that is transmitted in the cell. For an MC-PQ only the counter in the serving HS-DSCH cell (of the UE to which the MC-PQ belongs) is updated. However, the aggregated measurement, based on all cells where the MC-PQ may be served, is considered when that counter is updated. The counter reflects the PQ perspective..";
      type uint32;
      config false;
    }
    leaf pmNoInactiveRequiredSubFramesSpi02 {
      description "Number of subframes in which no data with scheduling priority class 02 is transmitted although there is user data to be sent in the validated PQ. This user data is either waiting for first transmission, or data waiting for transmission (NACK is received or no ACK/NACK). If a subframe goes without scheduling priority class 02, that is, just carrying other scheduling priority classes or going totally empty, then the counter is stepped. If the buffer of an MC-PQ is emptied, due to prior scheduling in another cell in the same subframe, and no other buffer in the cell contains data the counter is not incremented. The counter reflects the cell perspective..";
      type uint16;
      config false;
    }
    leaf pmAqmBasedDiscardSpi03 {
      description "Number of discards performed by the AQM feature for all Priority Queues (PQs) for Scheduling Priority Indicator (SPI) 03..";
      type uint32;
      config false;
    }
    leaf pmSumDelaySpi14 {
      description "Sum of delay of transmitted data before it is scheduled for scheduling priority class 14. Counter unit: 1 ms..";
      type uint32;
      config false;
    }
    leaf pmSumBlockedTransmissionsRlim {
      description "Counts number of 2ms TTIs where UE units are blocked. UE unit is considered blocked in TTI if it is not scheduled to transmit any data even though it has data available in its queues. For each UE unit, only blocked TTIs that are immediately followed by resource-limited scheduling without any other UE unit scheduled in parallel, are counted. Scheduling decision is defined to be resource-limited if transport block size is limited only by available codes or power, or both..";
      type uint32;
      config false;
    }
    leaf pmSumJitterSpi03 {
      description "Sum of delay jitter of transmitted data before it is scheduled for scheduling priority class 03. The jitter delay is defined as a time difference between current delay and the previous one. Counter unit: 1 ms..";
      type uint32;
      config false;
    }
    leaf pmNoInactiveRequiredSubFramesSpi14 {
      description "Number of subframes in which no data with scheduling priority class 14 is transmitted although there is user data to be sent in the validated PQ. This user data is either waiting for first transmission, or data waiting for transmission (NACK is received or no ACK/NACK). If a subframe goes without scheduling priority class 14, that is, just carrying other scheduling priority classes or going totally empty, then the counter is stepped. If the buffer of an MC-PQ is emptied, due to prior scheduling in another cell in the same subframe, and no other buffer in the cell contains data the counter is not incremented. The counter reflects the cell perspective..";
      type uint16;
      config false;
    }
    leaf pmSumNonEmptyUserBuffersMcPqSpi03 {
      description "Number of PQs with data in the buffer for each 2 ms subframe. Only PQs with scheduling priority class 03 and belonging to UEs units configured to use cell as serving HS-DSCH cell in MC mode are considered. The counter reflects the PQ perspective..";
      type uint32;
      config false;
    }
    leaf-list pmSamplesSumAckedBitsUsersRlim {
      description "Distribution over number of multiplexed UE units for each 2ms TTI, indicates how many sample values pmSumAckedBitsUsersRlim is incremented. Value used to index distribution is same as used to index pmSumAckedBitsUsersRlim when it is incremented. Ranges: [0] : Number of increments of pmSumAckedBitsUsersRlim for 2ms TTIs with 2 multiplexed UE units [1] : Number of increments of pmSumAckedBitsUsersRlim for 2ms TTIs with 3 multiplexed UE units [2] : Number of increments of pmSumAckedBitsUsersRlim for 2ms TTIs with 4 multiplexed UE units transmission.";
      type uint16;
      max-elements 3;
    }
    leaf pmNoInactiveRequiredSubFramesSpi15 {
      description "Number of subframes in which no data with scheduling priority class 15 is transmitted although there is user data to be sent in the validated PQ. This user data is either waiting for first transmission, or data waiting for transmission (NACK is received or no ACK/NACK). If a subframe goes without scheduling priority class 15, that is, just carrying other scheduling priority classes or going totally empty, then the counter is stepped. If the buffer of an MC-PQ is emptied, due to prior scheduling in another cell in the same subframe, and no other buffer in the cell contains data the counter is not incremented. The counter reflects the cell perspective..";
      type uint16;
      config false;
    }
    leaf-list pmSumOfHsScchUsedPwrHsFach {
      description "The distribution of HS-SCCH transmitted power per cell for HS-FACH. Bins: [0]: Number of samples with values less than 0 dBm or no transmission [1]: Number of samples in range [0..0.5[ dBm [2]: Number of samples in range [0.5..1[ dBm ... [101]: Number of samples in range [50..50.5[ dBm [102]: Number of samples >= 50.5 dBm.";
      type uint16;
      max-elements 103;
    }
    leaf pmSumTransmittedBitsSpi02 {
      description "Measurement to observe the total amount of data, in kbits, sent on MAC-hs level per scheduling priority class 02. The counter does not consider whether or not the transmitted data originates from an MC-PQ. The counter reflects the cell perspective..";
      type uint32;
      config false;
    }
    leaf pmSumDelaySpi08 {
      description "Sum of delay of transmitted data before it is scheduled for scheduling priority class 08. Counter unit: 1 ms..";
      type uint32;
      config false;
    }
    leaf pmNoInactiveRequiredSubFramesSpi05 {
      description "Number of subframes in which no data with scheduling priority class 05 is transmitted although there is user data to be sent in the validated PQ. This user data is either waiting for first transmission, or data waiting for transmission (NACK is received or no ACK/NACK). If a subframe goes without scheduling priority class 05, that is, just carrying other scheduling priority classes or going totally empty, then the counter is stepped. If the buffer of an MC-PQ is emptied, due to prior scheduling in another cell in the same subframe, and no other buffer in the cell contains data the counter is not incremented. The counter reflects the cell perspective..";
      type uint16;
      config false;
    }
    leaf pmNoActiveSubFramesSpi13 {
      description "Sum of active 2 ms subframes for scheduling priority class 13..";
      type uint32;
      config false;
    }
    leaf pmSumNonEmptyUserBuffers3McPqSpi09 {
      description "Number of PQs with data in the buffer for each 2 ms subframe. Only PQs with scheduling priority class 09 and belonging to UEs units configured to use cell as serving HS-DSCH cell in 3MC mode are considered. The counter reflects the PQ perspective..";
      type uint32;
      config false;
    }
    leaf pmAqmBasedDiscardSpi14 {
      description "Number of discards performed by the AQM feature for all Priority Queues (PQs) for Scheduling Priority Indicator (SPI) 14..";
      type uint32;
      config false;
    }
    leaf-list pmAvailableMixedModeExtraPower {
      description "Measures and observes the distribution of available extra power borrowed from other RAT(s), which is configured on the same Power Amplifier(PA). Presented as percentage of maximum power limit indicated by pmAvailableMixedModeExtraPowerLimit. Bins: [0] Number of sampled values in range [0..2[ % [1] Number of sampled values in range [2..4[ % ... [49] Number of sampled values is range [98..100] %.";
      type uint32;
      max-elements 50;
    }
    leaf pmSumNoOfUsersSpi06 {
      description "Counts the total number of users for scheduling priority class 06 selected for each 2 ms subframe that is transmitted in the cell. For an MC-PQ only the counter in the serving HS-DSCH cell (of the UE to which the MC-PQ belongs) is updated. However, the aggregated measurement, based on all cells where the MC-PQ may be served, is considered when that counter is updated. The counter reflects the PQ perspective..";
      type uint32;
      config false;
    }
    leaf pmSumAckedBits3McPqSpi07 {
      description "Total amount of acknowledged MAC-hs/ehs data to UEs using any cell as serving HS-DSCH cell in 3MC mode. Only acknowledged data originating from a PQ with scheduling priority class 07 is considered. The counter reflects the PQ perspective. Unit: 1 kilobit..";
      type uint32;
      config false;
    }
    leaf pmNoActiveSubFrames {
      description "Number of active 2 ms subframes. The counter does not consider whether or not the transmitted data originates from an MC-PQ. The counter reflects the cell perspective..";
      type uint16;
      config false;
    }
    leaf pmSumNonEmptyUserBuffersPqSpi01 {
      description "Number of PQs with data in the buffer for each 2 ms subframe. Only PQs with scheduling priority class 01 and belonging to UEs units configured to use cell as serving HS-DSCH cell are considered. The counter reflects the PQ perspective..";
      type uint32;
      config false;
    }
    leaf pmNoActiveSubFramesSpi00 {
      description "Sum of active 2 ms subframes for scheduling priority class 00..";
      type uint32;
      config false;
    }
    leaf pmSumAckedBitsMcPqSpi13 {
      description "Total amount of acknowledged MAC-hs/ehs data to UEs using any cell as serving HS-DSCH cell in MC mode. Only acknowledged data originating from a PQ with scheduling priority class 13 is considered. The counter reflects the PQ perspective. Unit: 1 kilobit..";
      type uint32;
      config false;
    }
    leaf pmSumNonEmptyUserBuffersSpi06 {
      description "Number of user buffers for scheduling priority class 06 with data in buffer for each 2 ms subframes. The counter reflects the cell perspective..";
      type uint32;
      config false;
    }
    leaf pmSumAckedBitsMcPqSpi00 {
      description "Total amount of acknowledged MAC-hs/ehs data to UEs using any cell as serving HS-DSCH cell in MC mode. Only acknowledged data originating from a PQ with scheduling priority class 00 is considered. The counter reflects the PQ perspective. Unit: 1 kilobit..";
      type uint32;
      config false;
    }
    leaf pmNoInactiveRequiredSubFramesSpi09 {
      description "Number of subframes in which no data with scheduling priority class 09 is transmitted although there is user data to be sent in the validated PQ. This user data is either waiting for first transmission, or data waiting for transmission (NACK is received or no ACK/NACK). If a subframe goes without scheduling priority class 09, that is, just carrying other scheduling priority classes or going totally empty, then the counter is stepped. If the buffer of an MC-PQ is emptied, due to prior scheduling in another cell in the same subframe, and no other buffer in the cell contains data the counter is not incremented. The counter reflects the cell perspective..";
      type uint16;
      config false;
    }
    leaf pmSumAckedBitsSpi07 {
      description "Total amount of acknowledged data sent on MAC-hs level per scheduling priority class 07. The counter does not consider whether or not the transmitted data originates from an MC-PQ. The counter reflects the cell perspective. Unit: 1 kilobit..";
      type uint32;
      config false;
    }
    leaf pmSumDelaySpi03 {
      description "Sum of delay of transmitted data before it is scheduled for scheduling priority class 03. Counter unit: 1 ms..";
      type uint32;
      config false;
    }
    leaf pmIubBasedDiscardFrameLossUserSpi02 {
      description "Number of Iub discards on all Priority Queues (PQs), that experienced the frame loss due to Iub congestion, for Scheduling Priority Indicator (SPI) 02..";
      type uint32;
      config false;
    }
    leaf pmSumJitterSpi01 {
      description "Sum of delay jitter of transmitted data before it is scheduled for scheduling priority class 01. The jitter delay is defined as a time difference between current delay and the previous one. Counter unit: 1 ms..";
      type uint32;
      config false;
    }
    leaf pmSumNonEmptyUserBuffersMcPqSpi09 {
      description "Number of PQs with data in the buffer for each 2 ms subframe. Only PQs with scheduling priority class 09 and belonging to UEs units configured to use cell as serving HS-DSCH cell in MC mode are considered. The counter reflects the PQ perspective..";
      type uint32;
      config false;
    }
    leaf pmSumNonEmptyUserBuffersSpi01 {
      description "Number of user buffers for scheduling priority class 01 with data in buffer for each 2 ms subframes. The counter reflects the cell perspective..";
      type uint32;
      config false;
    }
    leaf pmSumNonEmptyUserBuffers3McPqSpi12 {
      description "Number of PQs with data in the buffer for each 2 ms subframe. Only PQs with scheduling priority class 12 and belonging to UEs units configured to use cell as serving HS-DSCH cell in 3MC mode are considered. The counter reflects the PQ perspective..";
      type uint32;
      config false;
    }
    leaf pmSumTransmittedBitsSpi10 {
      description "Measurement to observe the total amount of data, in kbits, sent on MAC-hs level per scheduling priority class 10. The counter does not consider whether or not the transmitted data originates from an MC-PQ. The counter reflects the cell perspective..";
      type uint32;
      config false;
    }
    leaf pmSumAckedBitsSpi00 {
      description "Total amount of acknowledged data sent on MAC-hs level per scheduling priority class 00. The counter does not consider whether or not the transmitted data originates from an MC-PQ. The counter reflects the cell perspective. Unit: 1 kilobit..";
      type uint32;
      config false;
    }
    leaf pmSumDelaySpi00 {
      description "Sum of delay of transmitted data before it is scheduled for scheduling priority class 00. Counter unit: 1 ms..";
      type uint32;
      config false;
    }
    leaf pmSumAckedBits3McPqSpi03 {
      description "Total amount of acknowledged MAC-hs/ehs data to UEs using any cell as serving HS-DSCH cell in 3MC mode. Only acknowledged data originating from a PQ with scheduling priority class 03 is considered. The counter reflects the PQ perspective. Unit: 1 kilobit..";
      type uint32;
      config false;
    }
    leaf pmSumAckedBits3McPqSpi15 {
      description "Total amount of acknowledged MAC-hs/ehs data to UEs using any cell as serving HS-DSCH cell in 3MC mode. Only acknowledged data originating from a PQ with scheduling priority class 15 is considered. The counter reflects the PQ perspective. Unit: 1 kilobit..";
      type uint32;
      config false;
    }
    leaf pmSumNoOfUsersSpi10 {
      description "Counts the total number of users for scheduling priority class 10 selected for each 2 ms subframe that is transmitted in the cell. For an MC-PQ only the counter in the serving HS-DSCH cell (of the UE to which the MC-PQ belongs) is updated. However, the aggregated measurement, based on all cells where the MC-PQ may be served, is considered when that counter is updated. The counter reflects the PQ perspective..";
      type uint32;
      config false;
    }
    leaf pmNoInactiveRequiredSubFramesSpi06 {
      description "Number of subframes in which no data with scheduling priority class 06 is transmitted although there is user data to be sent in the validated PQ. This user data is either waiting for first transmission, or data waiting for transmission (NACK is received or no ACK/NACK). If a subframe goes without scheduling priority class 06, that is, just carrying other scheduling priority classes or going totally empty, then the counter is stepped. If the buffer of an MC-PQ is emptied, due to prior scheduling in another cell in the same subframe, and no other buffer in the cell contains data the counter is not incremented. The counter reflects the cell perspective..";
      type uint16;
      config false;
    }
    leaf pmSumAckedBits3McPqSpi05 {
      description "Total amount of acknowledged MAC-hs/ehs data to UEs using any cell as serving HS-DSCH cell in 3MC mode. Only acknowledged data originating from a PQ with scheduling priority class 05 is considered. The counter reflects the PQ perspective. Unit: 1 kilobit..";
      type uint32;
      config false;
    }
    leaf pmSumTransmittedBitsSpi07 {
      description "Measurement to observe the total amount of data, in kbits, sent on MAC-hs level per scheduling priority class 07. The counter does not consider whether or not the transmitted data originates from an MC-PQ. The counter reflects the cell perspective..";
      type uint32;
      config false;
    }
    leaf pmIubMacdPduCellReceivedBits {
      description "Number of Mbit (1 000 000 bits) received over Iub HS MAC-d PDU in the cell. MAC-d PDUs, belonging to a MC-PQ, are counted in the serving HS-DSCH cell of the UE to which the PQ belongs (regardless of if the PDU is sent in that cell or not). The counter reflects the cell perspective..";
      type uint32;
      config false;
    }
    leaf pmSumNoOfUsersSpi07 {
      description "Counts the total number of users for scheduling priority class 07 selected for each 2 ms subframe that is transmitted in the cell. For an MC-PQ only the counter in the serving HS-DSCH cell (of the UE to which the MC-PQ belongs) is updated. However, the aggregated measurement, based on all cells where the MC-PQ may be served, is considered when that counter is updated. The counter reflects the PQ perspective..";
      type uint32;
      config false;
    }
    leaf-list pmDelayDistributionSpi12 {
      description "Measurement to observe the distribution of the scheduling delay for scheduling priority class 12 on each subframe on those priority queue(s) selected for transmission. Bins: [0]: Number of delays in [0..10[ % [1]: Number of delays in [10..20[ % ... [9]: Number of delays in [90..100[ % [10]: Number of delays greater than or equal to 100%.";
      type uint32;
      max-elements 11;
    }
    leaf pmCapacityLimitHsDschUsers {
      description "Licensed limit for number of HS-DSCH users in the cell. License key value if valid license key, else default value of NodeBLocalCell::maxNumHsdpaUsers if invalid/missing license key, else max value of NodeBLocalCell::maxNumHsdpaUsers if emergency unlock is active..";
      type int64;
      config false;
    }
    leaf pmSumNonEmptyUserBuffersPqSpi00 {
      description "Number of PQs with data in the buffer for each 2 ms subframe. Only PQs with scheduling priority class 00 and belonging to UEs units configured to use cell as serving HS-DSCH cell are considered. The counter reflects the PQ perspective..";
      type uint32;
      config false;
    }
    leaf-list pmSumTransmissionsUsersRlim {
      description "Distribution over number of multiplexed UE units for each 2ms TTI, of total amount of transmissions to UE units configured to use cell, including retransmissions, on MAC-hs or MAC-ehs level until acknowledgement is received, under resource-limited conditions. Scheduling decision is defined to be resource-limited if transport block size is limited only by available codes or power, or both. In addition, condition is not fulfilled if any retransmissions or transmissions to UE units configured in MIMO or HS-FACH mode occur among multiplexed UE units. Ranges: [0] : Number of transmissions for data initially scheduled in 2ms TTIs with 2 multiplexed UE units [1] : Number of transmissions for data initially scheduled in 2ms TTIs with 3 multiplexed UE units [2] : Number of transmissions for data initially scheduled in 2ms TTIs with 4 multiplexed UE units.";
      type uint16;
      max-elements 3;
    }
    leaf pmSumDelaySpi12 {
      description "Sum of delay of transmitted data before it is scheduled for scheduling priority class 12. Counter unit: 1 ms..";
      type uint32;
      config false;
    }
    leaf-list pmAck64Qam {
      description "Counting the number of received ACKs for a specified transport block size (TBS) with 64 QAM. The number of successful HARQ transmissions are counted of the MAC-hs layer. The counter does not consider whether or not the transmitted data originates from an MC-PQ. The counter does not consider ACK/NACKs corresponding to HS-SCCH orders. The counter reflects the cell perspective. Bins: [0]: Number of ACKs for transport block with size [0..1000[ bits [1]: Number of ACKs for transport block with size [1000..2000[ bits ... [15]: Number of ACKs for transport block with size [15000..16000[ bits [16]: Number of ACKs for transport block with size [16000..17000[ bits [17]: Number of ACKs for transport block with size [17000..19000[ bits [16]: Number of ACKs for transport block with size [19000..21000[ bits ... [28]: Number of ACKs for transport block with size [39000..41000[ bits [29]: Number of ACKs for transport block with size [41000..43000[ bits.";
      type uint32;
      max-elements 30;
    }
    leaf pmNoInactiveRequiredSubFramesSpi04 {
      description "Number of subframes in which no data with scheduling priority class 04 is transmitted although there is user data to be sent in the validated PQ. This user data is either waiting for first transmission, or data waiting for transmission (NACK is received or no ACK/NACK). If a subframe goes without scheduling priority class 04, that is, just carrying other scheduling priority classes or going totally empty, then the counter is stepped. If the buffer of an MC-PQ is emptied, due to prior scheduling in another cell in the same subframe, and no other buffer in the cell contains data the counter is not incremented. The counter reflects the cell perspective..";
      type uint16;
      config false;
    }
    leaf pmSumAckedBits3McPqSpi01 {
      description "Total amount of acknowledged MAC-hs/ehs data to UEs using any cell as serving HS-DSCH cell in 3MC mode. Only acknowledged data originating from a PQ with scheduling priority class 01 is considered. The counter reflects the PQ perspective. Unit: 1 kilobit..";
      type uint32;
      config false;
    }
    leaf pmSumJitterSpi06 {
      description "Sum of delay jitter of transmitted data before it is scheduled for scheduling priority class 06. The jitter delay is defined as a time difference between current delay and the previous one. Counter unit: 1 ms..";
      type uint32;
      config false;
    }
    leaf pmSumNonEmptyUserBuffers3McPqSpi07 {
      description "Number of PQs with data in the buffer for each 2 ms subframe. Only PQs with scheduling priority class 07 and belonging to UEs units configured to use cell as serving HS-DSCH cell in 3MC mode are considered. The counter reflects the PQ perspective..";
      type uint32;
      config false;
    }
    leaf-list pmUsedTbs64Qam {
      description "Counting the number of used transport block size (TBS) with 64 QAM. The number of successful HARQ transmissions are counted on the MAC-hs layer. The counter does not consider whether or not the transmitted data originates from an MC-PQ. The counter reflects the cell perspective. Bins: [0]: Number of used transport blocks with size [0..1000[ bits [1]: Number of used transport blocks with size [1000..2000[ bits ... [15]: Number of used transport blocks with size [15000..16000[ bits [16]: Number of used transport blocks with size [16000..17000[ bits [17]: Number of used transport blocks with size [17000..19000[ bits [16], number of used transport blocks with size [19000..21000[ bits ... [28]: Number of used transport blocks with size [39000..41000[ bits [29]: Number of used transport blocks with size [41000..43000[ bits.";
      type uint32;
      max-elements 30;
    }
    leaf pmSumNonEmptyUserBuffersPqSpi07 {
      description "Number of PQs with data in the buffer for each 2 ms subframe. Only PQs with scheduling priority class 07 and belonging to UEs units configured to use cell as serving HS-DSCH cell are considered. The counter reflects the PQ perspective..";
      type uint32;
      config false;
    }
    leaf pmSumNonEmptyUserBuffersPqSpi06 {
      description "Number of PQs with data in the buffer for each 2 ms subframe. Only PQs with scheduling priority class 06 and belonging to UEs units configured to use cell as serving HS-DSCH cell are considered. The counter reflects the PQ perspective..";
      type uint32;
      config false;
    }
    leaf pmNoInactiveRequiredSubFramesSpi10 {
      description "Number of subframes in which no data with scheduling priority class 10 is transmitted although there is user data to be sent in the validated PQ. This user data is either waiting for first transmission, or data waiting for transmission (NACK is received or no ACK/NACK). If a subframe goes without scheduling priority class 10, that is, just carrying other scheduling priority classes or going totally empty, then the counter is stepped. If the buffer of an MC-PQ is emptied, due to prior scheduling in another cell in the same subframe, and no other buffer in the cell contains data the counter is not incremented. The counter reflects the cell perspective..";
      type uint16;
      config false;
    }
    leaf pmSumNonEmptyUserBuffersMcPqSpi02 {
      description "Number of PQs with data in the buffer for each 2 ms subframe. Only PQs with scheduling priority class 02 and belonging to UEs units configured to use cell as serving HS-DSCH cell in MC mode are considered. The counter reflects the PQ perspective..";
      type uint32;
      config false;
    }
    leaf pmNoActiveSubFramesSpi15 {
      description "Sum of active 2 ms subframes for scheduling priority class 15..";
      type uint32;
      config false;
    }
    leaf pmSumAckedBitsSpi11 {
      description "Total amount of acknowledged data sent on MAC-hs level per scheduling priority class 11. The counter does not consider whether or not the transmitted data originates from an MC-PQ. The counter reflects the cell perspective. Unit: 1 kilobit..";
      type uint32;
      config false;
    }
    leaf pmCapacityAllocRejHsDschUsers {
      description "Number of rejected attempts to allocate resources for new HS-DSCH user (related to pmCapacityLimitHsDschUsers)..";
      type uint64;
      config false;
    }
    leaf-list pmSamplesSumAckedBits {
      description "Distribution states how many sample values pmSumAckedBits is incremented. Ranges: [0] : Number of increments of pmSumAckedBits[0] [1] : Number of increments of pmSumAckedBits[1] ... [30] : Number of increments of pmSumAckedBits[30].";
      type uint16;
      max-elements 31;
    }
    leaf pmSumNonEmptyUserBuffersMcPqSpi01 {
      description "Number of PQs with data in the buffer for each 2 ms subframe. Only PQs with scheduling priority class 01 and belonging to UEs units configured to use cell as serving HS-DSCH cell in MC mode are considered. The counter reflects the PQ perspective..";
      type uint32;
      config false;
    }
    leaf-list pmUnusedPowerWHs {
      description "Distribution of HS power not used in the cell and available for other cells. Presented as percentage of maximum power visible in NodeBSectorCarrier::pmTransmittedCarrierPowerWLimit. Bins: [0]: Number of sampled values in range [0..2[ % [1]: Number of sampled values in range [2..4[ % [2]: Number of sampled values in range [4..6[ % ... [49]: Number of sampled values in range [98..100] %.";
      type uint32;
      max-elements 50;
    }
    leaf pmNoActiveSubFramesSpi12 {
      description "Sum of active 2 ms subframes for scheduling priority class 12..";
      type uint32;
      config false;
    }
    leaf pmSumNonEmptyUserBuffers3McPqSpi02 {
      description "Number of PQs with data in the buffer for each 2 ms subframe. Only PQs with scheduling priority class 02 and belonging to UEs units configured to use cell as serving HS-DSCH cell in 3MC mode are considered. The counter reflects the PQ perspective..";
      type uint32;
      config false;
    }
    leaf pmSumAckedBits3McPqSpi13 {
      description "Total amount of acknowledged MAC-hs/ehs data to UEs using any cell as serving HS-DSCH cell in 3MC mode. Only acknowledged data originating from a PQ with scheduling priority class 13 is considered. The counter reflects the PQ perspective. Unit: 1 kilobit..";
      type uint32;
      config false;
    }
    leaf pmSumAckedBits3McPqSpi12 {
      description "Total amount of acknowledged MAC-hs/ehs data to UEs using any cell as serving HS-DSCH cell in 3MC mode. Only acknowledged data originating from a PQ with scheduling priority class 12 is considered. The counter reflects the PQ perspective. Unit: 1 kilobit..";
      type uint32;
      config false;
    }
    leaf-list pmNoOfHsUsersPerTti {
      description "Average number of users (including HS-FACH users) scheduled in cell at each 2 ms subframe. A HS-FACH user is a UE unit that is in the RRC state CELL_FACH (on the RNC level) and uses transport channel HS-DSCH, not FACH. The counter reflects the cell perspective. Bins: [0]: Number of samples equal to 0 users [1]: Number of samples equal to 1 user [2]: Number of samples equal to 2 users [3]: Number of samples equal to 3 users [4]: Number of samples equal to 4 users.";
      type uint16;
      max-elements 5;
    }
    leaf pmAqmBasedDiscardSpi08 {
      description "Number of discards performed by the AQM feature for all Priority Queues (PQs) for Scheduling Priority Indicator (SPI) 08..";
      type uint32;
      config false;
    }
    leaf pmSumNonEmptyUserBuffersPqSpi13 {
      description "Number of PQs with data in the buffer for each 2 ms subframe. Only PQs with scheduling priority class 13 and belonging to UEs units configured to use cell as serving HS-DSCH cell are considered. The counter reflects the PQ perspective..";
      type uint32;
      config false;
    }
    leaf pmSumTransmittedBitsSpi09 {
      description "Measurement to observe the total amount of data, in kbits, sent on MAC-hs level per scheduling priority class 09. The counter does not consider whether or not the transmitted data originates from an MC-PQ. The counter reflects the cell perspective..";
      type uint32;
      config false;
    }
    leaf pmSumMcSecActUes {
      description "Number of UEs configured to use cell as activated secondary serving HS-DSCH cell. As a consequence only UEs in MC mode are considered by the counter. The counter is the aggregate of sample values taken every 100 ms. The counter reflects the cell perspective..";
      type uint32;
      config false;
    }
    leaf pmSumJitterSpi11 {
      description "Sum of delay jitter of transmitted data before it is scheduled for scheduling priority class 11. The jitter delay is defined as a time difference between current delay and the previous one. Counter unit: 1 ms..";
      type uint32;
      config false;
    }
    leaf pmSumScAndMcActUes {
      description "The number of UEs configured to use the cell as serving HS-DSCH cell or as activated secondary serving HS-DSCH cell. As a consequence both UEs in single-carrier mode and in multi-carrier mode are considered by the counter. The counter is the aggregate of sample values taken every 100 ms. The counter reflects the cell perspective..";
      type uint16;
      config false;
    }
    leaf pmSumNonEmptyUserBuffers3McPqSpi00 {
      description "Number of PQs with data in the buffer for each 2 ms subframe. Only PQs with scheduling priority class 00 and belonging to UEs units configured to use cell as serving HS-DSCH cell in 3MC mode are considered. The counter reflects the PQ perspective..";
      type uint32;
      config false;
    }
    leaf pmSumAckedBitsMcPqSpi07 {
      description "Total amount of acknowledged MAC-hs/ehs data to UEs using any cell as serving HS-DSCH cell in MC mode. Only acknowledged data originating from a PQ with scheduling priority class 07 is considered. The counter reflects the PQ perspective. Unit: 1 kilobit..";
      type uint32;
      config false;
    }
    leaf pmSumNonEmptyUserBuffersPqSpi09 {
      description "Number of PQs with data in the buffer for each 2 ms subframe. Only PQs with scheduling priority class 09 and belonging to UEs units configured to use cell as serving HS-DSCH cell are considered. The counter reflects the PQ perspective..";
      type uint32;
      config false;
    }
    leaf pmAqmBasedDiscardSpi06 {
      description "Number of discards performed by the AQM feature for all Priority Queues (PQs) for Scheduling Priority Indicator (SPI) 06..";
      type uint32;
      config false;
    }
    leaf pmSumNonEmptyUserBuffersPqSpi14 {
      description "Number of PQs with data in the buffer for each 2 ms subframe. Only PQs with scheduling priority class 14 and belonging to UEs units configured to use cell as serving HS-DSCH cell are considered. The counter reflects the PQ perspective..";
      type uint32;
      config false;
    }
    leaf pmSumTransmittedBitsSpi03 {
      description "Measurement to observe the total amount of data, in kbits, sent on MAC-hs level per scheduling priority class 03. The counter does not consider whether or not the transmitted data originates from an MC-PQ. The counter reflects the cell perspective..";
      type uint32;
      config false;
    }
    leaf-list pmCapacityOfHsDschUsers {
      description "Distribution of number of HS-DSCH users, as percentages of the license controlled limit visible in pmCapacityLimitHsDschUsers. Bins: [0]: Number of sampled values in range [0..5[ % [1]: Number of sampled values in range [5..10[ % ... [18]: Number of sampled values in range [90..95[ % [19]: Number of sampled values >= 95%.";
      type uint64;
      max-elements 20;
    }
    leaf pmCapacityLimitHsPdschCodes {
      description "Licensed limit for number of HS-PDSCH codes in the cell. License key value if valid license key, else default value of NodeBLocalCell::maxNumHsPdschCodes if invalid/missing license key, else max value of NodeBLocalCell::maxNumHsPdschCodes if emergency unlock is active..";
      type int64;
      config false;
    }
    leaf pmSumAckedBitsPqSpi02 {
      description "Total amount of acknowledged MAC-hs/ehs data to UEs using any cell as serving HS-DSCH cell. Only acknowledged data originating from a PQ with scheduling priority class 02 is considered. The counter reflects the PQ perspective. Unit: 1 kilobit..";
      type uint32;
      config false;
    }
    leaf-list pmDelayDistributionSpi09 {
      description "Measurement to observe the distribution of the scheduling delay for scheduling priority class 09 on each subframe on those priority queue(s) selected for transmission. Bins: [0]: Number of delays in [0..10[ % [1]: Number of delays in [10..20[ % ... [9]: Number of delays in [90..100[ % [10]: Number of delays greater than or equal to 100%.";
      type uint32;
      max-elements 11;
    }
    leaf pmSumAckedBitsMcPqSpi05 {
      description "Total amount of acknowledged MAC-hs/ehs data to UEs using any cell as serving HS-DSCH cell in MC mode. Only acknowledged data originating from a PQ with scheduling priority class 05 is considered. The counter reflects the PQ perspective. Unit: 1 kilobit..";
      type uint32;
      config false;
    }
    leaf pmSumMcSecDeactUes {
      description "Number of UEs configured to use cell as deactivated secondary serving HS-DSCH cell. As a consequence only UEs in multi-carrier mode are considered by the counter. The counter is the aggregate of sample values taken every 100 ms. The counter reflects the cell perspective..";
      type uint32;
      config false;
    }
    leaf pmAqmBasedDiscardSpi01 {
      description "Number of discards performed by the AQM feature for all Priority Queues (PQs) for Scheduling Priority Indicator (SPI) 01..";
      type uint32;
      config false;
    }
    leaf pmSumNonEmptyUserBuffersPqSpi04 {
      description "Number of PQs with data in the buffer for each 2 ms subframe. Only PQs with scheduling priority class 04 and belonging to UEs units configured to use cell as serving HS-DSCH cell are considered. The counter reflects the PQ perspective..";
      type uint32;
      config false;
    }
    leaf pmSumNonEmptyUserBuffersMcPqSpi00 {
      description "Number of PQs with data in the buffer for each 2 ms subframe. Only PQs with scheduling priority class 00 and belonging to UEs units configured to use cell as serving HS-DSCH cell in MC mode are considered. The counter reflects the PQ perspective..";
      type uint32;
      config false;
    }
    leaf pmSumTransmittedBitsSpi08 {
      description "Measurement to observe the total amount of data, in kbits, sent on MAC-hs level per scheduling priority class 08. The counter does not consider whether or not the transmitted data originates from an MC-PQ. The counter reflects the cell perspective..";
      type uint32;
      config false;
    }
    leaf pmSumTransmittedBitsSpi06 {
      description "Measurement to observe the total amount of data, in kbits, sent on MAC-hs level per scheduling priority class 06. The counter does not consider whether or not the transmitted data originates from an MC-PQ. The counter reflects the cell perspective..";
      type uint32;
      config false;
    }
    leaf-list pmSumAckedBitsRlim {
      description "Distribution over CQI, of total amount of acknowledged data sent on MAC-hs or MAC-ehs level to UE units configured to use cell, under resource limited conditions. Scheduling decision is defined to be resource-limited if transport block size is limited only by available codes or power, or both. In addition, only one single UE unit must be scheduled for data transmission in 2ms TTI. CQI value used to index distribution is one reported by UE units and applicable during initial transmission. For non-64QAM-capable UE units, CQI value is mapped down to align with CQI reporting for 64QAM-capable UE units, as further described for PDF range 26...30. Ranges: [0] : Sum of acknowledged data sent for reported CQI=0 at initial transmission [1] : Sum of acknowledged data sent for reported CQI=1 at initial transmission ... [25] : Sum of acknowledged data sent for reported CQI=25 at initial transmission [26] : Sum of acknowledged data sent for reported CQI=26 for 64QAM-capable UE units, or reported CQI=26 and 27 for non-64QAM-capable UE units, at initial transmission [27] : Sum of acknowledged data sent for reported CQI=27 for 64QAM-capable UE units, or reported CQI=28 and 29 for non-64QAM-capable UE units, at initial transmission [28] : Sum of acknowledged data sent for reported CQI=28 for 64QAM-capable UE units, or reported CQI=30 for non-64QAM-capable UE units, at initial transmission [29] : Sum of acknowledged data sent for reported CQI=29 at initial transmission for 64QAM-capable UE units (not used for non-64QAM-capable UE units) [30] : Sum of acknowledged data sent for reported CQI=30 at initial transmission for 64QAM-capable UE units (not used for non-64QAM-capable UE units).";
      type uint32;
      max-elements 31;
    }
    leaf pmAqmBasedDiscardSpi00 {
      description "Number of discards performed by the AQM feature for all Priority Queues (PQs) for Scheduling Priority Indicator (SPI) 00..";
      type uint32;
      config false;
    }
    leaf pmSumNoOfUsersSpi08 {
      description "Counts the total number of users for scheduling priority class 08 selected for each 2 ms subframe that is transmitted in the cell. For an MC-PQ only the counter in the serving HS-DSCH cell (of the UE to which the MC-PQ belongs) is updated. However, the aggregated measurement, based on all cells where the MC-PQ may be served, is considered when that counter is updated. The counter reflects the PQ perspective..";
      type uint32;
      config false;
    }
  }
  grouping Iub-attributes {
    leaf iubId {
      description "The value component of the RDN..";
      type string;
      mandatory true;
    }
    leaf userLabel {
      description "Label for free use.; length 1..128.";
      type string {
        length "1..128";
      }
    }
    leaf ipv4Address {
      description "Reference to the MO AddressIPv4, which is used to carry Frame Protocol..";
      type ietfinet:ipv4-address;
      mandatory true;
    }
    leaf rbsId {
      description "Used by OSS-RC to identify a Node B and the corresponding Iub in RNC. The attribute is not used by the Node B itself, it only serves as storage for OSS-RC..";
      type uint32;
      mandatory true;
    }
    leaf rSiteRef {
      description "A label used for grouping radio nodes located at the same site.; length 1..35.";
      type string {
        length "1..35";
      }
      config false;
    }
    leaf pmNoOfDiscardedMsg {
      description "Number of discarded messages because of SCTP congestion control on the control plane over Iub..";
      type uint64;
      config false;
    }
    leaf pmTotalTimeIubLinkCongestedUl {
      description "The time the Iub link is congested for the NBAP Common part of the control plane in the uplink direction..";
      type uint64;
      config false;
    }
  }
  grouping IubDataStreams-attributes {
    leaf iubDataStreamsId {
      description "The value component of the RDN..";
      type string;
      mandatory true;
    }
    leaf maxHsRate {
      description "Maximum HSDPA bit rate over Iub.; range 1..10000; Default value: 470.";
      type int16 {
        range "1..10000";
      }
      default "470";
      units "Mbps";
    }
    leaf hsDataFrameDelayThreshold {
      description "Maximum build-up delay for transport network buffer, a dynamic delay. Measured dynamic delay above this limit is interpreted as IUB congestion detection.; range 10..200; Default value: 60.";
      type int16 {
        range "10..200";
      }
      default "60";
      units "ms";
    }
    leaf hsRbrDiscardProbability {
      description "Discard probability for flow where IUB congestion is detected. Used when HSDPA RBR QoS Profiling feature and AQM-based congestion control for HSDPA feature are both activated.; range 0..100; Default value: 0.";
      type eytypes:int16_range_0-100;
      default "0";
      units "percent";
    }
    leaf-list hsRbrWeight {
      description "Attribute controls relative bitrates that users get. Weight ranges of value are normalized for peak factor around 100% when being calculated or configured. Weight is needed to implement RBR functions. Weight is used by the algorithm HSDPA Flow Control and its AIMD method, which is used for Transport Network limited scenarios. For SPIs where value OFF is set for IubDataStreams::schHsFlowControlOnOff, value 100% is used for hsRbrWeight. This attribute is not supported when AQM-based congestion control for HSDPA is activated. The first value in the sequence represents SPI0 and the last SPI15.; Default values sequence: 100,100,50,100,200,100,100,100,100,100,100,100,100,100,100,100.";
      type int16 {
        range "32..320";
      }
      ordered-by user;
      min-elements 16;
      max-elements 16;
    }
    leaf noOfCommonStreams {
      description "Total number of common data streams and HS-DSCH data streams allocated in Node B.; range 0..999.";
      type int16 {
        range "0..999";
      }
      config false;
    }
    leaf noOfDedicatedStreams {
      description "Total DCH data streams allocated in Node B.; range 0..9999.";
      type int16 {
        range "0..9999";
      }
      config false;
    }
    leaf userLabel {
      description "Label for free use.; length 1..128.";
      type string {
        length "1..128";
      }
    }
    leaf-list schHsFlowControlOnOff {
      description "HSDPA flow control status. ON or OFF for each scheduling priority class. First sequence value is for scheduling priority class 0..";
      type SchFlowControlState;
      min-elements 16;
      max-elements 16;
    }
    leaf-list hsAqmCongCtrlSpiOnOff {
      description "AQM Based Congestion Control for HSDPA status; activated (ON) or deactivated (OFF) for each scheduling priority class. First value in the sequence is for scheduling priority class 0..";
      type SchFlowControlState;
      min-elements 16;
      max-elements 16;
    }
    leaf pmHsDataFramesReceivedSpi14 {
      description "Counts all correctly received HS-DSCH data frames in RBS for priority class 14..";
      type uint32;
      config false;
    }
    leaf pmCapAllocIubHsLimitingRatioSpi06 {
      description "Degree that HSDPA traffic in DL for SPI 06 is limited by Iub/Iur interfaces, between SRNC and RBS. Ratio between number of occurrences, when capacity allocation figures are limited by the Iub high-speed bandwidth and number of active flows. Measured every 100 ms. Unit: 1%.";
      type int16;
      config false;
    }
    leaf pmCapAllocIubHsLimitingRatioSpi15 {
      description "Degree that HSDPA traffic in DL for SPI 15 is limited by Iub/Iur interfaces, between SRNC and RBS. Ratio between number of occurrences, when capacity allocation figures are limited by the Iub high-speed bandwidth and number of active flows. Measured every 100 ms. Unit: 1%.";
      type int16;
      config false;
    }
    leaf pmCapAllocIubHsLimitingRatioSpi05 {
      description "Degree that HSDPA traffic in DL for SPI 05 is limited by Iub/Iur interfaces, between SRNC and RBS. Ratio between number of occurrences, when capacity allocation figures are limited by the Iub high-speed bandwidth and number of active flows. Measured every 100 ms. Unit: 1%.";
      type int16;
      config false;
    }
    leaf pmCapAllocIubHsLimitingRatioSpi12 {
      description "Degree that HSDPA traffic in DL for SPI 12 is limited by Iub/Iur interfaces, between SRNC and RBS. Ratio between number of occurrences, when capacity allocation figures are limited by the Iub high-speed bandwidth and number of active flows. Measured every 100 ms. Unit: 1%.";
      type int16;
      config false;
    }
    leaf pmHsDataFramesReceivedSpi11 {
      description "Counts all correctly received HS-DSCH data frames in RBS for priority class 11..";
      type uint32;
      config false;
    }
    leaf pmHsDataFramesReceivedSpi04 {
      description "Counts all correctly received HS-DSCH data frames in RBS for priority class 04..";
      type uint32;
      config false;
    }
    leaf pmHsDataFramesReceivedSpi02 {
      description "Counts all correctly received HS-DSCH data frames in RBS for priority class 02..";
      type uint32;
      config false;
    }
    leaf pmHsDataFramesLostSpi05 {
      description "Lost or discarded HS-DSCH data frames for priotity class 05..";
      type uint32;
      config false;
    }
    leaf-list pmHsDataFrameDelayIubSpi10 {
      description "Presents a histogram over the dynamic delay experienced between SRNC and RBS by the flow controlled HSDPA flows, that is, the buffer build-up delay distribution for HS traffic on priority class 10. Bins: [0]: Number of samples in range [0..10[ ms [1]: Number of samples in range [10..20[ ms [2]: Number of samples in range [20..30[ ms ... [14]: Number of samples in range [140..150[ ms [15]: Number of samples greater than or equal to 150 ms.";
      type uint16;
      max-elements 16;
    }
    leaf pmHsDataFramesLostSpi02 {
      description "Lost or discarded HS-DSCH data frames for priotity class 02..";
      type uint32;
      config false;
    }
    leaf pmHsDataFramesReceivedSpi00 {
      description "Counts all correctly received HS-DSCH data frames in RBS for priority class 00..";
      type uint32;
      config false;
    }
    leaf-list pmHsDataFrameDelayIubSpi00 {
      description "Presents a histogram over the dynamic delay experienced between SRNC and RBS by the flow controlled HSDPA flows, that is, the buffer build-up delay distribution for HS traffic on priority class 00. Bins: [0]: Number of samples in range [0..10[ ms [1]: Number of samples in range [10..20[ ms [2]: Number of samples in range [20..30[ ms ... [14]: Number of samples in range [140..150[ ms [15]: Number of samples greater than or equal to 150 ms.";
      type uint16;
      max-elements 16;
    }
    leaf pmHsDataFramesLostSpi11 {
      description "Lost or discarded HS-DSCH data frames for priotity class 11..";
      type uint32;
      config false;
    }
    leaf pmHsDataFramesLostSpi13 {
      description "Lost or discarded HS-DSCH data frames for priotity class 13..";
      type uint32;
      config false;
    }
    leaf-list pmIubFrameLossIntensity {
      description "Number of 100 ms intervals within each frame loss interval according to pdf [0..15] below. Bins: [0]: Samples with 0 losses [1]: Samples within 1 to 2 losses [2]: Samples within 3 to 4 losses ... [14]: Samples within 8193 to 16384 losses [15]: Samples with >16385 losses.";
      type uint16;
      max-elements 16;
    }
    leaf-list pmHsDataFrameDelayIubSpi15 {
      description "Presents a histogram over the dynamic delay experienced between SRNC and RBS by the flow controlled HSDPA flows, that is, the buffer build-up delay distribution for HS traffic on priority class 15. Bins: [0]: Number of samples in range [0..10[ ms [1]: Number of samples in range [10..20[ ms [2]: Number of samples in range [20..30[ ms ... [14]: Number of samples in range [140..150[ ms [15]: Number of samples greater than or equal to 150 ms.";
      type uint16;
      max-elements 16;
    }
    leaf pmEdchIubLimitingRatio {
      description "Indicates in what degree the EUL traffic in uplink is limited by the Iub/Iur interfaces, between RBS and SRNC. When a high value is indicated, it should be considered to extend Iub/Iur with higher EUL bandwidth. Indicates the percentage of 100 ms periods with scheduled EUL traffic where Iub has been the only limiting factor during at least one TTI. Unit: 0.1%.";
      type int64;
      config false;
    }
    leaf pmHsDataFramesReceivedSpi03 {
      description "Counts all correctly received HS-DSCH data frames in RBS for priority class 03..";
      type uint32;
      config false;
    }
    leaf-list pmHsDataFrameDelayIubSpi12 {
      description "Presents a histogram over the dynamic delay experienced between SRNC and RBS by the flow controlled HSDPA flows, that is, the buffer build-up delay distribution for HS traffic on priority class 12. Bins: [0]: Number of samples in range [0..10[ ms [1]: Number of samples in range [10..20[ ms [2]: Number of samples in range [20..30[ ms ... [14]: Number of samples in range [140..150[ ms [15]: Number of samples greater than or equal to 150 ms.";
      type uint16;
      max-elements 16;
    }
    leaf pmHsDataFramesReceivedSpi01 {
      description "Counts all correctly received HS-DSCH data frames in RBS for priority class 01..";
      type uint32;
      config false;
    }
    leaf pmHsDataFramesReceivedSpi13 {
      description "Counts all correctly received HS-DSCH data frames in RBS for priority class 13..";
      type uint32;
      config false;
    }
    leaf pmDchFramesCrcMismatch {
      description "The number of DCH Iub FP frames discarded owing to header or payload CRC mismatch..";
      type uint64;
      config false;
    }
    leaf pmHsDataFramesLostSpi15 {
      description "Lost or discarded HS-DSCH data frames for priotity class 15..";
      type uint32;
      config false;
    }
    leaf pmHsDataFramesLostSpi00 {
      description "Lost or discarded HS-DSCH data frames for priotity class 00..";
      type uint32;
      config false;
    }
    leaf-list pmHsDataFrameDelayIubSpi01 {
      description "Presents a histogram over the dynamic delay experienced between SRNC and RBS by the flow controlled HSDPA flows, that is, the buffer build-up delay distribution for HS traffic on priority class 01. Bins: [0]: Number of samples in range [0..10[ ms [1]: Number of samples in range [10..20[ ms [2]: Number of samples in range [20..30[ ms ... [14]: Number of samples in range [140..150[ ms [15]: Number of samples greater than or equal to 150 ms.";
      type uint16;
      max-elements 16;
    }
    leaf pmCapAllocIubHsLimitingRatioSpi02 {
      description "Degree that HSDPA traffic in DL for SPI 02 is limited by Iub/Iur interfaces, between SRNC and RBS. Ratio between number of occurrences, when capacity allocation figures are limited by the Iub high-speed bandwidth and number of active flows. Measured every 100 ms. Unit: 1%.";
      type int16;
      config false;
    }
    leaf pmDchFramesOutOfSequenceDl {
      description "The number of Iub DCH Frame Protocol frames received out-of-sequence in the downlink direction..";
      type uint64;
      config false;
    }
    leaf pmDchFramesLate {
      description "The number of DCH Iub FP frames arrived after ToAWE but before LTOA..";
      type uint64;
      config false;
    }
    leaf-list pmHsDataFrameDelayIubSpi14 {
      description "Presents a histogram over the dynamic delay experienced between SRNC and RBS by the flow controlled HSDPA flows, that is, the buffer build-up delay distribution for HS traffic on priority class 14. Bins: [0]: Number of samples in range [0..10[ ms [1]: Number of samples in range [10..20[ ms [2]: Number of samples in range [20..30[ ms ... [14]: Number of samples in range [140..150[ ms [15]: Number of samples greater than or equal to 150 ms.";
      type uint16;
      max-elements 16;
    }
    leaf pmDchFramesTooLate {
      description "The number of DCH Iub FP frames discarded owing to too late arrival, that is, after LTOA..";
      type uint64;
      config false;
    }
    leaf pmCapAllocIubHsLimitingRatioSpi03 {
      description "Degree that HSDPA traffic in DL for SPI 03 is limited by Iub/Iur interfaces, between SRNC and RBS. Ratio between number of occurrences, when capacity allocation figures are limited by the Iub high-speed bandwidth and number of active flows. Measured every 100 ms. Unit: 1%.";
      type int16;
      config false;
    }
    leaf pmHsDataFramesReceivedSpi09 {
      description "Counts all correctly received HS-DSCH data frames in RBS for priority class 09..";
      type uint32;
      config false;
    }
    leaf pmDchFramesEarly {
      description "The number of DCH Iub FP frames arrived before ToAWS but after TOAE..";
      type uint64;
      config false;
    }
    leaf pmHsDataFramesLostSpi07 {
      description "Lost or discarded HS-DSCH data frames for priotity class 07..";
      type uint32;
      config false;
    }
    leaf pmCapAllocIubHsLimitingRatioSpi00 {
      description "Degree that HSDPA traffic in DL for SPI 00 is limited by Iub/Iur interfaces, between SRNC and RBS. Ratio between number of occurrences, when capacity allocation figures are limited by the Iub high-speed bandwidth and number of active flows. Measured every 100 ms. Unit: 1%.";
      type int16;
      config false;
    }
    leaf-list pmHsDataFrameDelayIubSpi04 {
      description "Presents a histogram over the dynamic delay experienced between SRNC and RBS by the flow controlled HSDPA flows, that is, the buffer build-up delay distribution for HS traffic on priority class 04. Bins: [0]: Number of samples in range [0..10[ ms [1]: Number of samples in range [10..20[ ms [2]: Number of samples in range [20..30[ ms ... [14]: Number of samples in range [140..150[ ms [15]: Number of samples greater than or equal to 150 ms.";
      type uint16;
      max-elements 16;
    }
    leaf-list pmHsDataFrameDelayIubSpi11 {
      description "Presents a histogram over the dynamic delay experienced between SRNC and RBS by the flow controlled HSDPA flows, that is, the buffer build-up delay distribution for HS traffic on priority class 11. Bins: [0]: Number of samples in range [0..10[ ms [1]: Number of samples in range [10..20[ ms [2]: Number of samples in range [20..30[ ms ... [14]: Number of samples in range [140..150[ ms [15]: Number of samples greater than or equal to 150 ms.";
      type uint16;
      max-elements 16;
    }
    leaf pmCapAllocIubHsLimitingRatioSpi04 {
      description "Degree that HSDPA traffic in DL for SPI 04 is limited by Iub/Iur interfaces, between SRNC and RBS. Ratio between number of occurrences, when capacity allocation figures are limited by the Iub high-speed bandwidth and number of active flows. Measured every 100 ms. Unit: 1%.";
      type int16;
      config false;
    }
    leaf pmDchFramesTooEarly {
      description "The number of DCH Iub FP frames discarded owing to too early arrival, that is, before TOAE..";
      type uint64;
      config false;
    }
    leaf-list pmHsDataFrameDelayIubSpi03 {
      description "Presents a histogram over the dynamic delay experienced between SRNC and RBS by the flow controlled HSDPA flows, that is, the buffer build-up delay distribution for HS traffic on priority class 03. Bins: [0]: Number of samples in range [0..10[ ms [1]: Number of samples in range [10..20[ ms [2]: Number of samples in range [20..30[ ms ... [14]: Number of samples in range [140..150[ ms [15]: Number of samples greater than or equal to 150 ms.";
      type uint16;
      max-elements 16;
    }
    leaf-list pmHsDataFrameDelayIubSpi07 {
      description "Presents a histogram over the dynamic delay experienced between SRNC and RBS by the flow controlled HSDPA flows, that is, the buffer build-up delay distribution for HS traffic on priority class 07. Bins: [0]: Number of samples in range [0..10[ ms [1]: Number of samples in range [10..20[ ms [2]: Number of samples in range [20..30[ ms ... [14]: Number of samples in range [140..150[ ms [15]: Number of samples greater than or equal to 150 ms.";
      type uint16;
      max-elements 16;
    }
    leaf-list pmHsDataFrameDelayIubSpi06 {
      description "Presents a histogram over the dynamic delay experienced between SRNC and RBS by the flow controlled HSDPA flows, that is, the buffer build-up delay distribution for HS traffic on priority class 06. Bins: [0]: Number of samples in range [0..10[ ms [1]: Number of samples in range [10..20[ ms [2]: Number of samples in range [20..30[ ms ... [14]: Number of samples in range [140..150[ ms [15]: Number of samples greater than or equal to 150 ms.";
      type uint16;
      max-elements 16;
    }
    leaf pmHsDataFramesLostSpi03 {
      description "Lost or discarded HS-DSCH data frames for priotity class 03..";
      type uint32;
      config false;
    }
    leaf pmHsDataFramesLostSpi04 {
      description "Lost or discarded HS-DSCH data frames for priotity class 04..";
      type uint32;
      config false;
    }
    leaf pmHsDataFramesLostSpi08 {
      description "Lost or discarded HS-DSCH data frames for priotity class 08..";
      type uint32;
      config false;
    }
    leaf pmHsDataFramesReceivedSpi12 {
      description "Counts all correctly received HS-DSCH data frames in RBS for priority class 12..";
      type uint32;
      config false;
    }
    leaf pmHsDataFramesReceivedSpi06 {
      description "Counts all correctly received HS-DSCH data frames in RBS for priority class 06..";
      type uint32;
      config false;
    }
    leaf pmHsDataFramesReceivedSpi10 {
      description "Counts all correctly received HS-DSCH data frames in RBS for priority class 10..";
      type uint32;
      config false;
    }
    leaf pmHsDataFramesLostSpi01 {
      description "Lost or discarded HS-DSCH data frames for priotity class 01..";
      type uint32;
      config false;
    }
    leaf-list pmHsDataFrameDelayIubSpi13 {
      description "Presents a histogram over the dynamic delay experienced between SRNC and RBS by the flow controlled HSDPA flows, that is, the buffer build-up delay distribution for HS traffic on priority class 13. Bins: [0]: Number of samples in range [0..10[ ms [1]: Number of samples in range [10..20[ ms [2]: Number of samples in range [20..30[ ms ... [14]: Number of samples in range [140..150[ ms [15]: Number of samples greater than or equal to 150 ms.";
      type uint16;
      max-elements 16;
    }
    leaf pmCapAllocIubHsLimitingRatioSpi08 {
      description "Degree that HSDPA traffic in DL for SPI 08 is limited by Iub/Iur interfaces, between SRNC and RBS. Ratio between number of occurrences, when capacity allocation figures are limited by the Iub high-speed bandwidth and number of active flows. Measured every 100 ms. Unit: 1%.";
      type int16;
      config false;
    }
    leaf pmHsDataFramesLostSpi09 {
      description "Lost or discarded HS-DSCH data frames for priotity class 09..";
      type uint32;
      config false;
    }
    leaf-list pmHsDataFrameDelayIubSpi05 {
      description "Presents a histogram over the dynamic delay experienced between SRNC and RBS by the flow controlled HSDPA flows, that is, the buffer build-up delay distribution for HS traffic on priority class 05. Bins: [0]: Number of samples in range [0..10[ ms [1]: Number of samples in range [10..20[ ms [2]: Number of samples in range [20..30[ ms ... [14]: Number of samples in range [140..150[ ms [15]: Number of samples greater than or equal to 150 ms.";
      type uint16;
      max-elements 16;
    }
    leaf-list pmIubMacdPduRbsReceivedBits {
      description "Iub HS MAC-d PDU received number of bits per one second interval in the RBS. Bins: [0]: Number of samples in range [0..200[ kbits/s [1]: Number of samples in range [200..400[ kbits/s ... [99]: Number of samples in range [19800..20000[ kbits/s [100]: Number of samples in range [20000..30000[ kbits/s [101]: Number of samples in range [30000..40000[ kbits/s [102]: Number of samples in range [40000..50000[ kbits/s ... [148]: Number of samples in range [500000..510000[ kbits/s.";
      type uint32;
      max-elements 149;
    }
    leaf pmCapAllocIubHsLimitingRatioSpi14 {
      description "Degree that HSDPA traffic in DL for SPI 14 is limited by Iub/Iur interfaces, between SRNC and RBS. Ratio between number of occurrences, when capacity allocation figures are limited by the Iub high-speed bandwidth and number of active flows. Measured every 100 ms. Unit: 1%.";
      type int16;
      config false;
    }
    leaf pmCapAllocIubHsLimitingRatioSpi09 {
      description "Degree that HSDPA traffic in DL for SPI 09 is limited by Iub/Iur interfaces, between SRNC and RBS. Ratio between number of occurrences, when capacity allocation figures are limited by the Iub high-speed bandwidth and number of active flows. Measured every 100 ms. Unit: 1%.";
      type int16;
      config false;
    }
    leaf pmHsDataFramesLostSpi12 {
      description "Lost or discarded HS-DSCH data frames for priotity class 12..";
      type uint32;
      config false;
    }
    leaf-list pmHsDataFrameDelayIubSpi08 {
      description "Presents a histogram over the dynamic delay experienced between SRNC and RBS by the flow controlled HSDPA flows, that is, the buffer build-up delay distribution for HS traffic on priority class 08. Bins: [0]: Number of samples in range [0..10[ ms [1]: Number of samples in range [10..20[ ms [2]: Number of samples in range [20..30[ ms ... [14]: Number of samples in range [140..150[ ms [15]: Number of samples greater than or equal to 150 ms.";
      type uint16;
      max-elements 16;
    }
    leaf pmHsDataFramesLostSpi10 {
      description "Lost or discarded HS-DSCH data frames for priotity class 10..";
      type uint32;
      config false;
    }
    leaf pmCapAllocIubHsLimitingRatioSpi13 {
      description "Degree that HSDPA traffic in DL for SPI 13 is limited by Iub/Iur interfaces, between SRNC and RBS. Ratio between number of occurrences, when capacity allocation figures are limited by the Iub high-speed bandwidth and number of active flows. Measured every 100 ms. Unit: 1%.";
      type int16;
      config false;
    }
    leaf pmHsDataFramesLostSpi14 {
      description "Lost or discarded HS-DSCH data frames for priotity class 14..";
      type uint32;
      config false;
    }
    leaf pmDchFramesReceived {
      description "The number of received DCH Iub frames in kframes (1000 frames)..";
      type uint64;
      config false;
    }
    leaf pmCapAllocIubHsLimitingRatioSpi11 {
      description "Degree that HSDPA traffic in DL for SPI 11 is limited by Iub/Iur interfaces, between SRNC and RBS. Ratio between number of occurrences, when capacity allocation figures are limited by the Iub high-speed bandwidth and number of active flows. Measured every 100 ms. Unit: 1%.";
      type int16;
      config false;
    }
    leaf pmHsDataFramesReceivedSpi15 {
      description "Counts all correctly received HS-DSCH data frames in RBS for priority class 15..";
      type uint32;
      config false;
    }
    leaf pmHsDataFramesReceivedSpi05 {
      description "Counts all correctly received HS-DSCH data frames in RBS for priority class 05..";
      type uint32;
      config false;
    }
    leaf pmHsDataFramesReceivedSpi07 {
      description "Counts all correctly received HS-DSCH data frames in RBS for priority class 07..";
      type uint32;
      config false;
    }
    leaf pmCapAllocIubHsLimitingRatioSpi07 {
      description "Degree that HSDPA traffic in DL for SPI 07 is limited by Iub/Iur interfaces, between SRNC and RBS. Ratio between number of occurrences, when capacity allocation figures are limited by the Iub high-speed bandwidth and number of active flows. Measured every 100 ms. Unit: 1%.";
      type int16;
      config false;
    }
    leaf pmHsDataFramesReceivedSpi08 {
      description "Counts all correctly received HS-DSCH data frames in RBS for priority class 08..";
      type uint32;
      config false;
    }
    leaf pmHsDataFramesLostSpi06 {
      description "Lost or discarded HS-DSCH data frames for priotity class 06..";
      type uint32;
      config false;
    }
    leaf pmCapAllocIubHsLimitingRatioSpi01 {
      description "Degree that HSDPA traffic in DL for SPI 01 is limited by Iub/Iur interfaces, between SRNC and RBS. Ratio between number of occurrences, when capacity allocation figures are limited by the Iub high-speed bandwidth and number of active flows. Measured every 100 ms. Unit: 1%.";
      type int16;
      config false;
    }
    leaf-list pmHsDataFrameDelayIubSpi02 {
      description "Presents a histogram over the dynamic delay experienced between SRNC and RBS by the flow controlled HSDPA flows, that is, the buffer build-up delay distribution for HS traffic on priority class 02. Bins: [0]: Number of samples in range [0..10[ ms [1]: Number of samples in range [10..20[ ms [2]: Number of samples in range [20..30[ ms ... [14]: Number of samples in range [140..150[ ms [15]: Number of samples greater than or equal to 150 ms.";
      type uint16;
      max-elements 16;
    }
    leaf pmCapAllocIubHsLimitingRatioSpi10 {
      description "Degree that HSDPA traffic in DL for SPI 10 is limited by Iub/Iur interfaces, between SRNC and RBS. Ratio between number of occurrences, when capacity allocation figures are limited by the Iub high-speed bandwidth and number of active flows. Measured every 100 ms. Unit: 1%.";
      type int16;
      config false;
    }
    leaf-list pmHsDataFrameDelayIubSpi09 {
      description "Presents a histogram over the dynamic delay experienced between SRNC and RBS by the flow controlled HSDPA flows, that is, the buffer build-up delay distribution for HS traffic on priority class 09. Bins: [0]: Number of samples in range [0..10[ ms [1]: Number of samples in range [10..20[ ms [2]: Number of samples in range [20..30[ ms ... [14]: Number of samples in range [140..150[ ms [15]: Number of samples greater than or equal to 150 ms.";
      type uint16;
      max-elements 16;
    }
  }
  grouping NbapCommon-attributes {
    leaf auditRetransmissionT {
      description "Time between successive retransmissions of AUDIT REQUIRED INDICATION messages.; range 1..150; Default value: 5.";
      type int16 {
        range "1..150";
      }
      default "5";
      units "s";
    }
    leaf l3EstablishSupervisionT {
      description "Maximum allowed time to establish NBAP communication, that is successful establishment of layer 3 followed by a sucessful audit procedure.; range 1..500; Default value: 30.";
      type int16 {
        range "1..500";
      }
      default "30";
      units "s";
    }
    leaf nbapCommonId {
      description "The value component of the RDN..";
      type string;
      mandatory true;
    }
    leaf-list availabilityStatus {
      description "The availability status. It contains details about operationalState..";
      type AvailStatus;
      min-elements 0;
    }
    leaf userLabel {
      description "Label for free use.; length 1..128.";
      type string {
        length "1..128";
      }
    }
    leaf operationalState {
      description "Defines the operational state..";
      type enumeration {
        enum DISABLED;
        enum ENABLED;
      }
      config false;
    }
    leaf sctpEndpointRef {
      description "Reference to an SctpEndpoint MO which corresponds to the end point for NBAP common procedure messages..";
      type string;
      mandatory true;
    }
  }
  grouping NbapDedicated-attributes {
    leaf nbapDedicatedId {
      description "The value component of the RDN..";
      type string;
      mandatory true;
    }
    leaf-list availabilityStatus {
      description "The availability status. It contains details about operationalState..";
      type AvailStatus;
      min-elements 0;
    }
    leaf userLabel {
      description "Label for free use.; length 1..128.";
      type string {
        length "1..128";
      }
    }
    leaf operationalState {
      description "Defines the operational state..";
      type enumeration {
        enum DISABLED;
        enum ENABLED;
      }
      config false;
    }
    leaf sctpEndpointRef {
      description "Reference to an SctpEndpoint MO which corresponds to the end point for NBAP dedicated procedure messages..";
      type string;
      mandatory true;
    }
  }
  grouping NodeBFunction-attributes {
    leaf eulTargetRate {
      description "The target scheduled grant for a user.; range 0..6016; Default value: 128.";
      type eytypes:int16_range_0-6016;
      default "128";
      units "kbps";
    }
    leaf nodeBFunctionId {
      description "The value component of the RDN..";
      type string;
      mandatory true;
    }
    leaf eul2msFirstSchedStep {
      description "Specifies if initial ramp-up step from zero rate stops at the 20 kbps step introduced by the feature 'EUL Single HARQ Process Scheduling' (Per HARQ Process Grant). Dependencies: The attribute is ignored if the feature 'EUL Single HARQ Process Scheduling' is not active.; Default value: 160.";
      type int16 {
        range "20 | 160";
      }
      default "160";
      units "kbps";
    }
    leaf eulDchMaxAllowedSchRate {
      description "The maximum allowed scheduled data rate per user when a user has both DCH and E-DCH configured.; range 0..3200; Default value: 1920.";
      type int16 {
        range "0..3200";
      }
      default "1920";
      units "kbps";
    }
    leaf eulInactivityHighRateTime {
      description "Time that the E-DCH user has zero kbps scheduled data rate to be considered \"inactive high rate\" when this user's scheduled grant > eulMinHwSchRate.; range 0..1000; Default value: 20.";
      type int16 {
        range "0..1000";
      }
      default "20";
      units "ms";
    }
    leaf eulInactivityLowRateTime {
      description "Time that the E-DCH user has zero kbps scheduled data rate to be considered \"inactive low rate\" when this user's scheduled grant = eulMinHwSchRate..";
      type int16;
      units "ms";
    }
    leaf eulLowRate {
      description "Defines an EUL scheduling grant below eulTargetRate. A user's grant will at most be reduced to this level in a single step during overload situations.; range 0..6016; Default value: 32.";
      type eytypes:int16_range_0-6016;
      default "32";
      units "kbps";
    }
    leaf eulLowUsageTime {
      description "Rate measurement period for utilization based grant reduction.; range 10..1000; Default value: 400.";
      type int16 {
        range "10..1000";
      }
      default "400";
      units "ms";
    }
    leaf eulMaxAllowedSchRate {
      description "The maximum allowed scheduled data rate per user.; range 0..6016; Default value: 5120.";
      type eytypes:int16_range_0-6016;
      default "5120";
      units "kbps";
    }
    leaf eulMaxShoRate {
      description "Defines the maximum rate that may be allocated in the serving cell for scheduled data to an E-DCH user during a soft handover.; range 0..6016; Default value: 5760.";
      type eytypes:int16_range_0-6016;
      default "5760";
      units "kbps";
    }
    leaf eulMaxTotalProtectedRate {
      description "Maximum protected D-EDCH grant per cell. D-EDCH serving radio links with a protected grant, are protected at minimum grant level. This can avoid E-DCH grant starvation in case Uu headroom is low.; range 0..20000; Default value: 1280.";
      type int16 {
        range "0..20000";
      }
      default "1280";
      units "kbps";
    }
    leaf eulNonServHwRate {
      description "The amount of hardware resources (in terms of a bit rate) that dynamically may be allocated to a non-serving E-DCH radio link for processing scheduled data.; range 0..5760; Default value: 480.";
      type int16 {
        range "0..5760";
      }
      default "480";
      units "kbps";
    }
    leaf eulNoReschUsers {
      description "The number of simultaneous users per cell that are allowed to perform rescheduling.; range 0..32; Default value: 5.";
      type int16 {
        range "0..32";
      }
      default "5";
    }
    leaf-list eulSchedulingWeight {
      description "This is a sequence of 16 weight factors associated with the 16 Scheduling Priority Indicators (SPIs). The weight factors represent the relative bandwidth between users assigned to the different scheduling priorities. The special value 0xFFFE (65534) is used to represent infinity. When eulSchedulingWeight is set to infinity, users with higher SPI values have absolute priority over those with lower SPI. [0]: Weight for SPI = 0 [1]: Weight for SPI = 1 ... [15]: Weight for SPI = 15; Default values sequence: 1,1,1,1,1,1,1,1,1,1,1,1,1,1,1,1.";
      type int32 {
        range "1..10000 | 65534";
      }
      ordered-by user;
      min-elements 16;
      max-elements 16;
    }
    leaf userLabel {
      description "Label for free use.; length 1..128.";
      type string {
        length "1..128";
      }
    }
    leaf release {
      description "The product release of the Node B managed function..";
      type string;
      config false;
    }
    leaf-list dualBandSectorGroup1 {
      description "Sector Group 1 in dual-band configuration. By definition, MO class SectorEquipmentFunction is limited to one frequency band. It associates two SectorEquipmentFunction MOs, that represent same geographical area to form one sector group. This information is used in order to determine which cells can operate in dual-band HSDPA multi-carrier fashion..";
      type string;
      min-elements 0;
      max-elements 2;
    }
    leaf-list dualBandSectorGroup2 {
      description "Sector Group 2 in dual-band configuration. By definition, MO class SectorEquipmentFunction is limited to one frequency band. It associates two SectorEquipmentFunction MOs, that represent same geographical area to form one sector group. This information is used in order to determine which cells can operate in dual-band HSDPA multi-carrier fashion..";
      type string;
      min-elements 0;
      max-elements 2;
    }
    leaf-list dualBandSectorGroup3 {
      description "Sector Group 3 in dual-band configuration. By definition, MO class SectorEquipmentFunction is limited to one frequency band. It associates two SectorEquipmentFunction MOs, that represent same geographical area to form one sector group. This information is used in order to determine which cells can operate in dual-band HSDPA multi-carrier fashion..";
      type string;
      min-elements 0;
      max-elements 2;
    }
    leaf-list dualBandSectorGroup4 {
      description "Sector Group 4 in dual-band configuration. By definition, MO class SectorEquipmentFunction is limited to one frequency band. It associates two SectorEquipmentFunction MOs, that represent same geographical area to form one sector group. This information is used in order to determine which cells can operate in dual-band HSDPA multi-carrier fashion..";
      type string;
      min-elements 0;
      max-elements 2;
    }
    leaf-list dualBandSectorGroup5 {
      description "Sector Group 5 in dual-band configuration. By definition, MO class SectorEquipmentFunction is limited to one frequency band. It associates two SectorEquipmentFunction MOs, that represent same geographical area to form one sector group. This information is used in order to determine which cells can operate in dual-band HSDPA multi-carrier fashion..";
      type string;
      min-elements 0;
      max-elements 2;
    }
    leaf-list dualBandSectorGroup6 {
      description "Sector Group 6 in dual-band configuration. By definition, MO class SectorEquipmentFunction is limited to one frequency band. It associates two SectorEquipmentFunction MOs, that represent same geographical area to form one sector group. This information is used in order to determine which cells can operate in dual-band HSDPA multi-carrier fashion..";
      type string;
      min-elements 0;
      max-elements 2;
    }
    leaf eulFachInitialRate {
      description "Initial granted rate for EUL-FACH users.; range 0..1376; Default value: 134.";
      type int16 {
        range "0..1376";
      }
      default "134";
      units "kbps";
    }
    leaf eulFachMinAllocation {
      description "The minimum number of pooled static HW resources for EUL-FACH, for each LocalCell Group; range 1..90; Default value: 8.";
      type int16 {
        range "1..90";
      }
      default "8";
      units "HW resource";
    }
    leaf ipOptimizedHsTnSettingsOnOff {
      description "Usage of IP Optimized TN settings for HSDPA flow control. Improves throughput when high bandwidth IP links are used..";
      type enumeration {
        enum OFF;
        enum ON;
      }
    }
    leaf featCtrlDlPowerControlEul {
      description "Whether unlicensed feature \"Downlink Power Control for Eul\" is ON or OFF..";
      type enumeration {
        enum OFF;
        enum ON;
      }
    }
    leaf rSiteRef {
      description "A label used for grouping radio nodes located at the same site. Recommended characters: \"a-z\", \"A-Z\", \"0-9\", \"_\", \"-\".; length 1..35.";
      type string {
        length "1..35";
      }
    }
    leaf combinedCellConfiguration {
      description "The type of combined cell deployment..";
      type enumeration {
        enum COMBINED_CELL_NORMAL;
        enum COMBINED_CELL_INDOOR;
      }
    }
    leaf bsctModeStatus {
      description "If NodeB is in Normal or Base Station Conformance Testing operating mode..";
      type enumeration {
        enum NORMAL;
        enum BASE_STATION_CONFORMANCE_TEST;
      }
      config false;
    }
    leaf advCellSupActions {
      description "Recovery action performed when Advanced Cell Supervision feature detects a sleeping cell..";
      type enumeration {
        enum NO_ACTION;
        enum CELL_RESTART;
      }
    }
    list ceCapacitiesNodeBDl {
      config false;
      description "Downlink channel element capacities..";
      uses CeCapacitiesDl-struct;
    }
    list ceCapacitiesNodeBTotalUl {
      config false;
      description "Total uplink channel element capacities, including both static and dynamic uplink channel elements..";
      uses CeCapacitiesTotalUl-struct;
    }
    list ceCapacitiesNodeBUl {
      config false;
      description "Static uplink channel element capacities..";
      uses CeCapacitiesUl-struct;
    }
    leaf featCtrlOptimizedAntennaSelection {
      description "Whether unlicensed feature \"Optimized Antenna Selection\" is ON or OFF.; Default value: OFF; Status info: Since 20.Q2. Has no functional behavior. Planned to be removed..";
      type enumeration {
        enum OFF;
        enum ON;
      }
      status deprecated;
      default "OFF";
    }
    leaf featCtrlOptmAntennaSelection {
      description "Whether unlicensed feature \"Optimized Antenna Selection\" is ON or OFF..";
      type enumeration {
        enum OFF;
        enum ON;
      }
    }
    leaf pmCapacityNodeBLimitHsCode {
      description "Limits the number of HS-PDSCH codes used in NodeB by granted BB HWAC capacity of Baseband unit or units. In Emergency Unlock state, hardware capacity is on maximum level..";
      type int64;
      config false;
    }
    leaf pmCapacityNodeBLimitDlCe {
      description "Limiting number of DL CE. Lower of RBS Channel Elements Downlink license value and available Channel Elements Downlink HWAC capacity. In case of Emergency Unlock, Channel Elements Downlink HWAC capacity..";
      type int64;
      config false;
    }
    leaf-list pmCapacityOfNodeBUlCeExt {
      description "Distribution of RBS UL Channel Element utilization (for all NodeBLocalCellGroup MOs) above licensed limit. Reported as percentages of the license controlled level visible in pmCapacityNodeBLimitUlCe. Channel Element utilization above licensed limit is possible for dynamically allocated CEs, when feature CE extension for EUL or additional CE extension for EUL is activated. Bins: [0]: Number of sampled values in range [0] % [1]: Number of sampled values in range ]0..5[ % [2]: Number of sampled values in range [5..10[ % [3]: Number of sampled values in range [10..15[ % [4]: Number of sampled values in range [15..20[ % [5]: Number of sampled values in range [20..30[ % [6]: Number of sampled values in range [30..40[ % ... [45]: Number of sampled values in range [420..430[ % [46]: Number of sampled values >= 430%.";
      type uint64;
      max-elements 47;
    }
    leaf pmCapacityNodeBLimitUlCe {
      description "Limiting number of UL CE. Lower of RBS Channel Elements Uplink license value and available Channel Elements Uplink HWAC capacity. In case of Emergency Unlock, Channel Elements Uplink HWAC capacity..";
      type int64;
      config false;
    }
    leaf-list pmCapacityOfNodeBUlCe {
      description "Distribution of RBS UL Channel Element utilization (for all NodeBLocalCellGroup MOs). Reported as percentages of the limit of UL CE visible in pmCapacityNodeBLimitUlCe. Bins: [0]: Number of sampled values in range [0..20[ % [1]: Number of sampled values in range [20..40[ % [2]: Number of sampled values in range [40..50[ % [3]: Number of sampled values in range [50..60[ % [4]: Number of sampled values in range [60..70[ % [5]: Number of sampled values in range [70..80[ % [6]: Number of sampled values in range [80..85[ % [7]: Number of sampled values in range [85..90[ % [8]: Number of sampled values in range [90..95[ % [9]: Number of sampled values >= 95%.";
      type uint64;
      max-elements 10;
    }
    leaf-list pmCapacityOfNodeBDlCe {
      description "Distribution of RBS DL Channel Element utilization (for all NodeBLocalCellGroup MOs). Reported as percentages of the limit of DL CE visible in pmCapacityNodeBLimitDlCe. Bins: [0]: Number of sampled values in range [0..20[ % [1]: Number of sampled values in range [20..40[ % [2]: Number of sampled values in range [40..50[ % [3]: Number of sampled values in range [50..60[ % [4]: Number of sampled values in range [60..70[ % [5]: Number of sampled values in range [70..80[ % [6]: Number of sampled values in range [80..85[ % [7]: Number of sampled values in range [85..90[ % [8]: Number of sampled values in range [90..95[ % [9]: Number of sampled values >= 95%.";
      type uint64;
      max-elements 10;
    }
  }
  grouping NodeBLocalCell-attributes {
    leaf nodeBLocalCellId {
      description "The value component of the RDN..";
      type string;
      mandatory true;
    }
    leaf administrativeState {
      description "The administrative state. If set to SHUTTING_DOWN, the state will immediately be brought to LOCKED..";
      type enumeration {
        enum LOCKED;
        enum UNLOCKED;
        enum SHUTTINGDOWN;
      }
    }
    leaf-list availabilityStatus {
      description "The availability status. It contains details about operationalState..";
      type AvailStatus;
      min-elements 0;
    }
    leaf localCellId {
      description "The identity of the RBS local cell.; range 0..268435455.";
      type int32 {
        range "0..268435455";
      }
      mandatory true;
    }
    leaf maxDlPowerCapability {
      description "Maximum downlink power capability for cell. For Combined Cell configuration, value is maximum DL power capability among sector carriers. For Psi-Coverage configuration, value is maximum DL power capability among sector carriers. Value is reported to RNC.; range 0..500.";
      type int16 {
        range "0..500";
      }
      config false;
      units "dBm";
    }
    leaf minDlPowerCapability {
      description "Minimum downlink power capability for the cell. For a Combined Cell configuration, this value is the minimum DL power capability from the carrier with maximum DL power capability. For a Psi-Coverage configuration, this value is the sum of the sector carriers' minimum DL power capabilities. The value is reported to the RNC.; range -300..500.";
      type int16 {
        range "-300..500";
      }
      config false;
      units "dBm";
    }
    leaf minSpreadingFactor {
      description "Indicates the minimum spreading factor supported by the cell..";
      type int16 {
        range "4 | 8 | 16 | 32 | 64 | 128 | 256 | 512";
      }
      config false;
    }
    leaf operatingBand {
      description "Operating frequency band..";
      type int16 {
        range "1..14 | 19..21";
      }
      mandatory true;
    }
    leaf operationalState {
      description "Defines the operational state..";
      type enumeration {
        enum DISABLED;
        enum ENABLED;
      }
      config false;
    }
    leaf uarfcnDl {
      description "Downlink UTRA Absolute Radio Frequency Channel Number. Specifies the channel number for the central downlink frequency.; range 0..16383.";
      type int16 {
        range "0..16383";
      }
      mandatory true;
    }
    leaf uarfcnUl {
      description "Uplink UTRA Absolute Radio Frequency Channel Number. Specifies the channel number for the central uplink frequency.; range 0..16383.";
      type int16 {
        range "0..16383";
      }
      config false;
    }
    leaf usageState {
      description "Indicates the usage state of the NodeBLocalCell. The NodeBLocalCell becomes BUSY when the cell has been setup by the RNC..";
      type enumeration {
        enum IDLE;
        enum ACTIVE;
        enum BUSY;
      }
      config false;
    }
    leaf airRateTypeSelector {
      description "Scheduling index to weight the factor (air rate) in the queue selection procedure..";
      type enumeration {
        enum ACKNOWLEDGED;
        enum TRANSMITTED;
      }
    }
    leaf cqiAdjustmentOn {
      description "Turns the CQI adjustment of the UE reported CQI on or off per cell.; Default value: true.";
      type boolean;
      default "true";
    }
    leaf defaultCqiHsFach {
      description "CQI value used for the transmission of the BCCH specific H-RNTI when data for a HS-FACH user is transmitted. A HS-FACH user is a UE which is in RRC state CELL_FACH (on RNC level) and is using transport channel HS-DSCH and not FACH.; range 1..30; Default value: 1.";
      type int16 {
        range "1..30";
      }
      default "1";
    }
    leaf extraCompForSigHsFach {
      description "Additional compensation applied to the converted CQI value used for TFRC selection when the signaling data for DCCH and CCCH for the HS-FACH user is transmitted. A HS-FACH user is a UE which is in RRC state CELL_FACH (on RNC level) and is using transport channel HS-DSCH and not FACH.; range 0..100; Default value: 10.";
      type eytypes:int16_range_0-100-44;
      default "10";
      units "dB";
    }
    leaf extraCompHsFach {
      description "Additional compensation applied to the converted CQI value used for TFRC selection when data for the HS-FACH user is transmitted. A HS-FACH user is a UE which is in RRC state CELL_FACH (on RNC level) and is using transport channel HS-DSCH and not FACH.; Default value: 100.";
      type int16 {
        range "0..200 | 1000";
      }
      default "100";
      units "dB";
    }
    leaf extraHsScchCompForSigHsFach {
      description "Additional power compensation applied to the HS-SCCH power calculated with the converted CQI value when the signaling data for DCCH and CCCH for the HS-FACH user is transmitted. A HS-FACH user is a UE which is in RRC state CELL_FACH (on RNC level) and is using transport channel HS-DSCH and not FACH.; range 0..100; Default value: 10.";
      type eytypes:int16_range_0-100-44;
      default "10";
      units "dB";
    }
    leaf extraHsScchCompHsFach {
      description "Additional power compensation applied to the HS-SCCH power calculated with the converted CQI value when data for the HS-FACH user is transmitted. A HS-FACH user is a UE which is in RRC state CELL_FACH (on RNC level) and is using transport channel HS-DSCH and not FACH.; Default value: 40.";
      type int16 {
        range "0..200 | 1000";
      }
      default "40";
      units "dB";
    }
    leaf extraHsScchPowerForSrbOnHsdpa {
      description "Extra power used for HS-SCCH for a user with SRB on HS. Relative to the output from the HS-SCCH power control.; range 0..100; Default value: 20.";
      type eytypes:int16_range_0-100-44;
      default "20";
      units "dB";
    }
    leaf extraPowerForSrbOnHsdpa {
      description "Extra power used for sending the data during a HSDPA TTI which includes SRB data. Relative to the output from the HS scheduler.; range 0..100; Default value: 20.";
      type eytypes:int16_range_0-100-44;
      default "20";
      units "dB";
    }
    leaf hsPowerMargin {
      description "Power margin the HSDPA scheduler is using when allocating remaining power of cell carrier. It is relative the maximum available power of the cell.; range 0..200; Default value: 0.";
      type int16 {
        range "0..200";
      }
      default "0";
      units "dB";
    }
    leaf hsScchMaxCodePower {
      description "HS-SCCH maximum code power relative PCPICH power. This parameter also determines the fixed power level for HS-SCCH.; range -350..150; Default value: -20.";
      type eytypes:int16_range_-350-150;
      default "-20";
      units "dB";
    }
    leaf hsScchMinCodePower {
      description "HS-SCCH minimum transmit code power relative PCPICH reference power.; range -350..150; Default value: -150.";
      type eytypes:int16_range_-350-150;
      default "-150";
      units "dB";
    }
    leaf-list minBitRate {
      description "The target minimum bit rate of HS priority queues for scheduling priority class 0 to 15 (the first value in the sequence is for scheduling priority class 0). Value -1 disables the function for that scheduling priority class. Dependencies: Only relevant when NodeBFunction::featureStateHsdpaMinBitRate = ACTIVATED. Undefined value: -1; Default values sequence: -1,-1,-1,-1,-1,-1,-1,-1,-1,-1,-1,-1,-1,-1,-1,-1.";
      type int16 {
        range "-1 | 1..2048";
      }
      ordered-by user;
      min-elements 16;
      max-elements 16;
    }
    leaf minBitRateMinCqi {
      description "The minimum CQI adjust value that allows performing minimum bit rate scheduling.; range 0..30; Default value: 8.";
      type int16 {
        range "0..30";
      }
      default "8";
      units "dB";
    }
    leaf queueSelectAlgorithm {
      description "Specifies the scheduling algorithm used in the cell..";
      type enumeration {
        enum ROUND_ROBIN;
        enum PROPORTIONAL_FAIR_MEDIUM;
        enum PROPORTIONAL_FAIR_HIGH;
        enum PROPORTIONAL_FAIR_LOW;
        enum MAXIMUM_CQI;
        enum EQUAL_RATE;
      }
    }
    leaf schCongPeriodGbr {
      description "Minimum time period to define the congestion situation of the guaranteed service.; range 1..50; Default value: 50.";
      type int16 {
        range "1..50";
      }
      default "50";
      units "ms";
    }
    leaf schCongThreshGbr {
      description "Threshold to detect the congestion situation of the guaranteed service.; range 0..250; Default value: 5.";
      type int16 {
        range "0..250";
      }
      default "5";
      units "ms";
    }
    leaf schCongThreshNonGbr {
      description "Threshold to detect the congestion situation of the non-guaranteed service.; range 0..20; Default value: 2.";
      type int16 {
        range "0..20";
      }
      default "2";
      units "ms";
    }
    leaf-list schMaxDelay {
      description "Parameter to define the maximum scheduling delay for scheduling priority class 0 to 15 (the first value in the sequence is for scheduling priority class 0). Undefined value: -1; Default values sequence: -1,-1,-1,-1,-1,100,10,-1,-1,-1,-1,-1,-1,-1,-1,-1.";
      type int16 {
        range "-1 | 1..300";
      }
      ordered-by user;
      min-elements 16;
      max-elements 16;
    }
    leaf schMinPowerNonGbrHsUsers {
      description "Parameter to define the minimum reserved power for the non-guaranteed service in congestion situation. The value is defined as a percentage of maximum transmission power.; range 0..100; Default value: 0.";
      type eytypes:int16_range_0-100;
      default "0";
      units "percent";
    }
    leaf schNoCongPeriodGbr {
      description "Minimum time period to define the time that congestion situation of the guaranteed service ends.; range 1..50; Default value: 25.";
      type int16 {
        range "1..50";
      }
      default "25";
      units "ms";
    }
    leaf schNoCongThreshGbr {
      description "Threshold to detect the time that congestion situation of the guaranteed service ends.; range 0..250; Default value: 15.";
      type int16 {
        range "0..250";
      }
      default "15";
      units "ms";
    }
    leaf schPowerDeltaCongGbr {
      description "Parameter to define the minimum necessary power for the guaranteed service in congestion situation. The value is defined as a percentage of maximum transmission power.; range 0..100; Default value: 15.";
      type eytypes:int16_range_0-100;
      default "15";
      units "percent";
    }
    leaf schPrioForAbsResSharing {
      description "Parameter to decide the priority class(es) where absolute resource sharing will be applied.; range 0..15; Default value: 15.";
      type int16 {
        range "0..15";
      }
      default "15";
    }
    leaf-list schWeight {
      description "Parameter to define the scheduling weight for scheduling priority class 0 to 15 (the first value in the sequence is for scheduling priority class 0).; Default values sequence: 1,10,200,300,450,900,1000,4000,1,1,1,1,1,1,1,10000.";
      type int16 {
        range "1..10000";
      }
      ordered-by user;
      min-elements 16;
      max-elements 16;
    }
    leaf-list throughputPqxHsFach {
      description "Default values sequence: 0,0,0,30,0,0,0,0,0,0,0,0,0,0,0,0; Status info: Deprecated: Not to be used. Ignored by the system. In 16B replaced by throughputPqxHsdpaFach..";
      type int16 {
        range "0..100";
      }
      ordered-by user;
      min-elements 16;
      max-elements 16;
    }
    leaf hsdpaMcActivityBufferThreshold {
      description "Determines required amount of data in MC PQ data buffer. Used to re-activate secondary serving HS-DSCH cell for UE in MC mode when it is deactivated. If multiple MC-PQs belong to same UE any data buffer can contain required amount of data to perform re-activation.; range 0..200; Default value: 2.";
      type int16 {
        range "0..200";
      }
      default "2";
      units "bytes";
    }
    leaf hsdpaMcInactivityTimer {
      description "Parameter determining the required time of empty multi-carrier (MC) priority queue (PQ) data buffer in order to deactivating the secondary serving HS-DSCH cell for a UE in MC mode. In the case of multiple MC-PQs belonging to the same UE all data buffers should be empty during the required time to perform the deactivation.; range 1..2550; Default value: 2.";
      type int16 {
        range "1..2550";
      }
      default "2";
      units "seconds";
    }
    leaf qualityCheckPower {
      description "Feedback from the HS-SCCH received quality.; range -2..6; Default value: 0.";
      type int16 {
        range "-2..6";
      }
      default "0";
      units "dB";
    }
    leaf chQualOffset {
      description "The parameter is used to offset the channel quality estimation.; range 0..30; Default value: 18.";
      type int16 {
        range "0..30";
      }
      default "18";
      units "dB";
    }
    leaf extraCompEnhUeDrx {
      description "Additional compensation applied to the converted CQI value used for TFRC selection when data for the Enhanced UE DRX users are transmitted.; Default value: 10.";
      type int16 {
        range "0..200 | 1000";
      }
      default "10";
      units "dB";
    }
    leaf extraHsScchCompEnhUeDrx {
      description "Additional compensation applied to the HS-SCCH power calculated with the converted CQI value when data for the Enhanced UE DRX users are transmitted.; Default value: 10.";
      type int16 {
        range "0..200 | 1000";
      }
      default "10";
      units "dB";
    }
    leaf eHichMinCodePower {
      description "Minimum downlink power in a cell to be used for an individual E-HICH channel on 10 ms TTI. Note that the minimum power for 2 ms TTI users is 6 dB higher than the value given by this parameter.; range -350..150; Default value: -220.";
      type eytypes:int16_range_-350-150;
      default "-220";
      units "dB";
    }
    leaf maxEAgchPowerDl {
      description "Maximum downlink power for an individual E-AGCH channel in the cell.; range -350..150; Default value: -140.";
      type eytypes:int16_range_-350-150;
      default "-140";
      units "dB";
    }
    leaf maxEAgchPowerDlTti2 {
      description "Maximum downlink power for an individual E-AGCH channel in the cell. Applicable to 2 ms TTI.; range -350..150; Default value: -80.";
      type eytypes:int16_range_-350-150;
      default "-80";
      units "dB";
    }
    leaf maxUserEHichERgchPowerDl {
      description "E-HICH for serving and non serving/E-RGCH have fixed power relative CPICH power. But if feature 'DL Power Control EUL' is active, then the parameter defines the maximum power for E-HICH relative to CPICH for serving E-DCH RL. The parameter value is still fixed for all other cases.; range -350..150; Default value: -140.";
      type eytypes:int16_range_-350-150;
      default "-140";
      units "dB";
    }
    leaf maxUserEHichPowerDlTti2 {
      description "E-HICH (for serving and non serving) have fixed power relative CPICH power. But if feature 'DL Power Control EUL' is active, then the parameter defines the maximum power for E-HICH relative to CPICH for serving E-DCH RL. The parameter value is still fixed for non-Serving RL. Applicable to 2 ms TTI.; range -350..150; Default value: -80.";
      type eytypes:int16_range_-350-150;
      default "-80";
      units "dB";
    }
    leaf qualityCheckPowerEHich {
      description "Offset to be used in E-HICH power.; range -350..150; Default value: 0.";
      type eytypes:int16_range_-350-150;
      default "0";
      units "dB";
    }
    leaf userLabel {
      description "Label for free use.; length 1..128.";
      type string {
        length "1..128";
      }
    }
    leaf eulMinMarginCoverage {
      description "The uplink interference contribution from other cells is estimated in the load estimator, but is never allowed to go below the value of this parameter. The unit is load factor, that is, interference power from other cells divided by total interference power.; range 0..100; Default value: 0.";
      type eytypes:int16_range_0-100-45;
      default "0";
    }
    leaf cqiErrors {
      description "Denotes the repetition factor for triggering consecutive erroneous CQI reports. Value 0 -> the RBS triggered updates are turned off.; range 0..100; Default value: 0.";
      type eytypes:int16_range_0-100-45;
      default "0";
    }
    leaf cqiErrorsAbsent {
      description "Denotes the repetition factor for triggering consecutive correct CQI reports. Value 0 -> the RBS triggered updates are turned off.; range 0..100; Default value: 0.";
      type eytypes:int16_range_0-100-45;
      default "0";
    }
    leaf eulNoERgchGroups {
      description "Number of E-RGCH groups per channelization code and cell.; range 1..20; Default value: 8.";
      type int32 {
        range "1..20";
      }
      default "8";
    }
    leaf eulMaxNoSchEDch {
      description "The maximum number of simultaneous scheduled E-DCH users.; range 0..100; Default value: 100.";
      type eytypes:int16_range_0-100-45;
      default "100";
    }
    leaf featCtrlEnhancedLayer2 {
      description "Whether licensed feature 'Enhanced Layer 2' is ON or OFF..";
      type enumeration {
        enum OFF;
        enum ON;
      }
    }
    leaf featCtrlHsdpaMc {
      description "Whether licensed feature 'Multi-Carrier' is ON or OFF..";
      type enumeration {
        enum OFF;
        enum ON;
      }
    }
    leaf hsdpaMcCapability {
      description "Indicates whether or not this local cell is capable of acting as serving cell for a HSDPA Multi-Carrier connection..";
      type enumeration {
        enum HSDPA_MC_NON_CAPABLE;
        enum HSDPA_MC_CAPABLE;
      }
      config false;
    }
    leaf featCtrlHsdpaDynamicCodeAllocation {
      description "Whether licensed feature 'HSDPA Dynamic Code Allocation' is ON or OFF..";
      type enumeration {
        enum OFF;
        enum ON;
      }
    }
    leaf featCtrlHsdpaIncrementalRedundancy {
      description "Whether licensed feature 'HSDPA Incremental Redundancy' is ON or OFF..";
      type enumeration {
        enum OFF;
        enum ON;
      }
    }
    leaf featCtrlFDpchSrbOnHsdpa {
      description "Whether licensed feature 'Fractional DPCH and SRB on HSDPA' is ON or OFF..";
      type enumeration {
        enum OFF;
        enum ON;
      }
    }
    leaf featCtrlImprovedLayer2 {
      description "Whether unlicensed feature 'Improved Layer 2' is ON or OFF..";
      type enumeration {
        enum OFF;
        enum ON;
      }
    }
    leaf maxNumEulUsers {
      description "Maximum number of serving EUL users allowed per cell. Alarm Licensed Capacity Exceeded is given if: • administrativeState=UNLOCKED and • maxNumEulUsers higher than the upper limit and • Emergency Unlock is not activated Where upper limit is: • License key value if Licensed capacity 'Number of EUL users' is enabled (see licenseState in MO CapacityState) or • default value (maximum 4 EUL users) if license key is disabled. During Emergency Unlock, maximum 128 EUL users are allowed in each cell.; range 1..128; Default value: 4.";
      type int16 {
        range "1..128";
      }
      default "4";
    }
    leaf maxNumHsdpaUsers {
      description "Maximum number of HSDPA users allowed per cell. Alarm Licensed Capacity Exceeded is given if: • administrativeState=UNLOCKED and • maxNumHsdpaUsers higher than the upper limit and • Emergency Unlock is not activated Where upper limit is: • License key value if Licensed capacity 'Number of HSDPA Users per cell' is enabled (see licenseState in MO CapacityState) or • default value (maximum 16 HSDPA users) if license key is disabled. During Emergency Unlock, maximum 128 HSDPA users are allowed in each cell.; range 1..128; Default value: 16.";
      type int16 {
        range "1..128";
      }
      default "16";
    }
    leaf maxNumHsPdschCodes {
      description "Maximum number of HS-PDSCH codes allowed per cell. Alarm Licensed Capacity Exceeded is given if: • administrativeState=UNLOCKED and • maxNumHsPdschCodes higher than the upper limit and • Emergency Unlock is not activated Where upper limit is: • License key value if Licensed capacity 'Number of HSDPA Codes per cell' is enabled (see licenseState in MO CapacityState) or • default value (maximum 5 HS-PDSCH codes) if license key is disabled. During Emergency Unlock, maximum 15 HS-PDSCH codes are allowed in each cell.; range 5..15; Default value: 5.";
      type int16 {
        range "5..15";
      }
      default "5";
    }
    leaf featCtrlNbir {
      description "Whether licensed feature 'Narrowband Interferece Rejection' is ON or OFF..";
      type enumeration {
        enum OFF;
        enum ON;
      }
    }
    leaf featCtrlHsFach {
      description "Whether licensed feature 'High Speed Downlink for FACH' is ON or OFF..";
      type enumeration {
        enum OFF;
        enum ON;
      }
    }
    leaf featCtrlEnhUeDrx {
      description "Whether licensed feature 'Battery efficiency for high speed FACH' is ON or OFF..";
      type enumeration {
        enum OFF;
        enum ON;
      }
    }
    leaf featCtrlHsdpaPowerSharing {
      description "Whether licensed feature 'HSDPA Dynamic Power Sharing' is ON or OFF..";
      type enumeration {
        enum OFF;
        enum ON;
      }
    }
    leaf powerSharingMaxTransmissionPower {
      description "Maximum allowed transmission power for the cell in case of power sharing.; range 0..530; Default value: 530.";
      type int16 {
        range "0..530";
      }
      default "530";
      units "dBm";
    }
    leaf hsdpaPowerSharingCapability {
      description "Indicates whether this local cell is capable of HSDPA dynamic power sharing or not..";
      type enumeration {
        enum HSDPA_POWER_SHARING_NON_CAPABLE;
        enum HSDPA_POWER_SHARING_CAPABLE;
      }
      config false;
    }
    leaf featCtrlHsdpaMcInactCtrl {
      description "Whether licensed feature 'Multi-Carrier Inactivity Control' is ON or OFF..";
      type enumeration {
        enum OFF;
        enum ON;
      }
    }
    leaf featCtrlHsdpaDbMc {
      description "Whether licensed feature 'Dual Band HSDPA Multi-Carrier' is ON or OFF..";
      type enumeration {
        enum OFF;
        enum ON;
      }
    }
    leaf hsdpaDbMcCapability {
      description "Indicates whether or not this local cell is capable of acting as serving cell for a Dual Band HSDPA Multi-Carrier connection..";
      type enumeration {
        enum HSDPA_DB_MC_NON_CAPABLE;
        enum HSDPA_DB_MC_CAPABLE;
      }
      config false;
    }
    leaf-list reservedBy {
      description "Contains a list of MO instances that reserve this MO instance..";
      type string;
      min-elements 0;
    }
    leaf-list throughputPqxHsdpaFach {
      description "Throughput bandwidth set for the common priority queues for DTCH when data for a HS-FACH user is transmitted, defined per SPI (the first value in the sequence is for SPI 0 and the last one is for SPI 14). A HS-FACH user is a UE which is in RRC state CELL_FACH (on RNC level) and is using transport channel HS-DSCH and not FACH.; Default values sequence: 0,0,0,30,0,0,0,0,0,0,0,0,0,0,0.";
      type int16 {
        range "0..100";
      }
      ordered-by user;
      min-elements 15;
      max-elements 15;
    }
    leaf eulMcCapability {
      description "Indicates whether or not this local cell is capable of acting as serving cell for a EUL Multi-Carrier connection..";
      type enumeration {
        enum EUL_MC_NON_CAPABLE;
        enum EUL_MC_CAPABLE;
      }
      config false;
    }
    leaf featCtrlEulMc {
      description "Whether licensed feature 'EUL Multi-Carrier' is ON or OFF..";
      type enumeration {
        enum OFF;
        enum ON;
      }
    }
    leaf eulMcActivationDelayTime {
      description "Activation delay time for secondary UL carrier in serving Node B. This delay ensures that RNC and UE have time to measure secondary carrier before secondary UL carrier activation in serving Node B. This will mitigate interference to neighboring cells from secondary carrier in heterogeneous network case. Delay applies to all EUL Multi-Carrier users with their primary serving E-DCH cell in this cell. Set to 20 (1000 ms) for cells that act as primary E-DCH cell, when neighboring cell on corresponding secondary carrier exists, and no corresponding neighboring cell on primary carrier is available. Otherwise, set to 0.; range 0..2000; Default value: 0.";
      type int16 {
        range "0..2000";
      }
      default "0";
      units "ms";
    }
    leaf featCtrlHsdpa3Mc {
      description "Whether licensed feature 'HSDPA 3x Multi-Carrier' is ON or OFF..";
      type enumeration {
        enum OFF;
        enum ON;
      }
    }
    leaf hsdpa3McCapability {
      description "Indicates whether or not this local cell is capable of acting as serving cell for a HSDPA 3x Multi-Carrier connection..";
      type enumeration {
        enum HSDPA_3MC_CAPABLE;
        enum HSDPA_3MC_NON_CAPABLE;
      }
      config false;
    }
    leaf eulFachMaxDcchDtchTime {
      description "Maximum number of TTIs user can transmit on C-EDCH for DCCH and DTCH transmissions.; range 5..500; Default value: 40.";
      type int16 {
        range "5..500";
      }
      default "40";
    }
    leaf featCtrlEulFach {
      description "Whether licensed feature 'Enhanced Uplink for FACH' is ON or OFF..";
      type enumeration {
        enum OFF;
        enum ON;
      }
    }
    leaf featCtrlHsdpaMmPowerSharing {
      description "Whether licensed feature 'HSDPA Mixed Mode Dynamic Power Sharing' is ON or OFF..";
      type enumeration {
        enum OFF;
        enum ON;
      }
    }
    leaf hsdpaMmPowerSharingCapability {
      description "Whether this local cell is capable of HSDPA Mixed Mode Dynamic Power Sharing or not..";
      type enumeration {
        enum HSDPA_MM_POWER_SHARING_NON_CAPABLE;
        enum HSDPA_MM_POWER_SHARING_CAPABLE;
      }
      config false;
    }
    leaf cpcCapability {
      description "Whether or not this local cell is capable of acting as serving cell for a CPC connection..";
      type enumeration {
        enum CPC_NON_CAPABLE;
        enum CPC_CAPABLE;
      }
      config false;
    }
    leaf featCtrlCpc {
      description "Whether licensed feature 'Continuous Packet Connectivity - CPC' is ON or OFF..";
      type enumeration {
        enum OFF;
        enum ON;
      }
    }
    leaf featCtrlHsAdaptiveBler {
      description "Whether licensed feature 'HSDPA Adaptive BLER' is ON or OFF..";
      type enumeration {
        enum OFF;
        enum ON;
      }
    }
    leaf eulMaxTdUsers {
      description "Maximum number of simultaneous TD cell users. If 0, feature is deactivated. If 2, feature is activated for 2 users. If 8, feature is activated for 8 users.; Default value: 0.";
      type int16 {
        range "0 | 2..8";
      }
      default "0";
    }
    leaf eulTdSchedulingFactor {
      description "Used to increase the user priorities for EUL TD Scheduled users (EUL 2 ms TTI users within the EUL TD schedule) over CDM users (EUL 10 ms TTI users and EUL 2 ms TTI users outside the EUL TD schedule) which gives preferential treatment of EUL TD Scheduled users over CDM users. A value of 0 means that EUL CDM users and EUL TD Scheduled users will be treated equally.; range 0..15; Default value: 0.";
      type int16 {
        range "0..15";
      }
      default "0";
    }
    leaf rSiteRef {
      description "A label used for grouping radio nodes located at the same site.; length 1..35.";
      type string {
        length "1..35";
      }
      config false;
    }
    leaf bsctTestModel {
      description "Active test model..";
      type enumeration {
        enum TEST_MODEL_1;
        enum TEST_MODEL_2;
        enum TEST_MODEL_3;
        enum TEST_MODEL_4;
        enum TEST_MODEL_5;
        enum TEST_MODEL_6;
        enum NOT_APPLICABLE;
      }
      config false;
    }
    leaf bsctBerMeasStatus {
      description "Whether or not BER measurement started..";
      type enumeration {
        enum STOPPED;
        enum STARTED;
        enum NOT_APPLICABLE;
      }
      config false;
    }
    leaf bsctPnTransStatus {
      description "Whether or not PN transmission started..";
      type enumeration {
        enum STOPPED;
        enum STARTED;
        enum NOT_APPLICABLE;
      }
      config false;
    }
    leaf bsctSirMeasStatus {
      description "Whether or not SIR measurement started..";
      type enumeration {
        enum STOPPED;
        enum STARTED;
        enum NOT_APPLICABLE;
      }
      config false;
    }
    leaf steeredHsCoreId {
      description "HSDPA cores allocated manually to this local cell. Default -1, means steeredHsCoreId is not set.; Default value: -1.";
      type int32;
      default "-1";
    }
    leaf hsCoreId {
      description "Indicates the present HSDPA core ID allocated to the local cell. Set after the cell has been setup by the RNC..";
      type int32;
      config false;
    }
    leaf hostingDigitalUnit {
      description "Shows the Baseband on which baseband processing for the cell is located..";
      type string;
      config false;
    }
  }
  grouping NodeBLocalCellGroup-attributes {
    leaf nodeBLocalCellGroupId {
      description "The value component of the RDN..";
      type string;
      mandatory true;
    }
    leaf administrativeState {
      description "The administrative state. If set to SHUTTING_DOWN, the state will immediately be brought to LOCKED..";
      type enumeration {
        enum LOCKED;
        enum UNLOCKED;
        enum SHUTTINGDOWN;
      }
    }
    leaf userLabel {
      description "Label for free use.; length 1..128.";
      type string {
        length "1..128";
      }
    }
    leaf-list multiCarrierPair1 {
      description "First multi-carrier pair. Two local cells of a multi carrier pair are candidates to share downlink carriers as used by features 'Multi-Carrier' and 'Dual Band HSDPA Multi-Carrier'. When a multi carrier pair is specified, the automatic multi carrier pair selection is turned off..";
      type string;
      min-elements 0;
      max-elements 2;
    }
    leaf-list multiCarrierPair2 {
      description "Second multi-carrier pair. Two local cells of a multi carrier pair are candidates to share downlink carriers as used by features 'Multi-Carrier' and 'Dual Band HSDPA Multi-Carrier'. When a multi carrier pair is specified, the automatic multi carrier pair selection is turned off..";
      type string;
      min-elements 0;
      max-elements 2;
    }
    leaf-list multiCarrierPair3 {
      description "Third multi-carrier pair. Two local cells of a multi carrier pair are candidates to share downlink carriers as used by features 'Multi-Carrier' and 'Dual Band HSDPA Multi-Carrier'. When a multi carrier pair is specified, the automatic multi carrier pair selection is turned off..";
      type string;
      min-elements 0;
      max-elements 2;
    }
    leaf-list multiCarrierPair4 {
      description "Fourth multi-carrier pair. Two local cells of a multi carrier pair are candidates to share downlink carriers as used by features 'Multi-Carrier' and 'Dual Band HSDPA Multi-Carrier'. When a multi carrier pair is specified, the automatic multi carrier pair selection is turned off..";
      type string;
      min-elements 0;
      max-elements 2;
    }
    leaf-list multiCarrierPair5 {
      description "Fifth multi-carrier pair. Two local cells of a multi carrier pair are candidates to share downlink carriers as used by features 'Multi-Carrier' and 'Dual Band HSDPA Multi-Carrier'. When a multi carrier pair is specified, the automatic multi carrier pair selection is turned off..";
      type string;
      min-elements 0;
      max-elements 2;
    }
    leaf-list multiCarrierPair6 {
      description "Sixth multi-carrier pair. Two local cells of a multi carrier pair are candidates to share downlink carriers as used by features 'Multi-Carrier' and 'Dual Band HSDPA Multi-Carrier'. When a multi carrier pair is specified, the automatic multi carrier pair selection is turned off..";
      type string;
      min-elements 0;
      max-elements 2;
    }
    leaf-list availabilityStatus {
      description "The availability status. It contains details about operationalState..";
      type AvailStatus;
      min-elements 0;
    }
    leaf operationalState {
      description "Defines the operational state..";
      type enumeration {
        enum DISABLED;
        enum ENABLED;
      }
      config false;
    }
    list ceCapacitiesDl {
      config false;
      description "Downlink channel element capacities..";
      uses CeCapacitiesDl-struct;
    }
    list ceCapacitiesTotalUl {
      config false;
      description "Total uplink channel element capacities. Both static and dynamic uplink channel elements..";
      uses CeCapacitiesTotalUl-struct;
    }
    list ceCapacitiesUl {
      config false;
      description "Uplink channel element capacities. Static uplink channel elements..";
      uses CeCapacitiesUl-struct;
    }
    leaf rSiteRef {
      description "A label used for grouping radio nodes located at the same site.; length 1..35.";
      type string {
        length "1..35";
      }
      config false;
    }
    list hsPdschCodeCapacities {
      config false;
      description "HS-PDSCH code capacity with BB HWAC limit..";
      uses HsPdschCodeCapacities-struct;
    }
    leaf featCtrlSteerHsAllocation {
      description "Whether unlicensed feature 'Steered HS Allocation' is ON or OFF for the NodeBLocalCellGroup..";
      type enumeration {
        enum OFF;
        enum ON;
      }
    }
    leaf numberOfHsCores {
      description "The number of HSDPA cores for the local cell group. Set after first local cell is unlocked and enabled..";
      type int32;
      config false;
    }
    leaf bbPowerSavingMode {
      description "Baseband power saving mode status.; Status info: Since 20.Q2, Replaced by PowerSaving::bbPowerSavingStatus. Planned to be removed..";
      type enumeration {
        enum NOT_SUPPORTED;
        enum IN_POWER_SAVING;
        enum OUT_OF_POWER_SAVING;
      }
      config false;
      status deprecated;
    }
    leaf hostingDigitalUnit {
      description "Shows the Baseband on which baseband processing for the cell is located..";
      type string;
      config false;
    }
    leaf featCtrlLoadBasedSteHsAlloc {
      description "Indicates whether the unlicensed feature 'Load-based Steered HS Allocation' is ON or OFF..";
      type enumeration {
        enum OFF;
        enum ON;
      }
    }
    leaf steHsThreshRejCntOneCore {
      description "Threshold for the number of rejected attempts to setup HS user due to lack of HS resource capacity in one HS core. The attribute is used for evaluating traffic uneven distribution together with steHsThreshUneven and steHsThreshHsUsersOneCore. The action of looking for optimal HS core allocation is triggered when the traffic is uneven distributed (the three thresholds are all met). The lower the value, the higher possibility to trigger attempt of looking for new HS core allocation. The value 0 means ignoring this threshold.; range 0..10000; Default value: 100.";
      type uint16 {
        range "0..10000";
      }
      default "100";
    }
    leaf steHsThreshHsUsersOneCore {
      description "Threshold for the number of HS users in one HS core. Expressed as a percentage of corresponding HS core capacity limit. For example, 75 means the number of HS user reach 75% of HS core capacity. The attribute is used for evaluating traffic uneven distribution together with steHsThreshUneven and steHsThreshRejCntOneCore. The action of looking for optimal HS core allocation is triggered when the traffic is uneven distributed (the three thresholds are all met). The lower the value, the higher possibility to trigger attempt of finding new HS core allocation. The value 0 means ignoring this threshold.; range 0..100; Default value: 75.";
      type uint16 {
        range "0..100";
      }
      default "75";
    }
    leaf steHsThreshUneven {
      description "Threshold of uneven level of the numbers of HS users on all HS cores. The attribute is used for evaluating traffic uneven distribution together with steHsThreshHsUsersOneCore and steHsThreshRejCntOneCore. The action of looking for optimal HS core allocation is triggered when the traffic is uneven distributed (the three thresholds are all met). The lower the value, the higher possibility to trigger attempt of looking for new HS core allocation. The value 0 means ignoring this threshold.; range 0..8; Default value: 4.";
      type uint16 {
        range "0..8";
      }
      default "4";
    }
    leaf newSteHsAllocReady {
      description "Indicates whether the optimal HS allocation is ready based on the feature Load-based Steered HS Allocation..";
      type enumeration {
        enum NOT_APPLICABLE;
        enum NEW_STE_HS_ALLOC_NOT_READY;
        enum NEW_STE_HS_ALLOC_READY;
      }
      config false;
    }
    leaf pmCapacityLimitHsCode {
      description "Limits the number of HS-PDSCH codes used in the local cell group by granted BB HWAC capacity of Baseband unit. The local cell group is allocated to this Baseband unit. In Emergency Unlock state, hardware capacity is on maximum level..";
      type int64;
      config false;
    }
    leaf pmSumCapacityUlCe {
      description "Aggregate of all sample values recorded within the granularity period for number of used total UL Channel Elements..";
      type uint64;
      config false;
    }
    leaf pmSetupFailures {
      description "The number of uplink setup failures for all spreading factors..";
      type uint64;
      config false;
    }
    leaf-list pmCapacityUlCeEulFach {
      description "Distribution of static UL CE utilization which are allocated for EUL-FACH. Reported as percentages of the limit of UL CE visible in pmCapacityLimitUlCe. Bins: [0]: Samples in range [0..1[ % [1]: Samples in range [1..2[ % [2]: Samples in range [2..3[ % [3]: Samples in range [3..4[ % [4]: Samples in range [4..5[ % [5]: Samples in range [5..10[ % [6]: Samples in range [10..20[ % [7]: Samples in range [20..40[ % [8]: Samples in range [40..60[ % [9]: Samples in range [60..80[ % [10]: Samples in range [80..100[ %.";
      type uint64;
      max-elements 11;
    }
    leaf pmSumCapacityUlCeStatic {
      description "Aggregate of all sample values recorded within the granularity period for number of used static UL Channel Elements..";
      type uint64;
      config false;
    }
    leaf pmCapacityLimitUlCe {
      description "Limiting number of UL CE. Lower of RBS Channel Elements Uplink license value and available Channel Elements Uplink HWAC capacity. In case of Emergency Unlock, Channel Elements Uplink HWAC capacity..";
      type int64;
      config false;
    }
    leaf pmCapacityAllocRejUlCe {
      description "Number of rejected attempts to allocate UL CE..";
      type uint64;
      config false;
    }
    leaf-list pmCpcUlActivityFactor {
      description "Distribution of the UL channel (DPCCH) activity factor for CPC activated E-DCH connections, as a percentage of time. This counter gives, on a per connection basis, the ratio between the number of slots where the UL DPCCH is transmitted and the total number of slots during the connection. The counter accumulates all CPC users. Bins: [0]: Number of samples in range [0..5[ % [1]: Number of samples in range [5..10[ % ... [18]: Number of samples in range [90..95[ % [19]: Number of samples in range [95..100] %.";
      type uint64;
      max-elements 20;
    }
    leaf pmSamplesCapacityDlCe {
      description "Number of samples in pmSumCapacityDlCe (that is, pmSamplesCapacityDlCe = pmSamplesCapacityDlCe + 1, whenever pmSumCapacityDlCe is to be updated)..";
      type uint64;
      config false;
    }
    leaf-list pmStaticHwCePoolEul {
      description "Number of E-DCH Channel Elements (CEs) allocated at the setup of EUL users on the UL hardware, that is, the static CE cost. The reported CE consumption for EUL includes hardware cost, according to the current E-DCH licensed ladder, and the initial CE cost for 2 ms E-DCH radio links in the RBS. Bins: [0]: Number of samples in range [0..10[ CEs [1]: Number of samples in range [10..20[ CEs ... [9]: Number of samples in range [90..100[ CEs [10]: Number of samples in range [100..120[ CEs [11]: Number of samples in range [120..140[ CEs ... [61]: Number of samples in range [1120.. 1140[ CEs [62]: Number of samples >= 1140 CEs.";
      type uint64;
      max-elements 63;
    }
    leaf-list pmHwCePoolEul {
      description "Total sum of E-DCH Channel Elements (CEs) allocated on the UL hardware. Counter applies hardware cost according to the current E-DCH licensed ladder. Bins: [0]: Number of samples in range [0..10[ CEs [1]: Number of samples in range [10..20[ CEs ... [9]: Number of samples in range [90..100[ CEs [10]: Number of samples in range [100..120[ CEs [11]: Number of samples in range [120..140[ CEs ... [100]: Number of samples in range [1900..1920[ CEs [101]: Number of samples in range [1920..2000[ CEs ... [127]: Number of samples in range [4000..4080[ CEs [128]: Number of samples >= 4080 CEs.";
      type uint64;
      max-elements 129;
    }
    leaf-list pmCapacityOfUlCeExt {
      description "Distribution of total UL Channel Element utilization above licensed limit. Reported as percentages of the license controlled level visible in pmCapacityLimitUlCe. Channel Element utilization above licensed limit is possible for dynamically allocated CEs, when feature CE extension for EUL or additional CE extension for EUL is activated. Bins: [0]: Number of sampled values in range [0] % [1]: Number of sampled values in range ]0..5[ % [2]: Number of sampled values in range [5..10[ % [3]: Number of sampled values in range [10..15[ % [4]: Number of sampled values in range [15..20[ % [5]: Number of sampled values in range [20..30[ % [6]: Number of sampled values in range [30..40[ % ... [45]: Number of sampled values in range [420..430[ % [46]: Number of sampled values >= 430%.";
      type uint64;
      max-elements 47;
    }
    leaf pmIsUsersRatio {
      description "Indicate percentage of users having Interference Suppression (IS) relative all users that can get IS per baseband pool during a granularity period. The result is a percentage figure between 0.0 and 100.0% in units of 0.1%..";
      type int64;
      config false;
    }
    leaf pmSumCapacityUlCeEulFach {
      description "Aggregated number of static UL CEs allocated for EUL-FACH. All sampled values are during granularity period..";
      type uint64;
      config false;
    }
    leaf pmCapacityAllocAttUlCe {
      description "Number of attempts to allocate UL CE..";
      type uint64;
      config false;
    }
    leaf pmSetupAttempts {
      description "The number of setup attempts for all spreading factors..";
      type uint64;
      config false;
    }
    leaf pmSamplesCapacityUlCe {
      description "Number of samples in pmSumCapacityUlCe (that is, pmSamplesCapacityUlCe = pmSamplesCapacityUlCe + 1, whenever pmSumCapacityUlCe is to be updated)..";
      type uint64;
      config false;
    }
    leaf pmSetupRejSwLoad {
      description "Number of failed radio link set setup attempts due to high SW load..";
      type uint64;
      config false;
    }
    leaf-list pmCapacityOfUlCe {
      description "Distribution of total UL Channel Element utilization. Reported as percentages of the limit of UL CE visible in pmCapacityLimitUlCe. Bins: [0]: Number of sampled values in range [0..20[ % [1]: Number of sampled values in range [20..40[ % [2]: Number of sampled values in range [40..50[ % [3]: Number of sampled values in range [50..60[ % [4]: Number of sampled values in range [60..70[ % [5]: Number of sampled values in range [70..80[ % [6]: Number of sampled values in range [80..85[ % [7]: Number of sampled values in range [85..90[ % [8]: Number of sampled values in range [90..95[ % [9]: Number of sampled values >= 95%.";
      type uint64;
      max-elements 10;
    }
    leaf pmSumCapacityDlCe {
      description "Aggregate of all sample values recorded within the granularity period for number of used DL Channel Elements..";
      type uint64;
      config false;
    }
    leaf pmCapacityLimitDlCe {
      description "Limiting number of DL CE. Lower of RBS Channel Elements Downlink license value and available Channel Elements Downlink HWAC capacity. In case of Emergency Unlock, Channel Elements Downlink HWAC capacity..";
      type int64;
      config false;
    }
    leaf pmCapacityAllocAttDlCe {
      description "Number of attempts to allocate DL CE..";
      type uint64;
      config false;
    }
    leaf pmNoUlHwLimitEul {
      description "Counter for the number of times a scheduling decision is taken to increase the hardware rate of an E-DCH user and there is a need to decrease the hardware rate for another E-DCH user owing to UL hardware resource limitations..";
      type uint64;
      config false;
    }
    leaf pmCapacityAllocRejDlCe {
      description "Number of rejected attempts to allocate DL CE..";
      type uint64;
      config false;
    }
    leaf-list pmCapacityOfDlCe {
      description "Distribution of DL Channel Element utilization. Reported as percentages of the limit of DL CE visible in pmCapacityLimitDlCe. Bins: [0]: Number of sampled values in range [0..20[ % [1]: Number of sampled values in range [20..40[ % [2]: Number of sampled values in range [40..50[ % [3]: Number of sampled values in range [50..60[ % [4]: Number of sampled values in range [60..70[ % [5]: Number of sampled values in range [70..80[ % [6]: Number of sampled values in range [80..85[ % [7]: Number of sampled values in range [85..90[ % [8]: Number of sampled values in range [90..95[ % [9]: Number of sampled values >= 95%.";
      type uint64;
      max-elements 10;
    }
    leaf pmSamplesCapacityUlCeStatic {
      description "Number of samples in pmSumCapacityUlCeStatic (that is, pmSamplesCapacityUlCeStatic = pmSamplesCapacityUlCeStatic + 1, whenever pmSumCapacityUlCeStatic is to be updated)..";
      type uint64;
      config false;
    }
  }
  grouping NodeBSectorCarrier-attributes {
    leaf nodeBSectorCarrierId {
      description "The value component of the RDN..";
      type string;
      mandatory true;
    }
    leaf-list availabilityStatus {
      description "The availability status. It contains details about operationalState..";
      type AvailStatus;
      min-elements 0;
    }
    leaf operationalState {
      description "Defines the operational state..";
      type enumeration {
        enum DISABLED;
        enum ENABLED;
      }
      config false;
    }
    leaf bandwidthDl {
      description "DL carrier bandwidth. Feature Psi-Coverage requires same attribute value for all NodeBSectorCarriers in given NodeBLocalCell.; range 38..50; Default value: 50.";
      type int16 {
        range "38..50";
      }
      default "50";
      units "MHz";
    }
    leaf bandwidthUl {
      description "UL carrier bandwidth. Feature Psi-Coverage requires same attribute value for all NodeBSectorCarriers in given NodeBLocalCell.; range 38..50; Default value: 50.";
      type int16 {
        range "38..50";
      }
      default "50";
      units "MHz";
    }
    leaf cellRange {
      description "Maximum range for random access detection. For soft handover, RBS adds soft handover margin internally. Note: actual cell range resolution is 3 chips, that is, about 234 m. Feature Psi-Coverage requires same attribute value for all NodeBSectorCarriers in given NodeBLocalCell.; range 250..200000; Default value: 35000.";
      type int32 {
        range "250..200000";
      }
      default "35000";
      units "m";
    }
    leaf numOfRxAntennas {
      description "Number of UL antennas. Features Psi-Coverage and Combined Cell require same attribute value for all NodeBSectorCarriers in given NodeBLocalCell..";
      type int16 {
        range "0..2 | 4";
      }
      mandatory true;
    }
    leaf numOfTxAntennas {
      description "Number of DL antennas. Features Psi-Coverage and Combined Cell require same attribute value for all NodeBSectorCarriers in given NodeBLocalCell..";
      type int16 {
        range "1..2 | 4";
      }
      mandatory true;
    }
    leaf partOfSectorPower {
      description "Part of total sector power allocated for sector carrier. Output power is evenly distributed over antenna connectors, used for TX transmission allocated for the sector carrier. If total power for each antenna connector is over 100% at cell unlock, an alarm is generated. Local cell must be locked to prevent transmission. Feature Psi-Coverage requires same attribute for all NodeBSectorCarriers in a given NodeBLocalCell. Total cell power must be equally distributed over all NodeBSectorCarriers, and their sum not over 100%.; range 0..100; Default value: 0; Takes effect: At next unlock of Node B Local Cell.; Status info: Since 16B. Replaced by configuredMaxTxPower..";
      type eytypes:int16_range_0-100;
      status deprecated;
      default "0";
      units "percent";
      reference "Takes effect: At next unlock of Node B Local Cell..";
    }
    leaf sectorEquipmentFunctionRef {
      description "Reference to a SectorEquipmentFunction MO..";
      type string;
      mandatory true;
    }
    leaf eulMaxOwnUuLoad {
      description "Maximum allowed contribution to UL interference rise from own cell carrier traffic. Scheduler limits E-DCH power based on this parameter. Feature Psi-Coverage requires same attribute value for all NodeBSectorCarriers in given NodeBLocalCell.; range 0..550; Default value: 100.";
      type int16 {
        range "0..550";
      }
      default "100";
      units "dB";
    }
    leaf eulMaxRotCoverage {
      description "Maximum Rise over Thermal level allowed to preserve coverage. Feature Psi-Coverage requires same attribute value for all NodeBSectorCarriers in given NodeBLocalCell.; range 0..550; Default value: 100.";
      type int16 {
        range "0..550";
      }
      default "100";
      units "dB";
    }
    leaf eulThermalLevelPrior {
      description "The anticipated uplink noise floor of the unloaded RBS, including feeder and TMA contributions.; range -1150..-600; Default value: -1040.";
      type int16 {
        range "-1150..-600";
      }
      default "-1040";
      units "dBm";
    }
    leaf eulNoiseFloorLock {
      description "Locks the noise floor level for RoT calculation to the given value, when set. The locked level is shown by the attribute eulLockedNoiseFloor. Attribute is empty -> The noise floor level is not locked. Value = -1 -> The noise floor level is locked to current level. If the cell is setup, the value -1 locks the noise floor to the current estimated noise floor level. If the cell is not setup, the value -1 locks the noise floor to the value given by eulThermalLevelPrior at next cell setup. The level used for the locked noise floor will be lost at next cell deletion..";
      type int16 {
        range "-1150..-600 | -1";
      }
      units "dBm";
    }
    leaf maxDlPowerCapability {
      description "Maximum DL power capability for sector carrier.; range 0..500.";
      type int16 {
        range "0..500";
      }
      config false;
      units "dBm";
    }
    leaf minDlPowerCapability {
      description "Minimum DL power capability for sector carrier.; range -300..500.";
      type int16 {
        range "-300..500";
      }
      config false;
      units "dBm";
    }
    leaf eulLockedNoiseFloor {
      description "The noise floor level used when the noise floor is locked by eulNoiseFloorLock.; range -1150..-600.";
      type int16 {
        range "-1150..-600";
      }
      config false;
      units "dBm";
    }
    leaf-list rfBranchRxRef {
      description "A list of references to MOs RfBranch and CcBranch instances, LDNs. These MOs represent the RF branches the NodeBSectorCarrier shall use for RX. If no reference is specified carrier allocation is based on the RF Branch MOM list (default behavior)..";
      type string;
      min-elements 0;
      max-elements 4;
    }
    leaf-list rfBranchTxRef {
      description "A list of references to MO RfBranch instances, LDNs. These MOs represents the RF branches the NodeBSectorCarrier shall use for TX. If no reference is specified carrier allocation is based on the RF Branch MOM list (default behavior)..";
      type string;
      min-elements 0;
      max-elements 4;
    }
    leaf fccRotMarginHigh {
      description "Rise over Thermal margin relative eulMaxRotCoverage. Defines high Rise over Thermal threshold for UL Fast Congestion Control. Stabilizes cell carrier Rise over Threshold by control of EUL serving cell traffic. Feature Psi-Coverage requires same attribute value for all NodeBSectorCarriers in given NodeBLocalCell.; range -550..550; Default value: 40.";
      type int16 {
        range "-550..550";
      }
      default "40";
      units "dB";
    }
    leaf fccRotMarginLow {
      description "Rise over Thermal margin relative eulMaxRotCoverage. Defines low Rise over Thermal threshold for UL Fast Congestion Control. Stabilizes cell carrier Rise over Thermal by control of EUL serving cell traffic. Feature Psi-Coverage requires same attribute value for all NodeBSectorCarriers in given NodeBLocalCell.; range -550..550; Default value: 25.";
      type int16 {
        range "-550..550";
      }
      default "25";
      units "dB";
    }
    leaf latitude {
      description "The latitude of the corresponding sector antenna, according to a certain geodetic datum (see attribute geoDatum). Allows a maximum resolution of 2.4 m. The integer value is calculated as follows based on a position expressed in degrees (dd), minutes (mm) and seconds (ss.s), where dd has a value between 0 and 90: latitude = ((dd + mm/60 + ss.s/3600) / 90) x 8388608 Example: Paris Orly airport has latitude 4542009 according to WGS84.; range 0..8388607.";
      type int32 {
        range "0..8388607";
      }
    }
    leaf longitude {
      description "The longitude of the corresponding sector antenna, according to a certain geodetic datum (see attribute geoDatum). Allows a maximum resolution of 2.4 m. The integer value is calculated as follows based on a position expressed in degrees (ddd), minutes (mm) and seconds (ss.s), where ddd has a value between -180 and 180: longitude = ((ddd + mm/60 + ss.s/3600) / 360) x 16777216 Example: Paris Orly airport has longitude 110422 according to WGS84.; range -8388608..8388607.";
      type int32 {
        range "-8388608..8388607";
      }
    }
    leaf latHemisphere {
      description "Defines the latitudinal hemisphere. Example: Paris has latHemisphere = NORTH Cape Town has latHemisphere = SOUTH.";
      type enumeration {
        enum NORTH;
        enum SOUTH;
      }
    }
    leaf beamDirection {
      description "Beam direction of the corresponding sector antenna. Use value \"000\" to \"359\", to define angel for beam direction. Examples: • 000 = North • 090 = East • 180 = South • 270 = West Unit: 1°; length 3..3.";
      type string {
        length "3";
      }
    }
    leaf geoDatum {
      description "Denotes the geodetic (geographic) datum for this sector. Example: WGS84 (World Geodetic System 1984).; length 5..5; Default value: WGS84.";
      type string {
        length "5";
      }
      default "WGS84";
    }
    leaf height {
      description "Height above ground. Example: 1015 = 10.15 meters Unit: 1 cm; length 0..6.";
      type string {
        length "0..6";
      }
    }
    leaf configuredMaxTxPower {
      description "Maximum absolute output power of sector carrier. Output power is evenly distributed over antenna connectors used for TX transmission by the sector carrier, unless attribute txBranchAPower is set. Feature Psi-Coverage requires same attribute value for all NodeBSectorCarriers in given NodeBLocalCell. Total cell power must be equally distributed over all sector carriers.; range 0..10000000; Default value: 20000.";
      type eytypes:int32_range_0-10000000;
      default "20000";
      units "mW";
    }
    leaf numOfBranchWithNbir {
      description "The number of branches where Narrowband Interference Rejection is currently active.; range 0..4.";
      type int16 {
        range "0..4";
      }
      config false;
    }
    leaf nbirAlgorithm {
      description "Narrowband Interference Rejection algorithm to use on cell carrier of Radio Units when feature NBIR is activated..";
      type enumeration {
        enum GENERIC_NBIR;
        enum ADAPTIVE_NOTCH_NBIR;
        enum FIXED_NOTCH_NBIR;
        enum AUTO_GENERIC_ADAPTIVE_NBIR;
        enum AUTO_GENERIC_ADAPTIVE_OFF_NBIR;
      }
    }
    leaf nbirFixedNotchPosition {
      description "Defines notch position for each cell carrier when feature Narrowband Interference Rejection is activated and nbirAlgorithm is FIXED_NOTCH_NBIR.; range -25..25; Default value: 25.";
      type int16 {
        range "-25..25";
      }
      default "25";
      units "MHz";
    }
    leaf dlPowerOffsetCombinedCell {
      description "Power offset of PCPICH for this NodeBSectorCarrier.; range -160..0; Default value: 0.";
      type int16 {
        range "-160..0";
      }
      default "0";
      units "dB";
    }
    leaf txPowerPersistentLock {
      description "Whether attributes configuredMaxTxPower and txBranchAPower are locked or not. When true, attributes configuredMaxTxPower and txBranchAPower cannot be changed and MO NodeBSectorCarrier cannot be deleted.; Default value: false.";
      type boolean;
      default "false";
    }
    leaf txBranchAPower {
      description "Maximum absolute output power of carrier branch A. When numOfTxAntennas=1, txBranchAPower is ignored When numOfTxAntennas=2 then • if txBranchAPower is not set (empty), output power is evenly distributed between TX branches of a sector carrier. • if txBranchAPower has a value, maximum absolute output power of carrier branch B is equal to configuredMaxTxPower - txBranchAPower.; range 1..10000000.";
      type int32 {
        range "1..10000000";
      }
      units "mW";
    }
    leaf noiseFloorEstimationMode {
      description "The noise floor estimation algorithm selection parameter..";
      type enumeration {
        enum SLIDING_WINDOW_NOISE_FLOOR;
        enum RECURSIVE_NOISE_FLOOR;
      }
    }
    leaf nbirAutoCurrentAlgorithm {
      description "Current NBIR algorithm when Automatic NBIR is enabled. NOT_APPLICABLE when Automatic NBIR is disabled.(Automatic NBIR is enabled when nbirAlgorithm is AUTO_GENERIC_ADAPTIVE_NBIR or AUTO_GENERIC_ADAPTIVE_OFF_NBIR.).";
      type enumeration {
        enum NBIR_OFF;
        enum GENERIC_NBIR;
        enum ADAPTIVE_NOTCH_NBIR;
        enum NOT_APPLICABLE;
      }
      config false;
    }
    leaf pmSumOasDeltaRscp {
      description "Sum of delta RSCP measurement values for configured branch pair. 30 dB offset is added to each measured sample of sum counter, unit: 1 dB. For example, sample of -10 dB result in value 20. Result is same for all NodeBSectorCarrier MO instances in sector. Scanner: Not included in any predefined scanner..";
      type uint32;
      config false;
    }
    leaf-list pmRxInterfererDetect {
      description "Percentage of time an interferer was detected in each 0.1 MHz interval of 5 MHz. Maximum value per bin during a ROP is 100%. Depending on where in the spectrum the interferer is detected, the corresponding counter bin is pegged. The counter consists of 51 bins with 100 kHz increments. PM-Counter Bins: Bins: [0]: The percentage of interference in frequency range [-2.55 .. -2.45[ MHz [1]: The percentage of interference in frequency range [-2.45 .. -2.35[ MHz .... [25]: The percentage of interference in frequency range [-0.05 .. 0.05[ MHz .... [49]: The percentage of interference in frequency range [ 2.35 .. 2.45[ MHz [50]: The percentage of interference in frequency range [ 2.45 .. 2.55[ MHz.";
      type int64;
      max-elements 51;
    }
    leaf-list pmRxPowerSpectrum {
      description "Average received power spectrum over 5 MHz in 0.1 MHz increments, unit: dBm. Bins: [ 0]: Average received power in frequency range [-2.55 .. -2.45[ MHz [ 1]: Average received power in frequency range [-2.45 .. -2.35[ MHz ... [25]: Average received power in frequency range [-0.05 .. 0.05[ MHz ... [49]: Average received power in frequency range [ 2.35 .. 2.45[ MHz [50]: Average received power in frequency range [ 2.45 .. 2.55[ MHz.";
      type int32;
      max-elements 51;
    }
    leaf-list pmTransmittedCarrierPower {
      description "The transmitted carrier power. Bins: [0]: Number of sampled values lower than or equal to 0 dBm [1]: Number of sampled values in range [0..1[ dBm [2]: Number of sampled values in range [1..2[ dBm ... [52]: Number of sampled values in range [51..52[ dBm [53]: Number of sampled values greater than or equal to 52 dBm.";
      type uint32;
      max-elements 54;
    }
    leaf-list pmBranchDeltaSir {
      description "The difference in SIR per receive branch per connection (DPCCH) per cell carrier. The purpose with the measurement is to detect faulty feeder installations. The measurement is valid only for 2 way Rx diversity configurations. Bins: [0]: Number of sampled values less than -29.5 dB [1]: Value : SIR sample in range [-29.5 .. -28.5[ dB [2]: Value : SIR sample in range [-28.5 .. -27.5[ dB ... [29]: Value : SIR sample in range [-1.5 .. -0.5[ dB [30]: Value : SIR sample in range [-0.5 .. 0.5[ dB [31]: Value : SIR sample in range [0.5 .. 1.5[ dB ... [58]: Value : SIR sample in range [27.5 .. 28.5[ dB [59]: Value : SIR sample in range [28.5 .. 29.5[ dB [60]: Number of sampled values greater than or equal to 29.5 dB.";
      type uint64;
      max-elements 61;
    }
    leaf pmCpriExtDelayChange {
      description "Total number of times there has been extended delay change in the NodeBSectorCarrier..";
      type uint32;
      config false;
    }
    leaf-list pmNbirRunningAlgorithm {
      description "Narrowband Interference Rejection (NBIR) algorithm in use. Bins: [0]: Algorithm is NBIR_OFF or NBIR is deactivated. [1]: Algorithm is GENERIC_NBIR. [2]: Algorithm is ADAPTIVE_NOTCH_NBIR. [3]: Algorithm is FIXED_NOTCH_NBIR. [4]: Not applicable. One of following scenarios when NBIR feature is activated: - Radio does not support NBIR - NBIR feature cannot work due to faulty status in radio.";
      type uint32;
      max-elements 5;
    }
    leaf pmOasDeltaRscpMeasurement {
      description "Average delta RSCP for configured branch pair in sector. Value is in offset by 30.0 dB, unit: 0.1 dB. For example, sample of -13.5 dB result in value 165. Result is same for all NodeBSectorCarrier MO instances in sector. Scanner: Not included in any predefined scanner..";
      type int32;
      config false;
    }
    leaf-list pmNbirSuggestAlgorithm {
      description "Recommended Narrowband Interference Rejection (NBIR) algorithm. Bins: [0]: Algorithm is NBIR_OFF. [1]: Algorithm is GENERIC_NBIR. [2]: Algorithm is ADAPTIVE_NOTCH_NBIR..";
      type uint32;
      max-elements 3;
    }
    leaf-list pmAverageRssiHigh {
      description "Received Signal Strength Indicator (RSSI) Bins: [0]: Number of sampled values less than -110.0 dBm [1]: Number of sampled values in range [-110.0..-109.5[ dBm [2]: Number of sampled values in range [-109.5..-109.0[ dBm [3]: Number of sampled values in range [-109.0..-108.5[ dBm ... [139]: Number of sampled values in range [-41...-40.5[ dBm [140]: Number of sampled values in range [-40.5..-40.0[ dBm [141]: Number of sampled values greater than or equal to -40.0 dBm.";
      type uint64;
      max-elements 142;
    }
    leaf-list pmTransmittedCarrierPowerW {
      description "The transmitted carrier power measured at the antenna reference point, as a percentage of the maximum power (indicated by the counter pmTransmittedCarrierPowerWLimit). Bins: [0]: Number of sampled values in range [0..2[ % [1]: Number of sampled values in range [2..4[ % [2]: Number of sampled values in range [4..6[ % ... [99]: Number of sampled values in range [198..200] %.";
      type uint64;
      max-elements 100;
    }
    leaf pmTransmittedCarrierPowerWLimit {
      description "Max limit of DL transmission power. Unit: 0.1 W..";
      type int64;
      config false;
    }
    leaf pmSamplesOasDeltaRscp {
      description "Number of samples that pmSumOasDeltaRscp is updated with. Result is same for all NodeBSectorCarrier MO instances in sector. Scanner: Not included in any predefined scanner..";
      type uint32;
      config false;
    }
  }
  grouping RadioLinks-attributes {
    leaf radioLinksId {
      description "The value component of the RDN..";
      type string;
      mandatory true;
    }
    leaf noOfRadioLinks {
      description "Total number of radio links in the cell using the corresponding local cell.; range 0..999.";
      type int16 {
        range "0..999";
      }
      config false;
    }
    leaf-list pmUlSynchTime {
      description "The synchronization time between DL TX resource assignment (when IP connection is established over Iub) and achievement of UL synchronization for RL, which belongs to first RLS. Bins: [0]: Number of sampled values in range [0..50[ms [1]: Number of sampled values in range [50..100[ms ... [9]: Number of sampled values in range [450..500[ms [10]: Number of sampled values in range [500..1000[ms [11]: Number of sampled values in range [1000..2000[ms [12]: Number of sampled values in range [2000..3000[ms ... [14]: Number of sampled values in range [4000..5000[ms [15]: Number of sampled values in range greater than or equal to 5000ms..";
      type uint64;
      max-elements 16;
    }
    leaf-list pmOutOfSynch {
      description "Duration of out-of-sync. Reported for all Radio Link Sets (RLSs) activated during the granularity period. Measurement is performed on RLS, not on Radio Link (RL) - that is, after RL combination in uplink. Bins: [0]: Number of sampled values in range [0..200[ms [1]: Number of sampled values in range [200..400[ms ... [48]: Number of sampled values in range [9600..9800[ms [49]: Number of sampled values in range greater than or equal to 9800ms..";
      type uint64;
      max-elements 50;
    }
    leaf-list pmDpchCodePowerSf16Low {
      description "Average transmitted code power on a DPCH channel for spreading factor 16 for small cells (with low output power)..";
      type uint64;
      max-elements 38;
    }
    leaf-list pmDpchCodePowerSf64 {
      description "Average transmitted code power on a DPCH channel for spreading factor 64. In case of a small cell (with low output power) pmDpchCodePowerSf64Low provides a more appropriate range..";
      type uint64;
      max-elements 38;
    }
    leaf pmRLSSupWaitToOutOfSynch {
      description "Number of times the RLSs are in state unsynchronized long enough to be reported disabled to the RNC..";
      type uint64;
      config false;
    }
    leaf-list pmDpchCodePowerSf32 {
      description "Average transmitted code power on a DPCH channel for spreading factor 32. In case of a small cell (with low output power) pmDpchCodePowerSf32Low provides a more appropriate range..";
      type uint64;
      max-elements 38;
    }
    leaf-list pmDpchCodePowerSf16 {
      description "Average transmitted code power on a DPCH channel for spreading factor 16. In case of a small cell (with low output power) pmDpchCodePowerSf16Low provides a more appropriate range..";
      type uint64;
      max-elements 38;
    }
    leaf-list pmUlSynchTimeSHO {
      description "The synchronization time between the acceptance of a Radio Link Setup Request and the achievement of UL synchronization for a RL not belonging to the first RLS. Bins: [0]: Number of sampled values in range [0..50[ ms [1]: Number of sampled values in range [50..100[ ms ... [9]: Number of sampled values in range [450..500[ ms [10]: Number of sampled values in range [500..1000[ ms [11]: Number of sampled values in range [1000..2000[ ms ... [14]: Number of sampled values in range [4000..5000[ ms [15]: Number of sampled values greater than or equal to 5000 ms..";
      type uint64;
      max-elements 16;
    }
    leaf pmRLSSupSynchToUnsynch {
      description "Number of times RLSs, within the related local cell, go from state synchronized to unsynchronized..";
      type uint64;
      config false;
    }
    leaf-list pmDpchCodePowerSf32Low {
      description "Average transmitted code power on a DPCH channel for spreading factor 32 for small cells (with low output power)..";
      type uint64;
      max-elements 38;
    }
    leaf-list pmDpchCodePowerSf64Low {
      description "Average transmitted code power on a DPCH channel for spreading factor 64 for small cells (with low output power)..";
      type uint64;
      max-elements 38;
    }
    leaf-list pmDpchCodePowerSf8Low {
      description "Average transmitted code power on a DPCH channel for spreading factor 8 for small cells (with low output power)..";
      type uint64;
      max-elements 38;
    }
    leaf-list pmDpchCodePowerSf8 {
      description "Average transmitted code power on a DPCH channel for spreading factor 8. In case of a small cell (with low output power) pmDpchCodePowerSf8Low provides a more appropriate range..";
      type uint64;
      max-elements 38;
    }
    leaf-list pmDpchCodePowerSf256 {
      description "Average transmitted code power on a DPCH channel for spreading factor 256 and F-DPCH channel. In case of a small cell (with low output power) pmDpchCodePowerSf256Low provides a more appropriate range..";
      type uint64;
      max-elements 38;
    }
    leaf-list pmDpchCodePowerSf128Low {
      description "Average transmitted code power on a DPCH channel for spreading factor 128 for small cells (with low output power)..";
      type uint64;
      max-elements 38;
    }
    leaf-list pmDpchCodePowerSf4 {
      description "Average transmitted code power on a DPCH channel for spreading factor 4. In case of a small cell (with low output power) pmDpchCodePowerSf4Low provides a more appropriate range..";
      type uint64;
      max-elements 38;
    }
    leaf-list pmDpchCodePowerSf128 {
      description "Average transmitted code power on a DPCH channel for spreading factor 128. In case of a small cell (with low output power) pmDpchCodePowerSf128Low provides a more appropriate range..";
      type uint64;
      max-elements 38;
    }
    leaf-list pmUlSynchTimeFromCEdch {
      description "The synchronization time between DL TX resource assignment (when IP connection is established over Iub) and achievement of UL synchronization for RL, which belongs to first RLS. The counter applies to EUL FACH users upswitching from CELL_FACH to CELL_DCH and seamless upswitch is performed. If the corresponding carrier is part of a cell using more than one carrier, all values are undefined. Bins: [0]: Number of sampled values in range [0..50[ms [1]: Number of sampled values in range [50..100[ms ... [9]: Number of sampled values in range [450..500[ms [10]: Number of sampled values in range [500..1000[ms [11]: Number of sampled values in range [1000..2000[ms [12]: Number of sampled values in range [2000..3000[ms ... [14]: Number of sampled values in range [4000..5000[ms [15]: Number of sampled values in range greater than or equal to 5000ms..";
      type uint64;
      max-elements 16;
    }
    leaf-list pmFDpchCodePower {
      description "Average transmitted code power on a F-DPCH channel. In case of a small cell (with low output power) pmFDpchCodePowerLow provides a more appropriate range..";
      type uint64;
      max-elements 38;
    }
    leaf-list pmDpchCodePowerSf256Low {
      description "Average transmitted code power on a DPCH channel for spreading factor 256 for small cells (with low output power)..";
      type uint64;
      max-elements 38;
    }
    leaf-list pmFDpchCodePowerLow {
      description "Average transmitted code power on an F-DPCH channel for small cells (with low output power)..";
      type uint64;
      max-elements 38;
    }
    leaf-list pmAverageSir {
      description "The average SIR on DPCCH physical channel. Measurement is performed on radio link set not on radio link, that is, after radio link combination in uplink. If the corresponding carrier is part of a cell using more than one carrier, all values are undefined. Bins: [0]: Number of sampled values less than -7 dB [1]: Number of sampled values in range [-7..-6.5[ dB [2]: Number of sampled values in range [-6.5..-6[ dB ... [36]: Number of sampled values in range [10.5..11[ dB [37]: Number of sampled values greater than or equal to 11 dB.";
      type uint64;
      max-elements 38;
    }
    leaf-list pmDpcchBer {
      description "The average BER detected on DPCCH pilot bits. Measurement is performed on radio link set not on radio link, that is, after radio link combination in uplink. If the corresponding carrier is part of a cell using more than one carrier, all values are undefined. Bins: [0]: Number of values = 0 BER [1]: Number of values in range [MIN_VALUE..-2.06375[ log10(BER) [2]: Number of values in range [-2.06375..-1.9825[ log10(BER) ... [23]: Number of values in range [-0.3575..-0.27625[ log10(BER) [24]: Number of values greater than or equal to -0.27625 log10(BER).";
      type uint64;
      max-elements 25;
    }
    leaf-list pmDpchCodePowerSf4Low {
      description "Average transmitted code power on a DPCH channel for spreading factor 4 for small cells (with low output power)..";
      type uint64;
      max-elements 38;
    }
    leaf-list pmAverageSirError {
      description "The average SIR error on DPCCH physical channel. SIR error is the difference between the measured SIR and SIR target. Measurement is performed on radio link set not on radio link, that is, after radio link combination in uplink. If the corresponding carrier is part of a cell using more than one carrier, all values are undefined. Bins: [0]: Number of sampled values less than -10 dB [1]: Number of sampled values in range [-10..-9.5[ dB [2]: Number of sampled values in range [-9.5..-9[ dB ... [40]: Number of sampled values in range [9.5..10[ dB [41]: Number of sampled values greater than or equal to 10 dB.";
      type uint64;
      max-elements 42;
    }
  }
}
