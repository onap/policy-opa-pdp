module ericsson-bfd-profile-rtn-radio {
  yang-version 1.1;
  namespace "urn:com:ericsson:ecim:RtnBfdProfile";
  prefix bfdpfrdo;
  import ericsson-yang-types {
    prefix eytypes;
  }
  import ericsson-l3-router-rtn-radio {
    prefix l3rtrdo;
  }
  import ericsson-managed-element {
    prefix emael;
  }
  description "Auto-generated from Ericsson CPI MOM XML 15554-lza7016014_33-v1uenfk.xml\nBFD Session Profile.";
  revision "2026-03-29" {
    description "Ericsson G3G4, version: CXP2020502/2-R32C08";
  }

  augment "/emael:ManagedElement/emael:Transport" {
    list BfdProfile {
      description "Additional definitions from MOM:min/max-elements:0/unbounded;root; This class defines BFD Session Profile. Maximum number of BfdProfile MOs defined under Transport MO or under Router MO is limited to: - For Baseband in RAN Compute Group 1, 2, or 3: 64, - For Baseband in RAN Compute Group 4 or higher: 120.";
      key "bfdProfileId";
      leaf bfdProfileId {
        type leafref {
          path "../attributes/bfdProfileId";
        }
      }
      container attributes {
      uses BfdProfile-attributes;
      }
    }
  }

  augment "/emael:ManagedElement/emael:Transport/l3rtrdo:Router" {
    list BfdProfile {
      description "Additional definitions from MOM:min/max-elements:0/unbounded;root; This class defines BFD Session Profile. Maximum number of BfdProfile MOs defined under Transport MO or under Router MO is limited to: - For Baseband in RAN Compute Group 1, 2, or 3: 64, - For Baseband in RAN Compute Group 4 or higher: 120.";
      key "bfdProfileId";
      leaf bfdProfileId {
        type leafref {
          path "../attributes/bfdProfileId";
        }
      }
      container attributes {
      uses BfdProfile-attributes;
      }
    }
  }
  grouping BfdProfile-attributes {
    leaf bfdProfileId {
      description "The value component of the RDN..";
      type string;
      mandatory true;
    }
    leaf detectionMultiplier {
      description "Detection Time multiplier. Desired detection multiplier. Negotiated control packet transmission interval, multiplied by multiplier, defines detection time for this session, as seen by remote system.; range 1..10; Default value: 5.";
      type uint8 {
        range "1..10";
      }
      default "5";
    }
    leaf dscp {
      description "DSCP value to be placed in IP header of control packets. Default value is CS6 (0x30).; range 0..63; Default value: 48.";
      type eytypes:uint8_range_0-63;
      default "48";
    }
    leaf intervalRxMinRequired {
      description "Minimum interval between received BFD control packets that local system is capable of supporting.; range 10..60000; Default value: 100.";
      type uint32 {
        range "10..60000";
      }
      default "100";
      units "ms";
    }
    leaf intervalTxMinDesired {
      description "Preferred minimum desired interval that local system uses when transmitting BFD control packets.; range 10..60000; Default value: 100.";
      type uint32 {
        range "10..60000";
      }
      default "100";
      units "ms";
    }
    leaf intervalTxSessionDown {
      description "Interval that local system uses when transmitting BFD control packets during session down.; range 1000..30000; Default value: 2000.";
      type uint32 {
        range "1000..30000";
      }
      default "2000";
      units "ms";
    }
    leaf-list reservedBy {
      description "Contains a list of MO instances that reserve this MO instance..";
      type string;
      min-elements 0;
    }
  }
}
