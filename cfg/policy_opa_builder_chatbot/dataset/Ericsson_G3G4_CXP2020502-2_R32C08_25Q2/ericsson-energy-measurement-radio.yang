module ericsson-energy-measurement-radio {
  yang-version 1.1;
  namespace "urn:com:ericsson:ecim:ResEnergyMeasurement";
  prefix enmrntrdo;
  import ericsson-equipment-support-function-radio {
    prefix eqsupfnrdo;
  }
  import ericsson-managed-element {
    prefix emael;
  }
  description "Auto-generated from Ericsson CPI MOM XML 15554-lza7016014_33-v1uenfk.xml\n.";
  revision "2026-03-29" {
    description "Ericsson G3G4, version: CXP2020502/2-R32C08";
  }

  augment "/emael:ManagedElement/eqsupfnrdo:EquipmentSupportFunction" {
    list EnergyMeasurement {
      description "Additional definitions from MOM:min/max-elements:0/unbounded;root; This MO displays the energy consumption for an RBS or part of an RBS.";
      key "energyMeasurementId";
      leaf energyMeasurementId {
        type leafref {
          path "../attributes/energyMeasurementId";
        }
      }
      container attributes {
      uses EnergyMeasurement-attributes;
      }
    }
  }
  typedef AvailStatus {
    description "The availability status is used to qualify the operational state. It indicates why the operational state has changed its value.";
    type enumeration {
      enum IN_TEST {
        description "The resource is undergoing a test procedure. If the administrative state is locked or shutting down, normal users are prevented from using the resource.";
      }
      enum FAILED {
        description "The resource has an internal fault that prevents it from operating.";
      }
      enum POWER_OFF {
        description "The resource requires power to be applied and is not powered on.";
      }
      enum OFF_LINE {
        description "The resource requires a routine operation to be performed. This routine operation is to place the resource online and make it available for use. The operation may be manual or automatic, or both. The operational state is disabled.";
      }
      enum OFF_DUTY {
        description "The resource has been made inactive by an internal control process.";
      }
      enum DEPENDENCY {
        description "The resource cannot operate because some other resource on which it depends is unavailable.";
      }
      enum DEGRADED {
        description "The service available from the resource is degraded in some respect.";
      }
      enum NOT_INSTALLED {
        description "The resource represented by the managed object is not present, or is incomplete.";
      }
      enum LOG_FULL {
        description "Indicates a log full condition. The semantics are defined in CCITT Rec. X.735 | ISO/IEC 10164-6.";
      }
      enum DEPENDENCY_LOCKED {
        description "The administrative state of a resource that this resource depends on is locked. Alternatively, the availability status of the other resource is dependency locked.";
      }
      enum DEPENDENCY_FAILED {
        description "The availability status of a resource that this resource depends on is failed or dependency failed.";
      }
      enum DEPENDENCY_SHUTTINGDOWN {
        description "The administrative state of a resource that this resource depends on is shutting down. Alternatively, the availability status of the other resource is dependency shutting down.";
      }
      enum DEPENDENCY_RECOVERY {
        description "Resource that this resource depends on is undergoing a recovery procedure.";
      }
      enum DEPENDENCY_HOLDING {
        description "Resource cannot operate because some other resource on which it depends is currently unavailable. The situation is expected to be resolved. Actions to facilitate dependency resolution may be ongoing.";
      }
    }
  }
  typedef OperState {
    description "Operational states of a resource.";
    type enumeration {
      enum DISABLED {
        description "The resource is totally inoperable.";
      }
      enum ENABLED {
        description "The resource is partially or fully operable.";
      }
    }
  }
  grouping EnergyMeasurement-attributes {
    leaf energyMeasurementId {
      description "The value component of the RDN..";
      type string;
      mandatory true;
    }
    leaf-list availabilityStatus {
      description "The availability status. It contains details about operationalState..";
      type AvailStatus;
      min-elements 0;
    }
    leaf energyConsumption {
      description "The consumed energy for the specified units from startTime, in other words the sum of the consumption from all the included units in the energyMeterListRef attribute..";
      type int32;
      config false;
      units "kWh";
    }
    leaf-list energyMeterListRef {
      description "List with references to which energy meter can be included in the calculation. Reference can be MO FieldReplaceableUnit representing a PSU, EMU or PDU of type ECM..";
      type string;
      ordered-by user;
      min-elements 1;
      max-elements 32;
    }
    leaf operationalState {
      description "Defines the operational state..";
      type enumeration {
        enum DISABLED;
        enum ENABLED;
      }
      config false;
    }
    leaf powerConsumption {
      description "The present power consumption of the units listed in the energyMeterListRef attribute. An undefined value indicates that it is not possible to calculate a measurement for the present power consumption..";
      type int32;
      config false;
      units "W";
    }
    leaf startTime {
      description "From when the energy consumption is calculated. If the field is left empty/undefined the system will start the measurements immediately at the creation of the MO. Format: YYYYMMDD hh:mm; length 14..14.";
      type string {
        length "14";
      }
    }
    leaf stopTime {
      description "When the measurement shall stop counting. An attribute to let the operator keep the measurement even when the calculating has stopped. If an empty/undefined value is set it means the measurement shall continue forever, i.e. until MO is deleted. Format: YYYYMMDD hh:mm; length 14..14.";
      type string {
        length "14";
      }
    }
    leaf userLabel {
      description "Label for free use.; length 1..128.";
      type string {
        length "1..128";
      }
    }
    leaf pmMaxPowerConsumption {
      description "Maximum power consumption during each ROP. Unit: 1 W.";
      type int32;
      config false;
    }
    leaf-list pmPowerConsumption {
      description "Average power consumption in 6 second periods averaged from one sample for each second. Unit: 1 W.";
      type int32;
      max-elements 150;
    }
    leaf pmAccumulatedEnergyConsumption {
      description "Accumulated energy consumption from start of EnergyMeasurement. Unit: 0.1 kWh.";
      type uint32;
      config false;
    }
    leaf pmEnergyConsumption {
      description "Energy consumed during each ROP. Unit: 0.1 kWh.";
      type uint32;
      config false;
    }
    leaf pmMinPowerConsumption {
      description "Minimum power consumption during each ROP. Unit: 1 W.";
      type int32;
      config false;
    }
  }
}
