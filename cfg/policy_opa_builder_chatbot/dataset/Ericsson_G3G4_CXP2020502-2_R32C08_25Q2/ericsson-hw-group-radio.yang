module ericsson-hw-group-radio {
  yang-version 1.1;
  namespace "urn:com:ericsson:ecim:ReqHwGroup";
  prefix hwgrrdo;
  import ericsson-equip-radio {
    prefix equiprdo;
  }
  import ericsson-managed-element {
    prefix emael;
  }
  description "Auto-generated from Ericsson CPI MOM XML 15554-lza7016014_33-v1uenfk.xml\n.";
  revision "2026-03-29" {
    description "Ericsson G3G4, version: CXP2020502/2-R32C08";
  }

  augment "/emael:ManagedElement/equiprdo:Equipment" {
    list HwGroup {
      description "Additional definitions from MOM:min/max-elements:0/unbounded;root; Represents HW unit group, adjacently mounted units. Each unit refers to HwGroup MO through attributes positionRef and controlDomainRef.";
      key "hwGroupId";
      leaf hwGroupId {
        type leafref {
          path "../attributes/hwGroupId";
        }
      }
      container attributes {
      uses HwGroup-attributes;
      }
    }
  }
  grouping HwGroup-attributes {
    leaf hwGroupId {
      description "The value component of the RDN..";
      type string;
      mandatory true;
    }
    leaf positionInformation {
      description "Information on where the HW group is located. This can be expressed in terms of a street address, building, floor, room, etc.; length 0..255.";
      type string {
        length "0..255";
      }
    }
    leaf-list reservedBy {
      description "Contains a list of MO instances that reserve this MO instance..";
      type string;
      min-elements 0;
    }
    leaf userLabel {
      description "Label for free use.; length 0..128.";
      type string {
        length "0..128";
      }
    }
  }
}
