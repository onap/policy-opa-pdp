module ericsson-gnbdu-radio {
  yang-version 1.1;
  namespace "urn:com:ericsson:ecim:GNBDU";
  prefix gnbdu;
  import ietf-inet-types {
    prefix ietfinet;
  }
  import ietf-yang-types {
    prefix ietfyang;
  }
  import ericsson-yang-types {
    prefix eytypes;
  }
  import ericsson-managed-element {
    prefix emael;
  }
  description "Auto-generated from Ericsson CPI MOM XML 15554-lza7016014_33-v1uenfk.xml\nThis MO is the top level MO for GNBDU functions in a gNodeB.";
  revision "2026-03-29" {
    description "Ericsson G3G4, version: CXP2020502/2-R32C08";
  }

  augment "/emael:ManagedElement" {
    list GNBDUFunction {
      description "Additional definitions from MOM:min/max-elements:0/unbounded;root; Represents gNodeB-DU function. Cannot be deleted if there are NRSectorCarrier instances configured.";
      key "gNBDUFunctionId";
      leaf gNBDUFunctionId {
        type leafref {
          path "../attributes/gNBDUFunctionId";
        }
      }
      container attributes {
      uses GNBDUFunction-attributes;
      }
    }
  }

  augment "/emael:ManagedElement/gnbdu:GNBDUFunction/gnbdu:DUQos/gnbdu:AutomatedQos" {
    list RrpController {
      description "Additional definitions from MOM:min/max-elements:0/16; Performance metrics for Automated RRP. Instance RrpController=NO_AUTO_CONTROL is created automatically when parent MO instance is created, unless created manually in same transaction. ResourceAllocationPolicy::rrpControllerRef and ServicePolicy::rrpControllerRef are automatically set to RrpController=NO_AUTO_CONTROL instance, unless manually set to refer to another MO instance. Precondition: Instance RrpController=NO_AUTO_CONTROL can only be created in same transaction as parent MO instance and cannot be deleted unless parent MO instance is deleted. Other instances can be created and deleted manually. Maximum 15 RrpController instances, with RDN different from NO_AUTO_CONTROL, can be created under parent MO instance.";
      key "rrpControllerId";
      leaf rrpControllerId {
        type leafref {
          path "../attributes/rrpControllerId";
        }
      }
      container attributes {
      uses RrpController-attributes;
      }
    }
  }

  augment "/emael:ManagedElement/gnbdu:GNBDUFunction/gnbdu:BWPSet" {
    list BWPSetUeCfg {
      description "Additional definitions from MOM:min/max-elements:1/8; Configuration of UE-specific capabilities within BWPSet instance.";
      key "bWPSetUeCfgId";
      leaf bWPSetUeCfgId {
        type leafref {
          path "../attributes/bWPSetUeCfgId";
        }
      }
      container attributes {
      uses BWPSetUeCfg-attributes;
      }
    }
  }

  augment "/emael:ManagedElement/gnbdu:GNBDUFunction/gnbdu:BWPSet" {
    list DynPowerOpt {
      description "Additional definitions from MOM:min/max-elements:0/12; Configuration of UE power saving through search space adaption for BWP.";
      key "dynPowerOptId";
      leaf dynPowerOptId {
        type leafref {
          path "../attributes/dynPowerOptId";
        }
      }
      container attributes {
      uses DynPowerOpt-attributes;
      }
    }
  }

  augment "/emael:ManagedElement/gnbdu:GNBDUFunction/gnbdu:BWPSet/gnbdu:BWPSetUeCfg" {
    list BWPSetCfg {
      description "Additional definitions from MOM:min/max-elements:1/4; Configuration of individual BWP within BWPSet instance. If BWPSet instance is configured for FDD cell in bWPSetRef, maximum 2 BWPSetCfg instances can be created under parent MO instance. If BWPSet instance is configured for TDD cell in bWPSetRef, maximum 4 BWPSetCfg instances can be created under parent MO instance. For each unique BWP frequency width, at least one BWPSetCfg instance must be created under parent MO instance.";
      key "bWPSetCfgId";
      leaf bWPSetCfgId {
        type leafref {
          path "../attributes/bWPSetCfgId";
        }
      }
      container attributes {
      uses BWPSetCfg-attributes;
      }
    }
  }

  augment "/emael:ManagedElement/gnbdu:GNBDUFunction/gnbdu:UeCC/gnbdu:Bsr" {
    list BsrUeCfg {
      description "Additional definitions from MOM:min/max-elements:0/8; BSR profile used for current UE. Instance BsrUeCfg=Base is created automatically when parent MO instance is created, unless created manually in same transaction. UeBbProfileUeCfg::bsrUeCfgRef is automatically set to BsrUeCfg=Base instance, unless manually set to refer to another MO instance. Precondition: Instance BsrUeCfg=Base can only be created in same transaction as parent MO instance and cannot be deleted unless parent MO instance is deleted. Other instances can be created and deleted at any time. Maximum 7 BsrUeCfg instances, with RDN different from Base, can be created under parent MO instance.";
      key "bsrUeCfgId";
      leaf bsrUeCfgId {
        type leafref {
          path "../attributes/bsrUeCfgId";
        }
      }
      container attributes {
      uses BsrUeCfg-attributes;
      }
    }
  }

  augment "/emael:ManagedElement/gnbdu:GNBDUFunction/gnbdu:UeCA/gnbdu:CaSCellHandling" {
    list CaSCellHandlingUeCfg {
      description "Additional definitions from MOM:min/max-elements:0/8; SCell handling parameters in NR Carrier Aggregation for UE groups. Instance CaSCellHandlingUeCfg=Base is created automatically when parent MO instance is created, unless created manually in same transaction. Attributes prefUeGroupList, ueGroupList and ueConfGroupList must be empty in instance CaSCellHandlingUeCfg=Base but cannot all be empty in any other instance of CaSCellHandlingUeCfg under same parent CaSCellHandling instance. Precondition: Instance CaSCellHandlingUeCfg=Base can only be created in same transaction as parent MO instance and cannot be deleted unless parent MO instance is deleted. Other instances can be created and deleted at any time. Maximum 7 CaSCellHandlingUeCfg instances, with RDN different from Base, can be created under parent MO instance.";
      key "caSCellHandlingUeCfgId";
      leaf caSCellHandlingUeCfgId {
        type leafref {
          path "../attributes/caSCellHandlingUeCfgId";
        }
      }
      container attributes {
      uses CaSCellHandlingUeCfg-attributes;
      }
    }
  }

  augment "/emael:ManagedElement/gnbdu:GNBDUFunction/gnbdu:ResourceAllocationPolicies/gnbdu:CellResourceMapping" {
    list PartitionMapping {
      description "Additional definitions from MOM:min/max-elements:0/13; Mapping of resource quotas to resource partition.";
      key "partitionMappingId";
      leaf partitionMappingId {
        type leafref {
          path "../attributes/partitionMappingId";
        }
      }
      container attributes {
      uses PartitionMapping-attributes;
      }
    }
  }

  augment "/emael:ManagedElement/gnbdu:GNBDUFunction/gnbdu:UeCC/gnbdu:CgSwitch" {
    list CgSwitchUeCfg {
      description "Additional definitions from MOM:min/max-elements:0/8; Cell group switch UE configuration group. Instance CgSwitchUeCfg=Base is created automatically when parent MO instance is created, unless created manually in same transaction. Each UE configuration group identifier can only be defined in one ueConfGroupList among CgSwitchUeCfg instances contained under parent CgSwitch instance. Any combination of one UE group identifier in ueGroupList and one preference UE group identifier in prefUeGroupList must be unique among CgSwitchUeCfg instances contained under parent CgSwitch instance. Attributes prefUeGroupList, ueGroupList and ueConfGroupList must be empty in instance CgSwitchUeCfg=Base but cannot all be empty in any other instance of CgSwitchUeCfg under same parent CgSwitch instance. Precondition: Instance CgSwitchUeCfg=Base can only be created in same transaction as parent MO instance and cannot be deleted unless parent MO instance is deleted. Other instances can be created and deleted at any time. Maximum 7 CgSwitchUeCfg instances, with RDN different from Base, can be created under parent MO instance.";
      key "cgSwitchUeCfgId";
      leaf cgSwitchUeCfgId {
        type leafref {
          path "../attributes/cgSwitchUeCfgId";
        }
      }
      container attributes {
      uses CgSwitchUeCfg-attributes;
      }
    }
  }

  augment "/emael:ManagedElement/gnbdu:GNBDUFunction/gnbdu:NRSectorCarrier/gnbdu:CommonBeamforming" {
    list Beam {
      description "Additional definitions from MOM:min/max-elements:0/64;systemCreated; SSB beam used by NRSectorCarrier. Created when NRCellDU::administrativeState is changed to UNLOCKED. The RDN of this MO is Beam=[wideBeamIndex]. Length of RDN value is up to 2 characters. Instance can be created without a preceding user-initiated transaction.";
      key "beamId";
      leaf beamId {
        type leafref {
          path "../attributes/beamId";
        }
      }
      container attributes {
      uses Beam-attributes;
      }
    }
  }

  augment "/emael:ManagedElement/gnbdu:GNBDUFunction/gnbdu:UeCC/gnbdu:ConfiguredGrant" {
    list ConfiguredGrantUeCfg {
      description "Additional definitions from MOM:min/max-elements:0/8; Configured grant configuration profile for UE groups. Instance ConfiguredGrantUeCfg=Base is created automatically when parent MO instance is created, unless created manually in same transaction. UeBbProfileUeCfg::configuredGrantUeCfgRef is automatically set to ConfiguredGrantUeCfg=Base instance, unless manually set to refer to another MO instance. Precondition: Instance ConfiguredGrantUeCfg=Base can only be created in same transaction as parent MO instance and cannot be deleted unless parent MO instance is deleted. Other instances can be created and deleted at any time. Maximum 7 ConfiguredGrantUeCfg instances, with RDN different from Base, can be created under parent MO instance.";
      key "configuredGrantUeCfgId";
      leaf configuredGrantUeCfgId {
        type leafref {
          path "../attributes/configuredGrantUeCfgId";
        }
      }
      container attributes {
      uses ConfiguredGrantUeCfg-attributes;
      }
    }
  }

  augment "/emael:ManagedElement/gnbdu:GNBDUFunction/gnbdu:ContentionControl" {
    list SessionLimit {
      description "Additional definitions from MOM:min/max-elements:0/16; Session limit definition. Instance SessionLimit=Default is created automatically when parent MO instance is created, unless created manually in same transaction. TrafficSet::sessionLimitRef is automatically set to SessionLimit=Default instance, unless manually set to refer to another MO instance. Precondition: Instance SessionLimit=Default can only be created in same transaction as parent MO instance and cannot be deleted unless parent MO instance is deleted. Other instances can be created and deleted at any time. Maximum 15 SessionLimit instances, with RDN different from Default, can be created under parent MO instance.";
      key "sessionLimitId";
      leaf sessionLimitId {
        type leafref {
          path "../attributes/sessionLimitId";
        }
      }
      container attributes {
      uses SessionLimit-attributes;
      }
    }
  }

  augment "/emael:ManagedElement/gnbdu:GNBDUFunction/gnbdu:UeCC/gnbdu:CsiProfile" {
    list CsiProfileUeCfg {
      description "Additional definitions from MOM:min/max-elements:0/4; Channel State Information profile configurations for UE groups. Instance CsiProfileUeCfg=Base is created automatically when parent MO instance is created, unless created manually in same transaction. UeBbProfileUeCfg::csiProfileUeCfgRef is automatically set to CsiProfileUeCfg=Base instance, unless manually set to refer to another MO instance. Precondition: Instance CsiProfileUeCfg=Base can only be created in same transaction as parent MO instance and cannot be deleted unless parent MO instance is deleted. Other instances can be created and deleted at any time. Maximum 3 CsiProfileUeCfg instances, with RDN different from Base, can be created under parent MO instance.";
      key "csiProfileUeCfgId";
      leaf csiProfileUeCfgId {
        type leafref {
          path "../attributes/csiProfileUeCfgId";
        }
      }
      container attributes {
      uses CsiProfileUeCfg-attributes;
      }
    }
  }

  augment "/emael:ManagedElement/gnbdu:GNBDUFunction/gnbdu:DU5qiTable" {
    list DU5qi {
      description "Additional definitions from MOM:min/max-elements:1/29; QoS configuration for each 5QI profile. Each profile can be present once in each table.";
      key "dU5qiId";
      leaf dU5qiId {
        type leafref {
          path "../attributes/dU5qiId";
        }
      }
      container attributes {
      uses DU5qi-attributes;
      }
    }
  }

  augment "/emael:ManagedElement/gnbdu:GNBDUFunction/gnbdu:DUQosModifier/gnbdu:DUModified5qi" {
    list DUModified5qiUeCfg {
      description "Additional definitions from MOM:min/max-elements:0/15; QoS modification version of parent 5QI profile. Value 0 is no longer allowed and is planned to be removed from the valid range of prefUeGroupList and ueGroupList.";
      key "dUModified5qiUeCfgId";
      leaf dUModified5qiUeCfgId {
        type leafref {
          path "../attributes/dUModified5qiUeCfgId";
        }
      }
      container attributes {
      uses DUModified5qiUeCfg-attributes;
      }
    }
  }

  augment "/emael:ManagedElement/gnbdu:GNBDUFunction/gnbdu:DUQos" {
    list AutomatedQos {
      description "Additional definitions from MOM:min/max-elements:0/1; Container class for Automated QoS attributes and classes. Instance AutomatedQos=1 is created automatically when parent MO instance is created, unless created manually in same transaction. The RDN of this MO must be AutomatedQos=1. Precondition: Instance AutomatedQos=1 can only be created in same transaction as parent MO instance and cannot be deleted unless parent MO instance is deleted.";
      key "automatedQosId";
      leaf automatedQosId {
        type leafref {
          path "../attributes/automatedQosId";
        }
      }
      container attributes {
      uses AutomatedQos-attributes;
      }
    }
  }

  augment "/emael:ManagedElement/gnbdu:GNBDUFunction/gnbdu:DUQos" {
    list ExtCaPriority {
      description "Additional definitions from MOM:min/max-elements:0/8; Carrier Aggregation QoS for external data. Not applicable in High-Band cells. Instance ExtCaPriority=Default is created automatically when parent MO instance is created, unless created manually in same transaction. NRCellDU::extCaPriorityRef is automatically set to ExtCaPriority=Default instance, unless manually set to refer to another MO instance. Precondition: Instance ExtCaPriority=Default can only be created in same transaction as parent MO instance and cannot be deleted unless parent MO instance is deleted. Other instances can be created and deleted at any time. Maximum 7 ExtCaPriority instances, with RDN different from Default, can be created under parent MO instance.";
      key "extCaPriorityId";
      leaf extCaPriorityId {
        type leafref {
          path "../attributes/extCaPriorityId";
        }
      }
      container attributes {
      uses ExtCaPriority-attributes;
      }
    }
  }

  augment "/emael:ManagedElement/gnbdu:GNBDUFunction/gnbdu:DUQos" {
    list QosPriorityShift {
      description "Additional definitions from MOM:min/max-elements:0/1; Container class for QoS priority shift attributes and classes.";
      key "qosPriorityShiftId";
      leaf qosPriorityShiftId {
        type leafref {
          path "../attributes/qosPriorityShiftId";
        }
      }
      container attributes {
      uses QosPriorityShift-attributes;
      }
    }
  }

  augment "/emael:ManagedElement/gnbdu:GNBDUFunction/gnbdu:DUQosModifier" {
    list DUModified5qi {
      description "Additional definitions from MOM:min/max-elements:0/29; QoS modification for a certain 5QI.";
      key "dUModified5qiId";
      leaf dUModified5qiId {
        type leafref {
          path "../attributes/dUModified5qiId";
        }
      }
      container attributes {
      uses DUModified5qi-attributes;
      }
    }
  }

  augment "/emael:ManagedElement/gnbdu:GNBDUFunction/gnbdu:UeCC/gnbdu:DlBeamOptProfile" {
    list DlBeamOptProfileUeCfg {
      description "Additional definitions from MOM:min/max-elements:0/4; Downlink Beamforming optimization profile configurations for UE groups. Instance DlBeamOptProfileUeCfg=Base is created automatically when parent MO instance is created, unless created manually in same transaction. UeBbProfileUeCfg::dlBeamOptProfileUeCfgRef is automatically set to DlBeamOptProfileUeCfg=Base instance, unless manually set to refer to another MO instance. Precondition: Instance DlBeamOptProfileUeCfg=Base can only be created in same transaction as parent MO instance and cannot be deleted unless parent MO instance is deleted. Other instances can be created and deleted at any time. Maximum 3 DlBeamOptProfileUeCfg instances, with RDN different from Base, can be created under parent MO instance.";
      key "dlBeamOptProfileUeCfgId";
      leaf dlBeamOptProfileUeCfgId {
        type leafref {
          path "../attributes/dlBeamOptProfileUeCfgId";
        }
      }
      container attributes {
      uses DlBeamOptProfileUeCfg-attributes;
      }
    }
  }

  augment "/emael:ManagedElement/gnbdu:GNBDUFunction/gnbdu:UeCC/gnbdu:DlMimo" {
    list DlMimoUeCfg {
      description "Additional definitions from MOM:min/max-elements:0/8; MIMO configuration profile used for current UE. Applies to UEs that use cell as SpCell. Attributes are used on cell level. Instance DlMimoUeCfg=Base is created automatically when parent MO instance is created, unless created manually in same transaction. UeBbProfileUeCfg::dlMimoUeCfgRef is automatically set to DlMimoUeCfg=Base instance, unless manually set to refer to another MO instance. Precondition: Instance DlMimoUeCfg=Base can only be created in same transaction as parent MO instance and cannot be deleted unless parent MO instance is deleted. Other instances can be created and deleted at any time. Maximum 7 DlMimoUeCfg instances, with RDN different from Base, can be created under parent MO instance.";
      key "dlMimoUeCfgId";
      leaf dlMimoUeCfgId {
        type leafref {
          path "../attributes/dlMimoUeCfgId";
        }
      }
      container attributes {
      uses DlMimoUeCfg-attributes;
      }
    }
  }

  augment "/emael:ManagedElement/gnbdu:GNBDUFunction/gnbdu:UeCC/gnbdu:RadioLinkControl/gnbdu:DrbRlc" {
    list DrbRlcUeCfg {
      description "Additional definitions from MOM:min/max-elements:0/4; Configuration of data radio bearer radio link control profile for UE groups. Instance DrbRlcUeCfg=Base is created automatically when parent MO instance is created, unless created manually in same transaction. Attributes prefUeGroupList, ueGroupList and ueConfGroupList must be empty in instance DrbRlcUeCfg=Base but cannot all be empty in any other instance of DrbRlcUeCfg under same parent DrbRlc instance. A combination of an element of ueGroupList and an element of prefUeGroupList in DrbRlcUeCfg instance must be unique under DrbRlc instance. Precondition: Instance DrbRlcUeCfg=Base can only be created in same transaction as parent MO instance and cannot be deleted unless parent MO instance is deleted. Other instances can be created and deleted at any time. Maximum 3 DrbRlcUeCfg instances, with RDN different from Base, can be created under parent MO instance.";
      key "drbRlcUeCfgId";
      leaf drbRlcUeCfgId {
        type leafref {
          path "../attributes/drbRlcUeCfgId";
        }
      }
      container attributes {
      uses DrbRlcUeCfg-attributes;
      }
    }
  }

  augment "/emael:ManagedElement/gnbdu:GNBDUFunction/gnbdu:UeCC/gnbdu:DrbUp" {
    list DrbUpUeCfg {
      description "Additional definitions from MOM:min/max-elements:0/8; Configuration of data radio bearer user plane UE profile for UE groups. Instance DrbUpUeCfg=Base is created automatically when parent MO instance is created, unless created manually in same transaction. Each UE configuration group identifier can be defined in only one ueConfGroupList among DrbUpUeCfg instances contained under same parent DrbUp instance. Any combination of one UE group identifier in ueGroupList and one preference UE group identifier in prefUeGroupList must be unique among DrbUpUeCfg instances contained under parent DrbUp instance. Attributes prefUeGroupList, ueGroupList and ueConfGroupList must be empty in instance DrbUpUeCfg=Base but cannot all be empty in any other instance of DrbUpUeCfg under same parent DrbUp instance. Only applicable when GNBDUFunction::altDepHServAdapUPProfEnabled is true. Precondition: Instance DrbUpUeCfg=Base can only be created in same transaction as parent MO instance and cannot be deleted unless parent MO instance is deleted. Other instances can be created and deleted at any time. Maximum 7 DrbUpUeCfg instances, with RDN different from Base, can be created under parent MO instance. To be able to create an instance, the total number of instances, including all auto created instances, must be less than the total allowed number of instances under a GNBCUCPFunction instance that is 32.";
      key "drbUpUeCfgId";
      leaf drbUpUeCfgId {
        type leafref {
          path "../attributes/drbUpUeCfgId";
        }
      }
      container attributes {
      uses DrbUpUeCfg-attributes;
      }
    }
  }

  augment "/emael:ManagedElement/gnbdu:GNBDUFunction/gnbdu:UeCC/gnbdu:DrxProfile" {
    list DrxProfileUeCfg {
      description "Additional definitions from MOM:min/max-elements:0/8; Configuration of DRX profile for UE groups. Instance DrxProfileUeCfg=Base is created automatically when parent MO instance is created, unless created manually in same transaction. Attributes prefUeGroupList, ueGroupList and ueConfGroupList must be empty in instance DrxProfileUeCfg=Base but cannot all be empty in any other instance of DrxProfileUeCfg under same parent DrxProfile instance. Value 0 is no longer allowed and is planned to be removed from the valid range of prefUeGroupList and ueGroupList. Precondition: Instance DrxProfileUeCfg=Base can only be created in same transaction as parent MO instance and cannot be deleted unless parent MO instance is deleted. Other instances can be created and deleted at any time. Maximum 7 DrxProfileUeCfg instances, with RDN different from Base, can be created under parent MO instance.";
      key "drxProfileUeCfgId";
      leaf drxProfileUeCfgId {
        type leafref {
          path "../attributes/drxProfileUeCfgId";
        }
      }
      container attributes {
      uses DrxProfileUeCfg-attributes;
      }
    }
  }

  augment "/emael:ManagedElement/gnbdu:GNBDUFunction/gnbdu:UeCC/gnbdu:DrxProfile/gnbdu:DrxProfileUeCfg" {
    list PuschRepRel16Drx {
      description "Additional definitions from MOM:min/max-elements:0/1; Configuration of PUSCH Repetition specific DRX parameters. Only applicable to Low-Band and Mid-Band cells.";
      key "puschRepRel16DrxId";
      leaf puschRepRel16DrxId {
        type leafref {
          path "../attributes/puschRepRel16DrxId";
        }
      }
      container attributes {
      uses PuschRepRel16Drx-attributes;
      }
    }
  }

  augment "/emael:ManagedElement/gnbdu:GNBDUFunction/gnbdu:EndpointResource" {
    list LocalIpEndpoint {
      description "Additional definitions from MOM:min/max-elements:0/unbounded; Local transport network endpoint for user plane interface.";
      key "localIpEndpointId";
      leaf localIpEndpointId {
        type leafref {
          path "../attributes/localIpEndpointId";
        }
      }
      container attributes {
      uses LocalIpEndpoint-attributes;
      }
    }
  }

  augment "/emael:ManagedElement/gnbdu:GNBDUFunction/gnbdu:EndpointResource" {
    list LocalSctpEndpoint {
      description "Additional definitions from MOM:min/max-elements:0/unbounded; Local transport network endpoint for control plane interface.";
      key "localSctpEndpointId";
      leaf localSctpEndpointId {
        type leafref {
          path "../attributes/localSctpEndpointId";
        }
      }
      container attributes {
      uses LocalSctpEndpoint-attributes;
      }
    }
  }

  augment "/emael:ManagedElement/gnbdu:GNBDUFunction/gnbdu:EnergyEfficiency" {
    list EnergyOptPwrAlloc {
      description "Additional definitions from MOM:min/max-elements:0/8; Energy-Optimized Power Allocation profile used for current UE. Container class for Energy-Optimized Power Allocation (EOPA) attributes and classes. Instance EnergyOptPwrAlloc=Default is created automatically when parent MO instance is created, unless created manually in same transaction. NRCellDU::energyOptPwrAllocRef is automatically set to EnergyOptPwrAlloc=Default instance, unless manually set to refer to another MO instance. Only applicable to Low-Band and Mid-Band cells. Precondition: Instance EnergyOptPwrAlloc=Default can only be created in same transaction as parent MO instance and cannot be deleted unless parent MO instance is deleted. Other instances can be created and deleted at any time. Maximum 7 EnergyOptPwrAlloc instance, with RDN different from Default, can be created under parent MO instance.";
      key "energyOptPwrAllocId";
      leaf energyOptPwrAllocId {
        type leafref {
          path "../attributes/energyOptPwrAllocId";
        }
      }
      container attributes {
      uses EnergyOptPwrAlloc-attributes;
      }
    }
  }

  augment "/emael:ManagedElement/gnbdu:GNBDUFunction/gnbdu:EnergyEfficiency/gnbdu:EnergyOptPwrAlloc" {
    list EnergyOptPwrAllocUeCfg {
      description "Additional definitions from MOM:min/max-elements:0/8; Energy-Optimized Power Allocation profile for UE groups. Instance EnergyOptPwrAllocUeCfg=Base is created automatically when parent MO instance is created, unless created manually in same transaction. Attributes prefUeGroupList, ueGroupList and ueConfGroupList must be empty in instance EnergyOptPwrAllocUeCfg=Base but cannot all be empty in any other instance of EnergyOptPwrAllocUeCfg under same parent EnergyOptPwrAlloc instance. Precondition: Instance EnergyOptPwrAllocUeCfg=Base can only be created in same transaction as parent MO instance and cannot be deleted unless parent MO instance is deleted. Other instances can be created and deleted at any time. Maximum 7 EnergyOptPwrAllocUeCfg instance, with RDN different from Base, can be created under parent MO instance.";
      key "energyOptPwrAllocUeCfgId";
      leaf energyOptPwrAllocUeCfgId {
        type leafref {
          path "../attributes/energyOptPwrAllocUeCfgId";
        }
      }
      container attributes {
      uses EnergyOptPwrAllocUeCfg-attributes;
      }
    }
  }

  augment "/emael:ManagedElement/gnbdu:GNBDUFunction/gnbdu:ExtENodeBPartnerFunction" {
    list LteInterMeLink {
      description "Additional definitions from MOM:min/max-elements:0/1;systemCreated; Elastic RAN link between a local ME and a neighboring ME. Created when an inter-ME link is established. Deleted when an inter-ME link is released. The RDN of this MO is LteInterMeLink=1. Length of RDN value is 1 character. Instance can be created without a preceding user-initiated transaction.";
      key "lteInterMeLinkId";
      leaf lteInterMeLinkId {
        type leafref {
          path "../attributes/lteInterMeLinkId";
        }
      }
      container attributes {
      uses LteInterMeLink-attributes;
      }
    }
  }

  augment "/emael:ManagedElement/gnbdu:GNBDUFunction/gnbdu:ExtGNBDUPartnerFunction" {
    list InterMeLink {
      description "Additional definitions from MOM:min/max-elements:0/9;systemCreated; ERAN Link between a local ME and a neighboring ME. Created when an inter ME link is established. Deleted when an inter ME link is released. The RDNs of these MOs are InterMeLink=1 to InterMeLink=9. Length of RDN value is 1 character. Instance can be created without a preceding user-initiated transaction.";
      key "interMeLinkId";
      leaf interMeLinkId {
        type leafref {
          path "../attributes/interMeLinkId";
        }
      }
      container attributes {
      uses InterMeLink-attributes;
      }
    }
  }

  augment "/emael:ManagedElement/gnbdu:GNBDUFunction" {
    list AdmissionControl {
      description "Additional definitions from MOM:min/max-elements:1/1;systemCreated; Contains parameters for admission control function. The RDN of this MO is AdmissionControl=1.";
      key "admissionControlId";
      leaf admissionControlId {
        type leafref {
          path "../attributes/admissionControlId";
        }
      }
      container attributes {
      uses AdmissionControl-attributes;
      }
    }
  }

  augment "/emael:ManagedElement/gnbdu:GNBDUFunction" {
    list Aes {
      description "Additional definitions from MOM:min/max-elements:0/1; Controls Automated Energy Saver feature and configures intent. The RDN of this MO must be Aes=1.";
      key "aesId";
      leaf aesId {
        type leafref {
          path "../attributes/aesId";
        }
      }
      container attributes {
      uses Aes-attributes;
      }
    }
  }

  augment "/emael:ManagedElement/gnbdu:GNBDUFunction" {
    list BWP {
      description "Additional definitions from MOM:min/max-elements:0/unbounded; Bandwidth Part (BWP) definition. BWP is related to downlink or uplink resource grids, and is defined by its subcarrier spacing (SCS), cyclic prefix and location and size related to the common resource grid for the applicable SCS. A BWP can be either an initial BWP used for initial access, or other (\"regular\") BWP configured for relevant UEs that support the BWP's characteristics.";
      key "bWPId";
      leaf bWPId {
        type leafref {
          path "../attributes/bWPId";
        }
      }
      container attributes {
      uses BWP-attributes;
      }
    }
  }

  augment "/emael:ManagedElement/gnbdu:GNBDUFunction" {
    list BWPSet {
      description "Additional definitions from MOM:min/max-elements:0/12; Configuration of regular BWP.";
      key "bWPSetId";
      leaf bWPSetId {
        type leafref {
          path "../attributes/bWPSetId";
        }
      }
      container attributes {
      uses BWPSet-attributes;
      }
    }
  }

  augment "/emael:ManagedElement/gnbdu:GNBDUFunction" {
    list CardinalityLimits {
      description "Additional definitions from MOM:min/max-elements:1/1;systemCreated; Cardinality limits for current deployment. Listed cardinality limits is maximum number of MO instances that can be created. The RDN of this MO is CardinalityLimits=1.";
      key "cardinalityLimitsId";
      leaf cardinalityLimitsId {
        type leafref {
          path "../attributes/cardinalityLimitsId";
        }
      }
      container attributes {
      uses CardinalityLimits-attributes;
      }
    }
  }

  augment "/emael:ManagedElement/gnbdu:GNBDUFunction" {
    list ContentionControl {
      description "Additional definitions from MOM:min/max-elements:0/1; Container class for contention control definitions. Instance ContentionControl=1 is created automatically when parent MO instance is created, unless created manually in same transaction. The RDN of this MO must be ContentionControl=1. Precondition: Instance ContentionControl=1 can only be created in same transaction as parent MO instance and cannot be deleted unless parent MO instance is deleted.";
      key "contentionControlId";
      leaf contentionControlId {
        type leafref {
          path "../attributes/contentionControlId";
        }
      }
      container attributes {
      uses ContentionControl-attributes;
      }
    }
  }

  augment "/emael:ManagedElement/gnbdu:GNBDUFunction" {
    list DU5qiTable {
      description "Additional definitions from MOM:min/max-elements:0/36; Mapping from 5G QoS Identifier to parameters that have impact on QoS. At least one DU5qi instance must be created in same transaction when a DU5qiTable instance is created.";
      key "dU5qiTableId";
      leaf dU5qiTableId {
        type leafref {
          path "../attributes/dU5qiTableId";
        }
      }
      container attributes {
      uses DU5qiTable-attributes;
      }
    }
  }

  augment "/emael:ManagedElement/gnbdu:GNBDUFunction" {
    list DUQos {
      description "Additional definitions from MOM:min/max-elements:0/1; Container class for QoS attributes and classes. Instance DUQos=1 is created automatically when parent MO instance is created, unless created manually in same transaction. The RDN of this MO must be DUQos=1. Precondition: Instance DUQos=1 can only be created in same transaction as parent MO instance and cannot be deleted unless parent MO instance is deleted.";
      key "dUQosId";
      leaf dUQosId {
        type leafref {
          path "../attributes/dUQosId";
        }
      }
      container attributes {
      uses DUQos-attributes;
      }
    }
  }

  augment "/emael:ManagedElement/gnbdu:GNBDUFunction" {
    list DUQosModifier {
      description "Additional definitions from MOM:min/max-elements:0/1; QoS modification mapping to 5QI. The RDN of this MO must be DUQosModifier=1.";
      key "dUQosModifierId";
      leaf dUQosModifierId {
        type leafref {
          path "../attributes/dUQosModifierId";
        }
      }
      container attributes {
      uses DUQosModifier-attributes;
      }
    }
  }

  augment "/emael:ManagedElement/gnbdu:GNBDUFunction" {
    list EndpointResource {
      description "Additional definitions from MOM:min/max-elements:0/unbounded; Transport network endpoints for RAN interfaces. Configuration is valid for an entity that refers to an instance of this MO.";
      key "endpointResourceId";
      leaf endpointResourceId {
        type leafref {
          path "../attributes/endpointResourceId";
        }
      }
      container attributes {
      uses EndpointResource-attributes;
      }
    }
  }

  augment "/emael:ManagedElement/gnbdu:GNBDUFunction" {
    list EnergyEfficiency {
      description "Additional definitions from MOM:min/max-elements:0/1; Container class for Energy Efficiency and Management attributes and classes. Instance EnergyEfficiency=1 is created automatically when parent MO instance is created, unless created manually in same transaction. The RDN of this MO must be EnergyEfficiency=1. Precondition: Instance EnergyEfficiency=1 can only be created in same transaction as parent MO instance and cannot be deleted unless parent MO instance is deleted.";
      key "energyEfficiencyId";
      leaf energyEfficiencyId {
        type leafref {
          path "../attributes/energyEfficiencyId";
        }
      }
      container attributes {
      uses EnergyEfficiency-attributes;
      }
    }
  }

  augment "/emael:ManagedElement/gnbdu:GNBDUFunction" {
    list ExtENodeBPartnerFunction {
      description "Additional definitions from MOM:min/max-elements:0/256; List of candidate external eNodeBs that can be used as partner for PIM-A E5 tunnel.";
      key "extENodeBPartnerFunctionId";
      leaf extENodeBPartnerFunctionId {
        type leafref {
          path "../attributes/extENodeBPartnerFunctionId";
        }
      }
      container attributes {
      uses ExtENodeBPartnerFunction-attributes;
      }
    }
  }

  augment "/emael:ManagedElement/gnbdu:GNBDUFunction" {
    list ExtGNBDUPartnerFunction {
      description "Additional definitions from MOM:min/max-elements:0/18; Grouping point of ERAN links to a partner gNodeB distributed unit.";
      key "extGNBDUPartnerFunctionId";
      leaf extGNBDUPartnerFunctionId {
        type leafref {
          path "../attributes/extGNBDUPartnerFunctionId";
        }
      }
      container attributes {
      uses ExtGNBDUPartnerFunction-attributes;
      }
    }
  }

  augment "/emael:ManagedElement/gnbdu:GNBDUFunction" {
    list MassiveMimoSleep {
      description "Additional definitions from MOM:min/max-elements:0/1; Configuration and supervision support for Massive MIMO Sleep-related function. Instance MassiveMimoSleep=1 is created automatically when parent MO instance is created, unless created manually in same transaction. The RDN of this MO must be MassiveMimoSleep=1. Precondition: Instance MassiveMimoSleep=1 can only be created in same transaction as parent MO instance and cannot be deleted unless parent MO instance is deleted.";
      key "massiveMimoSleepId";
      leaf massiveMimoSleepId {
        type leafref {
          path "../attributes/massiveMimoSleepId";
        }
      }
      container attributes {
      uses MassiveMimoSleep-attributes;
      }
    }
  }

  augment "/emael:ManagedElement/gnbdu:GNBDUFunction" {
    list NRCellDU {
      description "Additional definitions from MOM:min/max-elements:0/unbounded; NR Cell representation in gNodeB-DU. Precondition: MO instance must be locked before deletion. Lock must be done in separate transaction. If TheftDeterrence::thdStatus is LOCKED or LOCKED_PERMANENTLY, this instance can only be created if all PLMN IDs on pLMNIdList are part of Lock Token or Operator List.";
      key "nRCellDUId";
      leaf nRCellDUId {
        type leafref {
          path "../attributes/nRCellDUId";
        }
      }
      container attributes {
      uses NRCellDU-attributes;
      }
    }
  }

  augment "/emael:ManagedElement/gnbdu:GNBDUFunction" {
    list NRSectorCarrier {
      description "Additional definitions from MOM:min/max-elements:0/unbounded; Power and frequency use of SectorEquipmentFunction that covers an area. Cannot be deleted once txPowerPersistentLock has been set to true. See description of txPowerPersistentLock.";
      key "nRSectorCarrierId";
      leaf nRSectorCarrierId {
        type leafref {
          path "../attributes/nRSectorCarrierId";
        }
      }
      container attributes {
      uses NRSectorCarrier-attributes;
      }
    }
  }

  augment "/emael:ManagedElement/gnbdu:GNBDUFunction" {
    list NRSynchronization {
      description "Additional definitions from MOM:min/max-elements:1/1;systemCreated; Top class for synchronization within NR. The RDN of this MO is NRSynchronization=1.";
      key "nRSynchronizationId";
      leaf nRSynchronizationId {
        type leafref {
          path "../attributes/nRSynchronizationId";
        }
      }
      container attributes {
      uses NRSynchronization-attributes;
      }
    }
  }

  augment "/emael:ManagedElement/gnbdu:GNBDUFunction" {
    list Paging {
      description "Additional definitions from MOM:min/max-elements:1/1;systemCreated; Configuration parameters for Paging in the RBS. The RDN of this MO is Paging=1.";
      key "pagingId";
      leaf pagingId {
        type leafref {
          path "../attributes/pagingId";
        }
      }
      container attributes {
      uses Paging-attributes;
      }
    }
  }

  augment "/emael:ManagedElement/gnbdu:GNBDUFunction" {
    list QosPriorityMapping {
      description "Additional definitions from MOM:min/max-elements:0/1; Mapping from 5G QoS priorities to parameters that have impact on QoS.";
      key "qosPriorityMappingId";
      leaf qosPriorityMappingId {
        type leafref {
          path "../attributes/qosPriorityMappingId";
        }
      }
      container attributes {
      uses QosPriorityMapping-attributes;
      }
    }
  }

  augment "/emael:ManagedElement/gnbdu:GNBDUFunction" {
    list RadioBearerTable {
      description "Additional definitions from MOM:min/max-elements:1/1;systemCreated; Container for radio bearer configurations. The RDN of this MO is RadioBearerTable=1.";
      key "radioBearerTableId";
      leaf radioBearerTableId {
        type leafref {
          path "../attributes/radioBearerTableId";
        }
      }
      container attributes {
      uses RadioBearerTable-attributes;
      }
    }
  }

  augment "/emael:ManagedElement/gnbdu:GNBDUFunction" {
    list ResourceAllocationPolicies {
      description "Additional definitions from MOM:min/max-elements:0/1; Container class for resource allocation attributes and classes. The RDN of this MO must be ResourceAllocationPolicies=1.";
      key "resourceAllocationPoliciesId";
      leaf resourceAllocationPoliciesId {
        type leafref {
          path "../attributes/resourceAllocationPoliciesId";
        }
      }
      container attributes {
      uses ResourceAllocationPolicies-attributes;
      }
    }
  }

  augment "/emael:ManagedElement/gnbdu:GNBDUFunction" {
    list ResourcePartitions {
      description "Additional definitions from MOM:min/max-elements:0/1; Set of resource partitions.";
      key "resourcePartitionsId";
      leaf resourcePartitionsId {
        type leafref {
          path "../attributes/resourcePartitionsId";
        }
      }
      container attributes {
      uses ResourcePartitions-attributes;
      }
    }
  }

  augment "/emael:ManagedElement/gnbdu:GNBDUFunction" {
    list RimRSGlobal {
      description "Additional definitions from MOM:min/max-elements:0/unbounded; Remote Interference Management Reference Signal (RIM RS) resource allocated for whole network. Resource for RIM RS transmission is defined by sequence domain resource, time domain resource, and frequency resource. Configured parameters of RIM RS resource are applied to all sets of RIM RS resources across cells in gNodeBs. Instance RimRSGlobal=1 is created automatically when parent MO instance is created, unless created manually in same transaction. Precondition: Instance RimRSGlobal=1 can only be created in same transaction as parent MO instance and cannot be deleted unless parent MO instance is deleted.";
      key "rimRSGlobalId";
      leaf rimRSGlobalId {
        type leafref {
          path "../attributes/rimRSGlobalId";
        }
      }
      container attributes {
      uses RimRSGlobal-attributes;
      }
    }
  }

  augment "/emael:ManagedElement/gnbdu:GNBDUFunction" {
    list Rrc {
      description "Additional definitions from MOM:min/max-elements:1/1;systemCreated; Manageable RRC protocol characteristics. The RDN of this MO is Rrc=1.";
      key "rrcId";
      leaf rrcId {
        type leafref {
          path "../attributes/rrcId";
        }
      }
      container attributes {
      uses Rrc-attributes;
      }
    }
  }

  augment "/emael:ManagedElement/gnbdu:GNBDUFunction" {
    list SrPeriodicityPoolSet {
      description "Additional definitions from MOM:min/max-elements:0/8; Configuration of Scheduling Request periodicity pools 1-5 at NR cell representation in gNodeB-DU.";
      key "srPeriodicityPoolSetId";
      leaf srPeriodicityPoolSetId {
        type leafref {
          path "../attributes/srPeriodicityPoolSetId";
        }
      }
      container attributes {
      uses SrPeriodicityPoolSet-attributes;
      }
    }
  }

  augment "/emael:ManagedElement/gnbdu:GNBDUFunction" {
    list SssgSwitch {
      description "Additional definitions from MOM:min/max-elements:0/unbounded; Profile for Search Space Set Group (SSSG) switch. At least one SssgSwitchPwrOpt instance must be created in same transaction when a SssgSwitch instance is created. At least one SssgSwitchUeCfg instance must be created in same transaction when a SssgSwitch instance is created.";
      key "sssgSwitchId";
      leaf sssgSwitchId {
        type leafref {
          path "../attributes/sssgSwitchId";
        }
      }
      container attributes {
      uses SssgSwitch-attributes;
      }
    }
  }

  augment "/emael:ManagedElement/gnbdu:GNBDUFunction" {
    list TermPointToGNBCUCP {
      description "Additional definitions from MOM:min/max-elements:0/1; Models an F1-C link to a gNodeB-CU-CP.";
      key "termPointToGNBCUCPId";
      leaf termPointToGNBCUCPId {
        type leafref {
          path "../attributes/termPointToGNBCUCPId";
        }
      }
      container attributes {
      uses TermPointToGNBCUCP-attributes;
      }
    }
  }

  augment "/emael:ManagedElement/gnbdu:GNBDUFunction" {
    list TrafficDefinitions {
      description "Additional definitions from MOM:min/max-elements:0/1; Container class for traffic definitions. Instance TrafficDefinitions=1 is created automatically when parent MO instance is created, unless created manually in same transaction. The RDN of this MO must be TrafficDefinitions=1. Precondition: Instance TrafficDefinitions=1 can only be created in same transaction as parent MO instance and cannot be deleted unless parent MO instance is deleted.";
      key "trafficDefinitionsId";
      leaf trafficDefinitionsId {
        type leafref {
          path "../attributes/trafficDefinitionsId";
        }
      }
      container attributes {
      uses TrafficDefinitions-attributes;
      }
    }
  }

  augment "/emael:ManagedElement/gnbdu:GNBDUFunction" {
    list TrafficGroups {
      description "Additional definitions from MOM:min/max-elements:0/1; Container class for traffic groups definitions. Instance TrafficGroups=1 is created automatically when parent MO instance is created, unless created manually in same transaction. The RDN of this MO must be TrafficGroups=1. Precondition: Instance TrafficGroups=1 can only be created in same transaction as parent MO instance and cannot be deleted unless parent MO instance is deleted.";
      key "trafficGroupsId";
      status deprecated;
      leaf trafficGroupsId {
        type leafref {
          path "../attributes/trafficGroupsId";
        }
        status deprecated;
      }
      container attributes {
      uses TrafficGroups-attributes;
      }
    }
  }

  augment "/emael:ManagedElement/gnbdu:GNBDUFunction" {
    list UeCA {
      description "Additional definitions from MOM:min/max-elements:0/1; Container class for UE Carrier Aggregation profile classes. Instance UeCA=1 is created automatically when parent MO instance is created, unless created manually in same transaction. The RDN of this MO must be UeCA=1. Precondition: Instance UeCA=1 can only be created in same transaction as parent MO instance and cannot be deleted unless parent MO instance is deleted.";
      key "ueCAId";
      leaf ueCAId {
        type leafref {
          path "../attributes/ueCAId";
        }
      }
      container attributes {
      uses UeCA-attributes;
      }
    }
  }

  augment "/emael:ManagedElement/gnbdu:GNBDUFunction" {
    list UeCC {
      description "Additional definitions from MOM:min/max-elements:0/1; Container class for UE connection control attributes and profile classes. Instance UeCC=1 is created automatically when parent MO instance is created, unless created manually in same transaction. The RDN of this MO must be UeCC=1. Precondition: Instance UeCC=1 can only be created in same transaction as parent MO instance and cannot be deleted unless parent MO instance is deleted.";
      key "ueCCId";
      leaf ueCCId {
        type leafref {
          path "../attributes/ueCCId";
        }
      }
      container attributes {
      uses UeCC-attributes;
      }
    }
  }

  augment "/emael:ManagedElement/gnbdu:GNBDUFunction/gnbdu:UeCC/gnbdu:Harq" {
    list HarqUeCfg {
      description "Additional definitions from MOM:min/max-elements:0/8; HARQ profile used for current UE. Instance HarqUeCfg=Base is created automatically when parent MO instance is created, unless created manually in same transaction. UeBbProfileUeCfg::harqUeCfgRef is automatically set to HarqUeCfg=Base instance, unless manually set to refer to another MO instance. Precondition: Instance HarqUeCfg=Base can only be created in same transaction as parent MO instance and cannot be deleted unless parent MO instance is deleted. Other instances can be created and deleted at any time. Maximum 7 HarqUeCfg instances, with RDN different from Base, can be created under parent MO instance.";
      key "harqUeCfgId";
      leaf harqUeCfgId {
        type leafref {
          path "../attributes/harqUeCfgId";
        }
      }
      container attributes {
      uses HarqUeCfg-attributes;
      }
    }
  }

  augment "/emael:ManagedElement/gnbdu:GNBDUFunction/gnbdu:UeCC/gnbdu:LinkAdaptation" {
    list LinkAdaptationUeCfg {
      description "Additional definitions from MOM:min/max-elements:0/8; Link adaptation profile used for current UE. Instance LinkAdaptationUeCfg=Base is created automatically when parent MO instance is created, unless created manually in same transaction. UeBbProfileUeCfg::linkAdaptationUeCfgRef is automatically set to LinkAdaptationUeCfg=Base instance, unless manually set to refer to another MO instance. Precondition: Instance LinkAdaptationUeCfg=Base can only be created in same transaction as parent MO instance and cannot be deleted unless parent MO instance is deleted. Other instances can be created and deleted at any time. Maximum 7 LinkAdaptationUeCfg instances, with RDN different from Base, can be created under parent MO instance.";
      key "linkAdaptationUeCfgId";
      leaf linkAdaptationUeCfgId {
        type leafref {
          path "../attributes/linkAdaptationUeCfgId";
        }
      }
      container attributes {
      uses LinkAdaptationUeCfg-attributes;
      }
    }
  }

  augment "/emael:ManagedElement/gnbdu:GNBDUFunction/gnbdu:UeCC/gnbdu:LinkAdaptation/gnbdu:LinkAdaptationUeCfg" {
    list DlLinkAdaptation {
      description "Additional definitions from MOM:min/max-elements:0/1; DL link adaptation profile used for current UE. Instance DlLinkAdaptation=1 is created automatically when parent MO instance is created, unless created manually in same transaction. DlLinkAdaptation values only apply if linkAdaptationUeMode=CUSTOM in parent MO instance. The RDN of this MO must be DlLinkAdaptation=1. Precondition: Instance DlLinkAdaptation=1 can only be created in same transaction as parent MO instance and cannot be deleted unless parent MO instance is deleted.";
      key "dlLinkAdaptationId";
      leaf dlLinkAdaptationId {
        type leafref {
          path "../attributes/dlLinkAdaptationId";
        }
      }
      container attributes {
      uses DlLinkAdaptation-attributes;
      }
    }
  }

  augment "/emael:ManagedElement/gnbdu:GNBDUFunction/gnbdu:UeCC/gnbdu:LinkAdaptation/gnbdu:LinkAdaptationUeCfg" {
    list PdcchLinkAdaptation {
      description "Additional definitions from MOM:min/max-elements:0/1; PDCCH link adaptation profile used for current UE. Instance PdcchLinkAdaptation=1 is created automatically when parent MO instance is created, unless created manually in same transaction. PdcchLinkAdaptation values only apply if linkAdaptationUeMode=CUSTOM in parent MO instance. The RDN of this MO must be PdcchLinkAdaptation=1. Precondition: Instance PdcchLinkAdaptation=1 can only be created in same transaction as parent MO instance and cannot be deleted unless parent MO instance is deleted.";
      key "pdcchLinkAdaptationId";
      leaf pdcchLinkAdaptationId {
        type leafref {
          path "../attributes/pdcchLinkAdaptationId";
        }
      }
      container attributes {
      uses PdcchLinkAdaptation-attributes;
      }
    }
  }

  augment "/emael:ManagedElement/gnbdu:GNBDUFunction/gnbdu:UeCC/gnbdu:LinkAdaptation/gnbdu:LinkAdaptationUeCfg" {
    list UlLinkAdaptation {
      description "Additional definitions from MOM:min/max-elements:0/1; UL link adaptation profile used for current UE. Instance UlLinkAdaptation=1 is created automatically when parent MO instance is created, unless created manually in same transaction. UlLinkAdaptation values only apply if linkAdaptationUeMode=CUSTOM in parent MO instance. The RDN of this MO must be UlLinkAdaptation=1. Precondition: Instance UlLinkAdaptation=1 can only be created in same transaction as parent MO instance and cannot be deleted unless parent MO instance is deleted.";
      key "ulLinkAdaptationId";
      leaf ulLinkAdaptationId {
        type leafref {
          path "../attributes/ulLinkAdaptationId";
        }
      }
      container attributes {
      uses UlLinkAdaptation-attributes;
      }
    }
  }

  augment "/emael:ManagedElement/gnbdu:GNBDUFunction/gnbdu:UeCC/gnbdu:LogicalChannel" {
    list LogicalChannelUeCfg {
      description "Additional definitions from MOM:min/max-elements:0/4; Logical channel configuration for current DRB. Instance LogicalChannelUeCfg=Base is created automatically when parent MO instance is created, unless created manually in same transaction. Attributes prefUeGroupList, ueGroupList and ueConfGroupList must be empty in instance LogicalChannelUeCfg=Base but cannot all be empty in any other instance of LogicalChannelUeCfg under same parent LogicalChannel instance. A combination of an element of ueGroupList and an element of prefUeGroupList in LogicalChannelUeCfg instance must be unique under LogicalChannel instance. Precondition: Instance LogicalChannelUeCfg=Base can only be created in same transaction as parent MO instance and cannot be deleted unless parent MO instance is deleted. Other instances can be created and deleted at any time. Maximum 3 LogicalChannelUeCfg instances, with RDN different from Base, can be created under parent MO instance.";
      key "logicalChannelUeCfgId";
      leaf logicalChannelUeCfgId {
        type leafref {
          path "../attributes/logicalChannelUeCfgId";
        }
      }
      container attributes {
      uses LogicalChannelUeCfg-attributes;
      }
    }
  }

  augment "/emael:ManagedElement/gnbdu:GNBDUFunction/gnbdu:MassiveMimoSleep/gnbdu:MMimoSleepTimeGroup" {
    list MMimoSleepTimeWindow {
      description "Additional definitions from MOM:min/max-elements:0/96; Periods of time when a given event occurs.";
      key "mMimoSleepTimeWindowId";
      leaf mMimoSleepTimeWindowId {
        type leafref {
          path "../attributes/mMimoSleepTimeWindowId";
        }
      }
      container attributes {
      uses MMimoSleepTimeWindow-attributes;
      }
    }
  }

  augment "/emael:ManagedElement/gnbdu:GNBDUFunction/gnbdu:MassiveMimoSleep" {
    list MMimoSleepProfile {
      description "Additional definitions from MOM:min/max-elements:0/50; Massive MIMO Sleep profile for the specified period of time.";
      key "mMimoSleepProfileId";
      leaf mMimoSleepProfileId {
        type leafref {
          path "../attributes/mMimoSleepProfileId";
        }
      }
      container attributes {
      uses MMimoSleepProfile-attributes;
      }
    }
  }

  augment "/emael:ManagedElement/gnbdu:GNBDUFunction/gnbdu:MassiveMimoSleep" {
    list MMimoSleepTimeGroup {
      description "Additional definitions from MOM:min/max-elements:0/96; Container class for Massive MIMO Sleep time windows. Each MMimoSleepTimeWindow instance, with dayOfWeek, startTime and stopTime, defines a time window. Time windows under same MMimoSleepTimeGroup instance cannot overlap. Time windows overlap if: Value of dayOfWeek is the same (including dayOfWeek value ALL) and 1) startTime of given time window is greater than or equal to startTime of other time window, and lesser than or equal to stopTime of that other time window, or 2) stopTime of given time window is greater than or equal to startTime of other time window, and lesser than or equal to stopTime of that other time window.";
      key "mMimoSleepTimeGroupId";
      leaf mMimoSleepTimeGroupId {
        type leafref {
          path "../attributes/mMimoSleepTimeGroupId";
        }
      }
      container attributes {
      uses MMimoSleepTimeGroup-attributes;
      }
    }
  }

  augment "/emael:ManagedElement/gnbdu:GNBDUFunction/gnbdu:NRCellDU" {
    list AdditionalPLMNInfo {
      description "Additional definitions from MOM:min/max-elements:0/11; PLMN-related information that can be additionally served by NR cell. Precondition: If TheftDeterrence::thdStatus is LOCKED or LOCKED_PERMANENTLY, this instance can only be created if all PLMN IDs on pLMNIdList are part of Lock Token or Operator List.";
      key "additionalPLMNInfoId";
      leaf additionalPLMNInfoId {
        type leafref {
          path "../attributes/additionalPLMNInfoId";
        }
      }
      container attributes {
      uses AdditionalPLMNInfo-attributes;
      }
    }
  }

  augment "/emael:ManagedElement/gnbdu:GNBDUFunction/gnbdu:NRCellDU" {
    list CellPortionRd {
      description "Additional definitions from MOM:min/max-elements:0/192;systemCreated; Represents a Radio Dot and coverage area of a Radio Dot in a cell. Created when cell is unlocked and precondition is true. Deleted at next cell unlock if precondition no longer is true. Only applicable to Mid-Band cells. The RDNs of these MOs are CellPortionRd=1 to CellPortionRd=192. Length of RDN value is up to 3 characters. Instance can be created without a preceding user-initiated transaction. Precondition: License for Advanced RDS Location Support for Private 5G is present and feature is active. NRCellDU::rdsUeAdvancedPosEnabled is true.";
      key "cellPortionRdId";
      leaf cellPortionRdId {
        type leafref {
          path "../attributes/cellPortionRdId";
        }
      }
      container attributes {
      uses CellPortionRd-attributes;
      }
    }
  }

  augment "/emael:ManagedElement/gnbdu:GNBDUFunction/gnbdu:NRCellDU" {
    list DlOuterLoop {
      description "Additional definitions from MOM:min/max-elements:1/1;systemCreated; Configuration of downlink outer loops. Only applicable to Low-Band cells. The RDN of this MO is DlOuterLoop=1.";
      key "dlOuterLoopId";
      leaf dlOuterLoopId {
        type leafref {
          path "../attributes/dlOuterLoopId";
        }
      }
      container attributes {
      uses DlOuterLoop-attributes;
      }
    }
  }

  augment "/emael:ManagedElement/gnbdu:GNBDUFunction/gnbdu:NRSectorCarrier" {
    list AesMMimoSleep {
      description "Additional definitions from MOM:min/max-elements:0/1;systemCreated; Threshold information for NR Massive MIMO Sleep Mode feature updated by Automated Energy Saver. Created when all following conditions are fulfilled: - Aes::aesEnabled is true. - NRSectorCarrier::massiveMimoSleepEnabled is ENABLED or DETECTION. - License for Automated Energy Saver is present and feature is active. Deleted when Aes::aesEnabled is false or NRSectorCarrier::massiveMimoSleepEnabled is DISABLED. Only applicable to Mid-Band sector carriers. The RDN of this MO is AesMMimoSleep is 1. Length of RDN value is 1 character. Instance can be created without a preceding user-initiated transaction.";
      key "aesMMimoSleepId";
      leaf aesMMimoSleepId {
        type leafref {
          path "../attributes/aesMMimoSleepId";
        }
      }
      container attributes {
      uses AesMMimoSleep-attributes;
      }
    }
  }

  augment "/emael:ManagedElement/gnbdu:GNBDUFunction/gnbdu:NRSectorCarrier" {
    list CommonBeamforming {
      description "Additional definitions from MOM:min/max-elements:0/1; Configuration parameters related to common beamforming. Created automatically when administrativeState under parent MO instance is changed to UNLOCKED. Can also be created and deleted manually. When created automatically, the RDN of this MO is CommonBeamforming=1. Length of RDN value is 1 character for automatically created instance. Instance can be created without a preceding user-initiated transaction. Precondition: Can only be deleted when parent NRSectorCarrier::administrativeState is LOCKED.";
      key "commonBeamformingId";
      leaf commonBeamformingId {
        type leafref {
          path "../attributes/commonBeamformingId";
        }
      }
      container attributes {
      uses CommonBeamforming-attributes;
      }
    }
  }

  augment "/emael:ManagedElement/gnbdu:GNBDUFunction/gnbdu:NRSectorCarrier" {
    list NRPimCancellationConfig {
      description "Additional definitions from MOM:min/max-elements:0/72; Configuration data for PIM cancellation of NRSectorCarrier attribute. Only one NRPimCancellationConfig instance can refer to same PimCancellationFunction instance. Among NRPimCancellationConfig instances that have same createdBy value, only one NRPimCancellationConfig instance can have ulPimCancellationMode value that is not EXCLUDED. When createdBy is SYSTEM, operator is not allowed to modify attributes. Only takes effect for CPRI-based radio equipment that does not support AAS functions. Not applicable to High-Band sector carriers. High-Band only supports AAS functions. Automatic configuration is active when GNBDUFunction::pimCancAutoConfigEnabled is true. Then instance is - created automatically when PIM victim is identified. - deleted automatically when PIM victim is no longer valid. Automatically created instances are deleted when GNBDUFunction::pimCancAutoConfigEnabled is false. Can also be created and deleted manually. When created automatically, the RDNs of these MOs are NRPimCancellationConfig=auto1, auto2 and so on. RDN value matches RDN value of PimCancellationFunction instance that this NRPimCancellationConfig instance refers to. Length of RDN value is up to 6 characters for automatically created instance. Instance can be created without a preceding user-initiated transaction. When created manually, RDN value must not start with 'auto'.";
      key "nRPimCancellationConfigId";
      leaf nRPimCancellationConfigId {
        type leafref {
          path "../attributes/nRPimCancellationConfigId";
        }
      }
      container attributes {
      uses NRPimCancellationConfig-attributes;
      }
    }
  }

  augment "/emael:ManagedElement/gnbdu:GNBDUFunction/gnbdu:NRSectorCarrier" {
    list PowerBackoff {
      description "Additional definitions from MOM:min/max-elements:0/1; Configuration parameters for EMF Power Lock Mid-Band feature. The feature intends to reduce radio safety distance in massive MIMO products. Power backoff is sector carrier-wide, same in all directions. Only applicable to Mid-Band sector carriers. Precondition: Parent MO must be locked when this MO is created or deleted. Cannot be created if PowerBackoffDir instance exists.";
      key "powerBackoffId";
      leaf powerBackoffId {
        type leafref {
          path "../attributes/powerBackoffId";
        }
      }
      container attributes {
      uses PowerBackoff-attributes;
      }
    }
  }

  augment "/emael:ManagedElement/gnbdu:GNBDUFunction/gnbdu:NRSectorCarrier" {
    list PowerBackoffDir {
      description "Additional definitions from MOM:min/max-elements:0/1; Configuration parameters related to NR Directional Control for EMF Power Lock Mid-Band feature. Only applicable to Mid-Band sector carriers. Creating this MO on NRSectorCarrier instance with non-C2 sector carrier type or non-AAS capable radios will result in an alarm. Precondition: Parent MO must be locked when this MO is created or deleted. Cannot be created if PowerBackoff MO exists or radio is not TDD.";
      key "powerBackoffDirId";
      leaf powerBackoffDirId {
        type leafref {
          path "../attributes/powerBackoffDirId";
        }
      }
      container attributes {
      uses PowerBackoffDir-attributes;
      }
    }
  }

  augment "/emael:ManagedElement/gnbdu:GNBDUFunction/gnbdu:UeCC/gnbdu:OutOfCov" {
    list OutOfCovUeCfg {
      description "Additional definitions from MOM:min/max-elements:0/3; Out of coverage (OOC) profile used for current UE. Instance OutOfCovUeCfg=Base is created automatically when parent MO instance is created, unless created manually in same transaction as parent MO. UeBbProfileUeCfg::outOfCovUeCfgRef is automatically set to OutOfCovUeCfg=Base instance, unless manually set to refer to another MO instance. Precondition: Instance OutOfCovUeCfg=Base can only be created in same transaction as parent MO instance and cannot be deleted unless parent MO instance is deleted. Other instances can be created and deleted at any time. Maximum 2 OutOfCovUeCfg instances, with RDN different from Base, can be created under parent MO instance.";
      key "outOfCovUeCfgId";
      leaf outOfCovUeCfgId {
        type leafref {
          path "../attributes/outOfCovUeCfgId";
        }
      }
      container attributes {
      uses OutOfCovUeCfg-attributes;
      }
    }
  }

  augment "/emael:ManagedElement/gnbdu:GNBDUFunction/gnbdu:UeCC/gnbdu:PdcchReuseForPdsch" {
    list PdcchReuseForPdschUeCfg {
      description "Additional definitions from MOM:min/max-elements:0/8; Configuration of PDCCH and PDSCH Frequency Division Multiplexing profile for UE groups. Instance PdcchReuseForPdschUeCfg=Base is created automatically when parent MO instance is created, unless created manually in same transaction. Attributes prefUeGroupList, ueGroupList and ueConfGroupList must be empty in instance PdcchReuseForPdschUeCfg=Base but cannot all be empty in any other instance of PdcchReuseForPdschUeCfg under same parent PdcchReuseForPdsch instance. A combination of an element of ueGroupList and an element of prefUeGroupList in PdcchReuseForPdschUeCfg instance must be unique under PdcchReuseForPdsch instance. Precondition: Instance PdcchReuseForPdschUeCfg=Base can only be created in same transaction as parent MO instance and cannot be deleted unless parent MO instance is deleted. Other instances can be created and deleted at any time. Maximum 7 PdcchReuseForPdschUeCfg instances, with RDN different from Base, can be created under parent MO instance.";
      key "pdcchReuseForPdschUeCfgId";
      leaf pdcchReuseForPdschUeCfgId {
        type leafref {
          path "../attributes/pdcchReuseForPdschUeCfgId";
        }
      }
      container attributes {
      uses PdcchReuseForPdschUeCfg-attributes;
      }
    }
  }

  augment "/emael:ManagedElement/gnbdu:GNBDUFunction/gnbdu:UeCC/gnbdu:PowerControl" {
    list PowerControlUeCfg {
      description "Additional definitions from MOM:min/max-elements:0/8; Power control profile used for current UE. Instance PowerControlUeCfg=Base is created automatically when parent MO instance is created, unless created manually in same transaction. UeBbProfileUeCfg::powerControlUeCfgRef is automatically set to PowerControlUeCfg=Base instance, unless manually set to refer to another MO instance. Precondition: Instance PowerControlUeCfg=Base can only be created in same transaction as parent MO instance and cannot be deleted unless parent MO instance is deleted. Other instances can be created and deleted at any time. Maximum 7 PowerControlUeCfg instances, with RDN different from Base, can be created under parent MO instance.";
      key "powerControlUeCfgId";
      leaf powerControlUeCfgId {
        type leafref {
          path "../attributes/powerControlUeCfgId";
        }
      }
      container attributes {
      uses PowerControlUeCfg-attributes;
      }
    }
  }

  augment "/emael:ManagedElement/gnbdu:GNBDUFunction/gnbdu:UeCC/gnbdu:Prescheduling" {
    list PreschedulingUeCfg {
      description "Additional definitions from MOM:min/max-elements:0/8; Configuration of prescheduling mode for UE groups. Instance PreschedulingUeCfg=Base is created automatically when parent MO instance is created, unless created manually in same transaction. UeBbProfileUeCfg::preschedulingUeCfgRef is automatically set to PreschedulingUeCfg=Base instance, unless manually set to refer to another MO instance. Precondition: Instance PreschedulingUeCfg=Base can only be created in same transaction as parent MO instance and cannot be deleted unless parent MO instance is deleted. Other instances can be created and deleted at any time. Maximum 7 PreschedulingUeCfg instances, with RDN different from Base, can be created under parent MO instance.";
      key "preschedulingUeCfgId";
      leaf preschedulingUeCfgId {
        type leafref {
          path "../attributes/preschedulingUeCfgId";
        }
      }
      container attributes {
      uses PreschedulingUeCfg-attributes;
      }
    }
  }

  augment "/emael:ManagedElement/gnbdu:GNBDUFunction/gnbdu:UeCC/gnbdu:PuschRep" {
    list PuschRepUeCfg {
      description "Additional definitions from MOM:min/max-elements:0/4; Configuration of PUSCH repetition profile for UE groups. Instance PuschRepUeCfg=Base is created automatically when parent MO instance is created, unless created manually in same transaction. Attributes prefUeGroupList, ueGroupList and ueConfGroupList must be empty in instance PuschRepUeCfg=Base but cannot all be empty in any other instance of PuschRepUeCfg under same parent PuschRep instance. Precondition: Instance PuschRepUeCfg=Base can only be created in same transaction as parent MO instance and cannot be deleted unless parent MO instance is deleted. Other instances can be created and deleted at any time. Maximum 3 PuschRepUeCfg instances, with RDN different from Base, can be created under parent MO instance.";
      key "puschRepUeCfgId";
      leaf puschRepUeCfgId {
        type leafref {
          path "../attributes/puschRepUeCfgId";
        }
      }
      container attributes {
      uses PuschRepUeCfg-attributes;
      }
    }
  }

  augment "/emael:ManagedElement/gnbdu:GNBDUFunction/gnbdu:QosPriorityMapping" {
    list PriorityDomainMapping {
      description "Additional definitions from MOM:min/max-elements:0/64; Mapping from 5G QoS priority level to internal parameters that have absolute priority realization.";
      key "priorityDomainMappingId";
      leaf priorityDomainMappingId {
        type leafref {
          path "../attributes/priorityDomainMappingId";
        }
      }
      container attributes {
      uses PriorityDomainMapping-attributes;
      }
    }
  }

  augment "/emael:ManagedElement/gnbdu:GNBDUFunction/gnbdu:DUQos/gnbdu:QosPriorityShift" {
    list CellPriorityShift {
      description "Additional definitions from MOM:min/max-elements:0/8; Cell-level parameters for delay-based priority shift. If NRCellDU::cellPriorityShiftRef is non-empty, attributes from referenced MO instance are used. If NRCellDU::cellPriorityShiftRef is empty, attribute default values according to CellPriorityShift MO class definition are used.";
      key "cellPriorityShiftId";
      leaf cellPriorityShiftId {
        type leafref {
          path "../attributes/cellPriorityShiftId";
        }
      }
      container attributes {
      uses CellPriorityShift-attributes;
      }
    }
  }

  augment "/emael:ManagedElement/gnbdu:GNBDUFunction/gnbdu:UeCC/gnbdu:Rach" {
    list RachUeCfg {
      description "Additional definitions from MOM:min/max-elements:0/4; Rach configuration profile for UE groups. Instance RachUeCfg=Base is created automatically when parent MO instance is created, unless created manually in same transaction. Attributes prefUeGroupList, ueGroupList and ueConfGroupList must be empty in instance RachUeCfg=Base but cannot all be empty in any other instance of RachUeCfg under same parent Rach instance. Precondition: Instance RachUeCfg=Base can only be created in same transaction as parent MO instance and cannot be deleted unless parent MO instance is deleted. Other instances can be created and deleted at any time. Maximum 3 RachUeCfg instances, with RDN different from Base, can be created under parent MO instance.";
      key "rachUeCfgId";
      leaf rachUeCfgId {
        type leafref {
          path "../attributes/rachUeCfgId";
        }
      }
      container attributes {
      uses RachUeCfg-attributes;
      }
    }
  }

  augment "/emael:ManagedElement/gnbdu:GNBDUFunction/gnbdu:RadioBearerTable" {
    list DataRadioBearer {
      description "Additional definitions from MOM:min/max-elements:1/1;systemCreated; Data radio bearer configuration. The RDN of this MO is DataRadioBearer=1.";
      key "dataRadioBearerId";
      leaf dataRadioBearerId {
        type leafref {
          path "../attributes/dataRadioBearerId";
        }
      }
      container attributes {
      uses DataRadioBearer-attributes;
      }
    }
  }

  augment "/emael:ManagedElement/gnbdu:GNBDUFunction/gnbdu:RadioBearerTable" {
    list SignalingRadioBearer {
      description "Additional definitions from MOM:min/max-elements:1/1;systemCreated; Parameters related to Signaling Radio Bearer. The RDN of this MO is SignalingRadioBearer=1.";
      key "signalingRadioBearerId";
      leaf signalingRadioBearerId {
        type leafref {
          path "../attributes/signalingRadioBearerId";
        }
      }
      container attributes {
      uses SignalingRadioBearer-attributes;
      }
    }
  }

  augment "/emael:ManagedElement/gnbdu:GNBDUFunction/gnbdu:UeCC/gnbdu:RadioLinkControl" {
    list DrbRlc {
      description "Additional definitions from MOM:min/max-elements:0/12; Data radio bearer radio link control profile used for current UE. Instance DrbRlc=Default is created automatically when parent MO instance is created, unless created manually in same transaction. DU5qi::drbRlcRef is automatically set to DrbRlc=Default instance, unless manually set to refer to another MO instance. Precondition: Instance DrbRlc=Default can only be created in same transaction as parent MO instance and cannot be deleted unless parent MO instance is deleted. Other instances can be created and deleted at any time. Maximum 11 DrbRlc instances, with RDN different from Default, can be created under same parent MO instance.";
      key "drbRlcId";
      leaf drbRlcId {
        type leafref {
          path "../attributes/drbRlcId";
        }
      }
      container attributes {
      uses DrbRlc-attributes;
      }
    }
  }

  augment "/emael:ManagedElement/gnbdu:GNBDUFunction/gnbdu:UeCC/gnbdu:RadioLinkControl" {
    list UeAdaptiveRlc {
      description "Additional definitions from MOM:min/max-elements:0/1; Adaptive radio link control poll retransmission profile for current UE. Instance UeAdaptiveRlc=1 is created automatically when parent MO instance is created, unless created manually in same transaction. The RDN of this MO must be UeAdaptiveRlc=1. Precondition: Instance UeAdaptiveRlc=Default can only be created in same transaction as parent MO instance and cannot be deleted unless parent MO instance is deleted.";
      key "ueAdaptiveRlcId";
      leaf ueAdaptiveRlcId {
        type leafref {
          path "../attributes/ueAdaptiveRlcId";
        }
      }
      container attributes {
      uses UeAdaptiveRlc-attributes;
      }
    }
  }

  augment "/emael:ManagedElement/gnbdu:GNBDUFunction/gnbdu:UeCC/gnbdu:ResourceAllocTypeDl" {
    list ResourceAllocTypeDlUeCfg {
      description "Additional definitions from MOM:min/max-elements:0/3; Configuration of downlink resource allocation profile for UE groups. Instance ResourceAllocTypeDlUeCfg=Base is created automatically when parent MO instance is created, unless created manually in same transaction. Attributes prefUeGroupList, ueGroupList and ueConfGroupList must be empty in instance ResourceAllocTypeDlUeCfg=Base but cannot all be empty in other instance of ResourceAllocTypeDlUeCfg under same parent ResourceAllocTypeDl instance. Precondition: Instance ResourceAllocTypeDlUeCfg=Base can only be created in same transaction as parent MO instance and cannot be deleted unless parent MO instance is deleted. Other instances can be created and deleted at any time. Maximum 2 ResourceAllocTypeDlUeCfg instances, with RDN different from Base, can be created under parent MO instance.";
      key "resourceAllocTypeDlUeCfgId";
      leaf resourceAllocTypeDlUeCfgId {
        type leafref {
          path "../attributes/resourceAllocTypeDlUeCfgId";
        }
      }
      container attributes {
      uses ResourceAllocTypeDlUeCfg-attributes;
      }
    }
  }

  augment "/emael:ManagedElement/gnbdu:GNBDUFunction/gnbdu:ResourceAllocationPolicies" {
    list CellResourceMapping {
      description "Additional definitions from MOM:min/max-elements:0/8; Cell mappings of resource quotas to resource partitions. Not applicable to High-Band cells.";
      key "cellResourceMappingId";
      leaf cellResourceMappingId {
        type leafref {
          path "../attributes/cellResourceMappingId";
        }
      }
      container attributes {
      uses CellResourceMapping-attributes;
      }
    }
  }

  augment "/emael:ManagedElement/gnbdu:GNBDUFunction/gnbdu:ResourceAllocationPolicies" {
    list ResourceAllocationPolicy {
      description "Additional definitions from MOM:min/max-elements:0/32; Resource usage quotas for partitioned resources.";
      key "resourceAllocationPolicyId";
      leaf resourceAllocationPolicyId {
        type leafref {
          path "../attributes/resourceAllocationPolicyId";
        }
      }
      container attributes {
      uses ResourceAllocationPolicy-attributes;
      }
    }
  }

  augment "/emael:ManagedElement/gnbdu:GNBDUFunction/gnbdu:ResourceAllocationPolicies" {
    list ResourceShareLimit {
      description "Additional definitions from MOM:min/max-elements:0/16; Resource share limit for Automated RRP. If ResourceAllocationPolicy::resourceShareLimitRef or ServicePolicy::resourceShareLimitRef is non-empty, attributes from referenced MO instance are used. If ResourceAllocationPolicy::resourceShareLimitRef or ServicePolicy::resourceShareLimitRef is empty, none of following features is operable for partition: - Load-based Automated Radio Resource Partitioning. - Automated Radio Resource Partitioning.";
      key "resourceShareLimitId";
      leaf resourceShareLimitId {
        type leafref {
          path "../attributes/resourceShareLimitId";
        }
      }
      container attributes {
      uses ResourceShareLimit-attributes;
      }
    }
  }

  augment "/emael:ManagedElement/gnbdu:GNBDUFunction/gnbdu:ResourceAllocationPolicies/gnbdu:ResourceAllocationPolicy" {
    list ServicePolicy {
      description "Additional definitions from MOM:min/max-elements:0/2; Resource usage quotas of resources for services within a resource partition. Services defined with 5QI values.";
      key "servicePolicyId";
      leaf servicePolicyId {
        type leafref {
          path "../attributes/servicePolicyId";
        }
      }
      container attributes {
      uses ServicePolicy-attributes;
      }
    }
  }

  augment "/emael:ManagedElement/gnbdu:GNBDUFunction/gnbdu:ResourcePartitions/gnbdu:ResourcePartition" {
    list ResourcePartitionMember {
      description "Additional definitions from MOM:min/max-elements:0/36; Set of member information of resource partition.";
      key "resourcePartitionMemberId";
      leaf resourcePartitionMemberId {
        type leafref {
          path "../attributes/resourcePartitionMemberId";
        }
      }
      container attributes {
      uses ResourcePartitionMember-attributes;
      }
    }
  }

  augment "/emael:ManagedElement/gnbdu:GNBDUFunction/gnbdu:ResourcePartitions" {
    list ResourcePartition {
      description "Additional definitions from MOM:min/max-elements:0/36; Combination of attributes specifying in which resource partition a UE is included.";
      key "resourcePartitionId";
      leaf resourcePartitionId {
        type leafref {
          path "../attributes/resourcePartitionId";
        }
      }
      container attributes {
      uses ResourcePartition-attributes;
      }
    }
  }

  augment "/emael:ManagedElement/gnbdu:GNBDUFunction/gnbdu:UeCC/gnbdu:RimOffload" {
    list RimOffloadUeCfg {
      description "Additional definitions from MOM:min/max-elements:0/8; Remote interference triggered offload configurations. Instance RimOffloadUeCfg=Base is created automatically when parent MO instance is created, unless created manually in same transaction. UeBbProfileUeCfg::rimOffloadUeCfgRef is automatically set to RimOffloadUeCfg=Base instance, unless manually set to refer to another MO instance. Precondition: Instance RimOffloadUeCfg=Base can only be created in same transaction as parent MO instance and cannot be deleted unless parent MO instance is deleted. Other instances can be created and deleted at any time. Maximum 7 RimOffloadUeCfg instances, with RDN different from Base, can be created under parent MO instance.";
      key "rimOffloadUeCfgId";
      leaf rimOffloadUeCfgId {
        type leafref {
          path "../attributes/rimOffloadUeCfgId";
        }
      }
      container attributes {
      uses RimOffloadUeCfg-attributes;
      }
    }
  }

  augment "/emael:ManagedElement/gnbdu:GNBDUFunction/gnbdu:RimRSGlobal" {
    list RimRSSet {
      description "Additional definitions from MOM:min/max-elements:0/unbounded; Configuration data for Remote Interference Management Reference Signal (RIM RS).";
      key "rimRSSetId";
      leaf rimRSSetId {
        type leafref {
          path "../attributes/rimRSSetId";
        }
      }
      container attributes {
      uses RimRSSet-attributes;
      }
    }
  }

  augment "/emael:ManagedElement/gnbdu:GNBDUFunction/gnbdu:UeCC/gnbdu:SchedulingProfile" {
    list DlDelayBasedPriority {
      description "Additional definitions from MOM:min/max-elements:0/1; Parameters for delay-based priority shift for downlink.";
      key "dlDelayBasedPriorityId";
      leaf dlDelayBasedPriorityId {
        type leafref {
          path "../attributes/dlDelayBasedPriorityId";
        }
      }
      container attributes {
      uses DlDelayBasedPriority-attributes;
      }
    }
  }

  augment "/emael:ManagedElement/gnbdu:GNBDUFunction/gnbdu:UeCC/gnbdu:SchedulingProfile" {
    list DlLatencyBasedPriority {
      description "Additional definitions from MOM:min/max-elements:0/1; Latency-based priority shift for downlink.";
      key "dlLatencyBasedPriorityId";
      leaf dlLatencyBasedPriorityId {
        type leafref {
          path "../attributes/dlLatencyBasedPriorityId";
        }
      }
      container attributes {
      uses DlLatencyBasedPriority-attributes;
      }
    }
  }

  augment "/emael:ManagedElement/gnbdu:GNBDUFunction/gnbdu:UeCC/gnbdu:SchedulingProfile" {
    list DlRateBasedPriority {
      description "Additional definitions from MOM:min/max-elements:0/1; Parameters for rate-based priority shift for downlink. The RDN of this MO must be DlRateBasedPriority=1.";
      key "dlRateBasedPriorityId";
      leaf dlRateBasedPriorityId {
        type leafref {
          path "../attributes/dlRateBasedPriorityId";
        }
      }
      container attributes {
      uses DlRateBasedPriority-attributes;
      }
    }
  }

  augment "/emael:ManagedElement/gnbdu:GNBDUFunction/gnbdu:UeCC/gnbdu:SchedulingProfile" {
    list DlResourceBasedPriority {
      description "Additional definitions from MOM:min/max-elements:0/1; Parameters for resource-based priority for downlink.";
      key "dlResourceBasedPriorityId";
      leaf dlResourceBasedPriorityId {
        type leafref {
          path "../attributes/dlResourceBasedPriorityId";
        }
      }
      container attributes {
      uses DlResourceBasedPriority-attributes;
      }
    }
  }

  augment "/emael:ManagedElement/gnbdu:GNBDUFunction/gnbdu:UeCC/gnbdu:SchedulingProfile" {
    list UlDelayBasedPriority {
      description "Additional definitions from MOM:min/max-elements:0/1; Parameters for delay-based priority shift for uplink.";
      key "ulDelayBasedPriorityId";
      leaf ulDelayBasedPriorityId {
        type leafref {
          path "../attributes/ulDelayBasedPriorityId";
        }
      }
      container attributes {
      uses UlDelayBasedPriority-attributes;
      }
    }
  }

  augment "/emael:ManagedElement/gnbdu:GNBDUFunction/gnbdu:UeCC/gnbdu:SchedulingProfile" {
    list UlLatencyBasedPriority {
      description "Additional definitions from MOM:min/max-elements:0/1; Latency-based priority shift for uplink.";
      key "ulLatencyBasedPriorityId";
      leaf ulLatencyBasedPriorityId {
        type leafref {
          path "../attributes/ulLatencyBasedPriorityId";
        }
      }
      container attributes {
      uses UlLatencyBasedPriority-attributes;
      }
    }
  }

  augment "/emael:ManagedElement/gnbdu:GNBDUFunction/gnbdu:UeCC/gnbdu:SchedulingProfile" {
    list UlRateBasedPriority {
      description "Additional definitions from MOM:min/max-elements:0/1; Parameters for rate-based priority shift for uplink. The RDN of this MO must be UlRateBasedPriority=1.";
      key "ulRateBasedPriorityId";
      leaf ulRateBasedPriorityId {
        type leafref {
          path "../attributes/ulRateBasedPriorityId";
        }
      }
      container attributes {
      uses UlRateBasedPriority-attributes;
      }
    }
  }

  augment "/emael:ManagedElement/gnbdu:GNBDUFunction/gnbdu:UeCC/gnbdu:SchedulingProfile" {
    list UlResourceBasedPriority {
      description "Additional definitions from MOM:min/max-elements:0/1; Parameters for resource-based priority for uplink.";
      key "ulResourceBasedPriorityId";
      leaf ulResourceBasedPriorityId {
        type leafref {
          path "../attributes/ulResourceBasedPriorityId";
        }
      }
      container attributes {
      uses UlResourceBasedPriority-attributes;
      }
    }
  }

  augment "/emael:ManagedElement/gnbdu:GNBDUFunction/gnbdu:ContentionControl/gnbdu:SessionLimit" {
    list FlowLimit {
      description "Additional definitions from MOM:min/max-elements:0/12; Flow limit definition. Instance FlowLimit=Default is created automatically when parent MO instance is created, unless created manually in same transaction. Precondition: Instance FlowLimit=Default can only be created in same transaction as parent MO instance and cannot be deleted unless parent MO instance is deleted. Other instances can be created and deleted at any time. Maximum 11 FlowLimit instances, with RDN different from Default, can be created under parent MO instance.";
      key "flowLimitId";
      leaf flowLimitId {
        type leafref {
          path "../attributes/flowLimitId";
        }
      }
      container attributes {
      uses FlowLimit-attributes;
      }
    }
  }

  augment "/emael:ManagedElement/gnbdu:GNBDUFunction/gnbdu:UeCC/gnbdu:SoftAcAssist" {
    list SoftAcAssistUeCfg {
      description "Additional definitions from MOM:min/max-elements:0/2; Configuration of Soft Antenna Calibration UE. Instance SoftAcAssistUeCfg=Base is created automatically when parent MO instance is created, unless created manually in same transaction. Attributes prefUeGroupList, ueGroupList and ueConfGroupList must be empty in instance SoftAcAssistUeCfg=Base but cannot all be empty in any other instance of SoftAcAssistUeCfg under same parent SoftAcAssist instance. Precondition: Instance SoftAcAssistUeCfg=Base can only be created in same transaction as parent MO instance and cannot be deleted unless parent MO instance is deleted. Other instances can be created and deleted at any time. Maximum 1 SoftAcAssistUeCfg instance, with RDN different from Base, can be created under parent MO instance.";
      key "softAcAssistUeCfgId";
      leaf softAcAssistUeCfgId {
        type leafref {
          path "../attributes/softAcAssistUeCfgId";
        }
      }
      container attributes {
      uses SoftAcAssistUeCfg-attributes;
      }
    }
  }

  augment "/emael:ManagedElement/gnbdu:GNBDUFunction/gnbdu:UeCC/gnbdu:SrHandling" {
    list SrHandlingUeCfg {
      description "Additional definitions from MOM:min/max-elements:0/4; Scheduling Request configuration profile for UE groups. Instance SrHandlingUeCfg=Base is created automatically when parent MO instance is created, unless created manually in same transaction. Attributes prefUeGroupList, ueGroupList and ueConfGroupList must be empty in instance SrHandlingUeCfg=Base but cannot all be empty in any other instance of SrHandlingUeCfg under same parent SrHandling instance. Precondition: Instance SrHandlingUeCfg=Base can only be created in same transaction as parent MO instance and cannot be deleted unless parent MO instance is deleted. Other instances can be created and deleted at any time. Maximum 3 SrHandlingUeCfg instances, with RDN different from Base, can be created under parent MO instance.";
      key "srHandlingUeCfgId";
      leaf srHandlingUeCfgId {
        type leafref {
          path "../attributes/srHandlingUeCfgId";
        }
      }
      container attributes {
      uses SrHandlingUeCfg-attributes;
      }
    }
  }

  augment "/emael:ManagedElement/gnbdu:GNBDUFunction/gnbdu:UeCC/gnbdu:SrPeriodicity" {
    list SrPeriodicityCovAdaptUeCfg {
      description "Additional definitions from MOM:min/max-elements:0/8; Configuration of Scheduling Request periodicity profile for UE groups. Instance SrPeriodicityCovAdaptUeCfg=Base is created automatically when parent MO instance is created, unless created manually in same transaction. Attributes prefUeGroupList, ueGroupList and ueConfGroupList must be empty in instance SrPeriodicityCovAdaptUeCfg=Base but cannot all be empty in other instance of SrPeriodicityCovAdaptUeCfg under same parent SrPeriodicity instance. A combination of an element of ueGroupList and an element of prefUeGroupList in SrPeriodicityCovAdaptUeCfg instance must be unique under SrPeriodicity instance. Precondition: Instance SrPeriodicityCovAdaptUeCfg=Base can only be created in same transaction as parent MO instance and cannot be deleted unless parent MO instance is deleted. Other instances can be created and deleted at any time. Maximum 7 SrPeriodicityCovAdaptUeCfg instances, with RDN different from Base, can be created under parent MO instance.";
      key "srPeriodicityCovAdaptUeCfgId";
      leaf srPeriodicityCovAdaptUeCfgId {
        type leafref {
          path "../attributes/srPeriodicityCovAdaptUeCfgId";
        }
      }
      container attributes {
      uses SrPeriodicityCovAdaptUeCfg-attributes;
      }
    }
  }

  augment "/emael:ManagedElement/gnbdu:GNBDUFunction/gnbdu:UeCC/gnbdu:SrPeriodicity" {
    list SrPeriodicityUeCfg {
      description "Additional definitions from MOM:min/max-elements:0/8; Configuration of Scheduling Request periodicity profile for UE groups. Instance SrPeriodicityUeCfg=Base is created automatically when parent MO instance is created, unless created manually in same transaction. Attributes prefUeGroupList, ueGroupList and ueConfGroupList must be empty in instance SrPeriodicityUeCfg=Base but cannot all be empty in other instance of SrPeriodicityUeCfg under same parent SrPeriodicity instance. A combination of an element of ueGroupList and an element of prefUeGroupList in SrPeriodicityUeCfg instance must be unique under SrPeriodicity instance. Precondition: Instance SrPeriodicityUeCfg=Base can only be created in same transaction as parent MO instance and cannot be deleted unless parent MO instance is deleted. Other instances can be created and deleted at any time. Maximum 7 SrPeriodicityUeCfg instances, with RDN different from Base, can be created under parent MO instance.";
      key "srPeriodicityUeCfgId";
      leaf srPeriodicityUeCfgId {
        type leafref {
          path "../attributes/srPeriodicityUeCfgId";
        }
      }
      container attributes {
      uses SrPeriodicityUeCfg-attributes;
      }
    }
  }

  augment "/emael:ManagedElement/gnbdu:GNBDUFunction/gnbdu:UeCC/gnbdu:SrbPriority" {
    list SrbPriorityUeCfg {
      description "Additional definitions from MOM:min/max-elements:0/8; Configuration of SRB priority profile for UE groups. Instance SrbPriorityUeCfg=Base is created automatically when parent MO instance is created, unless created manually in same transaction. Attributes prefUeGroupList, ueGroupList and ueConfGroupList must be empty in instance SrbPriorityUeCfg=Base but cannot all be empty in other instance of SrbPriorityUeCfg under same parent SrbPriority instance. A combination of an element of ueGroupList and an element of prefUeGroupList in SrbPriorityUeCfg instance must be unique under SrbPriority instance. Only applicable to Low-Band and Mid-Band cells. Precondition: Instance SrbPriorityUeCfg=Base can only be created in same transaction as parent MO instance and cannot be deleted unless parent MO instance is deleted. Other instances can be created and deleted at any time. Maximum 7 SrbPriorityUeCfg instances, with RDN different from Base, can be created under parent MO instance.";
      key "srbPriorityUeCfgId";
      leaf srbPriorityUeCfgId {
        type leafref {
          path "../attributes/srbPriorityUeCfgId";
        }
      }
      container attributes {
      uses SrbPriorityUeCfg-attributes;
      }
    }
  }

  augment "/emael:ManagedElement/gnbdu:GNBDUFunction/gnbdu:SssgSwitch" {
    list SssgSwitchPwrOpt {
      description "Additional definitions from MOM:min/max-elements:1/8; Configuration of UE power saving through Search Space Set Group (SSSG) switch.";
      key "sssgSwitchPwrOptId";
      leaf sssgSwitchPwrOptId {
        type leafref {
          path "../attributes/sssgSwitchPwrOptId";
        }
      }
      container attributes {
      uses SssgSwitchPwrOpt-attributes;
      }
    }
  }

  augment "/emael:ManagedElement/gnbdu:GNBDUFunction/gnbdu:SssgSwitch" {
    list SssgSwitchUeCfg {
      description "Additional definitions from MOM:min/max-elements:1/8; Configuration profile for Search Space Set Group (SSSG) switch. Attributes prefUeGroupList, ueGroupList and ueConfGroupList can be empty in exactly one instance of SssgSwitchUeCfg under parent SssgSwitch instance. Only one SssgSwitchUeCfg instance can have sssgSwitchPwrOptRef empty under parent SssgSwitch instance.";
      key "sssgSwitchUeCfgId";
      leaf sssgSwitchUeCfgId {
        type leafref {
          path "../attributes/sssgSwitchUeCfgId";
        }
      }
      container attributes {
      uses SssgSwitchUeCfg-attributes;
      }
    }
  }

  augment "/emael:ManagedElement/gnbdu:GNBDUFunction/gnbdu:TrafficDefinitions/gnbdu:TrafficDefinition" {
    list TrafficSet {
      description "Additional definitions from MOM:min/max-elements:0/36; Traffic set definitions. Instances TrafficSet=Default and Default_ENDC are created automatically when parent MO instance is created, unless created manually in same transaction. Precondition: Instance TrafficSet=Default can only be created in same transaction as parent MO instance and cannot be deleted unless parent MO instance is deleted. Instance TrafficSet=Default_ENDC can only be deleted if it has no child TrafficSetMember=Default_ENDC instance or if parent MO instance is deleted. Other instances can be created and deleted at any time. Maximum 34 TrafficSet instances, with RDN different from Default and Default_ENDC, can be created under parent MO instance.";
      key "trafficSetId";
      leaf trafficSetId {
        type leafref {
          path "../attributes/trafficSetId";
        }
      }
      container attributes {
      uses TrafficSet-attributes;
      }
    }
  }

  augment "/emael:ManagedElement/gnbdu:GNBDUFunction/gnbdu:TrafficDefinitions" {
    list TrafficDefinition {
      description "Additional definitions from MOM:min/max-elements:0/16; Traffic definition. Instance TrafficDefinition=Default is created automatically when parent MO instance is created, unless created manually in same transaction. NRCellDU::trafficDefinitionRef is automatically set to TrafficDefinition=Default instance, unless manually set to refer to another MO instance. Precondition: Instance TrafficDefinition=Default can only be created in same transaction as parent MO instance and cannot be deleted unless parent MO instance is deleted. Other instances can be created and deleted at any time. Maximum 15 TrafficDefinition instances, with RDN different from Default, can be created under parent MO instance.";
      key "trafficDefinitionId";
      leaf trafficDefinitionId {
        type leafref {
          path "../attributes/trafficDefinitionId";
        }
      }
      container attributes {
      uses TrafficDefinition-attributes;
      }
    }
  }

  augment "/emael:ManagedElement/gnbdu:GNBDUFunction/gnbdu:TrafficGroups/gnbdu:TrafficGroup" {
    list TrafficGroupMember {
      description "Additional definitions from MOM:min/max-elements:0/36; Traffic group member definition. Instances TrafficGroupMember=Defaut_SA and Default_ENDC are created automatically when parent MO instance is created, unless created manually in same transaction. Instance TrafficGroupMember=Default_ENDC is created with trafficCategory=ENDC. Precondition: Instances TrafficGroupMember=Default_SA and Default_ENDC can only be created in same transaction as parent MO instance and cannot be deleted unless parent MO instance is deleted. Other instances can be created and deleted at any time. Maximum 34 TrafficGroupMember instances, with RDN different from Default_SA and Default_ENDC, can be created under parent MO instance. Instance TrafficGroupMember=Default_SA must have trafficCategory=SA. Instance TrafficGroupMember=Default_ENDC must have trafficCategory=ENDC.";
      key "trafficGroupMemberId";
      status deprecated;
      leaf trafficGroupMemberId {
        type leafref {
          path "../attributes/trafficGroupMemberId";
        }
        status deprecated;
      }
      container attributes {
      uses TrafficGroupMember-attributes;
      }
    }
  }

  augment "/emael:ManagedElement/gnbdu:GNBDUFunction/gnbdu:TrafficGroups" {
    list TrafficGroup {
      description "Additional definitions from MOM:min/max-elements:0/16; Traffic group definitions. Instance TrafficGroup=Default is created automatically when parent MO instance is created, unless created manually in same transaction. NRCellDU::trafficGroupRef is automatically set to TrafficGroup=Default instance, unless manually set to refer to another MO instance. Precondition: Instance TrafficGroup=Default can only be created in same transaction as parent MO instance and cannot be deleted unless parent MO instance is deleted. Other instances can be created and deleted at any time. Maximum 15 TrafficGroup instances, with RDN different from Default, can be created under parent MO instance.";
      key "trafficGroupId";
      status deprecated;
      leaf trafficGroupId {
        type leafref {
          path "../attributes/trafficGroupId";
        }
        status deprecated;
      }
      container attributes {
      uses TrafficGroup-attributes;
      }
    }
  }

  augment "/emael:ManagedElement/gnbdu:GNBDUFunction/gnbdu:TrafficDefinitions/gnbdu:TrafficDefinition/gnbdu:TrafficSet" {
    list TrafficSetMember {
      description "Additional definitions from MOM:min/max-elements:0/4; Definition of traffic set member. Instances TrafficSetMember=Default_SA and Default_ENDC are created automatically when parent MO instance is created, unless created manually in same transaction. Instance TrafficSetMember=Default_SA is created automatically when TrafficSet=Default instance is created, unless created manually in same transaction. Instance TrafficSetMember=Default_ENDC is created automatically when TrafficSet=Default_ENDC instance is created, unless created manually in same transaction. But only if Default_ENDC instance does not already exist as a sibling under TrafficDefinition instance. Attributes sNSSAIList, pLMNIdList and spidRfspList must be empty in instance TrafficSetMember=Default_SA or TrafficSetMember=Default_ENDC but cannot all be empty in any other instance of TrafficSetMember under same parent TrafficSet instance. Precondition: Instance TrafficSetMember=Default_SA can only be created in same transaction as parent MO instance and cannot be deleted unless parent MO instance is deleted. Instance TrafficSetMember=Default_ENDC can be deleted only if it is in same transaction created in another MO instance sibling to its parent or only if parent MO instance is deleted. Other instances can be created and deleted at any time. Maximum 3 TrafficSetMember instances, with RDN different from Default_ENDC, can be created under parent TrafficSet=Default_ENDC instance. Maximum 3 TrafficSetMember instances, with RDN different from Default_SA, can be created under parent TrafficSet=Default instance. Instance TrafficSetMember=Default_SA must have trafficCategory set to SA. Instance TrafficSetMember=Default_ENDC must have trafficCategory set to ENDC. Maximum one TrafficSetMember=Default_SA instance can be created under same TrafficDefinition instance. Maximum one TrafficSetMember=Default_ENDC instance can be created under same TrafficDefinition instance. Instance TrafficSetMember=Default_SA must be created under TrafficSet=Default instance. Instance TrafficSetMember=Default_ENDC must be created under TrafficSet=Default or Default_ENDC instance.";
      key "trafficSetMemberId";
      leaf trafficSetMemberId {
        type leafref {
          path "../attributes/trafficSetMemberId";
        }
      }
      container attributes {
      uses TrafficSetMember-attributes;
      }
    }
  }

  augment "/emael:ManagedElement/gnbdu:GNBDUFunction/gnbdu:UeCC/gnbdu:RadioLinkControl/gnbdu:UeAdaptiveRlc" {
    list UeAdaptiveRlcUeCfg {
      description "Additional definitions from MOM:min/max-elements:0/4; Configuration of adaptive radio link control poll retransmission profile for UE groups. Attributes prefUeGroupList, ueGroupList and ueConfGroupList must be empty in instance UeAdaptiveRlcUeCfg=Base but cannot all be empty in any other instance of UeAdaptiveRlcUeCfg under same parent UeAdaptiveRlc instance. A combination of an element of ueGroupList and an element of prefUeGroupList in UeAdaptiveRlcUeCfg instance must be unique under UeAdaptiveRlc instance. Instance UeAdaptiveRlcUeCfg=Base is created automatically when parent MO instance is created, unless created manually in same transaction. Precondition: Instance UeAdaptiveRlcUeCfg=Base can only be created in same transaction as parent MO instance and cannot be deleted unless parent MO instance is deleted. Other instances can be created and deleted at any time. Maximum 3 UeAdaptiveRlcUeCfg instances, with RDN different from Base, can be created under parent MO instance.";
      key "ueAdaptiveRlcUeCfgId";
      leaf ueAdaptiveRlcUeCfgId {
        type leafref {
          path "../attributes/ueAdaptiveRlcUeCfgId";
        }
      }
      container attributes {
      uses UeAdaptiveRlcUeCfg-attributes;
      }
    }
  }

  augment "/emael:ManagedElement/gnbdu:GNBDUFunction/gnbdu:UeCC/gnbdu:UeBb" {
    list UeBbProfile {
      description "Additional definitions from MOM:min/max-elements:0/4; UE Baseband profile used for current UE. Instance UeBbProfile=Default is created automatically when parent MO instance is created, unless created manually in same transaction. NRCellDU::ueBbProfileRef is automatically set to UeBbProfile=Default instance, unless manually set to refer to another MO instance. Precondition: Instance UeBbProfile=Default can only be created in same transaction as parent MO instance and cannot be deleted unless parent MO instance is deleted. Other instances can be created and deleted at any time. Maximum 3 UeBbProfile instances, with RDN different from Default, can be created under same parent MO instance. When creating an instance there must be possible to create a child UeBbProfileUeCfg=Base among total allowed instances of that MO class that is 64.";
      key "ueBbProfileId";
      leaf ueBbProfileId {
        type leafref {
          path "../attributes/ueBbProfileId";
        }
      }
      container attributes {
      uses UeBbProfile-attributes;
      }
    }
  }

  augment "/emael:ManagedElement/gnbdu:GNBDUFunction/gnbdu:UeCC/gnbdu:UeBb/gnbdu:UeBbProfile" {
    list UeBbProfileUeCfg {
      description "Additional definitions from MOM:min/max-elements:0/16; Configuration of UE Baseband profile for UE groups. Instance UeBbProfileUeCfg=Base is created automatically when parent MO instance is created, unless created manually in same transaction. Attributes prefUeGroupList, ueGroupList and ueConfGroupList must be empty in instance UeBbProfileUeCfg=Base but cannot all be empty in any other instance of UeBbProfileUeCfg under same parent UeBbProfile instance. A combination of an element of ueGroupList and an element of prefUeGroupList in UeBbProfileUeCfg instance must be unique under UeBbProfile instance. Value 0 is no longer allowed and is planned to be removed from the valid range of prefUeGroupList and ueGroupList. Precondition: Instance UeBbProfileUeCfg=Base can only be created in same transaction as parent MO instance and cannot be deleted unless parent MO instance is deleted. Other instances can be created and deleted at any time. Maximum 15 UeBbProfileUeCfg instances, with RDN different from Base, can be created under parent MO instance. To be able to create an instance, the total number of instances, including all auto created instances, must be less than the total allowed number of instances under a GNBDUFunction instance that is 64.";
      key "ueBbProfileUeCfgId";
      leaf ueBbProfileUeCfgId {
        type leafref {
          path "../attributes/ueBbProfileUeCfgId";
        }
      }
      container attributes {
      uses UeBbProfileUeCfg-attributes;
      }
    }
  }

  augment "/emael:ManagedElement/gnbdu:GNBDUFunction/gnbdu:UeCA" {
    list CaSCellHandling {
      description "Additional definitions from MOM:min/max-elements:0/4; SCell handling profile for UEs configured for NR carrier aggregation. Instance CaSCellHandling=Default is created automatically when parent MO instance is created, unless created manually in same transaction. If NRCellDU::caSCellHandlingRef is non-empty, attributes from referenced MO instance are used. If NRCellDU::caSCellHandlingRef is empty, attribute default values according to CaSCellHandling and CaSCellHandlingUeCfg MO class definitions are used. Precondition: Instance CaSCellHandling=Default can only be created in same transaction as parent MO instance and cannot be deleted unless parent MO instance is deleted. Other instances can be created and deleted at any time. Maximum 3 CaSCellHandling instances, with RDN different from Default, can be created under parent MO instance.";
      key "caSCellHandlingId";
      leaf caSCellHandlingId {
        type leafref {
          path "../attributes/caSCellHandlingId";
        }
      }
      container attributes {
      uses CaSCellHandling-attributes;
      }
    }
  }

  augment "/emael:ManagedElement/gnbdu:GNBDUFunction/gnbdu:UeCC" {
    list AqmCfg {
      description "Additional definitions from MOM:min/max-elements:0/32; Automatic queue management configuration selection profile. Instances AqmCfg=Default_conversational_media instance, Default_application_signaling, and Default_other are created automatically when parent MO instance is created, unless created manually in same transaction. DrbUpUeCfg::aqmCfgRef is automatically set to following MO instance: - AqmCfg=Default_conversational_media instance, if DrbUpUeCfg instance is created under parent DrbUp=Default_conversational_media instance. - AqmCfg=Default_application_signaling, if DrbUpUeCfg instance is created under parent DrbUp=Default_application_signaling instance. - AqmCfg=Default_other, if DrbUpUeCfg instance is created under other parent Drb instance. Unless manually set to refer to another MO instance. Only applicable when GNBDUFunction::altDepHServAdapUPProfEnabled is true. Precondition: Instances AqmCfg=Default_application_signaling, Default_conversational_media, and Default_other can only be created in same transaction as parent MO instance and cannot be deleted unless parent MO instance is deleted. Other instances can be created and deleted manually. Maximum 29 AqmCfg instances, with RDN different from Default_application_signaling, Default_conversational_media, or Default_other can be created under same parent MO instance.";
      key "aqmCfgId";
      leaf aqmCfgId {
        type leafref {
          path "../attributes/aqmCfgId";
        }
      }
      container attributes {
      uses AqmCfg-attributes;
      }
    }
  }

  augment "/emael:ManagedElement/gnbdu:GNBDUFunction/gnbdu:UeCC" {
    list Bsr {
      description "Additional definitions from MOM:min/max-elements:0/1; BSR profile used for current UE. Instance Bsr=1 is created automatically when parent MO instance is created, unless created manually in same transaction. The RDN of this MO must be Bsr=1. Precondition: Instance Bsr=1 can only be created in same transaction as parent MO instance and cannot be deleted unless parent MO instance is deleted.";
      key "bsrId";
      leaf bsrId {
        type leafref {
          path "../attributes/bsrId";
        }
      }
      container attributes {
      uses Bsr-attributes;
      }
    }
  }

  augment "/emael:ManagedElement/gnbdu:GNBDUFunction/gnbdu:UeCC" {
    list CgSwitch {
      description "Additional definitions from MOM:min/max-elements:0/49; Cell group switch profile. Instance CgSwitch=Default is created automatically when parent MO instance is created, unless created manually in same transaction. NRCellDU::endcCgSwitchRef and NRCellDU::nrdcCgSwitchRef are automatically set to CgSwitch=Default instance, unless manually set to refer to another MO instance. Precondition: Instance CgSwitch=Default can only be created in same transaction as parent MO instance and cannot be deleted unless parent MO instance is deleted. Other instances can be created and deleted at any time. Maximum 48 CgSwitch instances, with RDN different from Default, can be created under parent MO instance.";
      key "cgSwitchId";
      leaf cgSwitchId {
        type leafref {
          path "../attributes/cgSwitchId";
        }
      }
      container attributes {
      uses CgSwitch-attributes;
      }
    }
  }

  augment "/emael:ManagedElement/gnbdu:GNBDUFunction/gnbdu:UeCC" {
    list CgSwitchCfg {
      description "Additional definitions from MOM:min/max-elements:0/49; Cell group switch configuration. Instance CgSwitchCfg=Default is created automatically when parent MO instance is created, unless created manually in same transaction. CgSwitchUeCfg::cgSwitchCfgRef is automatically set to CgSwitchCfg=Default instance, unless manually set to refer to another MO instance. Precondition: Instance CgSwitchCfg=Default can only be created in same transaction as parent MO instance and cannot be deleted unless parent MO instance is deleted. Other instances can be created and deleted at any time. Maximum 48 CgSwitchCfg instances, with RDN different from Default, can be created under parent MO instance.";
      key "cgSwitchCfgId";
      leaf cgSwitchCfgId {
        type leafref {
          path "../attributes/cgSwitchCfgId";
        }
      }
      container attributes {
      uses CgSwitchCfg-attributes;
      }
    }
  }

  augment "/emael:ManagedElement/gnbdu:GNBDUFunction/gnbdu:UeCC" {
    list ConfiguredGrant {
      description "Additional definitions from MOM:min/max-elements:0/1; Configured grant profile used for current UE. Instance ConfiguredGrant=1 is created automatically when parent MO instance is created, unless created manually in same transaction. The RDN of this MO must be ConfiguredGrant=1. Precondition: Instance ConfiguredGrant=1 can only be created in same transaction as parent MO instance and cannot be deleted unless parent MO instance is deleted.";
      key "configuredGrantId";
      leaf configuredGrantId {
        type leafref {
          path "../attributes/configuredGrantId";
        }
      }
      container attributes {
      uses ConfiguredGrant-attributes;
      }
    }
  }

  augment "/emael:ManagedElement/gnbdu:GNBDUFunction/gnbdu:UeCC" {
    list CsiProfile {
      description "Additional definitions from MOM:min/max-elements:0/1; Channel State Information profile used for current UE. Instance CsiProfile=1 is created automatically when parent MO instance is created, unless created manually in same transaction. The RDN of this MO must be CsiProfile=1. Precondition: Instance CsiProfile=1 can only be created in same transaction as parent MO instance and cannot be deleted unless parent MO instance is deleted.";
      key "csiProfileId";
      leaf csiProfileId {
        type leafref {
          path "../attributes/csiProfileId";
        }
      }
      container attributes {
      uses CsiProfile-attributes;
      }
    }
  }

  augment "/emael:ManagedElement/gnbdu:GNBDUFunction/gnbdu:UeCC" {
    list DlBeamOptProfile {
      description "Additional definitions from MOM:min/max-elements:0/1; Downlink Beamforming optimization profile used for current UE. Instance DlBeamOptProfile=1 is created automatically when parent MO instance is created, unless created manually in same transaction. The RDN of this MO must be DlBeamOptProfile=1. Precondition: Instance DlBeamOptProfile=1 can only be created in same transaction as parent MO instance and cannot be deleted unless parent MO instance is deleted.";
      key "dlBeamOptProfileId";
      leaf dlBeamOptProfileId {
        type leafref {
          path "../attributes/dlBeamOptProfileId";
        }
      }
      container attributes {
      uses DlBeamOptProfile-attributes;
      }
    }
  }

  augment "/emael:ManagedElement/gnbdu:GNBDUFunction/gnbdu:UeCC" {
    list DlMimo {
      description "Additional definitions from MOM:min/max-elements:0/1; Container class for MIMO configuration profile used for current UE. Instance DlMimo=1 is created automatically when parent MO instance is created, unless created manually in same transaction. The RDN of this MO must be DlMimo=1. Precondition: Instance DlMimo=1 can only be created in same transaction as parent MO instance and cannot be deleted unless parent MO instance is deleted.";
      key "dlMimoId";
      leaf dlMimoId {
        type leafref {
          path "../attributes/dlMimoId";
        }
      }
      container attributes {
      uses DlMimo-attributes;
      }
    }
  }

  augment "/emael:ManagedElement/gnbdu:GNBDUFunction/gnbdu:UeCC" {
    list DrbUp {
      description "Additional definitions from MOM:min/max-elements:0/32; Data radio bearer user plane profile. Instances DrbUp=Default_application_signaling, Default_conversational_media, and Default_other are created automatically when parent MO instance is created, unless created manually in same transaction. DU5qi::drbUpRef is automatically set to following MO instance: - DrbUp=Default_application_signaling instance for DU5qi instances for which profile5qi is 5 or 69. - DrbUp=Default_conversational_media instance for DU5qi instances for which profile5qi is 1, 65, or 66. - DrbUp=Default_other instance for all other DU5qi instances. Unless manually set to refer to another MO instance. DrbUp=Default_application_signaling, Default_conversational_media, and Default_other instances are used for DRBs when DU5qi instance with matching profile5qi does not exist. Only applicable when GNBDUFunction::altDepHServAdapUPProfEnabled is true. Precondition: Instances DrbUp=Default_application_signaling, Default_conversational_media, and Default_other can only be created in same transaction as parent MO instance and cannot be deleted unless parent MO instance is deleted. Other instances can be created and deleted at any time. Maximum 29 DrbUp instances, with RDN different from Default_application_signaling, Default_conversational_media, and Default_other, can be created under parent MO instance.";
      key "drbUpId";
      leaf drbUpId {
        type leafref {
          path "../attributes/drbUpId";
        }
      }
      container attributes {
      uses DrbUp-attributes;
      }
    }
  }

  augment "/emael:ManagedElement/gnbdu:GNBDUFunction/gnbdu:UeCC" {
    list DrxProfile {
      description "Additional definitions from MOM:min/max-elements:0/4; DRX profile used for current UE. Instance DrxProfile=Default is created automatically when parent MO instance is created, unless created manually in same transaction. If NRCellDU::drxProfileRef is non-empty, attributes from referenced MO instance are used. If NRCellDU::drxProfileRef is empty, attribute default values according to DrxProfile and DrxProfileUeCfg MO class definitions are used. Precondition: Instance DrxProfile=Default can only be created in same transaction as parent MO instance and cannot be deleted unless parent MO instance is deleted. Other instances can be created and deleted at any time. Maximum 3 DrxProfile instances, with RDN different from Default, can be created under parent MO instance.";
      key "drxProfileId";
      leaf drxProfileId {
        type leafref {
          path "../attributes/drxProfileId";
        }
      }
      container attributes {
      uses DrxProfile-attributes;
      }
    }
  }

  augment "/emael:ManagedElement/gnbdu:GNBDUFunction/gnbdu:UeCC" {
    list Harq {
      description "Additional definitions from MOM:min/max-elements:0/1; HARQ profile used for current UE. Instance Harq=1 is created automatically when parent MO instance is created, unless created manually in same transaction. The RDN of this MO must be Harq=1. Precondition: Instance Harq=1 can only be created in same transaction as parent MO instance and cannot be deleted unless parent MO instance is deleted.";
      key "harqId";
      leaf harqId {
        type leafref {
          path "../attributes/harqId";
        }
      }
      container attributes {
      uses Harq-attributes;
      }
    }
  }

  augment "/emael:ManagedElement/gnbdu:GNBDUFunction/gnbdu:UeCC" {
    list L4sCfg {
      description "Additional definitions from MOM:min/max-elements:0/8; Container for L4S configuration attributes. Only applicable if license for UL RAN Assisted Rate Adaptation is present and feature is active. If DUModified5qiUeCfg::l4sCfgRef is non-empty, attributes from referenced MO instance are used. If DUModified5qiUeCfg::l4sCfgRef is empty, l4sCfgRef in DU5qi instance is used. If DU5qi::l4sCfgRef is non-empty, attributes from referenced MO instance are used. If DU5qi::l4sCfgRef is empty, attribute default values according to MO class definition are used.";
      key "l4sCfgId";
      leaf l4sCfgId {
        type leafref {
          path "../attributes/l4sCfgId";
        }
      }
      container attributes {
      uses L4sCfg-attributes;
      }
    }
  }

  augment "/emael:ManagedElement/gnbdu:GNBDUFunction/gnbdu:UeCC" {
    list LinkAdaptation {
      description "Additional definitions from MOM:min/max-elements:0/1; Link adaptation profile used for current UE. Instance LinkAdaptation=1 is created automatically when parent MO instance is created, unless created manually in same transaction. The RDN of this MO must be LinkAdaptation=1. Precondition: Instance LinkAdaptation=1 can only be created in same transaction as parent MO instance and cannot be deleted unless parent MO instance is deleted.";
      key "linkAdaptationId";
      leaf linkAdaptationId {
        type leafref {
          path "../attributes/linkAdaptationId";
        }
      }
      container attributes {
      uses LinkAdaptation-attributes;
      }
    }
  }

  augment "/emael:ManagedElement/gnbdu:GNBDUFunction/gnbdu:UeCC" {
    list LogicalChannel {
      description "Additional definitions from MOM:min/max-elements:0/8; Container class for logical channel configurations. Instances LogicalChannel=Default and IMS_Voice are created automatically when parent MO instance is created, unless created manually in same transaction. DU5qi::logicalChannelRef and DUModified5qiUeCfg::logicalChannelRef are automatically set to following MO instance: - LogicalChannel=IMS_Voice instance for DU5qi instances which profile5qi is 1 or 5. - LogicalChannel=IMS_Voice instance for DUModified5qiUeCfg instances which modifiedProfile5qi is 1 or 5. - LogicalChannel=Default instance for all other DU5qi and DUModified5qiUeCfg instances. Unless manually set to refer to another MO instance. Precondition: Instances LogicalChannel=Default and IMS_Voice can only be created in same transaction as parent MO instance and cannot be deleted unless parent MO instance is deleted. Other instances can be created and deleted at any time. Maximum 6 LogicalChannel instances, with RDN different from Default and IMS_Voice, can be created under parent MO instance.";
      key "logicalChannelId";
      leaf logicalChannelId {
        type leafref {
          path "../attributes/logicalChannelId";
        }
      }
      container attributes {
      uses LogicalChannel-attributes;
      }
    }
  }

  augment "/emael:ManagedElement/gnbdu:GNBDUFunction/gnbdu:UeCC" {
    list OutOfCov {
      description "Additional definitions from MOM:min/max-elements:0/1; Out of coverage (OOC) profile used for current UE. Instance OutOfCov=1 is created automatically when parent MO instance is created, unless created manually in same transaction as parent MO. The RDN of this MO must be OutOfCov=1. Precondition: Instance OutOfCov=1 can only be created in same transaction as parent MO instance and cannot be deleted unless parent MO instance is deleted.";
      key "outOfCovId";
      leaf outOfCovId {
        type leafref {
          path "../attributes/outOfCovId";
        }
      }
      container attributes {
      uses OutOfCov-attributes;
      }
    }
  }

  augment "/emael:ManagedElement/gnbdu:GNBDUFunction/gnbdu:UeCC" {
    list PdcchReuseForPdsch {
      description "Additional definitions from MOM:min/max-elements:0/2; PDCCH and PDSCH Frequency Division Multiplexing profile used for current UE. Instance PdcchReuseForPdsch=Default is created automatically when parent MO instance is created, unless created manually in same transaction. NRCellDU::pdcchReuseForPdschRef is automatically set to PdcchReuseForPdsch=Default instance, unless manually set to refer to another MO instance. Only applicable to Low-Band and Mid-Band cells. Precondition: Instance PdcchReuseForPdsch=Default can only be created in same transaction as parent MO instance and cannot be deleted unless parent MO instance is deleted. Other instances can be created and deleted at any time. Maximum 1 PdcchReuseForPdsch instance, with RDN different from Default, can be created under parent MO instance.";
      key "pdcchReuseForPdschId";
      leaf pdcchReuseForPdschId {
        type leafref {
          path "../attributes/pdcchReuseForPdschId";
        }
      }
      container attributes {
      uses PdcchReuseForPdsch-attributes;
      }
    }
  }

  augment "/emael:ManagedElement/gnbdu:GNBDUFunction/gnbdu:UeCC" {
    list PowerControl {
      description "Additional definitions from MOM:min/max-elements:0/1; Power control profile used for current UE. Instance PowerControl=1 is created automatically when parent MO instance is created, unless created manually in same transaction. The RDN of this MO must be PowerControl=1. Precondition: Instance PowerControl=1 can only be created in same transaction as parent MO instance and cannot be deleted unless parent MO instance is deleted.";
      key "powerControlId";
      leaf powerControlId {
        type leafref {
          path "../attributes/powerControlId";
        }
      }
      container attributes {
      uses PowerControl-attributes;
      }
    }
  }

  augment "/emael:ManagedElement/gnbdu:GNBDUFunction/gnbdu:UeCC" {
    list Prescheduling {
      description "Additional definitions from MOM:min/max-elements:0/1; Prescheduling mode used for current UE. Instance Prescheduling=1 is created automatically when parent MO instance is created, unless created manually in same transaction. The RDN of this MO must be Prescheduling=1. Precondition: Instance Prescheduling=1 can only be created in same transaction as parent MO instance and cannot be deleted unless parent MO instance is deleted.";
      key "preschedulingId";
      leaf preschedulingId {
        type leafref {
          path "../attributes/preschedulingId";
        }
      }
      container attributes {
      uses Prescheduling-attributes;
      }
    }
  }

  augment "/emael:ManagedElement/gnbdu:GNBDUFunction/gnbdu:UeCC" {
    list PuschRep {
      description "Additional definitions from MOM:min/max-elements:0/4; PUSCH repetition profile used in each 5QI. Instance PuschRep=Default is created automatically when parent MO instance is created, unless created manually in same transaction. DU5qi::puschRepRef is automatically set to PuschRep=Default instance, unless manually set to refer to another MO instance. Precondition: Instance PuschRep=Default can only be created in same transaction as parent MO instance and cannot be deleted unless parent MO instance is deleted. Other instances can be created and deleted at any time. Maximum 3 PuschRep instances, with RDN different from Default, can be created under parent MO instance.";
      key "puschRepId";
      leaf puschRepId {
        type leafref {
          path "../attributes/puschRepId";
        }
      }
      container attributes {
      uses PuschRep-attributes;
      }
    }
  }

  augment "/emael:ManagedElement/gnbdu:GNBDUFunction/gnbdu:UeCC" {
    list Rach {
      description "Additional definitions from MOM:min/max-elements:0/4; Rach profile used for current UE. Instance Rach=Default is created automatically when parent MO instance is created, unless created manually in same transaction. NRCellDU::rachRef is automatically set to Rach=Default instance, unless manually set to refer to another MO instance. Precondition: Instance Rach=Default can only be created in same transaction as parent MO instance and cannot be deleted unless parent MO instance is deleted. Other instances can be created and deleted at any time. Maximum 3 Rach instances, with RDN different from Default, can be created under parent MO instance.";
      key "rachId";
      leaf rachId {
        type leafref {
          path "../attributes/rachId";
        }
      }
      container attributes {
      uses Rach-attributes;
      }
    }
  }

  augment "/emael:ManagedElement/gnbdu:GNBDUFunction/gnbdu:UeCC" {
    list RadioLinkControl {
      description "Additional definitions from MOM:min/max-elements:0/1; Container class for data radio bearer radio link control attributes and profile classes. Instance RadioLinkControl=1 is created automatically when parent MO instance is created, unless created manually in same transaction. The RDN of this MO must be RadioLinkControl=1. Precondition: Instance RadioLinkControl=1 can only be created in same transaction as parent MO instance and cannot be deleted unless parent MO instance is deleted.";
      key "radioLinkControlId";
      leaf radioLinkControlId {
        type leafref {
          path "../attributes/radioLinkControlId";
        }
      }
      container attributes {
      uses RadioLinkControl-attributes;
      }
    }
  }

  augment "/emael:ManagedElement/gnbdu:GNBDUFunction/gnbdu:UeCC" {
    list ResourceAllocTypeDl {
      description "Additional definitions from MOM:min/max-elements:0/3; Downlink resource allocation profile. Instance ResourceAllocTypeDl=Default is created automatically when parent MO instance is created, unless created manually in same transaction. NRCellDU::resourceAllocTypeDlRef is automatically set to ResourceAllocTypeDl=Default instance, unless manually set to refer to another MO instance. Precondition: Instance ResourceAllocTypeDl=Default can only be created in same transaction as parent MO instance and cannot be deleted unless parent MO instance is deleted. Other instances can be created and deleted at any time. Maximum 2 ResourceAllocTypeDl instances, with RDN different from Default, can be created under parent MO instance.";
      key "resourceAllocTypeDlId";
      leaf resourceAllocTypeDlId {
        type leafref {
          path "../attributes/resourceAllocTypeDlId";
        }
      }
      container attributes {
      uses ResourceAllocTypeDl-attributes;
      }
    }
  }

  augment "/emael:ManagedElement/gnbdu:GNBDUFunction/gnbdu:UeCC" {
    list RimOffload {
      description "Additional definitions from MOM:min/max-elements:0/1; Container class for remote interference triggered offload configurations. Instance RimOffload=1 is created automatically when parent MO instance is created, unless created manually in same transaction. The RDN of this MO must be RimOffload=1.";
      key "rimOffloadId";
      leaf rimOffloadId {
        type leafref {
          path "../attributes/rimOffloadId";
        }
      }
      container attributes {
      uses RimOffload-attributes;
      }
    }
  }

  augment "/emael:ManagedElement/gnbdu:GNBDUFunction/gnbdu:UeCC" {
    list SchedulingProfile {
      description "Additional definitions from MOM:min/max-elements:0/32; Scheduling profile used for current connection. If DUModified5qiUeCfg::schedulingProfileRef is non-empty, attributes from referenced MO instance are used. If DUModified5qiUeCfg::schedulingProfileRef is empty, schedulingProfileRef in DU5qi instance is used. If DU5qi::schedulingProfileRef is non-empty, attributes from referenced MO instance are used. If DU5qi::schedulingProfileRef is empty, attribute default values according to MO class definition are used.";
      key "schedulingProfileId";
      leaf schedulingProfileId {
        type leafref {
          path "../attributes/schedulingProfileId";
        }
      }
      container attributes {
      uses SchedulingProfile-attributes;
      }
    }
  }

  augment "/emael:ManagedElement/gnbdu:GNBDUFunction/gnbdu:UeCC" {
    list SoftAcAssist {
      description "Additional definitions from MOM:min/max-elements:0/1; Container class for Soft Antenna Calibration UE Assisted attributes and configuration classes. Instance SoftAcAssist=1 is created automatically when parent MO instance is created, unless created manually in same transaction. The RDN of this MO must be SoftAcAssist=1. Precondition: Instance SoftAcAssist=1 can only be created in same transaction as parent MO instance and cannot be deleted unless parent MO instance is deleted.";
      key "softAcAssistId";
      leaf softAcAssistId {
        type leafref {
          path "../attributes/softAcAssistId";
        }
      }
      container attributes {
      uses SoftAcAssist-attributes;
      }
    }
  }

  augment "/emael:ManagedElement/gnbdu:GNBDUFunction/gnbdu:UeCC" {
    list SrbPriority {
      description "Additional definitions from MOM:min/max-elements:0/4; SRB priority profile used for current UE. Instance SrbPriority=Default is created automatically when parent MO instance is created, unless created manually in same transaction. NRCellDU::srbPriorityRef is automatically set to SrbPriority=Default instance, unless manually set to refer to another MO instance. Only applicable to Low-Band and Mid-Band cells. Precondition: Instance SrbPriority=Default can only be created in same transaction as parent MO instance and cannot be deleted unless parent MO instance is deleted. Other instances can be created and deleted at any time. Maximum 3 SrbPriority instances, with RDN different from Default, can be created under parent MO instance.";
      key "srbPriorityId";
      leaf srbPriorityId {
        type leafref {
          path "../attributes/srbPriorityId";
        }
      }
      container attributes {
      uses SrbPriority-attributes;
      }
    }
  }

  augment "/emael:ManagedElement/gnbdu:GNBDUFunction/gnbdu:UeCC" {
    list SrHandling {
      description "Additional definitions from MOM:min/max-elements:0/8; Scheduling Request profile used for current connection. Instance SrHandling=Default is created automatically when parent MO instance is created, unless created manually in same transaction. DU5qi::srHandlingRef is automatically set to SrHandling=Default instance, unless manually set to refer to another MO instance. DUModified5qiUeCfg::srHandlingRef is automatically set to SrHandling=Default instance, unless manually set to refer to another MO instance. Precondition: Instance SrHandling=Default can only be created in same transaction as parent MO instance and cannot be deleted unless parent MO instance is deleted. Other instances can be created and deleted at any time.";
      key "srHandlingId";
      leaf srHandlingId {
        type leafref {
          path "../attributes/srHandlingId";
        }
      }
      container attributes {
      uses SrHandling-attributes;
      }
    }
  }

  augment "/emael:ManagedElement/gnbdu:GNBDUFunction/gnbdu:UeCC" {
    list SrPeriodicity {
      description "Additional definitions from MOM:min/max-elements:0/4; Scheduling Request periodicity profile used for current UE. Instance SrPeriodicity=Default is created automatically when parent MO instance is created, unless created manually in same transaction. NRCellDU::srPeriodicityRef is automatically set to SrPeriodicity=Default instance, unless manually set to refer to another MO instance. Precondition: Instance SrPeriodicity=Default can only be created in same transaction as parent MO instance and cannot be deleted unless parent MO instance is deleted. Other instances can be created and deleted at any time. Maximum 3 SrPeriodicity instances, with RDN different from Default, can be created under parent MO instance.";
      key "srPeriodicityId";
      leaf srPeriodicityId {
        type leafref {
          path "../attributes/srPeriodicityId";
        }
      }
      container attributes {
      uses SrPeriodicity-attributes;
      }
    }
  }

  augment "/emael:ManagedElement/gnbdu:GNBDUFunction/gnbdu:UeCC" {
    list UeBb {
      description "Additional definitions from MOM:min/max-elements:0/1; Container class for UE Baseband attributes and profile classes. Instance UeBb=1 is created automatically when parent MO instance is created, unless created manually in same transaction. The RDN of this MO must be UeBb=1. Precondition: Instance UeBb=1 can only be created in same transaction as parent MO instance and cannot be deleted unless parent MO instance is deleted.";
      key "ueBbId";
      leaf ueBbId {
        type leafref {
          path "../attributes/ueBbId";
        }
      }
      container attributes {
      uses UeBb-attributes;
      }
    }
  }

  augment "/emael:ManagedElement/gnbdu:GNBDUFunction/gnbdu:UeCC" {
    list UlCgSwitch {
      description "Additional definitions from MOM:min/max-elements:0/49; Cell group switch profile for uplink. Instance UlCgSwitch=Default is created automatically when parent MO instance is created, unless created manually in same transaction. NRCellDU::endcUlCgSwitchRef and NRCellDU::nrdcUlCgSwitchRef are automatically set to UlCgSwitch=Default instance, unless manually set to refer to another MO instance. Precondition: Instance UlCgSwitch=Default can only be created in same transaction as parent MO instance and cannot be deleted unless parent MO instance is deleted. Other instances can be created and deleted at any time. Maximum 48 CgSwitch instances, with RDN different from Default, can be created under parent MO instance.";
      key "ulCgSwitchId";
      leaf ulCgSwitchId {
        type leafref {
          path "../attributes/ulCgSwitchId";
        }
      }
      container attributes {
      uses UlCgSwitch-attributes;
      }
    }
  }

  augment "/emael:ManagedElement/gnbdu:GNBDUFunction/gnbdu:UeCC" {
    list UlCgSwitchCfg {
      description "Additional definitions from MOM:min/max-elements:0/49; Cell group switch configuration for uplink. Instance UlCgSwitchCfg=Default is created automatically when parent MO instance is created, unless created manually in same transaction. UlCgSwitchUeCfg::ulCgSwitchCfgRef is automatically set to UlCgSwitchCfg=Default instance, unless manually set to refer to another MO instance. Precondition: Instance UlCgSwitchCfg=Default can only be created in same transaction as parent MO instance and cannot be deleted unless parent MO instance is deleted. Other instances can be created and deleted at any time. Maximum 48 UlCgSwitchCfg instances, with RDN different from Default, can be created under parent MO instance.";
      key "ulCgSwitchCfgId";
      leaf ulCgSwitchCfgId {
        type leafref {
          path "../attributes/ulCgSwitchCfgId";
        }
      }
      container attributes {
      uses UlCgSwitchCfg-attributes;
      }
    }
  }

  augment "/emael:ManagedElement/gnbdu:GNBDUFunction/gnbdu:UeCC" {
    list UlServiceDefinition {
      description "Additional definitions from MOM:min/max-elements:0/1; Container class for uplink service definition profile used for current UE. Instance UlServiceDefinition=1 is created automatically when parent MO instance is created, unless created manually in same transaction. Only applicable to Low-Band and Mid-Band cells. The RDN of this MO must be UlServiceDefinition=1. Precondition: Instance UlServiceDefinition=1 can only be created in same transaction as parent MO instance and cannot be deleted unless parent MO instance is deleted.";
      key "ulServiceDefinitionId";
      leaf ulServiceDefinitionId {
        type leafref {
          path "../attributes/ulServiceDefinitionId";
        }
      }
      container attributes {
      uses UlServiceDefinition-attributes;
      }
    }
  }

  augment "/emael:ManagedElement/gnbdu:GNBDUFunction/gnbdu:UeCC" {
    list UlWfPortSwitch {
      description "Additional definitions from MOM:min/max-elements:0/1; Uplink waveform and port switch profile used for current UE. Instance UlWfPortSwitch=1 is created automatically when parent MO instance is created, unless created manually in same transaction. The RDN of this MO must be UlWfPortSwitch=1. Precondition: Instance UlWfPortSwitch=1 can only be created in same transaction as parent MO instance and cannot be deleted unless parent MO instance is deleted.";
      key "ulWfPortSwitchId";
      leaf ulWfPortSwitchId {
        type leafref {
          path "../attributes/ulWfPortSwitchId";
        }
      }
      container attributes {
      uses UlWfPortSwitch-attributes;
      }
    }
  }

  augment "/emael:ManagedElement/gnbdu:GNBDUFunction/gnbdu:UeCC/gnbdu:UlCgSwitch" {
    list UlCgSwitchUeCfg {
      description "Additional definitions from MOM:min/max-elements:0/8; Cell group switch UE configuration group for uplink. Instance UlCgSwitchUeCfg=Base is created automatically when parent MO instance is created, unless created manually in same transaction. Each UE configuration group identifier can only be defined in one ueConfGroupList among UlCgSwitchUeCfg instances contained under parent UlCgSwitch instance. Any combination of one UE group identifier in ueGroupList and one preference UE group identifier in prefUeGroupList must be unique among UlCgSwitchUeCfg instances contained under parent UlCgSwitch instance. Attributes prefUeGroupList, ueGroupList and ueConfGroupList must be empty in instance UlCgSwitchUeCfg=Base but cannot all be empty in any other instance of UlCgSwitchUeCfg under same parent UlCgSwitch instance. Precondition: Instance UlCgSwitchUeCfg=Base can only be created in same transaction as parent MO instance and cannot be deleted unless parent MO instance is deleted. Other instances can be created and deleted at any time. Maximum 7 UlCgSwitchUeCfg instances, with RDN different from Base, can be created under parent MO instance.";
      key "ulCgSwitchUeCfgId";
      leaf ulCgSwitchUeCfgId {
        type leafref {
          path "../attributes/ulCgSwitchUeCfgId";
        }
      }
      container attributes {
      uses UlCgSwitchUeCfg-attributes;
      }
    }
  }

  augment "/emael:ManagedElement/gnbdu:GNBDUFunction/gnbdu:UeCC/gnbdu:UlServiceDefinition" {
    list UlServiceDefinitionUeCfg {
      description "Additional definitions from MOM:min/max-elements:0/8; Uplink service definition profile used for current UE. Instance UlServiceDefinitionUeCfg=Base is created automatically when parent MO instance is created, unless created manually in same transaction. UeBbProfileUeCfg::ulServiceDefinitionUeCfgRef is automatically set to UlServiceDefinitionUeCfg=Base instance, unless manually set to refer to another MO instance. Only applicable to Low-Band and Mid-Band cells. Precondition: Instance UlServiceDefinitionUeCfg=Base can only be created in same transaction as parent MO instance and cannot be deleted unless parent MO instance is deleted. Other instances can be created and deleted at any time. Maximum 7 UlServiceDefinitionUeCfg instances, with RDN different from Base, can be created under parent MO instance.";
      key "ulServiceDefinitionUeCfgId";
      leaf ulServiceDefinitionUeCfgId {
        type leafref {
          path "../attributes/ulServiceDefinitionUeCfgId";
        }
      }
      container attributes {
      uses UlServiceDefinitionUeCfg-attributes;
      }
    }
  }

  augment "/emael:ManagedElement/gnbdu:GNBDUFunction/gnbdu:UeCC/gnbdu:UlServiceDefinition/gnbdu:UlServiceDefinitionUeCfg" {
    list UlService {
      description "Additional definitions from MOM:min/max-elements:0/1; Uplink service profile used for current UE. Instance UlService=1 is created automatically when parent MO instance is created, unless created manually in same transaction. Only applicable to Low-Band and Mid-Band cells. The RDN of this MO must be UlService=1. Precondition: Instance UlService=1 can only be created in same transaction as parent MO instance and cannot be deleted unless parent MO instance is deleted.";
      key "ulServiceId";
      leaf ulServiceId {
        type leafref {
          path "../attributes/ulServiceId";
        }
      }
      container attributes {
      uses UlService-attributes;
      }
    }
  }

  augment "/emael:ManagedElement/gnbdu:GNBDUFunction/gnbdu:UeCC/gnbdu:UlWfPortSwitch" {
    list UlWfPortSwitchUeCfg {
      description "Additional definitions from MOM:min/max-elements:0/8; Uplink waveform and port switch profile used for current UE. Instance UlWfPortSwitchUeCfg=Base is created automatically when parent MO instance is created, unless created manually in same transaction. UeBbProfileUeCfg::ulWfPortSwitchUeCfgRef is automatically set to UlWfPortSwitchUeCfg=Base instance, unless manually set to refer to another MO instance. Precondition: Instance UlWfPortSwitchUeCfg=Base can only be created in same transaction as parent MO instance and cannot be deleted unless parent MO instance is deleted. Other instances can be created and deleted at any time. Maximum 7 UlWfPortSwitchUeCfg instances, with RDN different from Base, can be created under parent MO instance.";
      key "ulWfPortSwitchUeCfgId";
      leaf ulWfPortSwitchUeCfgId {
        type leafref {
          path "../attributes/ulWfPortSwitchUeCfgId";
        }
      }
      container attributes {
      uses UlWfPortSwitchUeCfg-attributes;
      }
    }
  }
  typedef AdjustedPriorityMode {
    description "Adjusted Priority Mode.";
    type enumeration {
      enum STATIC_PRIO_WITHOUT_POLICING {
        description "Configured base priorities are used without policing performed on the SpCell side.";
      }
      enum STATIC_PRIO_WITH_POLICING {
        description "Configured base priorities are used with policing performed on the SpCell side. The policing will only allow data with priorities that exceed configured base priorities.";
      }
      enum DYNAMIC_PRIO {
        description "The priority provided by the SpCell is used with policing performed on the SpCell side. The SpCell will use an internal algorithm when prioritizing external SCell data. Policing will be done so the priorities will not exceed the configured priority limits received from the external SCell.";
      }
    }
  }
  typedef AdmState {
    description "Administrative state of a resource.";
    type enumeration {
      enum LOCKED {
        description "The resource is administratively prohibited from performing services for its users.";
      }
      enum UNLOCKED {
        description "The resource is administratively permitted to perform services for its users. This is independent of its inherent operability.";
      }
      enum SHUTTINGDOWN {
        description "Use of the resource is administratively permitted to existing instances of use only. While the system remains in the shutting down state the manager may at any time cause the managed object to revert to the locked state.";
      }
    }
  }
  typedef AilgModType {
    description "Air Interface Load Generator (AILG) modulation type.";
    type enumeration {
      enum AILG_MOD_QPSK {
        description "Modulation type for AILG PDSCH is QPSK.";
      }
      enum AILG_MOD_16QAM {
        description "Modulation type for AILG PDSCH is 16QAM.";
      }
      enum AILG_MOD_64QAM {
        description "Modulation type for AILG PDSCH is 64QAM.";
      }
      enum AILG_MOD_256QAM {
        description "Modulation type for AILG PDSCH is 256QAM.";
      }
    }
  }
  typedef AqmMode {
    description "AQM mode.";
    type enumeration {
      enum OFF {
        description "Turned off.";
      }
      enum MODE1 {
        description "Non-GBR.";
      }
      enum MODE2 {
        description "GBR.";
      }
    }
  }
  typedef AutoLockAction {
    description "An action performed automatically by the system when O&M connection loss is detected.";
    type enumeration {
      enum NO_LOCK {
        description "Cell administrativeState is not automatically changed.";
      }
      enum IMMEDIATE_LOCK {
        description "Cell administrativeState is automatically turned into LOCKED.";
      }
      enum SOFT_LOCK {
        description "Cell administrativeState is automatically turned into SHUTTINGDOWN.";
      }
    }
  }
  typedef AvailStatus {
    description "The availability status is used to qualify the operational state. It indicates why the operational state has changed its value.";
    type enumeration {
      enum IN_TEST {
        description "The resource is undergoing a test procedure. If the administrative state is locked or shutting down, normal users are prevented from using the resource.";
      }
      enum FAILED {
        description "The resource has an internal fault that prevents it from operating.";
      }
      enum POWER_OFF {
        description "The resource requires power to be applied and is not powered on.";
      }
      enum OFF_LINE {
        description "The resource requires a routine operation to be performed. This routine operation is to place the resource online and make it available for use. The operation may be manual or automatic, or both. The operational state is disabled.";
      }
      enum OFF_DUTY {
        description "The resource has been made inactive by an internal control process.";
      }
      enum DEPENDENCY {
        description "The resource cannot operate because some other resource on which it depends is unavailable.";
      }
      enum DEGRADED {
        description "The service available from the resource is degraded in some respect.";
      }
      enum NOT_INSTALLED {
        description "The resource represented by the managed object is not present, or is incomplete.";
      }
      enum LOG_FULL {
        description "Indicates a log full condition. The semantics are defined in CCITT Rec. X.735 | ISO/IEC 10164-6.";
      }
      enum DEPENDENCY_LOCKED {
        description "The administrative state of a resource that this resource depends on is locked. Alternatively, the availability status of the other resource is dependency locked.";
      }
      enum DEPENDENCY_FAILED {
        description "The availability status of a resource that this resource depends on is failed or dependency failed.";
      }
      enum DEPENDENCY_SHUTTINGDOWN {
        description "The administrative state of a resource that this resource depends on is shutting down. Alternatively, the availability status of the other resource is dependency shutting down.";
      }
      enum DEPENDENCY_RECOVERY {
        description "Resource that this resource depends on is undergoing a recovery procedure.";
      }
      enum DEPENDENCY_HOLDING {
        description "Resource cannot operate because some other resource on which it depends is currently unavailable. The situation is expected to be resolved. Actions to facilitate dependency resolution may be ongoing.";
      }
    }
  }
  typedef BWPContext {
    description "Whether BWP is used in downlink or uplink.";
    type enumeration {
      enum DOWNLINK {
        description "BWP is used for downlink.";
      }
      enum UPLINK {
        description "BWP is used for uplink.";
      }
    }
  }
  typedef BWPSetContext {
    description "Transmission direction of BWP set.";
    type enumeration {
      enum DL_AND_UL {
        description "Supports both downlink and uplink.";
      }
      enum DL {
        description "Supports downlink.";
      }
    }
  }
  typedef BackoffMode {
    description "Backoff mode for Modulation-Aware Power Control feature.";
    type enumeration {
      enum AUTO {
        description "Default operation of Modulation-Aware Power Control feature. Operation takes downlink transmit power and bandwidth allocation into consideration.";
      }
      enum OFF {
        description "Modulation-Aware Power Control feature disabled.";
      }
      enum STATIC {
        description "Static operation of Modulation-Aware Power Control feature. Operation excludes downlink transmit power and bandwidth checks.";
      }
    }
  }
  typedef BucketSizeDuration {
    description "Bucket size duration used in MAC multiplexing and assembly.";
    type enumeration {
      enum MS_5 {
        description "Bucket size duration 5 ms used in RRC logical channel configuration.";
      }
      enum MS_10 {
        description "Bucket size duration 10 ms used in RRC logical channel configuration.";
      }
      enum MS_20 {
        description "Bucket size duration 20 ms used in RRC logical channel configuration.";
      }
      enum MS_50 {
        description "Bucket size duration 50 ms used in RRC logical channel configuration.";
      }
      enum MS_100 {
        description "Bucket size duration 100 ms used in RRC logical channel configuration.";
      }
      enum MS_150 {
        description "Bucket size duration 150 ms used in RRC logical channel configuration.";
      }
      enum MS_300 {
        description "Bucket size duration 300 ms used in RRC logical channel configuration.";
      }
      enum MS_500 {
        description "Bucket size duration 500 ms used in RRC logical channel configuration.";
      }
      enum MS_1000 {
        description "Bucket size duration 1000 ms used in RRC logical channel configuration.";
      }
    }
  }
  typedef CapacityAllocationPolicy {
    description "Capacity allocation policy.";
    type enumeration {
      enum SYSTEM_SELECTED {
        description "Capacity allocation policy selected by system. Default allocation for energy efficiency.";
      }
      enum CAPACITY_PRIORITIZATION {
        description "Capacity allocation policy allows maximum utilization of resources to enhance capacity.";
      }
      enum CAPACITY_PRIORITIZATION_TDD {
        description "Capacity allocation policy allows maximum utilization of resources to enhance capacity. TDD sector carriers are prioritized.";
      }
    }
  }
  typedef CbfMacroTaperType {
    description "Specifies the taper type used for Macro coverage shape.";
    type enumeration {
      enum STANDARD {
        description "Standard tapering for Macro coverage shape.";
      }
      enum HIGHEIRP {
        description "High EIRP tapering for Macro coverage shape.";
      }
      enum HIGHSLS {
        description "Taper type used to suppress first and second upper sidelobes for macro coverage shape.";
      }
    }
  }
  typedef CbrsPriority {
    description "CBRS cell priority.";
    type enumeration {
      enum NORMAL {
        description "CBRS cell priority is set to normal.";
      }
      enum HIGH {
        description "CBRS cell priority is set to high.";
      }
    }
  }
  typedef CellBarred {
    description "Indicates if the NR cell is barred.";
    type enumeration {
      enum BARRED {
        description "The NR cell is barred";
      }
      enum NOT_BARRED {
        description "The NR cell is not barred";
      }
    }
  }
  typedef CellBarredReason {
    description "Reason why cell is barred.";
    type enumeration {
      enum MANUAL {
        description "Cell barred by operator.";
      }
      enum CELL_SOFT_LOCK {
        description "Cell barred by NR Cell Soft Lock feature.";
      }
      enum BOOSTER_CARRIER_SLEEP {
        description "Cell barred by NR Booster Carrier Sleep feature.";
      }
    }
  }
  typedef CellReservedForOperator {
    description "Whether the NR cell is reserved for operator use.";
    type enumeration {
      enum RESERVED {
        description "NR cell reserved for operator use.";
      }
      enum NOT_RESERVED {
        description "NR cell not reserved for operator use.";
      }
    }
  }
  typedef CgSwitchMode {
    description "Defines CG switch behavior.";
    type enumeration {
      enum DISABLED {
        description "Cell group switching is disabled.";
      }
      enum ENABLED {
        description "Cell group switching is enabled.";
      }
    }
  }
  typedef ConfiguredGrantConfMode {
    description "Configuration mode for configured grant periodicity.";
    type enumeration {
      enum CELL_CG_PERIODICITY {
        description "Configured grant periodicity is configured on cell level. Configured by NRCellDU::configuredGrantPeriodicity.";
      }
      enum CG_PROFILE_CG_PERIODICITY {
        description "Configured grant periodicity is configured on configured grant profile level. Configured by ConfiguredGrantUeCfg::configuredGrantPeriodicity.";
      }
    }
  }
  typedef ConfiguredGrantMode {
    description "Configured grant mode.";
    type enumeration {
      enum DEACTIVATED {
        description "Current ConfiguredGrantUeCfg is not used.";
      }
      enum SINGLE {
        description "ConfiguredGrantUeCfg is used for UE with single configured grant profile.";
      }
    }
  }
  typedef CoverageShape {
    description "Specifies the coverage shape of a sector carrier.";
    type enumeration {
      enum PRODUCT_DEFAULT {
        description "Product specific default coverage shape.";
      }
      enum MACRO_1 {
        description "Coverage shape with larger beam space ratio in azimuth plane than in elevation plane. Beam space ratio for MACRO is product specific. Only applicable to Low-Band and Mid-Band cells.";
      }
      enum HIGHRISE_1 {
        description "Coverage shape with larger beam space ratio in elevation plane than in azimuth plane. Beam space ratio for HIGHRISE is product specific. Only applicable to Low-Band and Mid-Band cells.";
      }
      enum HOTSPOT_1 {
        description "Coverage shape with full beam space in both azimuth plane and elevation plane. Full beam space range is product specific. Only applicable to Low-Band and Mid-Band cells.";
      }
      enum MACRO_120_20 {
        description "Coverage shape with larger service area ratio in azimuth plane than in elevation plane. 120 degrees in azimuth and 20 degrees in elevation. Only applicable to High-Band cells.";
      }
      enum HOTSPOT_120_30 {
        description "Coverage shape with full service area in both azimuth plane and elevation plane. 120 degrees in azimuth and 30 degrees in elevation. Only applicable to High-Band cells.";
      }
      enum MACRO_120_15 {
        description "Coverage shape with larger service area ratio in azimuth plane than in elevation plane. 120 degrees in azimuth and 15 degrees in elevation. Only applicable to High-Band cells.";
      }
      enum STREET_COVERAGE_1 {
        description "Coverage shape with normal service area in azimuth plane and narrow in elevation plane. Beam space range is product specific. Only applicable to Mid-Band cells.";
      }
      enum STREET_HOTSPOT_1 {
        description "Coverage shape with normal service area in azimuth plane and elevation plane. Beam space range is product specific. Only applicable to Mid-Band cells.";
      }
      enum STREET_HOTSPOT_WIDE_1 {
        description "Coverage shape with wide service area in azimuth plane and normal in elevation plane. Beam space range is product specific. Only applicable to Mid-Band cells.";
      }
      enum FLEXIBLE_COVERAGE_1 {
        description "Coverage shape with flexible service area used with azimuth and elevation coverage width.";
      }
      enum MACRO_WIDE_1 {
        description "Coverage shape with wide service area in both azimuth plane and elevation plane. Beam space ratio for MACRO is product specific.";
      }
    }
  }
  typedef CreatedBy {
    description "Identifies the creator of MO instance.";
    type enumeration {
      enum SYSTEM {
        description "Created by the system.";
      }
      enum OPERATOR {
        description "Created by operator.";
      }
    }
  }
  typedef CsiBufferThresh {
    description "Threshold in downlink priority queues.";
    type enumeration {
      enum OFF {
        description "No change of CSI reporting period.";
      }
      enum LOW {
        description "Extends CSI Reporting period when buffer data level is less than 400 bytes.";
      }
      enum MEDIUM {
        description "Extends CSI Reporting period when buffer data level is less than 2000 bytes.";
      }
      enum HIGH {
        description "Extends CSI Reporting period when buffer data level is less than 4000 bytes.";
      }
    }
  }
  typedef CsiReportFormat {
    description "Value for CSI Report Format.";
    type enumeration {
      enum CQI_WB_PMI_WB {
        description "Wideband CQI and wideband PMI feedback.";
      }
      enum CQI_WB_PMI_SB {
        description "Wideband CQI and subband PMI feedback.";
      }
      enum CQI_SB_PMI_WB {
        description "Subband CQI and wideband PMI feedback.";
      }
      enum CQI_SB_PMI_SB {
        description "Subband CQI and subband PMI feedback.";
      }
    }
  }
  typedef CsiRptPeriodAdd {
    description "Periodicity added to A-CSI periodicity.";
    type enumeration {
      enum OFF {
        description "No addition to CSI reporting period.";
      }
      enum LOW {
        description "Periodicity of 60 ms is added to A-CSI report.";
      }
      enum HIGH {
        description "Periodicity of 110 ms is added to A-CSI report.";
      }
    }
  }
  typedef CsiRsActivePortConfig {
    description "Shown the active CSI-RS configuration. Based on the MOM settings and its HW/SW resources, gNodeB chooses the most appropriate CSI-RS configuration, and shows in the form of list. Example: {\"PORT_4\",\"PORT_8\"} means that 4-port CSI-RS and 8-port CSI-RS are transmitted simultaneously.";
    type enumeration {
      enum PORT_2 {
        description "2-port CSI-RS is transmitted.";
      }
      enum PORT_4 {
        description "4-port CSI-RS is transmitted.";
      }
      enum PORT_8 {
        description "8-port CSI-RS is transmitted.";
      }
      enum PORT_16 {
        description "16-port CSI-RS is transmitted.";
      }
      enum PORT_32 {
        description "32-port CSI-RS is transmitted.";
      }
    }
  }
  typedef CsiRsControl16Ports {
    description "Value for configuration of 16-port CSI-RS.";
    type enumeration {
      enum OFF {
        description "The 16 port CSIRS is disabled.";
      }
      enum EIGHT_ONE_N1AZ {
        description "16 port CSI-RS is enabled; PMI feedback will be based on Type 1 single panel codebook (N1=8 N2=1). The N1 (i11) codebook dimension is associated with azimuth.";
      }
      enum FOUR_TWO_N1AZ {
        description "16 port CSI-RS is enabled; PMI feedback will be based on Type 1 single panel codebook (N1=4 N2=2). The N1 (i11) codebook dimension is associated with azimuth.";
      }
      enum FOUR_TWO_N1EL {
        description "16 port CSI-RS is enabled; PMI feedback will be based on Type 1 single panel codebook (N1=4 N2=2). The N1 (i11) codebook dimension is associated with elevation.";
      }
    }
  }
  typedef CsiRsControl2Ports {
    description "Value for configuration of 2-port CSI-RS.";
    type enumeration {
      enum OFF {
        description "2-port CSI-RS disabled.";
      }
      enum ON {
        description "2-port CSI-RS enabled.";
      }
    }
  }
  typedef CsiRsControl32Ports {
    description "Value for configuration of 32-port CSI-RS.";
    type enumeration {
      enum OFF {
        description "32 port CSIRS is disabled.";
      }
      enum EIGHT_TWO_N1AZ {
        description "32 port CSI-RS is enabled; PMI feedback will be based on Type 1 single panel codebook (N1=8 N2=2). The N1 (i11) codebook dimension is associated with azimuth.";
      }
      enum FOUR_FOUR {
        description "32 port CSI-RS is enabled; PMI feedback will be based on Type 1 single panel codebook (N1=4 N2=4).";
      }
    }
  }
  typedef CsiRsControl4Ports {
    description "Value for configuration of 4-port CSI-RS.";
    type enumeration {
      enum OFF {
        description "4-port CSI-RS is disabled.";
      }
      enum TWO_ONE {
        description "4-port CSI-RS enabled. PMI feedback based on Type 1 single panel codebook (N1=2 N2=1).";
      }
    }
  }
  typedef CsiRsControl8Ports {
    description "Value for configuration of 8-port CSI-RS.";
    type enumeration {
      enum OFF {
        description "The 8 port CSI-RS is disabled.";
      }
      enum FOUR_ONE_N1AZ {
        description "8 port CSI-RS is enabled; PMI feedback will be based on Type 1 single panel codebook (N1=4 N2=1). The N1 (i11) codebook dimension is associated with azimuth.";
      }
      enum FOUR_ONE_N1EL {
        description "8 port CSI-RS is enabled; PMI feedback will be based on Type 1 single panel codebook (N1=4 N2=1). The N1 (i11) codebook dimension is associated with elevation.";
      }
      enum TWO_TWO {
        description "8 port CSI-RS is enabled; PMI feedback will be based on Type 1 single panel codebook (N1=2 N2=2).";
      }
    }
  }
  typedef CsiRsResourceShifting {
    description "Value for csiRsResourceShifting.";
    type enumeration {
      enum DEACTIVATED {
        description "CSI-RS shifting is not activated. All cells use the same CSI-RS resource position.";
      }
      enum ACTIVATED_AUTOMATIC {
        description "Intra-slot CSI-RS resource shifting is activated. Shift is automatically assigned by gNodeB.";
      }
    }
  }
  typedef CtsFeatureState {
    description "Feature state on CTS.";
    type enumeration {
      enum __UNDEFINED__ {
      }
    }
  }
  typedef DayOfWeek {
    description "Presents the day of the week.";
    type enumeration {
      enum ALL {
        description "All days.";
      }
      enum MONDAY {
        description "Monday.";
      }
      enum TUESDAY {
        description "Tuesday.";
      }
      enum WEDNESDAY {
        description "Wednesday.";
      }
      enum THURSDAY {
        description "Thursday.";
      }
      enum FRIDAY {
        description "Friday.";
      }
      enum SATURDAY {
        description "Saturday.";
      }
      enum SUNDAY {
        description "Sunday.";
      }
    }
  }
  typedef DlCaSchedulingMode {
    description "Downlink Carrier Aggregation Scheduling Mode.";
    type enumeration {
      enum UNLIMITED {
        description "No limit for CA.";
      }
      enum PCELL_ONLY {
        description "Disallow CA.";
      }
    }
  }
  typedef DlCalibrationMethod {
    description "Describes which types of downlink antenna calibration are supported and/or used.";
    type enumeration {
      enum NONE {
        description "No antenna calibration method.";
      }
      enum INTERNAL {
        description "Internal antenna calibration method.";
      }
    }
  }
  typedef DlCalibrationStatus {
    description "Describes the current downlink antenna calibration status.";
    type enumeration {
      enum INACTIVE {
        description "Downlink antenna calibration is not activated.";
      }
      enum CONVERGING {
        description "Downlink antenna calibration is converging.";
      }
      enum CALIBRATED {
        description "Downlink antenna calibration is finished with success.";
      }
      enum FAILED {
        description "Downlink antenna calibration has failed.";
      }
    }
  }
  typedef DlChannelScramblingIdentity {
    description "Downlink channel scrambling identity.";
    type enumeration {
      enum PCI {
        description "Scrambling identities are same as Physical Cell Identity (PCI).";
      }
      enum GENERATED {
        description "Scrambling identities are generated by gNodeB SW.";
      }
    }
  }
  typedef DlSmallDataRobustnessMode {
    description "Robustness mode of downlink small data.";
    type enumeration {
      enum OFF {
        description "Mode is OFF.";
      }
      enum ON {
        description "Mode is ON.";
      }
    }
  }
  typedef DlUlSwitchingPeriod {
    description "Uplink-downlink switching period for RIM RS transmission.";
    type enumeration {
      enum MS0P5 {
        description "500 microseconds.";
      }
      enum MS0P625 {
        description "625 microseconds.";
      }
      enum MS1 {
        description "1000 microseconds.";
      }
      enum MS1P25 {
        description "1250 microseconds.";
      }
      enum MS2 {
        description "2000 microseconds.";
      }
      enum MS2P5 {
        description "2500 microseconds.";
      }
      enum MS3 {
        description "3 ms.";
      }
      enum MS4 {
        description "4 ms.";
      }
      enum MS5 {
        description "5 ms.";
      }
      enum MS10 {
        description "10 ms.";
      }
      enum MS20 {
        description "20 ms.";
      }
    }
  }
  typedef DrbOverloadHandling {
    description "Handle when UE is overloaded with rate-based priority shift algorithm.";
    type enumeration {
      enum BASIC {
        description "Accept DRB setup with basic attributes.";
      }
      enum REJECT {
        description "Reject attempt of DRB setup.";
      }
    }
  }
  typedef DrxInactivityTimer {
    description "Inactivity timer value for DRX.";
    type enumeration {
      enum INACTIVITYTIMER_0MS {
        description "Inactivity timer value 0.";
      }
      enum INACTIVITYTIMER_1MS {
        description "Inactivity timer value 1 ms.";
      }
      enum INACTIVITYTIMER_2MS {
        description "Inactivity timer value 2 ms.";
      }
      enum INACTIVITYTIMER_3MS {
        description "Inactivity timer value 3 ms.";
      }
      enum INACTIVITYTIMER_4MS {
        description "Inactivity timer value 4 ms.";
      }
      enum INACTIVITYTIMER_5MS {
        description "Inactivity timer value 5 ms.";
      }
      enum INACTIVITYTIMER_6MS {
        description "Inactivity timer value 6 ms.";
      }
      enum INACTIVITYTIMER_8MS {
        description "Inactivity timer value 8 ms.";
      }
      enum INACTIVITYTIMER_10MS {
        description "Inactivity timer value 10 ms.";
      }
      enum INACTIVITYTIMER_20MS {
        description "Inactivity timer value 20 ms.";
      }
      enum INACTIVITYTIMER_30MS {
        description "Inactivity timer value 30 ms.";
      }
      enum INACTIVITYTIMER_40MS {
        description "Inactivity timer value 40 ms.";
      }
      enum INACTIVITYTIMER_50MS {
        description "Inactivity timer value 50 ms.";
      }
      enum INACTIVITYTIMER_60MS {
        description "Inactivity timer value 60 ms.";
      }
      enum INACTIVITYTIMER_80MS {
        description "Inactivity timer value 80 ms.";
      }
      enum INACTIVITYTIMER_100MS {
        description "Inactivity timer value 100 ms.";
      }
      enum INACTIVITYTIMER_200MS {
        description "Inactivity timer value 200 ms.";
      }
      enum INACTIVITYTIMER_300MS {
        description "Inactivity timer value 300 ms.";
      }
      enum INACTIVITYTIMER_500MS {
        description "Inactivity timer value 500 ms.";
      }
      enum INACTIVITYTIMER_750MS {
        description "Inactivity timer value 750 ms.";
      }
      enum INACTIVITYTIMER_1280MS {
        description "Inactivity timer value 1280 ms.";
      }
      enum INACTIVITYTIMER_1920MS {
        description "Inactivity timer value 1920 ms.";
      }
      enum INACTIVITYTIMER_2560MS {
        description "Inactivity timer value 2560 ms.";
      }
    }
  }
  typedef DrxLongCycle {
    description "Long Cycle value for DRX.";
    type enumeration {
      enum LONGCYCLE_10MS {
        description "Long cycle value 10 ms.";
      }
      enum LONGCYCLE_20MS {
        description "Long cycle value 20 ms.";
      }
      enum LONGCYCLE_32MS {
        description "Long cycle value 32 ms.";
      }
      enum LONGCYCLE_40MS {
        description "Long cycle value 40 ms.";
      }
      enum LONGCYCLE_60MS {
        description "Long cycle value 60 ms.";
      }
      enum LONGCYCLE_64MS {
        description "Long cycle value 64 ms.";
      }
      enum LONGCYCLE_70MS {
        description "Long cycle value 70 ms.";
      }
      enum LONGCYCLE_80MS {
        description "Long cycle value 80 ms.";
      }
      enum LONGCYCLE_128MS {
        description "Long cycle value 128 ms.";
      }
      enum LONGCYCLE_160MS {
        description "Long cycle value 160 ms.";
      }
      enum LONGCYCLE_256MS {
        description "Long cycle value 256 ms.";
      }
      enum LONGCYCLE_320MS {
        description "Long cycle value 320 ms.";
      }
      enum LONGCYCLE_512MS {
        description "Long cycle value 512 ms.";
      }
      enum LONGCYCLE_640MS {
        description "Long cycle value 640 ms.";
      }
      enum LONGCYCLE_1024MS {
        description "Long cycle value 1024 ms.";
      }
      enum LONGCYCLE_1280MS {
        description "Long cycle value 1280 ms.";
      }
      enum LONGCYCLE_2048MS {
        description "Long cycle value 2048 ms.";
      }
      enum LONGCYCLE_2560MS {
        description "Long cycle value 2560 ms.";
      }
      enum LONGCYCLE_5120MS {
        description "Long cycle value 5120 ms.";
      }
      enum LONGCYCLE_10240MS {
        description "Long cycle value 10240 ms.";
      }
    }
  }
  typedef DrxOnDurationTimer {
    description "On-duration timer value for DRX.";
    type enumeration {
      enum ONDURATIONTIMER_1SUBMS {
        description "On-duration value 1/32 ms.";
      }
      enum ONDURATIONTIMER_2SUBMS {
        description "On-duration value 2/32 ms.";
      }
      enum ONDURATIONTIMER_3SUBMS {
        description "On-duration value 3/32 ms.";
      }
      enum ONDURATIONTIMER_4SUBMS {
        description "On-duration value 4/32 ms.";
      }
      enum ONDURATIONTIMER_5SUBMS {
        description "On-duration value 5/32 ms.";
      }
      enum ONDURATIONTIMER_6SUBMS {
        description "On-duration value 6/32 ms.";
      }
      enum ONDURATIONTIMER_7SUBMS {
        description "On-duration value 7/32 ms.";
      }
      enum ONDURATIONTIMER_8SUBMS {
        description "On-duration value 8/32 ms.";
      }
      enum ONDURATIONTIMER_9SUBMS {
        description "On-duration value 9/32 ms.";
      }
      enum ONDURATIONTIMER_10SUBMS {
        description "On-duration value 10/32 ms.";
      }
      enum ONDURATIONTIMER_11SUBMS {
        description "On-duration value 11/32 ms.";
      }
      enum ONDURATIONTIMER_12SUBMS {
        description "On-duration value 12/32 ms.";
      }
      enum ONDURATIONTIMER_13SUBMS {
        description "On-duration value 13/32 ms.";
      }
      enum ONDURATIONTIMER_14SUBMS {
        description "On-duration value 14/32 ms.";
      }
      enum ONDURATIONTIMER_15SUBMS {
        description "On-duration value 15/32 ms.";
      }
      enum ONDURATIONTIMER_16SUBMS {
        description "On-duration value 16/32 ms.";
      }
      enum ONDURATIONTIMER_17SUBMS {
        description "On-duration value 17/32 ms.";
      }
      enum ONDURATIONTIMER_18SUBMS {
        description "On-duration value 18/32 ms.";
      }
      enum ONDURATIONTIMER_19SUBMS {
        description "On-duration value 19/32 ms.";
      }
      enum ONDURATIONTIMER_20SUBMS {
        description "On-duration value 20/32 ms.";
      }
      enum ONDURATIONTIMER_21SUBMS {
        description "On-duration value 21/32 ms.";
      }
      enum ONDURATIONTIMER_22SUBMS {
        description "On-duration value 22/32 ms.";
      }
      enum ONDURATIONTIMER_23SUBMS {
        description "On-duration value 23/32 ms.";
      }
      enum ONDURATIONTIMER_24SUBMS {
        description "On-duration value 24/32 ms.";
      }
      enum ONDURATIONTIMER_25SUBMS {
        description "On-duration value 25/32 ms.";
      }
      enum ONDURATIONTIMER_26SUBMS {
        description "On-duration value 26/32 ms.";
      }
      enum ONDURATIONTIMER_27SUBMS {
        description "On-duration value 27/32 ms.";
      }
      enum ONDURATIONTIMER_28SUBMS {
        description "On-duration value 28/32 ms.";
      }
      enum ONDURATIONTIMER_29SUBMS {
        description "On-duration value 29/32 ms.";
      }
      enum ONDURATIONTIMER_30SUBMS {
        description "On-duration value 30/32 ms.";
      }
      enum ONDURATIONTIMER_31SUBMS {
        description "On-duration value 31/32 ms.";
      }
      enum ONDURATIONTIMER_1MS {
        description "On-duration value 1 ms.";
      }
      enum ONDURATIONTIMER_2MS {
        description "On-duration value 2 ms.";
      }
      enum ONDURATIONTIMER_3MS {
        description "On-duration value 3 ms.";
      }
      enum ONDURATIONTIMER_4MS {
        description "On-duration value 4 ms.";
      }
      enum ONDURATIONTIMER_5MS {
        description "On-duration value 5 ms.";
      }
      enum ONDURATIONTIMER_6MS {
        description "On-duration value 6 ms.";
      }
      enum ONDURATIONTIMER_8MS {
        description "On-duration value 8 ms.";
      }
      enum ONDURATIONTIMER_10MS {
        description "On-duration value 10 ms.";
      }
      enum ONDURATIONTIMER_20MS {
        description "On-duration value 20 ms.";
      }
      enum ONDURATIONTIMER_30MS {
        description "On-duration value 30 ms.";
      }
      enum ONDURATIONTIMER_40MS {
        description "On-duration value 40 ms.";
      }
      enum ONDURATIONTIMER_50MS {
        description "On-duration value 50 ms.";
      }
      enum ONDURATIONTIMER_60MS {
        description "On-duration value 60 ms.";
      }
      enum ONDURATIONTIMER_80MS {
        description "On-duration value 80 ms.";
      }
      enum ONDURATIONTIMER_100MS {
        description "On-duration value 100 ms.";
      }
      enum ONDURATIONTIMER_200MS {
        description "On-duration value 200 ms.";
      }
      enum ONDURATIONTIMER_300MS {
        description "On-duration value 300 ms.";
      }
      enum ONDURATIONTIMER_400MS {
        description "On-duration value 400 ms.";
      }
      enum ONDURATIONTIMER_500MS {
        description "On-duration value 500 ms.";
      }
      enum ONDURATIONTIMER_600MS {
        description "On-duration value 600 ms.";
      }
      enum ONDURATIONTIMER_800MS {
        description "On-duration value 800 ms.";
      }
      enum ONDURATIONTIMER_1000MS {
        description "On-duration value 1000 ms.";
      }
      enum ONDURATIONTIMER_1200MS {
        description "On-duration value 1200 ms.";
      }
      enum ONDURATIONTIMER_1600MS {
        description "On-duration value 1600 ms.";
      }
    }
  }
  typedef EdrxMode {
    description "Extended DRX mode.";
    type enumeration {
      enum DISABLED {
        description "Extended DRX is disabled.";
      }
      enum IDLE {
        description "Extended DRX for UEs in RRC IDLE state is enabled.";
      }
    }
  }
  typedef EnergyOptPwrAllocCellMode {
    description "Whether Energy-Optimized Power Allocation in NRCellDU is enabled.";
    type enumeration {
      enum DISABLED {
        description "Energy-Optimized Power Allocation feature is disabled.";
      }
      enum ENABLED {
        description "Energy-Optimized Power Allocation feature is enabled.";
      }
    }
  }
  typedef EnergyOptPwrAllocMode {
    description "Whether Energy Optimization Power Allocation in NRCellDU is enabled.";
    type enumeration {
      enum DISABLED {
        description "Energy Optimization Power Allocation feature is disabled.";
      }
      enum ENABLED {
        description "Energy Optimization Power Allocation feature is enabled.";
      }
    }
  }
  typedef EnoughNotEnoughIndication {
    description "Enough/Not enough indication state for RIM-RS1.";
    type enumeration {
      enum DISABLED {
        description "Enough/Not enough indication function is disabled for RIM-RS1.";
      }
      enum ENABLED {
        description "Enough/Not enough indication function is enabled for RIM-RS1.";
      }
    }
  }
  typedef EssMbsfnSubframeVariant {
    description "MBSFN subframe configuration for ESS enabled cell.";
    type enumeration {
      enum NSA_BASIC {
        description "Variant with three MBSFN subframes out of 40 subframes for EN-DC only.";
      }
      enum SA_BASIC {
        description "Variant with five MBSFN subframes out of 40 subframes for NR SA only, and NR SA-EN-DC coexistence.";
      }
      enum SA_SIB_ROBUST_15_PERCENT {
        description "Variant with six MBSFN subframes out of 40 subframes for NR SA only, and NR SA-EN-DC coexistence.";
      }
      enum NSA_25_PERCENT {
        description "Variant with 10 MBSFN subframes out of 40 subframes for EN-DC only.";
      }
      enum SA_25_PERCENT {
        description "Variant with 10 MBSFN subframes out of 40 subframes for NR SA only, and NR SA-EN-DC coexistence.";
      }
      enum NSA_SA_35_PERCENT {
        description "Variant with 14 MBSFN subframes out of 40 subframes for EN-DC, NR SA, and NR SA-EN-DC coexistence.";
      }
      enum NSA_SA_45_PERCENT {
        description "Variant with 18 MBSFN subframes out of 40 subframes for EN-DC, NR SA, and NR SA-EN-DC coexistence.";
      }
      enum NSA_SA_55_PERCENT {
        description "Variant with 22 MBSFN subframes out of 40 subframes for EN-DC, NR SA, and NR SA-EN-DC coexistence.";
      }
    }
  }
  typedef EssPdschEarlyStartConfig {
    description "Configuration of PDSCH early start symbol for ESS enabled cell.";
    type enumeration {
      enum NO_PDSCH_EARLY_START {
        description "No PDSCH early start is enabled.";
      }
      enum ADAPT_MIN_SECOND {
        description "PDSCH can start at as early as second symbol.";
      }
    }
  }
  typedef EssResourceAllocationMode {
    description "Operation mode for RAT resource allocation in ESS.";
    type enumeration {
      enum SCHED_POLICY {
        description "Scheduling policy based ESS resource allocation.";
      }
      enum DEMAND_WEIGHTED_RP {
        description "ESS resource allocation based on relative priority weighted by resource demand.";
      }
    }
  }
  typedef FddTddUlDlPatternType {
    description "FDD or TDD_ULDL pattern type.";
    type enumeration {
      enum TDD_ULDL_PATTERN_00 {
        description "Valid for TDD cell, uplink-downlink pattern is DDSU.";
      }
      enum TDD_ULDL_PATTERN_01 {
        description "Valid for TDD cell, uplink-downlink pattern is DDDSUUDDDD.";
      }
      enum TDD_ULDL_PATTERN_02 {
        description "Valid for TDD cell, uplink-downlink pattern is DDDSU.";
      }
      enum TDD_ULDL_PATTERN_03 {
        description "Valid for TDD cell, uplink-downlink pattern is DDDSUDDSUU.";
      }
      enum TDD_ULDL_PATTERN_04 {
        description "Valid for TDD cell, uplink-downlink pattern is DDDDDDDSUU.";
      }
      enum TDD_ULDL_PATTERN_05 {
        description "Valid for TDD cell, uplink-downlink pattern is DDSUU.";
      }
      enum TDD_ULDL_PATTERN_06 {
        description "Valid for TDD cell, uplink-downlink pattern is DSUUU.";
      }
      enum TDD_ULDL_PATTERN_07 {
        description "Valid for TDD cell, uplink-downlink pattern is DDDSUUDSUU.";
      }
      enum TDD_ULDL_PATTERN_08 {
        description "Valid for TDD cell, uplink-downlink pattern is DDDSUUUUDD.";
      }
      enum FDD {
        description "Valid for FDD cell.";
      }
    }
  }
  typedef FixWideBeamsForPeriodicSrType {
    description "Number of fixed wide beams for periodic Scheduling Request (SR). Periodic SR is sent in PRACH slot according to SSB relation.";
    type enumeration {
      enum FIX_WB_FOR_PERIODIC_SR_NONE {
        description "Number of fixed wide beams in PRACH slot according to SSB relation for periodic SR is set to 0.";
      }
      enum FIX_WB_FOR_PERIODIC_SR_LOW {
        description "Number of fixed wide beams in PRACH slot according to SSB relation for periodic SR is set to 2.";
      }
      enum FIX_WB_FOR_PERIODIC_SR_MEDIUM {
        description "Number of fixed wide beams in PRACH slot according to SSB relation for periodic SR is set to 4.";
      }
      enum FIX_WB_FOR_PERIODIC_SR_HIGH {
        description "Number of fixed wide beams in PRACH slot according to SSB relation for periodic SR is set to 6.";
      }
    }
  }
  typedef HarqMode {
    description "HARQ mode for UE.";
    type enumeration {
      enum HARQ_NORMAL {
        description "Normal HARQ operation for data services.";
      }
      enum HARQ_VONR {
        description "VoNR HARQ operation for communication services.";
      }
      enum HARQ_ROBUST {
        description "Robust HARQ operation for data services.";
      }
    }
  }
  typedef IntMitigationDlSched {
    description "Activation mode of NR Interference Mitigation for Downlink Scheduling.";
    type enumeration {
      enum DEACTIVATED {
        description "NR Interference Mitigation for Downlink Scheduling feature is deactivated.";
      }
      enum PM_ONLY {
        description "NR Interference Mitigation for Downlink Scheduling feature is activated in PM_ONLY mode. In this mode only PM counters are activated, algorithm for PDSCH resource allocation remains unchanged.";
      }
      enum ACTIVATED {
        description "NR Interference Mitigation for Downlink Scheduling feature is activated. Algorithm for PDSCH resource allocation considers value of NRCellDU::prioBoundaryCrb.";
      }
    }
  }
  typedef InterfaceName {
    description "RAN interfaces.";
    type enumeration {
      enum C5 {
        description "C5 for user plane.";
      }
      enum E1 {
        description "E1 for control and user plane.";
      }
      enum E6 {
        description "E6 for control plane.";
      }
      enum F1 {
        description "F1 for control and user plane.";
      }
      enum NG {
        description "NG for control and user plane.";
      }
      enum S1 {
        description "S1 for user plane.";
      }
      enum XN {
        description "Xn for control and user plane.";
      }
      enum X2 {
        description "X2 for control and user plane.";
      }
    }
  }
  typedef L4sMode {
    description "L4S mode.";
    type enumeration {
      enum DISABLED {
        description "L4S is disabled.";
      }
      enum QUEUE_BASED {
        description "Queue-based L4S algorithm is used.";
      }
    }
  }
  typedef LinkActive {
    description "Whether F1-C link to gNodeB-CU-CP is configured with cells and used for traffic.";
    type enumeration {
      enum NOT_ACTIVE {
        description "F1-C link is currently not used for traffic.";
      }
      enum ACTIVE {
        description "F1-C link is currently used for traffic.";
      }
    }
  }
  typedef LinkAdaptationMode {
    description "Link adaptation mode.";
    type enumeration {
      enum GENERAL {
        description "General link adaptation.";
      }
      enum ROBUST_BASIC {
        description "Robust link adaptation with basic robust block error rate target.";
      }
      enum ROBUST_HIGH {
        description "Robust link adaptation with high robust block error rate target.";
      }
      enum CUSTOM {
        description "Custom link adaptation.";
      }
      enum ROBUST_MCS {
        description "Robust link adaptation with MCS robust block error rate target.";
      }
    }
  }
  typedef MassiveMimoSleepEnabled {
    description "Whether Massive MIMO Sleep Mode is enabled.";
    type enumeration {
      enum DISABLED {
        description "Massive MIMO Sleep is not enabled. Disables both detection and switching support.";
      }
      enum ENABLED {
        description "Massive MIMO Sleep is enabled. Enables switching support.";
      }
      enum DETECTION {
        description "Massive MIMO Sleep is enabled in detection-only mode. Enables detection-only mode, no switching is triggered.";
      }
    }
  }
  typedef MassiveMimoSleepMode {
    description "Modes for massive MIMO sleep.";
    type enumeration {
      enum TXMUTE {
        description "TxMute mode.";
      }
      enum ECO {
        description "Eco mode.";
      }
    }
  }
  typedef MassiveMimoSleepState {
    description "Real time status of Massive MIMO Sleep Mode.";
    type enumeration {
      enum DEACTIVATED {
        description "State of Massive MIMO Sleep Mode is deactivated. Sleep thresholds have not been met.";
      }
      enum TXMUTE {
        description "State of Massive MIMO Sleep Mode is TxMute.";
      }
      enum ECO {
        description "State of Massive MIMO Sleep Mode is ECO.";
      }
      enum ECO_PENDING {
        description "State of Massive MIMO Sleep Mode is ECO pending.";
      }
    }
  }
  typedef MaxUeSpeed {
    description "Maximum UE moving speed support.";
    type enumeration {
      enum UP_TO_10KMPH {
        description "Up to 10 km/h UE speed is supported.";
      }
      enum UP_TO_50KMPH {
        description "Up to 50 km/h UE speed is supported.";
      }
      enum UP_TO_100KMPH {
        description "Up to 100 km/h UE speed is supported.";
      }
      enum UP_TO_200KMPH {
        description "Up to 200 km/h UE speed is supported.";
      }
      enum UP_TO_350KMPH {
        description "Up to 350 km/h UE speed is supported.";
      }
      enum UP_TO_500KMPH {
        description "Up to 500 km/h UE speed is supported.";
      }
    }
  }
  typedef McsTable {
    description "MCS table for UE.";
    type enumeration {
      enum QAM64 {
        description "Use QAM64 table.";
      }
      enum QAM256 {
        description "Use QAM256 table.";
      }
      enum LOW_SE_QAM64 {
        description "Use Low Spectral Efficiency 64 QAM table.";
      }
    }
  }
  typedef MeasGapUseCase {
    description "Mode of applying measurement gap length (MGL) for NR FR1 and E-UTRAN measurements.";
    type enumeration {
      enum OFF {
        description "MGL is 6 ms for both NR FR1 and E-UTRAN measurements.";
      }
      enum EUTRAN_3MS {
        description "MGL 3 ms is enabled for E-UTRAN measurements only.";
      }
      enum NR_FR1_3MS {
        description "MGL 3 ms is enabled for NR FR1 measurements only.";
      }
      enum ALL_3MS {
        description "MGL 3 ms is enabled for both NR FR1 and E-UTRAN measurements.";
      }
    }
  }
  typedef ModulationOrder {
    description "Modulation order supported by cell.";
    type enumeration {
      enum QAM_64 {
        description "Modulation order 64 QAM.";
      }
      enum QAM_256 {
        description "Modulation order 256 QAM.";
      }
    }
  }
  typedef NRCellServiceState {
    description "Cell service state.";
    type enumeration {
      enum OUT_OF_SERVICE {
        description "Cell is not operational and cannot serve UE instances. The gNodeB Distributed Unit (gNodeB-DU) is trying to make cell operational.";
      }
      enum IN_SERVICE {
        description "Cell is operational and Master Information Block is broadcast. UE instances can be served when active external connections are present.";
      }
    }
  }
  typedef NRCellState {
    description "Cell states.";
    type enumeration {
      enum IDLE {
        description "The resource is not currently in use.";
      }
      enum INACTIVE {
        description "The cell is known by both the gNodeB-DU and the gNodeB-CU-CP. The cell shall not serve UEs.";
      }
      enum ACTIVE {
        description "The cell is known by both the gNodeB-DU and the gNodeB-CU-CP. The cell should try to provide service to the UEs.";
      }
    }
  }
  typedef NRSectorCarrierAcsAction {
    description "Action performed by Advanced Cell Supervision feature when no downlink TX power is detected.";
    type enumeration {
      enum NO_ACTION {
        description "No Action. Recovery action is not allowed, observation only.";
      }
      enum SC_AND_CELL_RESTART {
        description "Sector Carrier And Cell Restart. Allowed recovery action is sector carrier and cell restart.";
      }
    }
  }
  typedef NValue {
    description "Number of PFs in the DRX cycle.";
    type enumeration {
      enum T {
        description "One T is every radio frame.";
      }
      enum T1_2 {
        description "Every second radio frame.";
      }
      enum T1_4 {
        description "Every fourth radio frame.";
      }
      enum T1_8 {
        description "Every eighth radio frame.";
      }
      enum T1_16 {
        description "Every sixteenth radio frame.";
      }
    }
  }
  typedef NearFarIndication {
    description "Near-far indication state for RIM-RS.";
    type enumeration {
      enum DISABLED {
        description "Near-far function is disabled for RIM-RS.";
      }
      enum ENABLED {
        description "Near-far function is enabled for RIM-RS.";
      }
    }
  }
  typedef NullSteeringMode {
    description "Spatial null-steering mode that determines impacted downlink channels.";
    type enumeration {
      enum ALL {
        description "Configured azimuthNull and elevationNull attributes applied to all downlink transmissions.";
      }
      enum COMMON_BEAMFORMING {
        description "Configured spatial nulls applied to downlink transmissions that employ common beamforming. Configured azimuthNull and elevationNull attributes are applied to PDSCH before PMI feedback, PDCCH, SSB, PBCH, and TRS transmission.";
      }
      enum CSI_RS_MAPPING {
        description "Configured spatial nulls applied to downlink transmissions that require CSI-RS ports to antenna mapping. Configured azimuthNull and elevationNull attributes are applied to PDSCH after PMI feedback and CSI-RS transmission.";
      }
    }
  }
  typedef NullWidth {
    description "Width of horizontal or vertical null.";
    type enumeration {
      enum NARROW {
        description "Narrow azimuth or elevation null. Only one null is generated.";
      }
      enum MEDIUM {
        description "Medium azimuth or elevation null. Two nulls are joined to create a medium width null.";
      }
      enum WIDE {
        description "Wide azimuth or elevation null. Three nulls are joined to create a wide null.";
      }
    }
  }
  typedef OperState {
    description "Operational states of a resource.";
    type enumeration {
      enum DISABLED {
        description "The resource is totally inoperable.";
      }
      enum ENABLED {
        description "The resource is partially or fully operable.";
      }
    }
  }
  typedef PagingPriority {
    description "Paging priority level for Mobile Terminating Access.";
    type enumeration {
      enum OFF {
        description "Paging priority level for Mobile Terminating Access is not active.";
      }
      enum PRIO_LEVEL_1 {
        description "Paging priority level 1: highest paging priority.";
      }
      enum PRIO_LEVEL_2 {
        description "Paging priority level 2.";
      }
      enum PRIO_LEVEL_3 {
        description "Paging priority level 3.";
      }
      enum PRIO_LEVEL_4 {
        description "Paging priority level 4.";
      }
      enum PRIO_LEVEL_5 {
        description "Paging priority level 5.";
      }
      enum PRIO_LEVEL_6 {
        description "Paging priority level 6.";
      }
      enum PRIO_LEVEL_7 {
        description "Paging priority level 7.";
      }
      enum PRIO_LEVEL_8 {
        description "Paging priority level 8: lowest paging priority.";
      }
    }
  }
  typedef PdcchBeamOptMode {
    description "PDCCH beamforming optimizer mode.";
    type enumeration {
      enum OFF {
        description "PDCCH beamforming optimization is disabled.";
      }
      enum SLOW {
        description "PDCCH beamforming optimization with slow reaction time and enhanced fallback capabilities.";
      }
      enum NORMAL {
        description "PDCCH beamforming optimization with normal reaction time and enhanced fallback capabilities.";
      }
      enum FAST {
        description "PDCCH beamforming optimization with fast reaction time and enhanced fallback capabilities.";
      }
    }
  }
  typedef PdcchLaOlaType {
    description "Ways to compute outer loop adjustment for PDCCH link adaptation.";
    type enumeration {
      enum NO_OLA {
        description "No PDCCH outer loop adjustment is computed.";
      }
      enum PDSCH_OLA {
        description "PDCCH outer loop adjustment is computed based on PDSCH outer loop adjustment.";
      }
    }
  }
  typedef PdcchSymbConfig {
    description "PDCCH symbol configuration.";
    type enumeration {
      enum MINIMUM {
        description "Minimum required number of PDCCH symbols for a given bandwidth.";
      }
      enum STATIC_2 {
        description "Number of PDCCH symbols is fixed to 2.";
      }
      enum ADAPT_MAX_2 {
        description "Number of PDCCH symbols is adaptive and maximum 2.";
      }
      enum ADAPT_MAX_3 {
        description "Number of PDCCH symbols is adaptive and maximum 3.";
      }
      enum STATIC_3 {
        description "Number of PDCCH symbols is fixed to 3.";
      }
    }
  }
  typedef PimAvoidLevel {
    description "PIM Avoidance behavior level.";
    type enumeration {
      enum DISABLED {
        description "Disables PIM Avoidance.";
      }
      enum LOW {
        description "Strict criteria for classification of uplink transmission as PIM-affected. Mitigation mechanism reduces number of uplink transmissions that might require PIM mitigation through PDSCH resource muting. Minimizes impact on downlink throughput.";
      }
      enum MEDIUM {
        description "Moderate criteria for classification of uplink transmission as PIM-affected. Mitigation mechanism increases number of uplink transmissions that might require PDSCH resource muting.";
      }
      enum HIGH {
        description "Lenient criteria for classification of uplink transmission as PIM-affected. Mitigation mechanism covers wide range of uplink transmissions. Yields noticeable degradation of downlink throughput.";
      }
    }
  }
  typedef PimAvoidanceModeStatus {
    description "Multi-Node PIM Avoidance mode status.";
    type enumeration {
      enum AGGRESSOR {
        description "PIM Avoidance is performed as aggressor.";
      }
      enum VICTIM {
        description "PIM Avoidance is performed as victim.";
      }
      enum AGGRESSOR_VICTIM {
        description "PIM Avoidance is performed as aggressor and victim.";
      }
    }
  }
  typedef PrefSrPeriodicityPool {
    description "Preferred SR periodicity pool.";
    type enumeration {
      enum SR_PERIODICITY_POOL_1 {
        description "SR periodicity pool 1.";
      }
      enum SR_PERIODICITY_POOL_2 {
        description "SR periodicity pool 2.";
      }
      enum SR_PERIODICITY_POOL_3 {
        description "SR periodicity pool 3.";
      }
      enum SR_PERIODICITY_POOL_4 {
        description "SR periodicity pool 4.";
      }
      enum SR_PERIODICITY_POOL_5 {
        description "SR periodicity pool 5.";
      }
    }
  }
  typedef PreschedulingMode {
    description "UE prescheduling operation mode.";
    type enumeration {
      enum DISABLE {
        description "Prescheduling is disabled.";
      }
      enum BASIC {
        description "Prescheduling in basic mode.";
      }
      enum HIGH_PRIORITY {
        description "Prescheduling in high-priority mode.";
      }
      enum DEFAULT {
        description "Prescheduling is disabled for FR1, and is in basic mode for FR2.";
      }
    }
  }
  typedef PrioritisedBitRate {
    description "Prioritized bit rate used in MAC multiplexing and assembly.";
    type enumeration {
      enum KBPS_0 {
        description "Prioritized bit rate 0 kBps used in RRC logical channel configuration.";
      }
      enum KBPS_8 {
        description "Prioritized bit rate 8 kBps used in RRC logical channel configuration.";
      }
      enum KBPS_16 {
        description "Prioritized bit rate 16 kBps used in RRC logical channel configuration.";
      }
      enum KBPS_32 {
        description "Prioritized bit rate 32 kBps used in RRC logical channel configuration.";
      }
      enum KBPS_64 {
        description "Prioritized bit rate 64 kBps used in RRC logical channel configuration.";
      }
      enum KBPS_128 {
        description "Prioritized bit rate 128 kBps used in RRC logical channel configuration.";
      }
      enum KBPS_256 {
        description "Prioritized bit rate 256 kBps used in RRC logical channel configuration.";
      }
      enum KBPS_512 {
        description "Prioritized bit rate 512 kBps used in RRC logical channel configuration.";
      }
      enum KBPS_1024 {
        description "Prioritized bit rate 1024 kBps used in RRC logical channel configuration.";
      }
      enum KBPS_2048 {
        description "Prioritized bit rate 2048 kBps used in RRC logical channel configuration.";
      }
      enum KBPS_4096 {
        description "Prioritized bit rate 4096 kBps used in RRC logical channel configuration.";
      }
      enum KBPS_8192 {
        description "Prioritized bit rate 8192 kBps used in RRC logical channel configuration.";
      }
      enum KBPS_16384 {
        description "Prioritized bit rate 16384 kBps used in RRC logical channel configuration.";
      }
      enum KBPS_32768 {
        description "Prioritized bit rate 32768 kBps used in RRC logical channel configuration.";
      }
      enum KBPS_65536 {
        description "Prioritized bit rate 65536 kBps used in RRC logical channel configuration.";
      }
      enum INFINITY {
        description "Prioritized bit rate infinity used in RRC logical channel configuration.";
      }
    }
  }
  typedef PriorityShiftLevel {
    description "Priority shift level.";
    type enumeration {
      enum LOW {
        description "Low priority.";
      }
      enum HIGH {
        description "High priority.";
      }
    }
  }
  typedef PuschModeOnFddSCell {
    description "PUSCH time domain allocation mode in Low-Band SCells. Short PUSCH refers to time domain allocation of less than 14 symbols. Long PUSCH refers to time domain allocation of 14 symbols.";
    type enumeration {
      enum LONG {
        description "Allow only long PUSCH in Low-Band SCells.";
      }
      enum SHORT_SRS_CONSEC_SL_OVERLAP {
        description "Allow short PUSCH at overlap with SRS slot or two consecutive uplink slots on Mid-Band PCells.";
      }
      enum SHORT_SRS_OVERLAP {
        description "Allow short PUSCH at overlap with SRS slot on Mid-Band PCells.";
      }
      enum SHORT_CONSEC_SL_OVERLAP {
        description "Allow short PUSCH at overlap with two consecutive uplink slots on Mid-Band PCells.";
      }
    }
  }
  typedef PuschPowerControlMode {
    description "PUSCH power control mode.";
    type enumeration {
      enum OLPC {
        description "Open loop power control.";
      }
      enum POWER_BASED_CLPC {
        description "Power based closed loop power control.";
      }
    }
  }
  typedef PuschRepDrxModeType {
    description "PUSCH repetition DRX mode type.";
    type enumeration {
      enum ACTIVE {
        description "PUSCH Repetition DRX mode ACTIVE. Use DRX parameters from PuschRepRel16Drx instance to override values from selected DrxProfileUeCfg instance when PUSCH Repetition Type A is configured on UE. Applied to UE not capable of supporting the start of drx-HARQ-RTT-TimerUL after end of the last transmission within a bundle, see lastTransmissionUL-r17, 3GPP 38.306 Rel. 17.2.0.";
      }
      enum FORCED {
        description "PUSCH Repetition DRX mode FORCED. Use DRX parameters from PuschRepRel16Drx instance to override values from selected DrxProfileUeCfg instance when PUSCH Repetition Type A is configured on UE.";
      }
    }
  }
  typedef PuschRepModeType {
    description "PUSCH repetition mode type.";
    type enumeration {
      enum NOT_ALLOWED {
        description "PUSCH repetition not allowed.";
      }
      enum DYNAMIC {
        description "PUSCH repetition Type A allowed.";
      }
    }
  }
  typedef RachPreambleFormatType {
    description "Defines preamble format for RACH.";
    type enumeration {
      enum RACH_PREAMBLE_FORMAT_00 {
        description "RACH preamble format 0.";
      }
      enum RACH_PREAMBLE_FORMAT_01 {
        description "RACH preamble format B4.";
      }
      enum RACH_PREAMBLE_FORMAT_02 {
        description "RACH preamble format 1.";
      }
      enum RACH_PREAMBLE_FORMAT_03 {
        description "RACH preamble format A3.";
      }
      enum RACH_PREAMBLE_FORMAT_04 {
        description "RACH preamble format C2.";
      }
    }
  }
  typedef RachRestrictedSetConfig {
    description "Restricted set configuration of random access preamble.";
    type enumeration {
      enum UNRESTRICTED_SET {
        description "Unrestricted set.";
      }
      enum RESTRICTED_SET_TYPE_A {
        description "Restricted set type A.";
      }
      enum RESTRICTED_SET_TYPE_B {
        description "Restricted set type B.";
      }
    }
  }
  typedef RadioOperatingModeEnhanced {
    description "Operating mode options for cell traffic profile set by operator.";
    type enumeration {
      enum COVERAGE {
        description "Can give higher output power.";
      }
      enum CAPACITY {
        description "Can give better signal quality.";
      }
      enum COVERAGE_GREEN {
        description "Can give higher output power when combined with power savings in some cases.";
      }
      enum CAPACITY_GREEN {
        description "Can give better signal quality when combined with power savings in some cases.";
      }
    }
  }
  typedef RedCapUeLimit {
    description "Amount of RedCap UEs allowed to connect to cell.";
    type enumeration {
      enum NONE {
        description "RedCap UEs are not accepted in cell.";
      }
      enum BASIC {
        description "Up to 20 RedCap UEs are accepted in cell.";
      }
      enum ADVANCED {
        description "Up to 100 RedCap UEs are accepted in cell.";
      }
      enum MAXIMUM {
        description "No upper bound for amount of RedCap UEs connected to cell.";
      }
    }
  }
  typedef RelativePriorityMode {
    description "Relative priority part of the scheduling weight is calculated.";
    type enumeration {
      enum RP_ONLY {
        description "Scheduling weight impact from relativePriority.";
      }
      enum PDB_ONLY {
        description "Scheduling weight impact from packetDelayBudget.";
      }
      enum RP_AND_PDB {
        description "Scheduling weight impact from relativePriority and packetDelayBudget attributes.";
      }
    }
  }
  typedef ResourceAllocationType {
    description "Resource allocation type.";
    type enumeration {
      enum RESOURCE_ALLOCATION_TYPE_0 {
        description "Resource allocation type 0.";
      }
      enum DYNAMIC_SWITCH_FB_TYPE_0 {
        description "Dynamic switch between resource allocation type 0 and type 1, with fallback to type 0.";
      }
      enum RESOURCE_ALLOCATION_TYPE_1 {
        description "Resource allocation type 1.";
      }
      enum DYNAMIC_SWITCH_FB_TYPE_1 {
        description "Dynamic switch between resource allocation type 0 and type 1, with fallback to type 1.";
      }
    }
  }
  typedef ResourceControlLevel {
    description "Resource control level used by Latancy Prioritized Scheduling.";
    type enumeration {
      enum LEVEL_0 {
        description "No resource control.";
      }
      enum LEVEL_1 {
        description "Resource control level 1.";
      }
      enum LEVEL_2 {
        description "Resource control level 2.";
      }
      enum LEVEL_3 {
        description "Resource control level 3.";
      }
      enum LEVEL_4 {
        description "Resource control level 4.";
      }
      enum LEVEL_5 {
        description "Resource control level 5.";
      }
    }
  }
  typedef ResourceLimitMode {
    description "Resource Limit Mode.";
    type enumeration {
      enum NO_LIMIT {
        description "No limited resource.";
      }
      enum LIMITED {
        description "DRB limited resource.";
      }
      enum LIMITED_TO_CELL_LIMIT {
        description "DRB and cell limited resource.";
      }
    }
  }
  typedef RimPdschSlotBlankMode {
    description "PDSCH slot blanking mode for remote interference mitigation.";
    type enumeration {
      enum DISABLED {
        description "PDSCH slot blanking is disabled.";
      }
      enum AUTO_MODE {
        description "Auto mode. Special slot, or special slot and one downlink slot are automatically blanked.";
      }
      enum SPECIAL_SLOT {
        description "Special slot is blanked.";
      }
      enum SPECIAL_DL_SLOT {
        description "Special slot and one downlink slot are blanked.";
      }
      enum AUTO_RS1 {
        description "PDSCH slot blanking is automatically handled by RIM location.";
      }
      enum SPECIAL_2DL_SLOT {
        description "Special slot and two downlink slots are blanked.";
      }
    }
  }
  typedef RimSetType {
    description "Reference signal type at cell level.";
    type enumeration {
      enum RS_1 {
        description "Reference signal RS1.";
      }
      enum RS_2 {
        description "Reference signal RS2.";
      }
    }
  }
  typedef RimSlopeFrontSymIndex {
    description "Symbol to use as front symbol in slope detection.";
    type enumeration {
      enum SS_LAST_UL {
        description "Last uplink symbol in special slot.";
      }
      enum SS_2LAST_UL {
        description "Second to last uplink symbol in special slot.";
      }
      enum SS_3LAST_UL {
        description "Third to last uplink symbol in special slot.";
      }
      enum SS_4LAST_UL {
        description "Fourth to last uplink symbol in special slot.";
      }
      enum UL1_FRONT_DMRS {
        description "Front DMRS symbol in first uplink slot after special slot.";
      }
      enum UL1_END_DMRS {
        description "End DMRS symbol in first uplink slot after special slot.";
      }
      enum UL2_FRONT_DMRS {
        description "Front DMRS symbol in second uplink slot after special slot.";
      }
    }
  }
  typedef RlcAckPduDelayMode {
    description "Mode selection for delay of RLC Ack STATUS PDU.";
    type enumeration {
      enum NO_DELAY {
        description "No delay in RLC Ack STATUS PDUs.";
      }
      enum VERY_LOW {
        description "Minimum delay duration for RLC Ack STATUS PDUs. Minimizes scheduling latency for RLC Ack STATUS PDUs, offering lowest opportunity for piggybacking with other downlink data.";
      }
      enum LOW {
        description "Lower delay duration for RLC Ack STATUS PDUs. Lowers scheduling latency for RLC Ack STATUS PDUs, offering lower opportunity for piggybacking with other downlink data.";
      }
      enum BALANCED {
        description "Moderate delay duration for RLC Ack STATUS PDUs. Balances need for efficient piggybacking with other downlink data while maintaining an acceptable scheduling latency for RLC Ack STATUS PDUs.";
      }
      enum HIGH {
        description "Maximum delay duration for RLC Ack STATUS PDUs. Maximum opportunity for piggybacking with other downlink data but potentially increases scheduling latency for RLC Ack STATUS PDUs.";
      }
    }
  }
  typedef RrpControllerMode {
    description "RRP controller mode.";
    type enumeration {
      enum NO_AUTO_CONTROL {
        description "No automated RRP controller mode.";
      }
      enum AUTO_CONTROL_1 {
        description "Automated RRP based on throughput measurement.";
      }
      enum AUTO_CONTROL_2 {
        description "Automated RRP based on service load.";
      }
    }
  }
  typedef RrpOperation {
    description "Property RRP operation favors.";
    type enumeration {
      enum BALANCED {
        description "Balances between latency and resource share fulfillment.";
      }
      enum FAIRNESS_FAVORED {
        description "Favors resource share fulfillment.";
      }
    }
  }
  typedef RrpSchedulingPriority {
    description "Scheduling domain used by RRP when resource usage is above configured share.";
    type enumeration {
      enum DEMOTED_NORMAL {
        description "Normal scheduling domain for demoted partition.";
      }
      enum DEMOTED_LOW {
        description "Lower scheduling domain for demoted partition.";
      }
    }
  }
  typedef SchedulingAlgorithm {
    description "Scheduling algorithm.";
    type enumeration {
      enum RESOURCE_FAIR {
        description "Resource Fair Algorithm.";
      }
      enum PRIORITIZED_RATE {
        description "Prioritized rate algorithm.";
      }
      enum SOFT_RATE_THROTTLING {
        description "Soft rate throttling algorithm.";
      }
      enum ELEVATION_TIME {
        description "Elevation time algorithm.";
      }
      enum LATENCY_PRIORITIZED {
        description "Latency prioritized basic algorithm.";
      }
      enum LATENCY_PRIORITIZED_TCC {
        description "Latency prioritized algorithm for TCC.";
      }
    }
  }
  typedef SetIdAllocation {
    description "RIM set ID allocation level.";
    type enumeration {
      enum G_NODE_B {
        description "GNodeB level.";
      }
      enum CELL {
        description "Cell level.";
      }
    }
  }
  typedef ShareAdjustmentMode {
    description "Property of RRP share adjustment mode.";
    type enumeration {
      enum ABSOLUTE {
        description "No compensation for dynamic changes in available resources in a slot.";
      }
      enum GENERAL_COMPENSATION {
        description "Generally compensated for dynamic changes in available resources in a slot.";
      }
    }
  }
  typedef ShareInheritance {
    description "Inheritance of prioritized resources.";
    type enumeration {
      enum NONE {
        description "No inheritance.";
      }
      enum HIERARCHICAL {
        description "Hierarchical inheritance.";
      }
    }
  }
  typedef SiBroadcastStatus {
    description "Broadcast status.";
    type enumeration {
      enum BROADCASTING {
        description "The SI-message is broadcast.";
      }
    }
  }
  typedef SrGrantSizeMode {
    description "Mode for calculation of DCI grant size.";
    type enumeration {
      enum STATIC {
        description "Always use configured BsrUeCfg::srGrantSize value.";
      }
      enum ADAPTIVE {
        description "Value 32 bits for BsrUeCfg::srGrantSize is used in slots with high uplink PRB usage. Configured BsrUeCfg::srGrantSize value is used in other slots.";
      }
    }
  }
  typedef SrGrantSizeOpt {
    description "Optimization level for calculation of DCI grant size.";
    type enumeration {
      enum THROUGHPUT_OPTIMIZED {
        description "High uplink PRB usage for grants triggered by Scheduling Request.";
      }
      enum BALANCED {
        description "Medium uplink PRB usage for grants triggered by Scheduling Request.";
      }
      enum RESOURCE_OPTIMIZED {
        description "Low uplink PRB usage for grants triggered by Scheduling Request.";
      }
    }
  }
  typedef SrHandlingMode {
    description "The initial SR priority used inherited from 5QI.";
    type enumeration {
      enum DISABLED {
        description "SR priority handling disabled.";
      }
      enum SR_PRIO_5QI {
        description "SR priority handling enabled.";
      }
    }
  }
  typedef SrMode {
    description "SR periodicity pool setting.";
    type enumeration {
      enum __UNDEFINED__ {
      }
    }
  }
  typedef SrPeriodicityValue {
    description "SR periodicity value for the pool.";
    type enumeration {
      enum SR_PERIODICITY_SYM2 {
        description "SR periodicity 2 symbol.";
      }
      enum SR_PERIODICITY_SYM6_OR_7 {
        description "SR periodicity 6 or 7 symbol. Corresponds to 6 symbols if extended cyclic prefix and a SCS of 60 kHz are configured, otherwise it corresponds to 7 symbols.";
      }
      enum SR_PERIODICITY_SL1 {
        description "SR periodicity 1 slot.";
      }
      enum SR_PERIODICITY_SL2 {
        description "SR periodicity 2 slots.";
      }
      enum SR_PERIODICITY_SL4 {
        description "SR periodicity 4 slots.";
      }
      enum SR_PERIODICITY_SL5 {
        description "SR periodicity 5 slots.";
      }
      enum SR_PERIODICITY_SL8 {
        description "SR periodicity 8 slots.";
      }
      enum SR_PERIODICITY_SL10 {
        description "SR periodicity 10 slots.";
      }
      enum SR_PERIODICITY_SL16 {
        description "SR periodicity 16 slots.";
      }
      enum SR_PERIODICITY_SL20 {
        description "SR periodicity 20 slots.";
      }
      enum SR_PERIODICITY_SL40 {
        description "SR periodicity 40 slots.";
      }
      enum SR_PERIODICITY_SL80 {
        description "SR periodicity 80 slots.";
      }
      enum SR_PERIODICITY_SL160 {
        description "SR periodicity 160 slots.";
      }
      enum SR_PERIODICITY_SL320 {
        description "SR periodicity 320 slots.";
      }
      enum SR_PERIODICITY_SL640 {
        description "SR periodicity 640 slots.";
      }
    }
  }
  typedef SrbToConfGrantMapType {
    description "Mapping between SRBs (SRB1 and SRB2) and configured grant profile.";
    type enumeration {
      enum UNRESTRICTED {
        description "Uplink transmission is not restricted to use this configured grant profile.";
      }
      enum NOT_ALLOWED {
        description "Uplink transmission is not allowed to use this configured grant profile.";
      }
    }
  }
  typedef SrsHoppingBandwidth {
    description "Frequency hopping bandwidth for SRS.";
    type enumeration {
      enum FULL {
        description "Full band transmission.";
      }
      enum HALF {
        description "Half band frequency hopping.";
      }
    }
  }
  typedef SrsImpactHandling {
    description "Handling for impact of SRS TX port switching in another cell.";
    type enumeration {
      enum DISABLED {
        description "Handling for impact of SRS TX port switching disabled.";
      }
      enum ENABLED {
        description "Handling for impact of SRS TX port switching enabled.";
      }
    }
  }
  typedef SrsSymbolCombSelectionMode {
    description "Selection mode of resources for SRS.";
    type enumeration {
      enum DEFAULT {
        description "Different uplink symbols or comb offsets for SRS transmissions from all cells are possible to set.";
      }
      enum COMMON {
        description "Same uplink symbols and comb offsets configuration are used for SRS transmissions from all cells.";
      }
    }
  }
  typedef SsbBeams {
    description "Number of SSB beams.";
    type enumeration {
      enum PRODUCT_DEFAULT {
        description "Product specific default number of SSB beams.";
      }
      enum SSB_BEAMS_12 {
        description "12 SSB beams.";
      }
      enum SSB_BEAMS_24 {
        description "24 SSB beams.";
      }
      enum SSB_BEAMS_4 {
        description "4 SSB beams.";
      }
      enum SSB_BEAMS_6 {
        description "6 SSB beams.";
      }
      enum SSB_BEAMS_8 {
        description "8 SSB beams.";
      }
    }
  }
  typedef StartPrbStrategy {
    description "Mitigate interference strategy that chooses way to allocate PRBs to UEs.";
    type enumeration {
      enum START_LOWER_EDGE {
        description "Mitigate interference strategy that chooses way of allocating PRBs to UEs. From lower frequency band edge, START_LOWER_EDGE is chosen.";
      }
      enum START_HIGHER_EDGE {
        description "Mitigate interference strategy that chooses way of allocating PRBs to UEs. From higher frequency band edge, START_HIGHER_EDGE is chosen.";
      }
      enum RANDOM_START_LOWER_OR_HIGHER {
        description "Mitigate interference strategy that chooses way of allocating PRBs to UEs. Both from lower and higher frequency band edges by random for each slot, RANDOM_START_LOWER_OR_HIGHER is chosen.";
      }
      enum RANDOM_START_WITHIN_BAND {
        description "Mitigate interference strategy that chooses way of allocating PRBs to UEs. From random starting point for each slot for interference spreading over the whole band, RANDOM_START_WITHIN_BAND is chosen.";
      }
    }
  }
  typedef TddBorderVersion {
    description "Adapted version of TDD for avoiding cross-link interference at cell border. TDD patterns are defined in enum TddUlDlPatternType and used in tddUlDlPattern. TDD special slot patterns are defined in enum TddSpecialSlotPatternType and used in tddSpecialSlotPattern.";
    type enumeration {
      enum DISABLED {
        description "TDD border version is disabled.";
      }
      enum VERSION_1 {
        description "TDD border version 1. Compensating for TDD_ULDL_PATTERN_01 and TDD_SPECIAL_SLOT_PATTERN_03 co-existence with TDD_ULDL_PATTERN_02 and TDD_SPECIAL_SLOT_PATTERN_00 or TDD_SPECIAL_SLOT_PATTERN_02.";
      }
    }
  }
  typedef TddSpecialSlotPatternType {
    description "Defines downlink, guard, and uplink symbols within special slot or slots. Symbols are listed in downlink:guard:uplink order. For example, a pattern given as 3:8:3 starts with three downlink symbols followed by an eight symbol guard and ending with three uplink symbols.";
    type enumeration {
      enum TDD_SPECIAL_SLOT_PATTERN_00 {
        description "Special slot pattern 11:3:0. Only applicable to Mid-Band cells.";
      }
      enum TDD_SPECIAL_SLOT_PATTERN_01 {
        description "Special slot pattern 3:8:3. Only applicable to Mid-Band cells.";
      }
      enum TDD_SPECIAL_SLOT_PATTERN_02 {
        description "Special slot pattern 10:2:2. Applicable to Mid-Band and High-Band cells.";
      }
      enum TDD_SPECIAL_SLOT_PATTERN_03 {
        description "NR special slot equivalent to LTE SSF conf 7, with 6 DL symbols, 4 guard symbols, and 4 UL symbols. Only applicable to Mid-Band cells.";
      }
      enum TDD_SPECIAL_SLOT_PATTERN_04 {
        description "NR special slot equivalent to LTE SSF conf 6, with 4 DL symbols, 6 guard symbols, and 4 UL symbols. Only applicable to Mid-Band cells.";
      }
      enum TDD_SPECIAL_SLOT_PATTERN_05 {
        description "NR special slots {6:8:0; 0:10:4} equivalent to LTE SSF conf 5, with two consecutive special slots. Only applicable to Mid-Band cells.";
      }
      enum TDD_SPECIAL_SLOT_PATTERN_06 {
        description "Special slot pattern 12:2:0. Only applicable to High-Band cells.";
      }
    }
  }
  typedef TddUlDlPatternType {
    description "Defines TDD pattern in terms of downlink, uplink, and special slots. Slots are indicated with D, S, and U for downlink, special, and uplink slots, respectively. For example, a pattern given as DDSU starts with two downlink slots followed by a special slot and finally a single uplink slot.";
    type enumeration {
      enum TDD_ULDL_PATTERN_00 {
        description "uplink-downlink pattern is DDSU. Only applicable to Mid-Band cells.";
      }
      enum TDD_ULDL_PATTERN_01 {
        description "uplink-downlink pattern is DDDSUUDDDD. Aligned with LTE TDD uplink-downlink configuration 2. Only applicable to Mid-Band cells.";
      }
      enum TDD_ULDL_PATTERN_02 {
        description "uplink-downlink pattern is DDDSU. Applicable to Mid-Band and High-Band cells.";
      }
      enum TDD_ULDL_PATTERN_03 {
        description "uplink-downlink pattern is DDDSUDDSUU. Only applicable to Mid-Band cells.";
      }
      enum TDD_ULDL_PATTERN_04 {
        description "uplink-downlink pattern is DDDDDDDSUU. Aligned with LTE TDD uplink-downlink configuration 2 with frame start offset. Only applicable to Mid-Band cells.";
      }
      enum TDD_ULDL_PATTERN_05 {
        description "uplink-downlink pattern is DDSUU. Only applicable to High-Band cells.";
      }
      enum TDD_ULDL_PATTERN_06 {
        description "uplink-downlink pattern is DSUUU. Only applicable to High-Band cells.";
      }
      enum TDD_ULDL_PATTERN_08 {
        description "Uplink-downlink pattern is DDDSUUUUDD. Aligned with LTE TDD uplink-downlink configuration 1. Only applicable to Mid-Band cells.";
      }
    }
  }
  typedef TermPointType {
    description "Type of the termination point.";
    type enumeration {
      enum __UNDEFINED__ {
      }
    }
  }
  typedef TrafficCategory {
    description "Traffic category.";
    type enumeration {
      enum SA {
        description "Traffic category is standalone.";
      }
      enum ENDC {
        description "Traffic category is EN-DC.";
      }
    }
  }
  typedef TrsConfigMode {
    description "TRS bandwidth configuration mode.";
    type enumeration {
      enum AUTO {
        description "System automatically selects TRS configuration.";
      }
      enum FULL_BW {
        description "TRS bandwidth is full bandwidth.";
      }
      enum PRB_52 {
        description "TRS bandwidth is 52 PRBs.";
      }
      enum FULL_BW_MUTE {
        description "TRS bandwidth is full bandwidth with muting function.";
      }
    }
  }
  typedef TrsResourceShifting {
    description "Value for configuring trsResourceShifting.";
    type enumeration {
      enum DEACTIVATED {
        description "TRS is not shifted. All cells use the same TRS resource position and PDSCH can be multiplexed in TRS symbols.";
      }
      enum ACTIVATED {
        description "TRS resource shifting is activated with no multiplexing of PDSCH in TRS symbols.";
      }
    }
  }
  typedef TxDirection {
    description "Transmission direction.";
    type enumeration {
      enum DL_AND_UL {
        description "Supports both downlink and uplink.";
      }
      enum DL {
        description "Supports downlink only.";
      }
    }
  }
  typedef TxPowerState {
    description "DL output power state.";
    type enumeration {
      enum INVALID {
        description "DL output power state is not available.";
      }
      enum STABLE {
        description "DL output power is stable.";
      }
      enum CHANGING {
        description "DL output power changes to reach txPowerRatio.";
      }
    }
  }
  typedef UeAdaptiveRlcRetxMode {
    description "Operation mode for service-adaptive RLC poll retransmission.";
    type enumeration {
      enum ENABLED {
        description "Service-adaptive RLC poll retransmission enabled.";
      }
      enum DISABLED {
        description "Service-adaptive RLC poll retransmission disabled.";
      }
    }
  }
  typedef UeAmbrMethod {
    description "UE AMBR method for limiting UEs.";
    type enumeration {
      enum __UNDEFINED__ {
      }
    }
  }
  typedef UeAmbrRestRateType {
    description "UE AMBR restricted rate source.";
    type enumeration {
      enum __UNDEFINED__ {
      }
    }
  }
  typedef UeAssistedPrecodingOptStatus {
    description "Status of the NR Assisted Precoding Optimization UE.";
    type enumeration {
      enum INACTIVE {
        description "Feature is not active.";
      }
      enum ACTIVE_NO_UPDATE {
        description "Feature is active, but no change in status.";
      }
      enum ACTIVE_FAILED {
        description "Feature is active, but configuration failed.";
      }
      enum ACTIVE_CALIBRATED {
        description "Feature is active, calibrated and estimation results are within preset limit.";
      }
      enum ACTIVE_CALIBRATED_UPDATING {
        description "Feature is active, calibrated and estimation results are out of preset limit.";
      }
    }
  }
  typedef UeConfGroupType {
    description "UE configuration group type.";
    type enumeration {
      enum UE_MOBILITY_GROUP {
        description "UE mobility group. Defined by UeMobilityGroupDefinition MO class.";
      }
      enum UE_SERVICE_GROUP {
        description "UE service group. Defined by UeServiceGroupDefinition MO class.";
      }
      enum UE_ADMISSION_GROUP {
        description "UE admission group. Defined by UeAdmissionGroupDefinition MO class.";
      }
    }
  }
  typedef UeSpecificDrxMode {
    description "Mode of UE specific DRX.";
    type enumeration {
      enum ENABLED {
        description "UE specific DRX is enabled.";
      }
      enum DISABLED {
        description "UE specific DRX is disabled.";
      }
    }
  }
  typedef UlCaTimeAlignmentMode {
    description "Timing advance offset selection mode in Low-Band cells.";
    type enumeration {
      enum N_TA_O_STANDARD {
        description "Configure N_TA offset according to NRCellDU::nrLteCoexistence description.";
      }
      enum N_TA_O_39936 {
        description "Configure N_TA offset to 39936 x T_c.";
      }
    }
  }
  typedef UlCalibrationMethod {
    description "Describes which types of uplink antenna calibration are supported and/or used.";
    type enumeration {
      enum NONE {
        description "No antenna calibration method.";
      }
      enum INTERNAL {
        description "Internal antenna calibration method.";
      }
    }
  }
  typedef UlCalibrationStatus {
    description "Describes the current uplink antenna calibration status.";
    type enumeration {
      enum INACTIVE {
        description "Uplink antenna calibration is not activated.";
      }
      enum CONVERGING {
        description "Uplink antenna calibration is converging.";
      }
      enum CALIBRATED {
        description "Uplink antenna calibration is finished with success.";
      }
      enum FAILED {
        description "Uplink antenna calibration has failed.";
      }
    }
  }
  typedef UlPacketPredictionMode {
    description "Packet prediction mode for uplink service.";
    type enumeration {
      enum DEACTIVATED {
        description "No packet prediction for current uplink service.";
      }
      enum BASIC {
        description "Packet prediction based on current uplink service definition.";
      }
    }
  }
  typedef UlPimCancellationMode {
    description "PIM cancellation mode on uplink carriers.";
    type enumeration {
      enum EXCLUDED {
        description "Excludes uplink carriers from PIM cancellation calculations.";
      }
      enum DEACTIVATED {
        description "Deactivates PIM cancellation for uplink carriers.";
      }
      enum ACTIVATED {
        description "Activates PIM cancellation for uplink carriers.";
      }
    }
  }
  typedef UlPortLayerSwitchMetric {
    description "Uplink quality metric used for FR1 port and layer switching functions.";
    type enumeration {
      enum UL_WB_SINR {
        description "Wideband SINR. Calculated based on UE reported transmitting power and scheduled PRB including current Outer Loop Adjustment (OLA) factor.";
      }
      enum UL_SINR_MAX {
        description "Maximum achievable SINR with only 1 PRB scheduled and UE at maximum power.";
      }
      enum UL_SINR_MIN {
        description "Minimum achievable SINR with full bandwidth PRB scheduled and UE at maximum power.";
      }
    }
  }
  typedef UlPortSwitchFr1Mode {
    description "Port switch mode.";
    type enumeration {
      enum PORT_FIXED_PC_DIFF {
        description "Uplink port number is fixed. Only uplink two ports are used for power class PC2 and PC3. Only uplink one port is used for power class PC1_5.";
      }
      enum PORT_SWITCHED {
        description "Uplink port number is switched. Uplink one port is used for power classes PC1_5, PC2, and PC3 from the start. Uplink port is switched between one port and two ports for power classes PC1_5, PC2, and PC3.";
      }
      enum PORT_SWITCHED_ONLY_PC1_5 {
        description "Uplink port number is switched for power class PC1_5 only. Uplink port is switched between one port and two ports for power class PC1_5 only. Only uplink two ports are used for power class PC2 and PC3.";
      }
      enum PORT_SWITCHED_INIT_2_PORT {
        description "Uplink port number is switched. If UE has two ports, uplink two ports is used for power classes PC1_5, PC2, and PC3 from the start. Uplink port switching is allowed between one port and two ports for power classes PC1_5, PC2, and PC3.";
      }
    }
  }
  typedef UlWfSwitchFr1Mode {
    description "Uplink waveform switch mode.";
    type enumeration {
      enum CP_OFDM_NOSWITCH {
        description "Uplink waveform is CP-OFDM. Waveform switch is not allowed.";
      }
      enum DFTS_OFDM_NOSWITCH {
        description "Uplink waveform is DFT-s-OFDM. Waveform switch is not allowed.";
      }
      enum WAVEFORM_SWITCH {
        description "Waveform switch is allowed between DFT-s-OFDM and CP-OFDM.";
      }
    }
  }
  typedef WeightOffset {
    description "Initial domain weight.";
    type enumeration {
      enum ZERO {
        description "No weight offset.";
      }
      enum LOW {
        description "Low weight offset.";
      }
      enum MEDIUM {
        description "Medium weight offset.";
      }
      enum HIGH {
        description "High weight offset.";
      }
    }
  }
  grouping AzimuthNull-struct {
    description "Characteristics of spatial null in azimuth.";
    leaf frequency {
      description "range 0..6000000; Default value: 0.";
      type int32 {
        range "0..6000000";
      }
      default "0";
      units "kHz";
    }
    leaf horizontalAngle {
      description "range -90..90.";
      type int32 {
        range "-90..90";
      }
      units "degree";
    }
    leaf nullWidth {
      type enumeration {
        enum NARROW;
        enum MEDIUM;
        enum WIDE;
      }
    }
    leaf verticalAngle {
      description "range -15..15; Default value: 0.";
      type int32 {
        range "-15..15";
      }
      default "0";
      units "degree";
    }
  }
  grouping CsiRsConfig16P-struct {
    description "Container for attributes specific to 16-port CSI-RS configuration. Includes attributes related to the port-to-antenna mapping, and codebook-related parameters including subset restrictions.";
    leaf csiRsControl16Ports {
      type enumeration {
        enum OFF;
        enum EIGHT_ONE_N1AZ;
        enum FOUR_TWO_N1AZ;
        enum FOUR_TWO_N1EL;
      }
    }
    leaf i11Restriction {
      description "length 0..8.";
      type string {
        length "0..8";
        pattern "[0-9A-F]*";
      }
    }
    leaf i12Restriction {
      description "length 0..2.";
      type string {
        length "0..2";
        pattern "[0-9A-F]*";
      }
    }
  }
  grouping CsiRsConfig2P-struct {
    description "Container for attributes specific to 2-port CSI-RS configuration. Attributes related to port-to-antenna mapping and codebook-related parameters including subset restrictions.";
    leaf aRestriction {
      description "length 0..2; Default value: 3F.";
      type string {
        length "0..2";
        pattern "([0-3][0-9A-F])?";
      }
      default "3F";
    }
    leaf csiRsControl2Ports {
      type enumeration {
        enum OFF;
        enum ON;
      }
    }
  }
  grouping CsiRsConfig32P-struct {
    description "Container for attributes specific to 32-port CSI-RS configuration. Includes attributes related to the port-to-antenna mapping, and codebook-related parameters including subset restrictions.";
    leaf csiRsControl32Ports {
      type enumeration {
        enum OFF;
        enum EIGHT_TWO_N1AZ;
        enum FOUR_FOUR;
      }
    }
    leaf i11Restriction {
      description "length 0..8.";
      type string {
        length "0..8";
        pattern "[0-9A-F]*";
      }
    }
    leaf i12Restriction {
      description "length 0..4.";
      type string {
        length "0..4";
        pattern "[0-9A-F]*";
      }
    }
  }
  grouping CsiRsConfig4P-struct {
    description "Container for attributes specific to 4-port CSI-RS configuration. Attributes related to port-to-antenna mapping and codebook-related parameters including subset restrictions.";
    leaf csiRsControl4Ports {
      type enumeration {
        enum OFF;
        enum TWO_ONE;
      }
    }
    leaf i11Restriction {
      description "length 0..2; Default value: FF.";
      type string {
        length "0..2";
        pattern "[0-9A-F]*";
      }
      default "FF";
    }
  }
  grouping CsiRsConfig8P-struct {
    description "Container for attributes specific to 8-port CSI-RS configuration. Includes attributes related to the port-to-antenna mapping, and codebook-related parameters including subset restrictions.";
    leaf csiRsControl8Ports {
      type enumeration {
        enum OFF;
        enum FOUR_ONE_N1AZ;
        enum FOUR_ONE_N1EL;
        enum TWO_TWO;
      }
    }
    leaf i11Restriction {
      description "length 0..4; Default value: FFFF.";
      type string {
        length "0..4";
        pattern "[0-9A-F]*";
      }
      default "FFFF";
    }
    leaf i12Restriction {
      description "length 0..2.";
      type string {
        length "0..2";
        pattern "[0-9A-F]*";
      }
    }
  }
  grouping CustomComBfwWideBeam-struct {
    description "Amplitude and phase for each antenna for custom beamforming weights of downlink common channels.";
    leaf amplitude {
      description "range 0..100.";
      type eytypes:int32_range_0-100-2;
    }
    leaf antennaNo {
      description "range 0..63.";
      type eytypes:int32_range_0-63;
    }
    leaf phase {
      description "range 0..359.";
      type int32 {
        range "0..359";
      }
      units "degree";
    }
  }
  grouping DlCalibrationDataRO-struct {
    description "Downlink antenna calibration information.";
    leaf dlCalibrationActiveMethod {
      type enumeration {
        enum NONE;
        enum INTERNAL;
      }
    }
    leaf dlCalibrationStatus {
      type enumeration {
        enum INACTIVE;
        enum CONVERGING;
        enum CALIBRATED;
        enum FAILED;
      }
    }
    leaf-list dlCalibrationSupportedMethods {
      type DlCalibrationMethod;
      ordered-by user;
      min-elements 0;
      max-elements 2;
    }
  }
  grouping ElevationNull-struct {
    description "Characteristics of spatial null in elevation.";
    leaf frequency {
      description "range 0..6000000; Default value: 0.";
      type int32 {
        range "0..6000000";
      }
      default "0";
      units "kHz";
    }
    leaf nullWidth {
      type enumeration {
        enum NARROW;
        enum MEDIUM;
        enum WIDE;
      }
    }
    leaf verticalAngle {
      description "range -15..15.";
      type int32 {
        range "-15..15";
      }
      units "degree";
    }
  }
  grouping FloorInfo-struct {
    description "Floor number and height above floor level.";
    leaf floorNumber {
      description "range -101..1000.";
      type int32 {
        range "-101..1000";
      }
    }
    leaf heightOfDot {
      description "range -1..500.";
      type int32 {
        range "-1..500";
      }
      units "m";
    }
  }
  grouping FrequencyDomainPara-struct {
    description "Frequency domain configuration parameters for Remote Interference Management Reference Signaling. If parent GNBDUFunction::setIdAllocation is G_NODE_B, all NRCellDU instances are associated to the RimRSGlobal instance. If parent GNBDUFunction::setIdAllocation is CELL, all NRCellDU instances with NRCellDU::rimVictimRSSetRef referencing a RimRSSet instance are associated to its parent RimRSGlobal instance.";
    leaf rimRSBandwidth {
      description "Default value: 48.";
      type int32 {
        range "11 | 24 | 38 | 48 | 96";
      }
      default "48";
      units "PRB";
    }
    leaf rimRSCommonCarrierRefPoint {
      description "range -1..7125000; Default value: -1.";
      type int32 {
        range "-1..7125000";
      }
      default "-1";
      units "kHz";
    }
    leaf-list rimRSStartingFreqOffsetIdList {
      description "Default values sequence: 51,144.";
      type int32 {
        range "0..549";
      }
      min-elements 1;
      max-elements 4;
    }
  }
  grouping LcsToGcsTranslation-struct {
    description "Translation information from Local Coordinate System (LCS) to Global Coordinate System (GCS).";
    leaf alpha {
      description "range 0..3599.";
      type int32 {
        range "0..3599";
      }
      units "degree";
    }
    leaf beta {
      description "range 0..3599.";
      type int32 {
        range "0..3599";
      }
      units "degree";
    }
    leaf gamma {
      description "range 0..3599.";
      type int32 {
        range "0..3599";
      }
      units "degree";
    }
  }
  grouping NRCoverage-struct {
    description "Transmission point coverage area used for UE positioning. Defined by bearing, opening angle and radius.";
    leaf bearing {
      description "range 0..3599.";
      type int32 {
        range "0..3599";
      }
      units "degree";
    }
    leaf openingAngle {
      description "range 0..3599.";
      type int32 {
        range "0..3599";
      }
      units "degree";
    }
    leaf radius {
      description "range 1..100000.";
      type int32 {
        range "1..100000";
      }
      units "m";
    }
  }
  grouping NRPolygonCorner-struct {
    description "Corner of Polygon that models transmission point coverage area.";
    leaf latitude {
      description "range -90000000..90000000.";
      type int32 {
        range "-90000000..90000000";
      }
      units "degree";
    }
    leaf longitude {
      description "range -180000000..180000000.";
      type int32 {
        range "-180000000..180000000";
      }
      units "degree";
    }
  }
  grouping PLMNId-struct {
    description "PLMN Identity consisting of Mobile Country Code (MCC) and Mobile Network Code (MNC).";
    leaf mcc {
      description "length 3..3.";
      type string {
        length "3";
        pattern "[02345679][0-9][0-9]";
      }
    }
    leaf mnc {
      description "length 2..3.";
      type string {
        length "2..3";
        pattern "(([0-9][0-9][0-9])|([0-9][0-9]))";
      }
    }
  }
  grouping PowerBackoffDirThresh-struct {
    description "Threshold per direction in percentage of configuredMaxTxPower.";
    leaf powerBackoffDirThresh1 {
      description "range 0..1000.";
      type eytypes:int32_range_0-1000-10;
    }
    leaf powerBackoffDirThresh2 {
      description "range 0..1000.";
      type eytypes:int32_range_0-1000-10;
    }
    leaf powerBackoffDirThresh3 {
      description "range 0..1000.";
      type eytypes:int32_range_0-1000-10;
    }
    leaf powerBackoffDirThresh4 {
      description "range 0..1000.";
      type eytypes:int32_range_0-1000-10;
    }
    leaf powerBackoffDirThresh5 {
      description "range 0..1000.";
      type eytypes:int32_range_0-1000-10;
    }
    leaf powerBackoffDirThresh6 {
      description "range 0..1000.";
      type eytypes:int32_range_0-1000-10;
    }
    leaf powerBackoffDirThresh7 {
      description "range 0..1000.";
      type eytypes:int32_range_0-1000-10;
    }
    leaf powerBackoffDirThresh8 {
      description "range 0..1000.";
      type eytypes:int32_range_0-1000-10;
    }
  }
  grouping SequenceDomainPara-struct {
    description "Sequence domain configuration parameters for Remote Interference Management Reference Signaling.";
    leaf enableEnoughNotEnoughIndication {
      type enumeration {
        enum DISABLED;
        enum ENABLED;
      }
    }
    leaf-list rimRSScrambleIdListofRS1 {
      description "Default values sequence: 25,138,267,494,576,683,1010,1020.";
      type eytypes:int32_range_0-1023-21;
      min-elements 1;
      max-elements 8;
    }
    leaf-list rimRSScrambleIdListofRS2 {
      description "Default values sequence: 25,138,267,494,576,683,1010,1020.";
      type eytypes:int32_range_0-1023-21;
      min-elements 1;
      max-elements 8;
    }
    leaf rimRSScrambleTimerMultiplier {
      description "range 0..2147483647; Default value: 1.";
      type eytypes:int32_range_0-2147483647;
      default "1";
    }
    leaf rimRSScrambleTimerOffset {
      description "range 0..2147483647; Default value: 0.";
      type eytypes:int32_range_0-2147483647;
      default "0";
    }
  }
  grouping SibType-struct {
    description "Information for SI message acquisition.";
    leaf siBroadcastStatus {
      type enumeration {
        enum BROADCASTING;
      }
    }
    leaf siPeriodicity {
      description "Default value: 64.";
      type int32 {
        range "8 | 16 | 32 | 64 | 128 | 256 | 512";
      }
      default "64";
      units "radio frame";
    }
  }
  grouping SibTypePws-struct {
    description "Information for SI message acquisition.";
    leaf siBroadcastStatus {
      type enumeration {
        enum BROADCASTING;
      }
    }
    leaf siPeriodicity {
      description "Default value: 16.";
      type int32 {
        range "8 | 16 | 32 | 64 | 128 | 256 | 512";
      }
      default "16";
      units "radio frame";
    }
  }
  grouping SibTypeSib9-struct {
    description "Information for SI message acquisition.";
    leaf includeReferenceTimeInfo {
      description "Default value: false.";
      type boolean;
      default "false";
    }
    leaf siBroadcastStatus {
      type enumeration {
        enum BROADCASTING;
      }
    }
    leaf siPeriodicity {
      description "Default value: 64.";
      type int32 {
        range "8 | 16 | 32 | 64 | 128 | 256 | 512";
      }
      default "64";
      units "radio frame";
    }
  }
  grouping SliceSelectionAssistInfo-struct {
    description "Single Network Slice Selection Assistance Information (S-NSSAI).";
    leaf sd {
      description "range 0..16777215.";
      type eytypes:int32_range_0-16777215;
    }
    leaf sst {
      description "range 0..255.";
      type eytypes:int32_range_0-255;
    }
  }
  grouping SlopeInfo-struct {
    description "Slope information for calculation of spectrum shares for Load-based Automated RRP feature.";
    leaf slope {
      description "range 0..1000.";
      type eytypes:int32_range_0-1000-11;
      units "percent";
    }
    leaf startOfRange {
      description "range 0..10000.";
      type int32 {
        range "0..10000";
      }
    }
  }
  grouping SlotSpecificLaConfig-struct {
    description "Slot-specific link adaptation configuration.";
    leaf modulationEnabledList {
      description "length 4..4.";
      type string {
        length "4";
        pattern "[01]*1[01]*";
      }
    }
    leaf outerLoopAdjustDisabled {
      type string;
    }
    leaf rankEnabledList {
      description "length 4..4.";
      type string {
        length "4";
        pattern "[01]*1[01]*";
      }
    }
    leaf sfnOffsetForLaConfig {
      description "range 0..1023.";
      type eytypes:int32_range_0-1023-21;
    }
    leaf sfnPeriodForLaConfig {
      description "range 1..1024.";
      type eytypes:int32_range_1-1024;
    }
    leaf sinrBackoff {
      description "range 0..300.";
      type int32 {
        range "0..300";
      }
      units "dB";
    }
    leaf slotForLaConfig {
      description "range -1..19.";
      type int32 {
        range "-1..19";
      }
    }
  }
  grouping SupportedCoverageOptions-struct {
    description "Coverage options.";
    leaf azimuthCoverageWidth {
      description "range 50..1800.";
      type int32 {
        range "50..1800";
      }
      units "degree";
    }
    leaf elevationCbfTaperTypes {
      description "length 1..100.";
      type string {
        length "1..100";
      }
    }
    leaf elevationCoverageWidth {
      description "range 20..1800.";
      type int32 {
        range "20..1800";
      }
      units "degree";
    }
    leaf panRange {
      description "length 1..100.";
      type string {
        length "1..100";
      }
    }
    leaf tiltRange {
      description "length 1..100.";
      type string {
        length "1..100";
      }
    }
  }
  grouping TimeDomainPara-struct {
    description "Time domain configuration parameters for Remote Interference Management Reference Signaling. If parent GNBDUFunction::setIdAllocation is G_NODE_B, all NRCellDU instances are associated to the RimRSGlobal instance. If parent GNBDUFunction::setIdAllocation is CELL, all NRCellDU instances with NRCellDU::rimVictimRSSetRef referencing a RimRSSet instance are associated to its parent RimRSGlobal instance.";
    leaf dlUlSwitchingPeriod1 {
      type enumeration {
        enum MS0P5;
        enum MS0P625;
        enum MS1;
        enum MS1P25;
        enum MS2;
        enum MS2P5;
        enum MS3;
        enum MS4;
        enum MS5;
        enum MS10;
        enum MS20;
      }
    }
    leaf enablenearfarIndicationRS1 {
      type enumeration {
        enum DISABLED;
        enum ENABLED;
      }
    }
    leaf enablenearfarIndicationRS2 {
      type enumeration {
        enum DISABLED;
        enum ENABLED;
      }
    }
    leaf farSymbolOffsetRS1 {
      description "range 26..28; Default value: 26.";
      type int32 {
        range "26..28";
      }
      default "26";
    }
    leaf farSymbolOffsetRS2 {
      description "range 26..28; Default value: 26.";
      type int32 {
        range "26..28";
      }
      default "26";
    }
    leaf nearOrOnlySymbolOffsetRS1 {
      description "Default value: 6.";
      type int32 {
        range "4 | 6 | 8 | 10";
      }
      default "6";
    }
    leaf nearOrOnlySymbolOffsetRS2 {
      description "Default value: 6.";
      type int32 {
        range "4 | 6 | 8 | 10";
      }
      default "6";
    }
    leaf nrofConsecutiveRIMRS1 {
      description "Default value: 2.";
      type int32 {
        range "1..2 | 4 | 8";
      }
      default "2";
    }
    leaf nrofConsecutiveRIMRS2 {
      description "Default value: 2.";
      type int32 {
        range "1..2 | 4 | 8";
      }
      default "2";
    }
    leaf symbolOffsetOfReferencePoint1 {
      description "Default value: 52.";
      type int32 {
        range "52..54 | 108";
      }
      default "52";
    }
    leaf totalNrOfSetIdOfRS1 {
      description "Default value: 524288.";
      type uint32 {
        range "32768 | 65536 | 131072 | 262144 | 524288 | 1048576 | 2097152 | 4194304";
      }
      default "524288";
    }
    leaf totalNrOfSetIdOfRS2 {
      description "Default value: 524288.";
      type uint32 {
        range "32768 | 65536 | 131072 | 262144 | 524288 | 1048576 | 2097152 | 4194304";
      }
      default "524288";
    }
  }
  grouping UlCalibrationDataRO-struct {
    description "Uplink antenna calibration information.";
    leaf ulCalibrationActiveMethod {
      type enumeration {
        enum NONE;
        enum INTERNAL;
      }
    }
    leaf ulCalibrationStatus {
      type enumeration {
        enum INACTIVE;
        enum CONVERGING;
        enum CALIBRATED;
        enum FAILED;
      }
    }
    leaf-list ulCalibrationSupportedMethods {
      type UlCalibrationMethod;
      ordered-by user;
      min-elements 0;
      max-elements 2;
    }
  }
  grouping AdditionalPLMNInfo-attributes {
    leaf additionalPLMNInfoId {
      description "The value component of the RDN..";
      type string;
      mandatory true;
    }
    leaf cellReservedForOperator {
      description "Whether cell is reserved for operator use..";
      type enumeration {
        enum RESERVED;
        enum NOT_RESERVED;
      }
    }
    leaf nRTAC {
      description "NR Tracking Area Code (TAC). When creating or deleting AdditionalPLMNInfo instance, value of this attribute applies at next cell unlock. Values 0, 16777214, and 16777215 are not broadcast in SIB1. Recommendation is to set NRCellDU::administrativeState to LOCKED in case of configuring or changing both this attribute and pLMNIdList, otherwise they can take effect at different points in time.; range 0..16777215.";
      type eytypes:int32_range_0-16777215;
      mandatory true;
    }
    leaf nRTACInSib1Enabled {
      description "Whether nRTAC can be included in SIB1. If false, nRTAC is excluded from SIB1 and NR cell is not used as a PCell within any of the PLMNs in pLMNIdList. If true and NRCellDU::secondaryCellOnly is false, nRTAC is included in SIB1..";
      type boolean;
    }
    list pLMNIdList {
      key "id";
      leaf id {
        type uint32;
        description "Synthetic key for struct sequence entry.";
      }
      min-elements 1;
      max-elements 12;
      uses PLMNId-struct;
    }
  }
  grouping AdmissionControl-attributes {
    leaf admissionControlId {
      description "The value component of the RDN..";
      type string;
      mandatory true;
    }
    leaf admissionPrioThreshold {
      description "Priority threshold for RRC message prioritization used by Priority-Based Admission Control. Message is prioritized if value of its priority attribute, for example rrcReestablishmentPrio, is lower than or equal to value of this attribute. Only applicable if license for Priority-Based Admission Control is present and feature is active.; range 1..12; Default value: 1.";
      type eytypes:int32_range_1-12;
      default "1";
    }
    leaf pagingPrioThreshold {
      description "Paging priority threshold for RRC message prioritization used by Priority-Based Admission Control. Message is prioritized if value of IE Paging Priority received in NGAP Paging message is lower or equal to value of this attribute. Only applicable if license for Priority-Based Admission Control is present and feature is active..";
      type enumeration {
        enum OFF;
        enum PRIO_LEVEL_1;
        enum PRIO_LEVEL_2;
        enum PRIO_LEVEL_3;
        enum PRIO_LEVEL_4;
        enum PRIO_LEVEL_5;
        enum PRIO_LEVEL_6;
        enum PRIO_LEVEL_7;
        enum PRIO_LEVEL_8;
      }
    }
    leaf rrcEmergencyPrio {
      description "Priority of RRCSetupRequest and RRCResumeRequest with cause emergency. Only applicable if license for Priority-Based Admission Control is present and feature is active.; range 1..12; Default value: 12.";
      type eytypes:int32_range_1-12;
      default "12";
    }
    leaf rrcHighPriorityAccessPrio {
      description "Priority of RRCSetupRequest and RRCResumeRequest with cause highPriorityAccess. Only applicable if license for Priority-Based Admission Control is present and feature is active.; range 1..12; Default value: 12.";
      type eytypes:int32_range_1-12;
      default "12";
    }
    leaf rrcMcsPriorityAccessPrio {
      description "Priority value for RRCSetupRequest and RRCResumeRequest with cause mcs-PriorityAccess. Only applicable if license for Priority-Based Admission Control is present and feature is active.; range 1..12; Default value: 12.";
      type eytypes:int32_range_1-12;
      default "12";
    }
    leaf rrcMoDataPrio {
      description "Priority value for RRCSetupRequest and RRCResumeRequest with cause mo-Data. Only applicable if license for Priority-Based Admission Control is present and feature is active.; range 1..12; Default value: 12.";
      type eytypes:int32_range_1-12;
      default "12";
    }
    leaf rrcMoSignalingPrio {
      description "Priority value for RRCSetupRequest and RRCResumeRequest with cause mo-Signalling. Only applicable if license for Priority-Based Admission Control is present and feature is active.; range 1..12; Default value: 12.";
      type eytypes:int32_range_1-12;
      default "12";
    }
    leaf rrcMoSmsPrio {
      description "Priority value for RRCSetupRequest and RRCResumeRequest with cause mo-SMS. Only applicable if license for Priority-Based Admission Control is present and feature is active.; range 1..12; Default value: 12.";
      type eytypes:int32_range_1-12;
      default "12";
    }
    leaf rrcMoVideoCallPrio {
      description "Priority value for RRCSetupRequest and RRCResumeRequest with cause mo-VideoCall. Only applicable if license for Priority-Based Admission Control is present and feature is active.; range 1..12; Default value: 12.";
      type eytypes:int32_range_1-12;
      default "12";
    }
    leaf rrcMoVoiceCallPrio {
      description "Priority value for RRCSetupRequest and RRCResumeRequest with cause mo-VoiceCall. Only applicable if license for Priority-Based Admission Control is present and feature is active.; range 1..12; Default value: 12.";
      type eytypes:int32_range_1-12;
      default "12";
    }
    leaf rrcMpsPriorityAccessPrio {
      description "Priority value for RRCSetupRequest and RRCResumeRequest with cause mps-PriorityAccess. Only applicable if license for Priority-Based Admission Control is present and feature is active.; range 1..12; Default value: 12.";
      type eytypes:int32_range_1-12;
      default "12";
    }
    leaf rrcMtAccessPrio {
      description "Priority value for RRCSetupRequest and RRCResumeRequest with cause mt-Access. Only applicable if license for Priority-Based Admission Control is present and feature is active.; range 1..12; Default value: 12.";
      type eytypes:int32_range_1-12;
      default "12";
    }
    leaf rrcReestablishmentPrio {
      description "Priority of RRCReestablishmentRequest. Only applicable if license for Priority-Based Admission Control is present and feature is active.; range 1..12; Default value: 1.";
      type eytypes:int32_range_1-12;
      default "1";
    }
    leaf rrcRnaUpdatePrio {
      description "Priority value for RRCResumeRequest with cause rna-Update. Only applicable if license for Priority-Based Admission Control is present and feature is active.; range 1..12; Default value: 12.";
      type eytypes:int32_range_1-12;
      default "12";
    }
  }
  grouping Aes-attributes {
    leaf aesEnabled {
      description "Whether Automated Energy Saver feature is enabled.; Default value: false.";
      type boolean;
      default "false";
    }
    leaf aesId {
      description "The value component of the RDN..";
      type string;
      mandatory true;
    }
    leaf targetUeDlThroughput {
      description "Target downlink throughput for Automated Energy Saver feature.; Default value: 30.";
      type int32 {
        range "5 | 10 | 15 | 20 | 30 | 50 | 70 | 100 | 150 | 200 | 300 | 500";
      }
      default "30";
      units "Mbps";
    }
    leaf targetUeRatio {
      description "Target ratio of UEs that satisfy target downlink throughput.; range 1..100; Default value: 70.";
      type eytypes:int32_range_1-100;
      default "70";
      units "percent";
    }
  }
  grouping AesMMimoSleep-attributes {
    leaf aesActive {
      description "Whether Automated Energy Saver feature is running. Value is true during period configured in MMimoSleepTimeWindow instance under MMimoSleeptimeGroup instance referenced from NRSectorCarrier instance. Only applicable if license for Automated Energy Saver is present and feature is active. Otherwise always false..";
      type boolean;
      config false;
    }
    leaf aesMMimoSleepId {
      description "The value component of the RDN..";
      type string;
      mandatory true;
    }
    leaf switchDownPrbThreshDl {
      description "Down-switching downlink PRB usage TxMute threshold used by Automated Energy Saver feature. Overrides MMimoSleepProfile::switchDownPrbThreshDl. Empty when aesActive is false.; range 0..100.";
      type eytypes:int32_range_0-100;
      config false;
      units "percent";
    }
    leaf switchDownRrcConnThresh {
      description "Down-switching RRC connections TxMute threshold used by Automated Energy Saver feature. Overrides MMimoSleepProfile::switchDownRrcConnThresh. Empty when aesActive is false.; range 0..5000.";
      type eytypes:int32_range_0-5000;
      config false;
    }
    leaf switchUpPrbThreshDl {
      description "Up-switching downlink PRB usage TxMute threshold used by Automated Energy Saver feature. Overrides MMimoSleepProfile::switchUpPrbThreshDl. Empty when aesActive is false.; range 0..100.";
      type eytypes:int32_range_0-100;
      config false;
      units "percent";
    }
    leaf switchUpRrcConnThresh {
      description "Up-switching RRC connections TxMute threshold used by Automated Energy Saver feature. Overrides MMimoSleepProfile::switchUpRrcConnThresh. Empty when aesActive is false.; range 0..5000.";
      type eytypes:int32_range_0-5000;
      config false;
    }
  }
  grouping AqmCfg-attributes {
    leaf aqmCfgId {
      description "The value component of the RDN..";
      type string;
      mandatory true;
    }
    leaf aqmMode {
      description "Active Queue Management mode. If DU5qi::profile5qi is 1, 65, or 66, recommendation is MODE2. If DU5qi::profile5qi is 5 or 69 recommendation is OFF. If DU5qi::profile5qi is anything else recommendation is MODE1..";
      type enumeration {
        enum OFF;
        enum MODE1;
        enum MODE2;
      }
    }
    leaf estimatedE2ERTT {
      description "Estimated end-to-end Round-Trip Time (RTT). Only applicable when aqmMode is MODE1.; range 0..1023; Default value: 50.";
      type eytypes:int32_range_0-1023;
      default "50";
      units "ms";
    }
    leaf-list reservedBy {
      description "Contains a list of MO instances that reserve this MO instance..";
      type string;
      min-elements 0;
    }
    leaf tDiscardDl {
      description "Packet age threshold for downlink packet discard. Downlink packets older than this threshold are discarded. Only applicable when aqmMode is MODE2.; range 0..2046; Default value: 200.";
      type int32 {
        range "0..2046";
      }
      default "200";
      units "ms";
    }
    leaf userLabel {
      description "Label for free use..";
      type string;
    }
  }
  grouping AutomatedQos-attributes {
    leaf automatedQosId {
      description "The value component of the RDN..";
      type string;
      mandatory true;
    }
  }
  grouping Beam-attributes {
    leaf beamId {
      description "The value component of the RDN..";
      type string;
      mandatory true;
    }
    leaf wideBeamIndex {
      description "Wide beam index representing logical beam index. Range is between 1 and number of supported wide beams. Only applicable to High-Band sector carriers..";
      type int32;
      config false;
    }
    leaf-list pmRadioSsbRsrpDistr {
      description "Distribution of RSRP values for each wide beam. Unit: N/A Ranges: Bin[0]: [..-140] dBm Bin[1]: [-139..-138] dBm Bin[2]: [-137..-136] dBm Bin[3]: [-135..-134] dBm Bin[4]: [-133..-132] dBm Bin[5]: [-131..-130] dBm Bin[6]: [-129..-128] dBm Bin[7]: [-127..-126] dBm Bin[8]: [-125..-124] dBm Bin[9]: [-123..-122] dBm Bin[10]: [-121..-120] dBm Bin[11]: [-119..-118] dBm Bin[12]: [-117..-116] dBm Bin[13]: [-115..-114] dBm Bin[14]: [-113..-112] dBm Bin[15]: [-111..-110] dBm Bin[16]: [-109..-108] dBm Bin[17]: [-107..-106] dBm Bin[18]: [-105..-104] dBm Bin[19]: [-103..-102] dBm Bin[20]: [-101..-100] dBm Bin[21]: [-99..-98] dBm Bin[22]: [-97..-96] dBm Bin[23]: [-95..-94] dBm Bin[24]: [-93..-92] dBm Bin[25]: [-91..-90] dBm Bin[26]: [-89..-88] dBm Bin[27]: [-87..-86] dBm Bin[28]: [-85..-84] dBm Bin[29]: [-83..-82] dBm Bin[30]: [-81..-80] dBm Bin[31]: [-79..-78] dBm Bin[32]: [-77..-76] dBm Bin[33]: [-75..-74] dBm Bin[34]: [-73..-72] dBm Bin[35]: [-71..-70] dBm Bin[36]: [-69..-68] dBm Bin[37]: [-67..-66] dBm Bin[38]: [-65..-64] dBm Bin[39]: [-63..-62] dBm Bin[40]: [-61..-60] dBm Bin[41]: [-59..-58] dBm Bin[42]: [-57..-56] dBm Bin[43]: [-55..-54] dBm Bin[44]: [-53..-52] dBm Bin[45]: [-51..-50] dBm Bin[46]: [-49..-48] dBm Bin[47]: [-47..-46] dBm Bin[48]: [-45..] dBm.";
      type uint64;
      max-elements 49;
    }
    leaf-list pmRadioSsbSinrPuschDistr {
      description "Distribution of SINR values calculated for PUSCH transmission for each wide beam. Unit: N/A Ranges: Bin[0]: [..-5] dB Bin[1]: ]-5..-2] dB Bin[2]: ]-2..1] dB Bin[3]: ]1..4] dB Bin[4]: ]4..7] dB Bin[5]: ]7..10] dB Bin[6]: ]10..13] dB Bin[7]: ]13..16] dB Bin[8]: ]16..19] dB Bin[9]: ]19..22] dB Bin[10]: ]22..25] dB Bin[11]: ]25..] dB.";
      type uint64;
      max-elements 12;
    }
    leaf pmRadioRaCbFailMsg1Ooc {
      description "Number of CBRA preambles discarded because timing offset corresponds to a greater distance than configured cell range. Unit: N/A.";
      type uint64;
      config false;
    }
    leaf-list pmRadioSsbSinrPucchF0Distr {
      description "Distribution of SINR values calculated for PUCCH transmission for each wide beam for format 0. Unit: N/A Ranges: Bin[0]: [..-15] dB Bin[1]: ]-15..-12] dB Bin[2]: ]-12..-9] dB Bin[3]: ]-9..-6] dB Bin[4]: ]-6..-3] dB Bin[5]: ]-3..0] dB Bin[6]: ]0..3] dB Bin[7]: ]3..6] dB Bin[8]: ]6..9] dB Bin[9]: ]9..] dB.";
      type uint64;
      max-elements 10;
    }
    leaf-list pmRadioRaAttTaDistr {
      description "Distribution of measured Timing Advance (TA) values from all detected random access attempts. TA values are expressed as percentage of maximum possible TA value in cell. Unit: N/A Ranges: Bin[0]: [0..9] % Bin[1]: [10..19] % Bin[2]: [20..29] % Bin[3]: [30..39] % Bin[4]: [40..49] % Bin[5]: [50..59] % Bin[6]: [60..69] % Bin[7]: [70..79] % Bin[8]: [80..89] % Bin[9]: [90..99] % Bin[10]: [100..109] % Bin[11]: [110..] %.";
      type uint64;
      max-elements 12;
    }
    leaf-list pmRadioSsbSinrPucchF2Distr {
      description "Distribution of SINR values calculated for PUCCH transmission for each wide beam for format 2. Unit: N/A Ranges: Bin[0]: [..-15] dB Bin[1]: ]-15..-12] dB Bin[2]: ]-12..-9] dB Bin[3]: ]-9..-6] dB Bin[4]: ]-6..-3] dB Bin[5]: ]-3..0] dB Bin[6]: ]0..3] dB Bin[7]: ]3..6] dB Bin[8]: ]6..9] dB Bin[9]: ]9..] dB.";
      type uint64;
      max-elements 10;
    }
    leaf-list pmRadioEirpDlDistr {
      description "Measures downlink Effective Isotropic Radiated Power (EIRP) in each beam direction. Distributes time-averaged values of EIRP in each beam direction relative to maximum transmission power for sectorCarrier. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
  }
  grouping Bsr-attributes {
    leaf bsrId {
      description "The value component of the RDN..";
      type string;
      mandatory true;
    }
  }
  grouping BsrUeCfg-attributes {
    leaf bsrUeCfgId {
      description "The value component of the RDN..";
      type string;
      mandatory true;
    }
    leaf-list reservedBy {
      description "Contains a list of MO instances that reserve this MO instance..";
      type string;
      min-elements 0;
    }
    leaf reTxBsrTimer {
      description "Number of subframes until new buffer status report is allowed.; Default value: 1280.";
      type int32 {
        range "10 | 20 | 40 | 80 | 160 | 320 | 640 | 1280 | 2560 | 5120 | 10240";
      }
      default "1280";
      units "subframe";
    }
    leaf srDelayTimer {
      description "Delay timer for scheduling request transmission. RRC parameter logicalChannelSR-DelayTimer is defined in 3GPP TS 38.331.; Default value: 40.";
      type int32 {
        range "20 | 40 | 64 | 128 | 512 | 1024 | 2560";
      }
      default "40";
      units "subframe";
    }
    leaf srGrantSize {
      description "Minimum size of DCI grant triggered by reception of a Scheduling Request on PUCCH. Used when UlService::ulServicePacketSize is -1. Only applicable to Low-Band and Mid-Band cells.; range 8..8000; Default value: 32.";
      type int32 {
        range "8..8000";
      }
      default "32";
      units "bit";
    }
    leaf srGrantSizeMode {
      description "Mode for calculation of DCI grant size triggered by reception of a Scheduling Request. Affects srGrantSize value based on estimated uplink PRB usage. Used when UlService::ulServicePacketSize is -1. Only applicable if license for NR Adaptive Uplink Grant Size is present and feature is active. Otherwise handled as default. Only applicable to Low-Band and Mid-Band cells..";
      type enumeration {
        enum STATIC;
        enum ADAPTIVE;
      }
    }
    leaf srGrantSizeOpt {
      description "Optimization for DCI grant size triggered by reception of a Scheduling Request. Affects uplink PRB usage for Scheduling Request triggered grants. Used when UlService::ulServicePacketSize is -1. Only applicable if license for NR Adaptive Uplink Grant Size is present and feature is active. Otherwise handled as default. Only applicable to Low-Band and Mid-Band cells..";
      type enumeration {
        enum THROUGHPUT_OPTIMIZED;
        enum BALANCED;
        enum RESOURCE_OPTIMIZED;
      }
    }
  }
  grouping BWP-attributes {
    leaf bwpContext {
      description "Transmission direction of BWP..";
      type enumeration {
        enum DOWNLINK;
        enum UPLINK;
      }
    }
    leaf bWPId {
      description "The value component of the RDN..";
      type string;
      mandatory true;
    }
    leaf isInitialBwp {
      description "Whether initial or regular BWP is used.; Default value: true.";
      type boolean;
      default "true";
    }
    leaf numberOfRBs {
      description "Number of PRBs for a given BWP. For FDD cell, following values are allowed: * 106: BWP bandwidth is 20 MHz * 133: BWP bandwidth is 25 MHz * 160: BWP bandwidth is 30 MHz * 188: BWP bandwidth is 35 MHz * 216: BWP bandwidth is 40 MHz * 270: BWP bandwidth is 50 MHz For TDD cell, following values are allowed: * 51: BWP bandwidth is 20 MHz * 78: BWP bandwidth is 30 MHz * 106: BWP bandwidth is 40 MHz * 133: BWP bandwidth is 50 MHz * 162: BWP bandwidth is 60 MHz * 189: BWP bandwidth is 70 MHz * 217: BWP bandwidth is 80 MHz * 245: BWP bandwidth is 90 MHz * 273: BWP bandwidth is 100 MHz; range 24..275; Default value: 106.";
      type int32 {
        range "24..275";
      }
      default "106";
      units "PRB";
    }
    leaf-list reservedBy {
      description "Contains a list of MO instances that reserve this MO instance..";
      type string;
      min-elements 0;
    }
    leaf startRB {
      description "Offset to CRB 0 for applicable subcarrier spacing for a given BWP. All BWP instances, which are defined less than NRSectorCarrier bandwidth, must be configured with same value. TDD cell: For a BWP instance, placement must be at low end of band (value 0) or at position compatible with NR Flexible Channel Bandwidth configuration. FDD cell: For a BWP instance, that is defined less than NRSectorCarrier bandwidth, placement must be at low end of band (value 0) or at high end of the band, with value depending on cell BW size: * 24: BWP bandwidth is 25 MHz * 48: BWP bandwidth is 30 MHz * 72: BWP bandwidth is 35 MHz * 96: BWP bandwidth is 40 MHz * 144: BWP bandwidth is 50 MHz For a BWP instance, that is defined equal to NRSectorCarrier bandwidth, placement must be at low end of band (value 0).; range 0..275; Default value: 0.";
      type int32 {
        range "0..275";
      }
      default "0";
      units "PRB";
    }
    leaf userLabel {
      description "Label for free use..";
      type string;
    }
  }
  grouping BWPSet-attributes {
    leaf-list allBWPRegularRef {
      description "References to instances of BWP MO. If non-empty at cell unlock, channel bandwidths from referenced MO instances are used. If empty at cell unlock, and NR Reduced UE Bandwidth Support or NR Dynamic Power Optimizer feature is active, and cell has this MO instance configured in bWPSetRef, then Inconsistency Configuration alarm is raised..";
      type string;
      ordered-by user;
      min-elements 0;
      max-elements 16;
    }
    leaf bwpSetContext {
      description "Transmission direction of BWP set..";
      type enumeration {
        enum DL_AND_UL;
        enum DL;
      }
    }
    leaf bWPSetId {
      description "The value component of the RDN..";
      type string;
      mandatory true;
    }
    leaf-list reservedBy {
      description "Contains a list of MO instances that reserve this MO instance..";
      type string;
      min-elements 0;
    }
    leaf startBWPDlRef {
      description "Reference to an instance of BWP MO. Reference to regular BWP for downlink used until UE Capability Information is received at gNodeB. If non-empty at cell unlock, channel bandwidth from referenced MO instance is used. If empty at cell unlock, and NR Reduced UE Bandwidth Support or NR Dynamic Power Optimizer feature is active, and cell has this MO instance configured in bWPSetRef, then Inconsistency Configuration alarm is raised..";
      type string;
    }
    leaf startBWPUlRef {
      description "Reference to an instance of BWP MO. Reference to regular BWP for uplink used until UE Capability Information is received at gNodeB. If non-empty at cell unlock, channel bandwidth from referenced MO instance is used. If empty at cell unlock, and NR Reduced UE Bandwidth Support or NR Dynamic Power Optimizer feature is active, and cell has this MO instance configured in bWPSetRef, then Inconsistency Configuration alarm is raised..";
      type string;
    }
    leaf ueConfGroupType {
      description "UE configuration group type. UE configuration group type that is applied in contained BWPSetUeCfg instances..";
      type enumeration {
        enum UE_MOBILITY_GROUP;
        enum UE_SERVICE_GROUP;
        enum UE_ADMISSION_GROUP;
      }
    }
    leaf userLabel {
      description "Label for free use..";
      type string;
    }
  }
  grouping BWPSetCfg-attributes {
    leaf bWPDlRef {
      description "Reference to an instance of BWP MO. Reference to a BWP configured for downlink..";
      type string;
      mandatory true;
    }
    leaf bWPSetCfgId {
      description "The value component of the RDN..";
      type string;
      mandatory true;
    }
    leaf bWPUlRef {
      description "Reference to an instance of BWP MO. Reference to a BWP configured for uplink. If empty, no BWP is configured for uplink of this MO instance..";
      type string;
    }
    leaf dynPowerOptRef {
      description "Reference to an instance of DynPowerOpt MO. UE power saving settings for feature NR Dynamic Power Optimizer. Only applicable if license for feature NR Dynamic Power Optimizer is present and feature is active. Configuration is not allowed in EN-DC, ESS, FDD, FR2 cells and TDD cells narrower than 40 MHz. Other tddUlDlPattern values than TDD_ULDL_PATTERN_01, TDD_ULDL_PATTERN_02, TDD_ULDL_PATTERN_03 and TDD_ULDL_PATTERN_04 are not supported. If empty, NR Dynamic Power Optimizer is inactive for this MO instance..";
      type string;
    }
    leaf userLabel {
      description "Label for free use..";
      type string;
    }
  }
  grouping BWPSetUeCfg-attributes {
    leaf bWPSetUeCfgId {
      description "The value component of the RDN..";
      type string;
      mandatory true;
    }
    leaf bwpSwitchingFilterRelaxation {
      description "Relaxation of Bandwidth Part (BWP) switching filter algorithm. If false, BWP switching is only applied for UEs reporting capability support for BWP switching and capability AccessStratumRelease greater than Rel15. If true, BWP switching is also applied for Rel15 UEs in a configured UE group reporting capability support for BWP switching.; Default value: false.";
      type boolean;
      default "false";
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping CardinalityLimits-attributes {
    leaf cardinalityLimitsId {
      description "The value component of the RDN..";
      type string;
      mandatory true;
    }
    leaf maxNRCellDU {
      description "Maximum number of NRCellDU instances that can be created in current deployment..";
      type int32;
      config false;
    }
    leaf maxNRSectorCarrier {
      description "Maximum number of NRSectorCarrier instances that can be created in current deployment..";
      type int32;
      config false;
    }
    leaf noOfNRCellDU {
      description "Maximum number of NRCellDU instances that can be created in current deployment..";
      type int32;
      config false;
    }
    leaf noOfNRSectorCarrier {
      description "Maximum number of NRSectorCarrier instances that can be created in current deployment..";
      type int32;
      config false;
    }
  }
  grouping CaSCellHandling-attributes {
    leaf caSCellHandlingId {
      description "The value component of the RDN..";
      type string;
      mandatory true;
    }
    leaf-list reservedBy {
      description "Contains a list of MO instances that reserve this MO instance..";
      type string;
      min-elements 0;
    }
    leaf ueConfGroupType {
      description "UE configuration group type. UE configuration group type that is applied in contained CaSCellHandlingUeCfg instances..";
      type enumeration {
        enum UE_MOBILITY_GROUP;
        enum UE_SERVICE_GROUP;
        enum UE_ADMISSION_GROUP;
      }
    }
  }
  grouping CaSCellHandlingUeCfg-attributes {
    leaf caSCellHandlingUeCfgId {
      description "The value component of the RDN..";
      type string;
      mandatory true;
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf sCellActDeactDataThres {
      description "SpCell-specific buffer based SCell activation threshold value. One or more SCells can be activated if number of downlink slots required to transmit all bits in UE queues is higher than sCellActDeactDataThres. When deciding SCell activation, minimum number of downlink slots needed to transmit all bits is calculated as number of bits in all priority queues, divided by number of bits that can be transmitted in one downlink slot by SpCell. If -1, data-triggered activation condition is always satisfied even with no data in buffer, and also that data-triggered deactivation condition is never satisfied.; range -1..5000; Default value: -1.";
      type int32 {
        range "-1..5000";
      }
      default "-1";
      units "slot";
    }
    leaf sCellActDeactDataThresHyst {
      description "SpCell-specific buffer based SCell deactivation threshold hysteresis value. One or more SCells can be deactivated if number of downlink slots required to transmit bits in UE queues is less than or equal to sCellActDeactDataThres minus value of this attribute. Minimum number of downlink slots needed to transmit all bits is calculated as number of bits in all priority queues, divided by number of bits that can be transmitted in one downlink slot by SpCell. If sCellActDeactDataThres is -1, data-triggered deactivation condition is never satisfied and value of this attribute is ignored.; range 0..5000; Default value: 90.";
      type int32 {
        range "0..5000";
      }
      default "90";
      units "slot";
    }
    leaf sCellActDeactUlDataThresh {
      description "Threshold for SpCell-specific buffer-based SCell activation in uplink. If number of uplink slots needed to transmit all bits for UE is higher than sCellActDeactUlDataThresh, one or more SCells can be activated. Number of uplink slots needed to transmit all bits is calculated as total number of bits in all priority queues divided by number of bits that can be transmitted in one uplink slot by SpCell. If -1, data-triggered activation condition is always fulfilled, even with no data in uplink buffer. This value means that data-triggered deactivation condition is never fulfilled.; range -1..5000; Default value: 100.";
      type int32 {
        range "-1..5000";
      }
      default "100";
      units "slot";
    }
    leaf sCellActDeactUlDataThreshHyst {
      description "Hysteresis of threshold for SpCell-specific buffer-based SCell deactivation in uplink. If number of uplink slots needed to transmit all bits is less than sCellActDeactUlDataThresh minus value of this attribute, one or more SCells can be deactivated. Number of uplink slots needed to transmit all bits is calculated as total number of bits in all priority queues divided by number of bits that can be transmitted in one uplink slot by SpCell. If sCellActDeactUlDataThresh is -1, data-triggered deactivation condition is never fulfilled and value of this attribute is ignored.; range 0..5000; Default value: 90.";
      type int32 {
        range "0..5000";
      }
      default "90";
      units "slot";
    }
    leaf sCellActProhibitTimer {
      description "Activation prohibit timer. No new SCell activation is allowed while this timer is running.; range 0..5000; Default value: 10.";
      type eytypes:int32_range_0-5000-4;
      default "10";
      units "ms";
    }
    leaf sCellDeactDelayTimer {
      description "SpCell specific buffer based SCell deactivation time control. One or more SCells are deactivated if time to transmit bits in queues is less than or equal to sCellActDeactDataThres minus sCellActDeactDataThresHyst for a duration of sCellDeactDelayTimer.; range 0..5000; Default value: 400.";
      type eytypes:int32_range_0-5000-4;
      default "400";
      units "ms";
    }
    leaf sCellDeactProhibitTimer {
      description "Deactivation prohibit timer. No new SCell deactivation is allowed while this timer is running.; range 0..5000; Default value: 500.";
      type eytypes:int32_range_0-5000-4;
      default "500";
      units "ms";
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 16;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping CellPortionRd-attributes {
    leaf altitude {
      description "Antenna altitude. Positive value for height and negative value for depth..";
      type int32;
      config false;
      units "m";
    }
    leaf cellPortionRdId {
      description "The value component of the RDN..";
      type string;
      mandatory true;
    }
    leaf fieldReplaceableUnitRef {
      description "Reference to an instance of FieldReplaceableUnit MO. Reference represents a Radio Dot..";
      type string;
      config false;
    }
    list floorInformation {
      config false;
      description "Floor number and height above floor level..";
      uses FloorInfo-struct;
    }
    leaf latitude {
      description "Antenna latitude..";
      type int32;
      config false;
      units "degree";
    }
    leaf longitude {
      description "Antenna longitude..";
      type int32;
      config false;
      units "degree";
    }
    leaf nrppaCellPortionId {
      description "NRPPa Cell Portion ID..";
      type int32;
      config false;
    }
    list radioDotCoverage {
      config false;
      description "Coverage area used for UE positioning. Cell portion coverage is defined by bearing, opening angle, and radius..";
      uses NRCoverage-struct;
    }
  }
  grouping CellPriorityShift-attributes {
    leaf cellDlDrbPriorityLimitBase {
      description "Cell scale of downlink spectrum resource limit in rate-controlled scheduling. The lower the value, the less spectrum resources can be utilized by rate-controlled UE within cell.; range 1..100; Default value: 100.";
      type eytypes:int32_range_1-100-3;
      default "100";
    }
    leaf cellDlElevationTime {
      description "Time since last scheduling or data arrival in buffer when a priority upshift occurs. Used for elevation time operation for downlink.; range 10..45; Default value: 20.";
      type int32 {
        range "10..45";
      }
      default "20";
      units "ms";
    }
    leaf cellDlMaxWaitingTime {
      description "Time since last scheduling or data arrival in buffer when a priority upshift occurs. Used for maximum waiting time operation for downlink if value is larger than 0.; Default value: 0.";
      type int32 {
        range "0 | 200 | 210 | 220 | 230 | 240 | 250 | 260 | 270 | 280 | 290 | 300 | 310 | 320 | 330 | 340 | 350 | 360 | 370 | 380 | 390 | 400 | 410 | 420 | 430 | 440 | 450 | 460 | 470 | 480 | 490 | 500 | 510 | 520 | 530 | 540 | 550 | 560 | 570 | 580 | 590 | 600 | 610 | 620 | 630 | 640 | 650 | 660 | 670 | 680 | 690 | 700 | 710 | 720 | 730 | 740 | 750 | 760 | 770 | 780 | 790 | 800 | 810 | 820 | 830 | 840 | 850 | 860 | 870 | 880 | 890 | 900 | 910 | 920 | 930 | 940 | 950 | 960 | 970 | 980 | 990 | 1000";
      }
      default "0";
      units "ms";
    }
    leaf cellMwtDlElevatedPriority {
      description "Downlink priority used after cellDlMaxWaitingTime is reached..";
      type enumeration {
        enum LOW;
        enum HIGH;
      }
    }
    leaf cellMwtUlElevatedPriority {
      description "Uplink priority used after cellUlMaxWaitingTime is reached..";
      type enumeration {
        enum LOW;
        enum HIGH;
      }
    }
    leaf cellPriorityShiftId {
      description "The value component of the RDN..";
      type string;
      mandatory true;
    }
    leaf cellUlDrbPriorityLimitBase {
      description "Cell scale of uplink spectrum resource limit in rate-controlled scheduling. The lower the value, the less spectrum resources can be utilized by rate-controlled UE within cell.; range 1..100; Default value: 100.";
      type eytypes:int32_range_1-100-3;
      default "100";
    }
    leaf cellUlElevationTime {
      description "Time since last scheduling or data arrival in buffer when a priority upshift occurs. Used for elevation time operation for uplink.; range 10..45; Default value: 20.";
      type int32 {
        range "10..45";
      }
      default "20";
      units "ms";
    }
    leaf cellUlMaxWaitingTime {
      description "Time since last scheduling or data arrival in buffer when a priority upshift occurs. Used for maximum waiting time operation for uplink if value is larger than 0.; Default value: 0.";
      type int32 {
        range "0 | 200 | 210 | 220 | 230 | 240 | 250 | 260 | 270 | 280 | 290 | 300 | 310 | 320 | 330 | 340 | 350 | 360 | 370 | 380 | 390 | 400 | 410 | 420 | 430 | 440 | 450 | 460 | 470 | 480 | 490 | 500 | 510 | 520 | 530 | 540 | 550 | 560 | 570 | 580 | 590 | 600 | 610 | 620 | 630 | 640 | 650 | 660 | 670 | 680 | 690 | 700 | 710 | 720 | 730 | 740 | 750 | 760 | 770 | 780 | 790 | 800 | 810 | 820 | 830 | 840 | 850 | 860 | 870 | 880 | 890 | 900 | 910 | 920 | 930 | 940 | 950 | 960 | 970 | 980 | 990 | 1000";
      }
      default "0";
      units "ms";
    }
    leaf-list reservedBy {
      description "Contains a list of MO instances that reserve this MO instance..";
      type string;
      min-elements 0;
    }
  }
  grouping CellResourceMapping-attributes {
    leaf cellResourceMappingId {
      description "The value component of the RDN..";
      type string;
      mandatory true;
    }
    leaf-list priorityPartition5qiList {
      description "List of 5QI values to be included in priority partition. To be appended to 5QI values configured in child PartitionMapping instances..";
      type eytypes:int32_range_1-255;
      ordered-by user;
      min-elements 0;
      max-elements 16;
    }
    leaf-list reservedBy {
      description "Contains a list of MO instances that reserve this MO instance..";
      type string;
      min-elements 0;
    }
    leaf shareInheritance {
      description "How prioritized resources are inherited..";
      type enumeration {
        enum NONE;
        enum HIERARCHICAL;
      }
    }
    leaf userLabel {
      description "Label for free use..";
      type string;
    }
  }
  grouping CgSwitch-attributes {
    leaf cgSwitchId {
      description "The value component of the RDN..";
      type string;
      mandatory true;
    }
    leaf-list reservedBy {
      description "Contains a list of MO instances that reserve this MO instance..";
      type string;
      min-elements 0;
    }
    leaf ueConfGroupType {
      description "UE configuration group type. UE configuration group type that is applied in contained CgSwitchUeCfg instances..";
      type enumeration {
        enum UE_MOBILITY_GROUP;
        enum UE_SERVICE_GROUP;
        enum UE_ADMISSION_GROUP;
      }
    }
    leaf userLabel {
      description "Label for free use..";
      type string;
    }
  }
  grouping CgSwitchCfg-attributes {
    leaf cgSwitchCfgId {
      description "The value component of the RDN..";
      type string;
      mandatory true;
    }
    leaf dlCgSwitchMode {
      description "Downlink cell group switching mode. Used for SN terminated split bearer. Applicable to EN-DC and NR-DC..";
      type enumeration {
        enum DISABLED;
        enum ENABLED;
      }
    }
    leaf dlScgLowQualHyst {
      description "Low SCG downlink radio quality hysteresis. Above dlScgLowQualThresh value plus this hysteresis, SCG downlink quality changes from low to good for UE. SINR is used to represent quality. Used for SN terminated split bearer. Applicable to EN-DC and NR-DC.; range 0..600; Default value: 50.";
      type int32 {
        range "0..600";
      }
      default "50";
      units "dB";
    }
    leaf dlScgLowQualThresh {
      description "Low SCG downlink radio quality level threshold. Below this threshold, SCG downlink quality is considered low for UE. SINR is used to represent quality. Value -160 corresponds to zero throughput, and lower values have no further impact. Used for SN terminated split bearer. Applicable to EN-DC and NR-DC.; range -400..400; Default value: 50.";
      type eytypes:int32_range_-400-400;
      default "50";
      units "dB";
    }
    leaf dlScgNoDataAcsiPeriodicity {
      description "Periodicity of aperiodic CSI report requests when there is no user data on SCG. Periodicity can vary because of cell load and DRX cycle. If dlCgSwitchMode is DISABLED, no aperiodic CSI report is triggered. Only applicable to Low-Band and Mid-Band cells. Applicable to EN-DC and NR-DC.; range 100..2600; Default value: 300.";
      type int32 {
        range "100..2600";
      }
      default "300";
      units "ms";
    }
    leaf-list reservedBy {
      description "Contains a list of MO instances that reserve this MO instance..";
      type string;
      min-elements 0;
    }
    leaf ulCgSwitchMode {
      description "Uplink cell group switching mode. Used for SN terminated split bearer. Applicable to EN-DC and NR-DC..";
      type enumeration {
        enum DISABLED;
        enum ENABLED;
      }
    }
    leaf ulScgCritQualHyst {
      description "Critical SCG uplink radio quality hysteresis. Above ulScgCritQualThresh value plus this hysteresis, SCG uplink quality changes from critical to low for UE. SINR is used to represent quality. Used for SN terminated split bearer. Applicable to EN-DC and NR-DC.; range 5..600.";
      type eytypes:int32_range_5-600;
      units "dB";
    }
    leaf ulScgCritQualThresh {
      description "Critical SCG uplink radio quality level threshold. Below this threshold, SCG uplink quality is considered critical for UE. If empty, SCG uplink quality is not considered critical for UE. SINR is used to represent quality. Applicable to EN-DC and NR-DC.; range -400..1450.";
      type eytypes:int32_range_-400-1450;
      units "dB";
    }
    leaf ulScgLowQualHyst {
      description "Low SCG uplink radio quality hysteresis. Above ulScgLowQualThresh value plus this hysteresis, SCG uplink quality changes from low to good for UE. SINR is used to represent quality. Used for SN terminated split bearer. Applicable to EN-DC and NR-DC.; range 5..600.";
      type eytypes:int32_range_5-600;
      units "dB";
    }
    leaf ulScgLowQualThresh {
      description "Low SCG uplink radio quality level threshold. Below this threshold, SCG uplink quality is considered low for UE. SINR is used to represent quality. Used for SN terminated split bearer. Applicable to EN-DC and NR-DC.; range -400..1450.";
      type eytypes:int32_range_-400-1450;
      units "dB";
    }
    leaf userLabel {
      description "Label for free use..";
      type string;
    }
  }
  grouping CgSwitchUeCfg-attributes {
    leaf cgSwitchCfgRef {
      description "Reference to an instance of CgSwitchCfg MO. Automatically set to CgSwitchCfg=Default instance, unless manually set to refer to another MO instance..";
      type string;
    }
    leaf cgSwitchUeCfgId {
      description "The value component of the RDN..";
      type string;
      mandatory true;
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping CommonBeamforming-attributes {
    leaf azimuthCoverageWidth {
      description "Target coverage width in azimuth. Azimuth is in horizontal plane. If empty or unsupported for configuration, system selects value within supported range. Attribute usedAzimuthCoverageWidth shows width in use. For Low-Band and Mid-Band cells in downlink, only applicable if any of the following is true: - customComBfwWideBeam is empty. - customComBfwWideBeam.amplitude is set to all zeros. Only applicable when usedCoverageShape is FLEXIBLE_COVERAGE_1. Only applicable to Low-Band and Mid-Band sector carriers. Select a value supported by installed radio equipment. Refer to radio equipment CPI for supported values.; range 50..1800.";
      type int32 {
        range "50..1800";
      }
      units "degree";
    }
    leaf cbfMacroTaperType {
      description "Type of tapering for vertical beam weights. Only applicable to coverage shapes with narrower elevation width. For example, HOTSPOT and HIGHRISE shapes are wider, full-elevation-width coverage shapes, not supporting taper type options. Only applicable to Low-Band and Mid-Band sector carriers..";
      type enumeration {
        enum STANDARD;
        enum HIGHEIRP;
        enum HIGHSLS;
      }
    }
    leaf commonBeamformingId {
      description "The value component of the RDN..";
      type string;
      mandatory true;
    }
    leaf coverageShape {
      description "Coverage shape of a sector carrier. If set to PRODUCT_DEFAULT, default coverage shape for radio product is selected by system. If not supported by radio equipment, system overrides setting. Attribute usedCoverageShape shows coverage shape in use. For Low-Band and Mid-Band sector carriers in downlink, only applicable if any of following options are true: - customComBfwWideBeam is empty - customComBfwWideBeam.amplitude is set to all zeros Only applicable if radio equipment supports AAS configuration. Select a value supported by installed radio equipment. Refer to CPI for installed radio equipment..";
      type enumeration {
        enum PRODUCT_DEFAULT;
        enum MACRO_1;
        enum HIGHRISE_1;
        enum HOTSPOT_1;
        enum MACRO_120_20;
        enum HOTSPOT_120_30;
        enum MACRO_120_15;
        enum STREET_COVERAGE_1;
        enum STREET_HOTSPOT_1;
        enum STREET_HOTSPOT_WIDE_1;
        enum FLEXIBLE_COVERAGE_1;
        enum MACRO_WIDE_1;
      }
    }
    list customComBfwWideBeam {
      key "id";
      leaf id {
        type uint32;
        description "Synthetic key for struct sequence entry.";
      }
      min-elements 0;
      max-elements 64;
      uses CustomComBfwWideBeam-struct;
    }
    leaf digitalPan {
      description "Digitally controlled pan through beamforming. Only applicable if radio equipment supports AAS configuration. Positive value gives clockwise pan and negative value gives counterclockwise pan. If empty, usedDigitalPan shows the digital pan in use. Only applicable to Low-Band and Mid-Band sector carriers. Select a value supported by installed radio equipment. Refer to CPI for installed radio equipment.; range -900..900.";
      type eytypes:int32_range_-900-900;
      units "degree";
    }
    leaf digitalTilt {
      description "Digitally controlled tilt through beamforming. Relative to horizontal plane, adjusted by mechanical tilt. Only applicable if radio equipment supports AAS configuration. Positive value gives downwards tilt and negative value gives upwards tilt. If empty or unsupported for configuration, system selects value within supported range. Attribute usedDigitalTilt shows tilt in use. Make sure that selected value is supported by installed radio equipment. For more information, see Antenna Integrated Radio Unit Description of installed radio equipment. If value of usedCoverageShape is HIGHRISE or HOTSPOT, a fixed digital tilt is applied.; range -900..900.";
      type eytypes:int32_range_-900-900;
      units "degree";
    }
    leaf elevationCoverageWidth {
      description "Target coverage width in elevation. Elevation is in vertical plane. If empty or unsupported for configuration, system selects value within supported range. Attribute usedElevationCoverageWidth shows width in use. For Low-Band and Mid-Band cells in downlink, only applicable if any of the following is true: - customComBfwWideBeam is empty. - customComBfwWideBeam.amplitude is set to all zeros. Only applicable when usedCoverageShape is FLEXIBLE_COVERAGE_1. Only applicable to Low-Band and Mid-Band sector carriers. Select a value supported by installed radio equipment. Refer to radio equipment CPI for supported values.; range 20..1800.";
      type int32 {
        range "20..1800";
      }
      units "degree";
    }
    leaf ssbBeams {
      description "Number of SSB beams. If PRODUCT_DEFAULT, system automatically selects number of SSB beams. Must be set to value supported by installed radio equipment. Otherwise system overrides setting. Attribute usedSsbBeams shows number of SSB beams in use. Only applicable to High-Band sector carriers..";
      type enumeration {
        enum PRODUCT_DEFAULT;
        enum SSB_BEAMS_12;
        enum SSB_BEAMS_24;
        enum SSB_BEAMS_4;
        enum SSB_BEAMS_6;
        enum SSB_BEAMS_8;
      }
    }
    leaf-list supportedCbfMacroTaperTypes {
      description "List of supported types for cbfMacroTaperType. Only applicable when usedCoverageShape is MACRO_1. Only applicable to Low-Band and Mid-Band sector carriers..";
      type CbfMacroTaperType;
      min-elements 0;
      max-elements 3;
    }
    list supportedCoverageOptions {
      config false;
      min-elements 0;
      max-elements 100;
      uses SupportedCoverageOptions-struct;
    }
    leaf-list supportedCoverageShapes {
      description "List of supported shapes for coverageShape. Only applicable to Low-Band and Mid-Band sector carriers..";
      type CoverageShape;
      min-elements 0;
      max-elements 9;
    }
    leaf supportedPanRange {
      description "Supported range for digitalPan. Format if support range is continuous: [low limit - high limit]. Format if supported range is restricted to smaller set of discrete values: [<pan1>,..,<pann>]. Only applicable to Low-Band and Mid-Band sector carriers..";
      type string;
      config false;
    }
    leaf supportedTiltRange {
      description "Supported range for digitalTilt. Format if support range is continuous: [<low limit>-<high limit>]. Format if supported range is restricted to a smaller set of discrete values: [<tilt1>,..,<tiltn>]. Only applicable when usedCoverageShape is MACRO_1 or STREET_COVERAGE_1. Only applicable to Low-Band and Mid-Band sector carriers..";
      type string;
      config false;
    }
    leaf usedAzimuthCoverageWidth {
      description "Used azimuth coverage width for sector carrier. Only valid when NRSectorCarrier instance is unlocked. Only applicable to Low-Band and Mid-Band sector carriers.; range 50..1800.";
      type int32 {
        range "50..1800";
      }
      config false;
      units "degree";
    }
    leaf usedCbfMacroTaperType {
      description "Used taper type for sector carrier. Only applicable to Low-Band and Mid-Band sector carriers..";
      type enumeration {
        enum STANDARD;
        enum HIGHEIRP;
        enum HIGHSLS;
      }
      config false;
    }
    leaf usedCoverageShape {
      description "Used coverage shape for sector carrier..";
      type enumeration {
        enum PRODUCT_DEFAULT;
        enum MACRO_1;
        enum HIGHRISE_1;
        enum HOTSPOT_1;
        enum MACRO_120_20;
        enum HOTSPOT_120_30;
        enum MACRO_120_15;
        enum STREET_COVERAGE_1;
        enum STREET_HOTSPOT_1;
        enum STREET_HOTSPOT_WIDE_1;
        enum FLEXIBLE_COVERAGE_1;
        enum MACRO_WIDE_1;
      }
      config false;
    }
    leaf usedDigitalPan {
      description "Selected digital pan for sector carrier. Only applicable to Low-Band and Mid-Band sector carriers..";
      type int32;
      config false;
    }
    leaf usedDigitalTilt {
      description "Selected digital tilt for sector carrier. Relative to horizontal plane, adjusted by mechanical tilt..";
      type int32;
      config false;
    }
    leaf usedElevationCoverageWidth {
      description "Used elevation coverage width for sector carrier. Only valid when NRSectorCarrier instance is unlocked. Only applicable to Low-Band and Mid-Band sector carriers.; range 20..1800.";
      type int32 {
        range "20..1800";
      }
      config false;
      units "degree";
    }
    leaf usedSsbBeams {
      description "Number of used SSB beams. Only applicable to High-Band sector carriers..";
      type enumeration {
        enum PRODUCT_DEFAULT;
        enum SSB_BEAMS_12;
        enum SSB_BEAMS_24;
        enum SSB_BEAMS_4;
        enum SSB_BEAMS_6;
        enum SSB_BEAMS_8;
      }
      config false;
    }
  }
  grouping ConfiguredGrant-attributes {
    leaf configuredGrantId {
      description "The value component of the RDN..";
      type string;
      mandatory true;
    }
  }
  grouping ConfiguredGrantUeCfg-attributes {
    leaf configuredGrantDataSize {
      description "Payload size in bytes for configured grant. A margin is added for size of IP header, PDCP header and RLC header. Bytes for Buffer Status Report (BSR) and Power Headroom Report (PHR) are always included in configured grant and do not need to be considered when setting configuredGrantDataSize. If 0, BSR can be reported at configured grant occasions. When receiving BSR, required data transmission can be scheduled with a dynamic scheme. Only applicable to Low-Band and Mid-Band cells.; range 0..10000; Default value: 0.";
      type int32 {
        range "0..10000";
      }
      default "0";
      units "byte";
    }
    leaf configuredGrantMode {
      description "Configured grant mode for corresponding UE. Only applicable to Low-Band and Mid-Band cells..";
      type enumeration {
        enum DEACTIVATED;
        enum SINGLE;
      }
    }
    leaf configuredGrantPeriodicity {
      description "Periodicity in slots for configured grant. For FDD, following values are applicable: 5, 10, 20, 40, 80, 160, 320, 640. For TDD, following values are applicable: 5, 10, 20, 40, 80, 160, 320, 640, 1280. Only applicable to Low-Band and Mid-Band cells.; Default value: 10.";
      type int32 {
        range "5 | 10 | 20 | 40 | 80 | 160 | 320 | 640 | 1280";
      }
      default "10";
    }
    leaf configuredGrantSrbConfig {
      description "Logical channel to configured grant mapping for SRB. SRB1 and SRB2 mapping of configured grant configuration profile for uplink transmission. Only applicable to Low-Band and Mid-Band cells..";
      type enumeration {
        enum UNRESTRICTED;
        enum NOT_ALLOWED;
      }
    }
    leaf configuredGrantUeCfgId {
      description "The value component of the RDN..";
      type string;
      mandatory true;
    }
    leaf-list notAllowed5qiList {
      description "List of 5QI values that do not use configured grant. List of 5QIs that are not allowed to use this configured grant configuration profile for uplink transmission. Only applicable to Low-Band and Mid-Band cells..";
      type eytypes:int32_range_1-255;
      ordered-by user;
      min-elements 0;
      max-elements 15;
    }
    leaf-list reservedBy {
      description "Contains a list of MO instances that reserve this MO instance..";
      type string;
      min-elements 0;
    }
    leaf userLabel {
      description "Label for free use..";
      type string;
    }
  }
  grouping ContentionControl-attributes {
    leaf contentionControlId {
      description "The value component of the RDN..";
      type string;
      mandatory true;
    }
  }
  grouping CsiProfile-attributes {
    leaf csiProfileId {
      description "The value component of the RDN..";
      type string;
      mandatory true;
    }
  }
  grouping CsiProfileUeCfg-attributes {
    leaf csiBufferThresh {
      description "Threshold for buffer level to determine if UE is to be treated as light downlink traffic. Only applicable if license for NR A-CSI Trigger Handling is present and feature is active. Otherwise handled as default. Only applicable to Low-Band and Mid-Band cells..";
      type enumeration {
        enum OFF;
        enum LOW;
        enum MEDIUM;
        enum HIGH;
      }
    }
    leaf csiPollRetransmitEnabled {
      description "Whether retriggering of A-CSI report is enabled. Report is retriggered when latest A-CSI report using extended period is not received. Only applicable if license for NR A-CSI Trigger Handling is present and feature is active. Otherwise handled as default. Only applicable to Low-Band and Mid-Band cells.; Default value: false.";
      type boolean;
      default "false";
    }
    leaf csiProfileUeCfgId {
      description "The value component of the RDN..";
      type string;
      mandatory true;
    }
    leaf csiRptPeriodAdd {
      description "Periodicity added to Aperiodic Channel State Information (A-CSI) periodicity. Offset is added if number of bytes in Priority Queue (PQ) is greater than zero but less than or equal to size mentioned in csiBufferThresh. Only applicable if license for NR A-CSI Trigger Handling is present and feature is active. Otherwise handled as default. Only applicable to Low-Band and Mid-Band cells..";
      type enumeration {
        enum OFF;
        enum LOW;
        enum HIGH;
      }
    }
    leaf-list reservedBy {
      description "Contains a list of MO instances that reserve this MO instance..";
      type string;
      min-elements 0;
    }
  }
  grouping DataRadioBearer-attributes {
    leaf dataRadioBearerId {
      description "The value component of the RDN..";
      type string;
      mandatory true;
    }
    leaf dlMaxRetxThreshold {
      description "Maximum number of AM RLC downlink retransmissions. When this value is reached, AM RLC downlink retransmission is stopped and RRC is notified..";
      type int32 {
        range "1..4 | 6 | 8 | 16 | 32";
      }
    }
    leaf dlPollPdu {
      description "Number of AM RLC PDUs before polling for a status report in gNodeB..";
      type int32 {
        range "4 | 8 | 16 | 32 | 64 | 128 | 256 | 512 | 1024 | 2048 | 4096 | 6144 | 8192 | 12288 | 16384 | 20480 | 24576 | 28672 | 32768 | 40960 | 49152 | 57344 | 65536";
      }
    }
    leaf tPollRetransmitDl {
      description "Timer supervising the poll for STATUS PDU. AM RLC DL transmitter to wait for RLC STATUS feedback after sending a poll for STATUS before retransmitting the poll..";
      type int32 {
        range "5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 2000 | 4000";
      }
      units "ms";
    }
    leaf tPollRetransmitUl {
      description "Timer for UE to supervise the poll for STATUS PDU. AM RLC UL transmitter waits for RLC STATUS feedback after sending a poll for STATUS before retransmitting the poll..";
      type int32 {
        range "5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 2000 | 4000";
      }
      units "ms";
    }
    leaf tStatusProhibitDl {
      description "Timer for the receiving side of AM RLC. Prevents transmission of a new status PDU in UE..";
      type int32 {
        range "0 | 5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 1200 | 1600 | 2000 | 2400";
      }
      units "ms";
    }
    leaf tStatusProhibitUl {
      description "Timer for the receiving side of AM RLC. Prevents transmission of a new status PDU in gNodeB..";
      type int32 {
        range "0 | 5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 1200 | 1600 | 2000 | 2400";
      }
      units "ms";
    }
    leaf ulMaxRetxThreshold {
      description "Maximum number of AM RLC uplink retransmissions. When this value is reached, AM RLC uplink retransmission is stopped and RRC is notified..";
      type int32 {
        range "1..4 | 6 | 8 | 16 | 32";
      }
    }
    leaf ulPollPdu {
      description "Number of AM RLC PDUs before polling for a status report in UE..";
      type int32 {
        range "4 | 8 | 16 | 32 | 64 | 128 | 256 | 512 | 1024 | 2048 | 4096 | 6144 | 8192 | 12288 | 16384 | 20480 | 24576 | 28672 | 32768 | 40960 | 49152 | 57344 | 65536";
      }
    }
  }
  grouping DlBeamOptProfile-attributes {
    leaf dlBeamOptProfileId {
      description "The value component of the RDN..";
      type string;
      mandatory true;
    }
  }
  grouping DlBeamOptProfileUeCfg-attributes {
    leaf dlBeamOptProfileUeCfgId {
      description "The value component of the RDN..";
      type string;
      mandatory true;
    }
    leaf pdcchBeamOptMode {
      description "PDCCH beamforming optimizer mode. Only applicable if licenses for both following features are present and features are active: - NR Downlink Beam Optimizer - Coverage and Capacity Optimized PDCCH Beamforming Otherwise handled as default. Only applicable to Low-Band and Mid-Band cells..";
      type enumeration {
        enum OFF;
        enum SLOW;
        enum NORMAL;
        enum FAST;
      }
    }
    leaf-list reservedBy {
      description "Contains a list of MO instances that reserve this MO instance..";
      type string;
      min-elements 0;
    }
  }
  grouping DlDelayBasedPriority-attributes {
    leaf dlDelayBasedPriorityId {
      description "The value component of the RDN..";
      type string;
      mandatory true;
    }
    leaf dlDemotedPriority {
      description "Priority used before CellPriorityShift::cellDlElevationTime is reached..";
      type enumeration {
        enum LOW;
        enum HIGH;
      }
    }
  }
  grouping DlLatencyBasedPriority-attributes {
    leaf dlDemotedPriority {
      description "Downlink demoted priority for latency prioritized scheduling..";
      type enumeration {
        enum LOW;
        enum HIGH;
      }
    }
    leaf dlLatencyBasedPriorityId {
      description "The value component of the RDN..";
      type string;
      mandatory true;
    }
    leaf dlPriorityScaler {
      description "Priority scaler that scales downlink weight slope for latency prioritized scheduling.; range 1..8; Default value: 1.";
      type eytypes:int32_range_1-8;
      default "1";
    }
    leaf dlPriorityShiftMargin {
      description "Time margin to determine downlink delay threshold for priority shift. The margin is relative to RAN packet delay budget (PDB) used for downlink. If time margin is greater than the RAN PDB used for downlink, it is set to RAN PDB used for downlink.; range -231..280; Default value: 0.";
      type int32 {
        range "-231..280";
      }
      default "0";
      units "ms";
    }
    leaf dlResourceControlLevel {
      description "Resource control level used by LPS in downlink..";
      type enumeration {
        enum LEVEL_0;
        enum LEVEL_1;
        enum LEVEL_2;
        enum LEVEL_3;
        enum LEVEL_4;
        enum LEVEL_5;
      }
    }
    leaf dlWeightOffset {
      description "Downlink weight offset for latency prioritized scheduling..";
      type enumeration {
        enum ZERO;
        enum LOW;
        enum MEDIUM;
        enum HIGH;
      }
    }
  }
  grouping DlLinkAdaptation-attributes {
    leaf dlBlerTarget {
      description "Target BLER for downlink after initial HARQ transmission. If license for Link Adaptation for Low Target BLER for Dedicated RAN is present and feature is active, following applies: - Applicable if dlBlerTargetExtended is -1. - For Low-Band and Mid-Band cells, this attribute is overridden by dlBlerTargetExtended, if dlBlerTargetExtended is not -1. Also applicable if license for Link Adaptation for Low Target BLER for Dedicated RAN is not active. Low range value, less than 1 %, can only be utilized if at least one of following licenses is present and feature is active: - Link Adaptation for Low Target BLER for Public RAN - Link Adaptation for Low Target BLER for Dedicated RAN Otherwise, handled as 1 %.; range 1..3000; Default value: 1000.";
      type int32 {
        range "1..3000";
      }
      default "1000";
      units "percent";
    }
    leaf dlBlerTargetExtended {
      description "Extended target BLER for downlink after initial HARQ transmission. Very low range value between 0.0001 % and 0.01 % can only be utilized if license for Link Adaptation for Low Target BLER for Dedicated RAN is present and feature is active. Otherwise, this attribute is not applicable. If -1, extended target BLER is disabled and dlBlerTarget is applicable. Only applicable to Low-Band and Mid-Band cells.; Default value: -1.";
      type int32 {
        range "-1 | 1..100";
      }
      default "-1";
      units "percent";
    }
    leaf dlDownStep {
      description "Downlink down step size. Used for outer loop. If 0, downlink link adaptation applies general mode outer loop adjustment steps. Only applicable if license for at least one of following features is present and feature is active: - Link Adaptation for Low Target BLER for Public RAN - Link Adaptation for Low Target BLER for Dedicated RAN Otherwise handled as 0 for Low-Band and Mid-Band cells and 1 for High-Band cells.; range 0..100; Default value: 0.";
      type eytypes:int32_range_0-100-5;
      default "0";
      units "dB";
    }
    leaf dlLinkAdaptationId {
      description "The value component of the RDN..";
      type string;
      mandatory true;
    }
    leaf dlMaxMcsIndex {
      description "Maximum allowed MCS index for downlink. Maximum MCS index for QAM256 is 27.; range 0..28; Default value: 27.";
      type eytypes:int32_range_0-28;
      default "27";
    }
    leaf dlMaxTbs {
      description "Maximum allowed TBS to allocate for UE in DCI grant. If 0, TBS is not limited.; range 0..65535; Default value: 0.";
      type int32 {
        range "0..65535";
      }
      default "0";
      units "bit";
    }
    leaf dlSinrBackoff {
      description "Downlink SINR backoff. Only applicable if license for at least one of following features is present and feature is active: - Link Adaptation for Low Target BLER for Public RAN - Link Adaptation for Low Target BLER for Dedicated RAN Otherwise handled as default.; range 0..100; Default value: 0.";
      type eytypes:int32_range_0-100-5;
      default "0";
      units "dB";
    }
  }
  grouping DlMimo-attributes {
    leaf dlMimoId {
      description "The value component of the RDN..";
      type string;
      mandatory true;
    }
  }
  grouping DlMimoUeCfg-attributes {
    leaf dlMimoUeCfgId {
      description "The value component of the RDN..";
      type string;
      mandatory true;
    }
    leaf-list reservedBy {
      description "Contains a list of MO instances that reserve this MO instance..";
      type string;
      min-elements 0;
    }
    leaf srsImpactHandling {
      description "Handling for impact of SRS TX port switching..";
      type enumeration {
        enum DISABLED;
        enum ENABLED;
      }
    }
  }
  grouping DlOuterLoop-attributes {
    leaf dlOuterLoopId {
      description "The value component of the RDN..";
      type string;
      mandatory true;
    }
    leaf dualOuterLoopEnabled {
      description "Whether dual downlink outer loop is enabled.; Default value: false.";
      type boolean;
      default "false";
    }
    leaf initValMixIpn {
      description "Initial value for loop with NR-LTE interference for non-MBSFN slots. Used for single outer loop when dualOuterLoopEnabled is false.; range -400..400; Default value: 0.";
      type eytypes:int32_range_-400-400;
      default "0";
      units "dB";
    }
    leaf initValNonMixIpn {
      description "Initial value for loop with only NR interference for MBSFN slots. Ignored when dualOuterLoopEnabled is false.; range -400..400; Default value: 0.";
      type eytypes:int32_range_-400-400;
      default "0";
      units "dB";
    }
    leaf largeStepMixIpn {
      description "Large down-step size for non-MBSFN slots, used initially for quick convergence. Ignored when dualOuterLoopEnabled is false.; range 0..50; Default value: 10.";
      type eytypes:int32_range_0-50;
      default "10";
      units "dB";
    }
    leaf largeStepNonMixIpn {
      description "Large down-step size for MBSFN slots, used initially for quick convergence. Ignored when dualOuterLoopEnabled is false.; range 0..50; Default value: 3.";
      type eytypes:int32_range_0-50;
      default "3";
      units "dB";
    }
    leaf smallDownStep {
      description "Common small down-step size. Used for both outer loops after convergence. Used for single outer loop when dualOuterLoopEnabled is false. Recommended to be set to value less than or equal to largeStepMixIpn or largeStepNonMixIpn for dual outer loop.; range 0..30; Default value: 1.";
      type eytypes:int32_range_0-30;
      default "1";
      units "dB";
    }
  }
  grouping DlRateBasedPriority-attributes {
    leaf dlDemotedPriority {
      description "Priority to use after priority downshift fulfills at rate..";
      type enumeration {
        enum LOW;
        enum HIGH;
      }
    }
    leaf dlDemotedRelativePriority {
      description "Whether relative priority for downlink is used in demoted state. If false, value of relative priority is 1. Otherwise, value of relative priority is SchedulingProfile::relativePriority.; Default value: false.";
      type boolean;
      default "false";
    }
    leaf dlDrbOverloadHandling {
      description "Determines what happens when UE is overloaded with rate-based priority shift algorithm. Overload means a DRB with rate tracking is attempted to be set up while UE already has two DRBs with rate tracking. Rate tracking is activated when SchedulingProfile::schedulingAlgorithm is PRIORITIZED_RATE or SOFT_RATE_THROTTLING..";
      type enumeration {
        enum BASIC;
        enum REJECT;
      }
    }
    leaf dlPrioritizedRate {
      description "Rate to be prioritized.; Default value: 1.";
      type int32 {
        range "1..10 | 20 | 30 | 40 | 50 | 60 | 70 | 80 | 90 | 100 | 200 | 300 | 400 | 500 | 600 | 700 | 800 | 900 | 1000 | 2000 | 3000 | 4000 | 5000 | 6000 | 7000 | 8000 | 9000 | 10000 | 20000 | 30000 | 40000 | 50000 | 60000 | 70000 | 80000 | 90000 | 100000 | 200000 | 300000 | 400000 | 500000 | 600000 | 700000 | 800000 | 900000 | 1000000";
      }
      default "1";
      units "kbps";
    }
    leaf dlRateBasedPriorityId {
      description "The value component of the RDN..";
      type string;
      mandatory true;
    }
  }
  grouping DlResourceBasedPriority-attributes {
    leaf dlDrbPriorityLimit {
      description "Limit of downlink spectrum resources. Used with elevated priority by a single DRB configured with a rate. The lower the value, the less spectrum resources can be utilized with elevated priority by rate-controlled scheduling.; range 1..100; Default value: 100.";
      type eytypes:int32_range_1-100-3;
      default "100";
    }
    leaf dlResourceBasedPriorityId {
      description "The value component of the RDN..";
      type string;
      mandatory true;
    }
    leaf dlResourceLimitMode {
      description "Controls operation of resource limit for downlink..";
      type enumeration {
        enum NO_LIMIT;
        enum LIMITED;
        enum LIMITED_TO_CELL_LIMIT;
      }
    }
  }
  grouping DrbRlc-attributes {
    leaf drbRlcId {
      description "The value component of the RDN..";
      type string;
      mandatory true;
    }
    leaf-list reservedBy {
      description "Contains a list of MO instances that reserve this MO instance..";
      type string;
      min-elements 0;
    }
    leaf ueConfGroupType {
      description "UE configuration group type. UE configuration group type that is applied in contained DrbRlcUeCfg instances..";
      type enumeration {
        enum UE_MOBILITY_GROUP;
        enum UE_SERVICE_GROUP;
        enum UE_ADMISSION_GROUP;
      }
    }
    leaf userLabel {
      description "Label for free use..";
      type string;
    }
  }
  grouping DrbRlcUeCfg-attributes {
    leaf dlHighRateTimerSwitchEnabled {
      description "Whether high rate timers are used. High rate timers tReassemblyDlHighRate and tStatusProhibitDlHighRate are used for configuring UE DRB RLC timer t-reassembly and t-statusProhibit respectively when UE DRB total throughput reaches high rate threshold. If true, UE is reconfigured with timer value defined in tReassemblyDlHighRate and tStatusProhibitDlHighRate, when UE DRB total throughput reaches high rate threshold. If false, no UE RLC timer reconfiguration is performed, when UE DRB total throughput reaches high rate threshold.; Default value: false.";
      type boolean;
      default "false";
    }
    leaf dlMaxRetxThreshold {
      description "Maximum number of AM RLC downlink retransmissions. When this value is reached, AM RLC downlink retransmission is stopped and RRC is notified.; Default value: 16.";
      type int32 {
        range "1..4 | 6 | 8 | 16 | 32";
      }
      default "16";
    }
    leaf dlPollPdu {
      description "Number of AM RLC PDUs before polling for a status report in gNodeB.; Default value: 32.";
      type int32 {
        range "4 | 8 | 16 | 32 | 64 | 128 | 256 | 512 | 1024 | 2048 | 4096 | 6144 | 8192 | 12288 | 16384 | 20480 | 24576 | 28672 | 32768 | 40960 | 49152 | 57344 | 65536";
      }
      default "32";
    }
    leaf drbRlcUeCfgId {
      description "The value component of the RDN..";
      type string;
      mandatory true;
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf rlcAckPduDelayMode {
      description "Delay mode of RLC Ack STATUS PDU. Only applicable if license for Energy-Optimized Slot Allocation is present and feature is active. Otherwise handled as default. Only applicable to Low-Band and Mid-Band cells..";
      type enumeration {
        enum NO_DELAY;
        enum VERY_LOW;
        enum LOW;
        enum BALANCED;
        enum HIGH;
      }
    }
    leaf rlcSNLength {
      description "Radio Link Control (RLC) SN field size. Following values are recommended: * 18 if profile5qi is 8 or 9. * 12 if profile5qi is 1, 2, 3, 4, 5, 6, 7, 65, 66, 67, 69, or 70. * 6 if profile5qi is 79, 80, 82, 83, 84, or 85, and for voice over NR with good RF conditions. 3GPP recommends 6 when profile5qi is 1, 2, 65, 66, or 67.; Default value: 18.";
      type int32 {
        range "6 | 12 | 18";
      }
      default "18";
      units "bit";
    }
    leaf tPollRetransmitDl {
      description "Timer supervising poll for STATUS PDU. AM RLC DL transmitter waits for RLC STATUS feedback after sending a poll for STATUS before retransmitting the poll.; Default value: 40.";
      type int32 {
        range "5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 2000 | 4000";
      }
      default "40";
      units "ms";
    }
    leaf tPollRetransmitUl {
      description "Timer for UE to supervise poll for STATUS PDU. AM RLC UL transmitter waits for RLC STATUS feedback after sending a poll for STATUS before retransmitting the poll.; Default value: 40.";
      type int32 {
        range "5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 2000 | 4000";
      }
      default "40";
      units "ms";
    }
    leaf tReassemblyDl {
      description "Downlink Radio Link Control (RLC) timer reassembly. Following values are recommended: * 35 if profile5qi is 1, 2, 65, 66, 67 or 79. * 25 if profile5qi is 3, 4, 5, 6, 7, 8, 9, 69, 70 or 84. * 10 if profile5qi is 80, 82 or 83. * 5 if profile5qi is 85.; Default value: 25.";
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200";
      }
      default "25";
      units "ms";
    }
    leaf tReassemblyDlHighRate {
      description "Downlink Radio Link Control (RLC) timer reassembly for high rate.; Default value: 10.";
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200";
      }
      default "10";
      units "ms";
    }
    leaf tReassemblyUl {
      description "Uplink Radio Link Control (RLC) timer reassembly. Following values are recommended: * 35 if profile5qi is 1, 2, 65, 66, 67 or 79. * 25 if profile5qi is 3, 4, 5, 6, 7, 8, 9, 69, 70 or 84. * 10 if profile5qi is 80, 82 or 83. * 5 if profile5qi is 85.; Default value: 25.";
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200";
      }
      default "25";
      units "ms";
    }
    leaf tStatusProhibitDl {
      description "Timer for receiving side of AM RLC. Prevents transmission of a new status PDU in UE.; Default value: 10.";
      type int32 {
        range "0 | 5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 1200 | 1600 | 2000 | 2400";
      }
      default "10";
      units "ms";
    }
    leaf tStatusProhibitDlHighRate {
      description "Timer for receiving side of AM RLC for high rate. Prevents transmission of a new status PDU in UE.; Default value: 5.";
      type int32 {
        range "0 | 5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 1200 | 1600 | 2000 | 2400";
      }
      default "5";
      units "ms";
    }
    leaf tStatusProhibitUl {
      description "Timer for receiving side of AM RLC. Prevents transmission of a new status PDU in gNodeB.; Default value: 10.";
      type int32 {
        range "0 | 5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 1200 | 1600 | 2000 | 2400";
      }
      default "10";
      units "ms";
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches UE group identifiers..";
      type eytypes:int32_range_1-255;
      ordered-by user;
      min-elements 0;
      max-elements 16;
    }
    leaf ulMaxRetxThreshold {
      description "Maximum number of AM RLC uplink retransmissions. When this value is reached, AM RLC uplink retransmission is stopped and RRC is notified.; Default value: 32.";
      type int32 {
        range "1..4 | 6 | 8 | 16 | 32";
      }
      default "32";
    }
    leaf ulPollPdu {
      description "Number of AM RLC PDUs before polling for a status report in UE.; Default value: 16.";
      type int32 {
        range "4 | 8 | 16 | 32 | 64 | 128 | 256 | 512 | 1024 | 2048 | 4096 | 6144 | 8192 | 12288 | 16384 | 20480 | 24576 | 28672 | 32768 | 40960 | 49152 | 57344 | 65536";
      }
      default "16";
    }
  }
  grouping DrbUp-attributes {
    leaf drbUpId {
      description "The value component of the RDN..";
      type string;
      mandatory true;
    }
    leaf-list reservedBy {
      description "Contains a list of MO instances that reserve this MO instance..";
      type string;
      min-elements 0;
    }
    leaf ueConfGroupType {
      description "UE configuration group type. UE configuration group type that is applied in contained DrbUpUeCfg instances..";
      type enumeration {
        enum UE_MOBILITY_GROUP;
        enum UE_SERVICE_GROUP;
        enum UE_ADMISSION_GROUP;
      }
    }
    leaf userLabel {
      description "Label for free use..";
      type string;
    }
  }
  grouping DrbUpUeCfg-attributes {
    leaf aqmCfgRef {
      description "Reference to an instance of AqmCfg MO. Automatically set to following MO instance: - AqmCfg=Default_conversational_media instance, if DrbUpUeCfg instance is created under parent DrbUp=Default_conversational_media instance. - AqmCfg=Default_application_signaling, if DrbUpUeCfg instance is created under parent DrbUp=Default_application_signaling instance. - AqmCfg=Default_other, if DrbUpUeCfg instance is created under other parent Drb instance. Unless manually set to refer to another MO instance..";
      type string;
    }
    leaf drbUpUeCfgId {
      description "The value component of the RDN..";
      type string;
      mandatory true;
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping DrxProfile-attributes {
    leaf drxProfileId {
      description "The value component of the RDN..";
      type string;
      mandatory true;
    }
    leaf-list reservedBy {
      description "Contains a list of MO instances that reserve this MO instance..";
      type string;
      min-elements 0;
    }
    leaf ueConfGroupType {
      description "UE configuration group type. UE configuration group type that is applied in contained DrxProfileUeCfg instances..";
      type enumeration {
        enum UE_MOBILITY_GROUP;
        enum UE_SERVICE_GROUP;
        enum UE_ADMISSION_GROUP;
      }
    }
  }
  grouping DrxProfileUeCfg-attributes {
    leaf drxEnabled {
      description "Whether Connected Mode DRX feature to save energy in UE is enabled. If feature is disabled, Connected Mode DRX can still be activated in UE during CGI measurement.; Default value: true.";
      type boolean;
      default "true";
    }
    leaf drxInactivityTimer {
      description "DRX inactivity. Specifies time period for which UE should be active after successfully decoding a PDCCH indicating a new uplink or downlink transmission. RRC parameter drx-InactivityTimer is specified in 3GPP TS 38.331 6.3.2. Recommended value for High-Band cell is INACTIVITYTIMER_8MS. If PUSCH Repetition Type A is configured on UE, PuschRepRel16Drx::puschRepDrxInactTimer is used if non-empty..";
      type enumeration {
        enum INACTIVITYTIMER_0MS;
        enum INACTIVITYTIMER_1MS;
        enum INACTIVITYTIMER_2MS;
        enum INACTIVITYTIMER_3MS;
        enum INACTIVITYTIMER_4MS;
        enum INACTIVITYTIMER_5MS;
        enum INACTIVITYTIMER_6MS;
        enum INACTIVITYTIMER_8MS;
        enum INACTIVITYTIMER_10MS;
        enum INACTIVITYTIMER_20MS;
        enum INACTIVITYTIMER_30MS;
        enum INACTIVITYTIMER_40MS;
        enum INACTIVITYTIMER_50MS;
        enum INACTIVITYTIMER_60MS;
        enum INACTIVITYTIMER_80MS;
        enum INACTIVITYTIMER_100MS;
        enum INACTIVITYTIMER_200MS;
        enum INACTIVITYTIMER_300MS;
        enum INACTIVITYTIMER_500MS;
        enum INACTIVITYTIMER_750MS;
        enum INACTIVITYTIMER_1280MS;
        enum INACTIVITYTIMER_1920MS;
        enum INACTIVITYTIMER_2560MS;
      }
    }
    leaf drxLongCycle {
      description "Long DRX cycle in number of sub-frames. Recommended value for High-Band cell is LONGCYCLE_80MS..";
      type enumeration {
        enum LONGCYCLE_10MS;
        enum LONGCYCLE_20MS;
        enum LONGCYCLE_32MS;
        enum LONGCYCLE_40MS;
        enum LONGCYCLE_60MS;
        enum LONGCYCLE_64MS;
        enum LONGCYCLE_70MS;
        enum LONGCYCLE_80MS;
        enum LONGCYCLE_128MS;
        enum LONGCYCLE_160MS;
        enum LONGCYCLE_256MS;
        enum LONGCYCLE_320MS;
        enum LONGCYCLE_512MS;
        enum LONGCYCLE_640MS;
        enum LONGCYCLE_1024MS;
        enum LONGCYCLE_1280MS;
        enum LONGCYCLE_2048MS;
        enum LONGCYCLE_2560MS;
        enum LONGCYCLE_5120MS;
        enum LONGCYCLE_10240MS;
      }
    }
    leaf drxOnDurationTimer {
      description "Time period for which UE should be active at beginning of a DRX cycle. RRC parameter drx-onDurationTimer is specified in 3GPP TS 38.331 6.3.2..";
      type enumeration {
        enum ONDURATIONTIMER_1SUBMS;
        enum ONDURATIONTIMER_2SUBMS;
        enum ONDURATIONTIMER_3SUBMS;
        enum ONDURATIONTIMER_4SUBMS;
        enum ONDURATIONTIMER_5SUBMS;
        enum ONDURATIONTIMER_6SUBMS;
        enum ONDURATIONTIMER_7SUBMS;
        enum ONDURATIONTIMER_8SUBMS;
        enum ONDURATIONTIMER_9SUBMS;
        enum ONDURATIONTIMER_10SUBMS;
        enum ONDURATIONTIMER_11SUBMS;
        enum ONDURATIONTIMER_12SUBMS;
        enum ONDURATIONTIMER_13SUBMS;
        enum ONDURATIONTIMER_14SUBMS;
        enum ONDURATIONTIMER_15SUBMS;
        enum ONDURATIONTIMER_16SUBMS;
        enum ONDURATIONTIMER_17SUBMS;
        enum ONDURATIONTIMER_18SUBMS;
        enum ONDURATIONTIMER_19SUBMS;
        enum ONDURATIONTIMER_20SUBMS;
        enum ONDURATIONTIMER_21SUBMS;
        enum ONDURATIONTIMER_22SUBMS;
        enum ONDURATIONTIMER_23SUBMS;
        enum ONDURATIONTIMER_24SUBMS;
        enum ONDURATIONTIMER_25SUBMS;
        enum ONDURATIONTIMER_26SUBMS;
        enum ONDURATIONTIMER_27SUBMS;
        enum ONDURATIONTIMER_28SUBMS;
        enum ONDURATIONTIMER_29SUBMS;
        enum ONDURATIONTIMER_30SUBMS;
        enum ONDURATIONTIMER_31SUBMS;
        enum ONDURATIONTIMER_1MS;
        enum ONDURATIONTIMER_2MS;
        enum ONDURATIONTIMER_3MS;
        enum ONDURATIONTIMER_4MS;
        enum ONDURATIONTIMER_5MS;
        enum ONDURATIONTIMER_6MS;
        enum ONDURATIONTIMER_8MS;
        enum ONDURATIONTIMER_10MS;
        enum ONDURATIONTIMER_20MS;
        enum ONDURATIONTIMER_30MS;
        enum ONDURATIONTIMER_40MS;
        enum ONDURATIONTIMER_50MS;
        enum ONDURATIONTIMER_60MS;
        enum ONDURATIONTIMER_80MS;
        enum ONDURATIONTIMER_100MS;
        enum ONDURATIONTIMER_200MS;
        enum ONDURATIONTIMER_300MS;
        enum ONDURATIONTIMER_400MS;
        enum ONDURATIONTIMER_500MS;
        enum ONDURATIONTIMER_600MS;
        enum ONDURATIONTIMER_800MS;
        enum ONDURATIONTIMER_1000MS;
        enum ONDURATIONTIMER_1200MS;
        enum ONDURATIONTIMER_1600MS;
      }
    }
    leaf drxProfileUeCfgId {
      description "The value component of the RDN..";
      type string;
      mandatory true;
    }
    leaf drxRetransmissionTimerDl {
      description "Maximum number of consecutive PDCCH-subframes until a DL DCI assignment is sent. RRC parameter drx-RetransmissionTimerDL in 3GPP TS 38.331 6.3.2. Value shows number of slots. The slot length is defined by BWP used for previous reception.; Default value: 8.";
      type int32 {
        range "6 | 8 | 16";
      }
      default "8";
      units "slot";
    }
    leaf drxRetransmissionTimerUl {
      description "Maximum number of consecutive PDCCH-subframes until uplink grant is received by UE. RRC parameter drx-RetransmissionTimerUL in 3GPP TS 38.331 6.3.2. Value shows number of slots. Slot length is defined by BWP used for previous transmission. If PUSCH Repetition Type A is configured on UE, PuschRepRel16Drx::puschRepDrxRetxTimerUl is used if non-empty.; Default value: 8.";
      type int32 {
        range "6 | 8 | 16";
      }
      default "8";
      units "slot";
    }
    leaf drxState {
      description "Whether Connected Mode DRX feature to save energy in UE is enabled. If feature is disabled, Connected Mode DRX can still be activated in UE during CGI measurement..";
      type boolean;
    }
    leaf-list prefUeGroupList {
      description "Preference UE group list. List of preference UE group identifiers. If empty, MO instance matches preference UE group identifiers not defined in prefUeGroupList of any other MO instances under parent MO instance. Value 0 is no longer allowed and is planned to be removed from valid range..";
      type eytypes:int32_range_0-255;
      ordered-by user;
      min-elements 0;
      max-elements 8;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 16;
    }
    leaf-list ueGroupList {
      description "UE group list. List of UE group identifiers. If empty, MO instance matches all UE group identifiers. Value 0 is no longer allowed and is planned to be removed from valid range..";
      type eytypes:int32_range_0-255;
      ordered-by user;
      min-elements 0;
      max-elements 16;
    }
    leaf userLabel {
      description "Label for free use..";
      type string;
    }
  }
  grouping DU5qi-attributes {
    leaf aqmMode {
      description "AQM mode. Only applicable when GNBDUFunction::altDepHServAdapUPProfEnabled is false.; Default value: MODE1; Takes effect: New connection; Status info: Since 24.Q3. Planned to be removed..";
      type enumeration {
        enum OFF;
        enum MODE1;
        enum MODE2;
      }
      status deprecated;
      default "MODE1";
      reference "Takes effect: New connection.";
    }
    leaf drbRlcInDu5qiEnabled {
      description "Whether DRB RLC attributes in DU5qi MO are used. Attributes rlcSNLength, tReassemblyDl and tReassemblyUl are DRB RLC attributes in DU5qi MO. These are mapped from different tables using specific conditions. If true, DRB RLC attributes in DU5qi instance are used. If false, corresponding attributes in matched DrbRlcUeCfg instance under DrbRlc instance referenced by drbRlcRef are used..";
      type boolean;
    }
    leaf drbRlcRef {
      description "Reference to an instance of DrbRlc MO. Attributes are used from corresponding DrbRlcUeCfg instance under DrbRlc instance. DrbRlcUeCfg instance is selected according to UE grouping framework. Automatically set to DrbRlc=Default instance, unless manually set to refer to another MO instance..";
      type string;
    }
    leaf drbUpRef {
      description "Reference to an instance of DrbUp MO. Automatically set to following MO instance: - DrbUp=Default_application_signaling instance for DU5qi instances for which profile5qi is 5 or 69. - DrbUp=Default_conversational_media instance for DU5qi instances for which profile5qi is 1, 65, or 66. - DrbUp=Default_other instance for all other DU5qi instances. Unless manually set to refer to another MO instance. Only applicable when GNBDUFunction::altDepHServAdapUPProfEnabled is true..";
      type string;
    }
    leaf dscp {
      description "DSCP for 5QI. Corresponds to mappings from RAN QoS to transport network QoS. Following values are recommended: * 46 if profile5qi is 1, 65, 66, 67, 75, 82 or 83. * 36 if profile5qi is 2. * 34 if profile5qi is 3 or 79. * 38 if profile5qi is 4. * 40 if profile5qi is 5 or 69. * 26 if profile5qi is 6 or 70. * 10 if profile5qi is 7. * 12 if profile5qi is 8. * 14 if profile5qi is 9.; range 0..63; Default value: 12.";
      type eytypes:int32_range_0-63;
      default "12";
    }
    leaf dU5qiId {
      description "The value component of the RDN..";
      type string;
      mandatory true;
    }
    leaf estimatedE2ERTT {
      description "Estimated end-to-end Round-Trip Time (RTT). Only applicable when GNBDUFunction::altDepHServAdapUPProfEnabled is false.; range 0..1023; Default value: 50; Takes effect: New connection; Status info: Since 24.Q3. Planned to be removed..";
      type eytypes:int32_range_0-1023;
      status deprecated;
      default "50";
      units "ms";
      reference "Takes effect: New connection.";
    }
    leaf l4sCfgRef {
      description "Reference to an instance of L4sCfg MO. If non-empty, attributes from referenced MO instance are used. If empty, attribute default values according to MO class definition are used..";
      type string;
    }
    leaf logicalChannelGroupId {
      description "Logical Channel Group ID. Assigns logical channel group to QoS Class Indicator (5QI).; range 1..7; Default value: 5.";
      type eytypes:int32_range_1-7;
      default "5";
    }
    leaf logicalChannelRef {
      description "Reference to an instance of LogicalChannel MO. Automatically set to following MO instance: - LogicalChannel=IMS_Voice instance for DU5qi instances which profile5qi is 1 or 5. - LogicalChannel=Default instance for all other DU5qi instances. Unless manually set to refer to another MO instance..";
      type string;
    }
    leaf packetDelayBudget {
      description "The gNodeB contribution to PDB on 5QI. Packet delays outside gNodeB are excluded, for example, in transport network. Following values are recommended: * 80 if profile5qi is 1, 5, 7, 66, or 67. * 130 if profile5qi is 2. * 30 if profile5qi is 3 or 79. * 280 if profile5qi is 4, 6, 8, or 9. * 65 if profile5qi is 65. * 50 if profile5qi is 69. * 190 if profile5qi is 70. * 8 if profile5qi is 80. * 9 if profile5qi is 82 or 83. * 25 if profile5qi is 84. * 3 if profile5qi is 85. 3GPP defined 5QIs use up to 500 ms range.; range 0..1023; Default value: 280.";
      type eytypes:int32_range_0-1023;
      default "280";
      units "ms";
    }
    leaf packetDelayBudgetOffset {
      description "Offset added to PDB. Following values are recommended: * 0 if profile5qi is 2, 3, 4, 5, 6, 7, 8, 9, 65, 66, 67, 69, 70, 79, 80, 82, 83, 84 or 85. * 50 if profile5qi is 1. Only applicable when GNBDUFunction::altDepHServAdapUPProfEnabled is false.; range 0..1023; Default value: 0; Takes effect: New connection; Status info: Since 24.Q3. Planned to be removed..";
      type eytypes:int32_range_0-1023;
      status deprecated;
      default "0";
      units "ms";
      reference "Takes effect: New connection.";
    }
    leaf priorityLevel {
      description "5QI-related priority. Following values are recommended: * 20 if profile5qi is 1 or 66. * 40 if profile5qi is 2. * 30 if profile5qi is 3. * 50 if profile5qi is 4. * 10 if profile5qi is 5. * 60 if profile5qi is 6. * 70 if profile5qi is 7. * 80 if profile5qi is 8. * 90 if profile5qi is 9. * 7 if profile5qi is 65. * 15 if profile5qi is 67. * 5 if profile5qi is 69. * 55 if profile5qi is 70. * 65 if profile5qi is 79. * 68 if profile5qi is 80. * 19 if profile5qi is 82. * 22 if profile5qi is 83. * 24 if profile5qi is 84. * 21 if profile5qi is 85.; range 1..127; Default value: 80.";
      type int32 {
        range "1..127";
      }
      default "80";
    }
    leaf profile5qi {
      description "5G QoS Identifier, unique within a table.; range 0..255.";
      type eytypes:int32_range_0-255;
      mandatory true;
    }
    leaf puschRepRef {
      description "Reference to an instance of PuschRep MO. Automatically set to PuschRep=Default instance, unless manually set to refer to another MO instance..";
      type string;
    }
    leaf rlcSNLength {
      description "Radio Link Control (RLC) SN field size. Following values are recommended: * 18 if profile5qi is 8 or 9. * 12 if profile5qi is 1, 2, 3, 4, 5, 6, 7, 65, 66, 67, 69, or 70. * 6 if profile5qi is 79, 80, 82, 83, 84, or 85, and for voice over NR with good RF conditions. 3GPP recommends 6 when profile5qi is 1, 2, 65, 66, or 67..";
      type int32 {
        range "6 | 12 | 18";
      }
      units "bit";
    }
    leaf schedulingProfileRef {
      description "Reference to an instance of SchedulingProfile MO. If non-empty, attributes from referenced MO instance are used. If empty, attribute default values according to MO class definition are used..";
      type string;
    }
    leaf srHandlingRef {
      description "Reference to an instance of SrHandling MO. Automatically set to SrHandling=Default instance, unless manually set to refer to another MO instance..";
      type string;
    }
    leaf tReassemblyDl {
      description "DL Radio Link Control (RLC) timer reassembly. Following values are recommended: * 35 if profile5qi is 1, 2, 65, 66, 67 or 79. * 25 if profile5qi is 3, 4, 5, 6, 7, 8, 9, 69, 70 or 84. * 10 if profile5qi is 80, 82 or 83. * 5 if profile5qi is 85..";
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200";
      }
      units "ms";
    }
    leaf tReassemblyUl {
      description "UL Radio Link Control (RLC) timer reassembly. Following values are recommended: * 35 if profile5qi is 1, 2, 65, 66, 67 or 79. * 25 if profile5qi is 3, 4, 5, 6, 7, 8, 9, 69, 70 or 84. * 10 if profile5qi is 80, 82 or 83. * 5 if profile5qi is 85..";
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200";
      }
      units "ms";
    }
    leaf ulPacketDelayBudget {
      description "The gNodeB contribution to PDB on 5QI in uplink. Packet delays outside gNodeB are excluded, for example, in transport network. Following values are recommended: * 80 if profile5qi is 1, 5, 7, 66 or 67. * 130 if profile5qi is 2. * 30 if profile5qi is 3 or 79. * 280 if profile5qi is 4, 6, 8, or 9. * 65 if profile5qi is 65. * 50 if profile5qi is 69. * 190 if profile5qi is 70. * 8 if profile5qi is 80. * 9 if profile5qi is 82 or 83. * 25 if profile5qi is 84. * 3 if profile5qi is 85. If empty, value from packetDelayBudget is used. Only applicable if SchedulingProfile::schedulingAlgorithm is LATENCY_PRIORITIZED_TCC. Only applicable if at least one of the following features is present and feature is active: - Latency-Prioritized Scheduling for Time-Critical Communication for Public RAN - Latency-Prioritized Scheduling for Time-Critical Communication for Dedicated RAN; range 0..1023.";
      type eytypes:int32_range_0-1023;
      units "ms";
    }
    leaf userLabel {
      description "Label for free use..";
      type string;
    }
  }
  grouping DU5qiTable-attributes {
    leaf default5qiTable {
      description "Indicates that DU5qiTable instance is a default 5QI table. The default 5QI table is used when no DU5qiTable instance has been configured for a resource partition.; Default value: false.";
      type boolean;
      default "false";
    }
    leaf dU5qiTableId {
      description "The value component of the RDN..";
      type string;
      mandatory true;
    }
    leaf-list reservedBy {
      description "Contains a list of MO instances that reserve this MO instance..";
      type string;
      min-elements 0;
    }
  }
  grouping DUModified5qi-attributes {
    leaf dUModified5qiId {
      description "The value component of the RDN..";
      type string;
      mandatory true;
    }
    leaf modifiedProfile5qi {
      description "NR QoS identifier of QoS flow to be modified. Must be unique among DUModified5qi instances under DUQosModifier instance.; range 1..255.";
      type eytypes:int32_range_1-255;
      mandatory true;
    }
    leaf ueConfGroupType {
      description "UE configuration group type. UE configuration group type that is applied in contained DUModified5qiUeCfg instances..";
      type enumeration {
        enum UE_MOBILITY_GROUP;
        enum UE_SERVICE_GROUP;
        enum UE_ADMISSION_GROUP;
      }
    }
  }
  grouping DUModified5qiUeCfg-attributes {
    leaf dUModified5qiUeCfgId {
      description "The value component of the RDN..";
      type string;
      mandatory true;
    }
    leaf l4sCfgRef {
      description "Reference to an instance of L4sCfg MO. If empty, DU5qi::l4sCfgRef is used..";
      type string;
    }
    leaf logicalChannelRef {
      description "Reference to an instance of LogicalChannel MO. Automatically set to following MO instance: - LogicalChannel=IMS_Voice instance for DUModified5qiUeCfg instances which modifiedProfile5qi is 1 or 5. - LogicalChannel=Default instance for all other DUModified5qiUeCfg instances. Unless manually set to refer to another MO instance..";
      type string;
    }
    leaf packetDelayBudget {
      description "The gNodeB contribution to PDB on 5QI. Packet delays outside gNodeB are excluded, for example, in transport network. If empty, DU5qi::packetDelayBudget is used. 3GPP defined 5QIs use up to 500 ms range.; range 1..512.";
      type int32 {
        range "1..512";
      }
      units "ms";
    }
    leaf-list prefUeGroupList {
      description "Preference UE group list. List of preference UE group identifiers. If empty, MO instance matches preference UE group identifiers not defined in prefUeGroupList of any other MO instances under parent MO instance. Value 0 is no longer allowed and is planned to be removed from valid range..";
      type eytypes:int32_range_0-255;
      ordered-by user;
      min-elements 0;
      max-elements 8;
    }
    leaf priorityLevel {
      description "5QI-related priority. If empty, DU5qi::priorityLevel is used.; range 1..127.";
      type int32 {
        range "1..127";
      }
    }
    leaf schedulingProfileRef {
      description "Reference to an instance of SchedulingProfile MO. If empty, DU5qi::schedulingProfileRef is used..";
      type string;
    }
    leaf srHandlingRef {
      description "Reference to an instance of SrHandling MO. Automatically set to SrHandling=Default instance, unless manually set to refer to another MO instance..";
      type string;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 16;
    }
    leaf-list ueGroupList {
      description "UE group list. List of UE group identifiers. If empty, MO instance matches all UE group identifiers. Value 0 is no longer allowed and is planned to be removed from valid range..";
      type eytypes:int32_range_0-255;
      ordered-by user;
      min-elements 0;
      max-elements 16;
    }
    leaf ulPacketDelayBudget {
      description "The gNodeB contribution to PDB on 5QI in uplink. Packet delays outside gNodeB are excluded, for example, in transport network. Following values are recommended: * 80 if profile5qi is 1, 5, 7, 66 or 67. * 130 if profile5qi is 2. * 30 if profile5qi is 3 or 79. * 280 if profile5qi is 4, 6, 8, or 9. * 65 if profile5qi is 65. * 50 if profile5qi is 69. * 190 if profile5qi is 70. * 8 if profile5qi is 80. * 9 if profile5qi is 82 or 83. * 25 if profile5qi is 84. * 3 if profile5qi is 85. If empty, value from packetDelayBudget is used. Only applicable if SchedulingProfile::schedulingAlgorithm is LATENCY_PRIORITIZED_TCC. Only applicable if at least one of the following features is present and feature is active: - Latency-Prioritized Scheduling for Time-Critical Communication for Public RAN - Latency-Prioritized Scheduling for Time-Critical Communication for Dedicated RAN; range 0..1023.";
      type eytypes:int32_range_0-1023;
      units "ms";
    }
    leaf userLabel {
      description "Label for free use..";
      type string;
    }
  }
  grouping DUQos-attributes {
    leaf dUQosId {
      description "The value component of the RDN..";
      type string;
      mandatory true;
    }
  }
  grouping DUQosModifier-attributes {
    leaf dUQosModifierId {
      description "The value component of the RDN..";
      type string;
      mandatory true;
    }
  }
  grouping DynPowerOpt-attributes {
    leaf downDlThreshold {
      description "Threshold used for DCI-based BWP switch from dense to sparse BWP in downlink. If 0, switch timer lowDlActivityTimer starts directly after downlink buffer is empty.; range 0..2000; Default value: 10.";
      type eytypes:int32_range_0-2000;
      default "10";
      units "slot";
    }
    leaf downUlThreshold {
      description "Threshold used for DCI-based BWP switch from dense to sparse BWP in uplink. If 0, switch timer lowUlActivityTimer starts directly after uplink buffer is empty.; range 0..2000; Default value: 10.";
      type eytypes:int32_range_0-2000;
      default "10";
      units "slot";
    }
    leaf dynPowerOptId {
      description "The value component of the RDN..";
      type string;
      mandatory true;
    }
    leaf lowDlActivityTimer {
      description "Timer used for DCI-based BWP switch from dense to sparse BWP in downlink. If 0, switch can be triggered as soon as amount of data in downlink buffer is not bigger than switch threshold calculated from downDlThreshold.; range 0..5000; Default value: 200.";
      type eytypes:int32_range_0-5000-4;
      default "200";
      units "ms";
    }
    leaf lowUlActivityTimer {
      description "Timer used for DCI-based BWP switch from dense to sparse BWP in uplink. If 0, switch can be triggered as soon as amount of data in uplink buffer is not bigger than switch threshold calculated from downUlThreshold.; range 0..5000; Default value: 200.";
      type eytypes:int32_range_0-5000-4;
      default "200";
      units "ms";
    }
    leaf-list reservedBy {
      description "Contains a list of MO instances that reserve this MO instance..";
      type string;
      min-elements 0;
    }
    leaf upDlThreshold {
      description "Threshold used for DCI-based BWP switch from sparse to dense BWP in downlink. If 0, switch is triggered as soon as downlink buffer is non-empty.; range 0..2000; Default value: 30.";
      type eytypes:int32_range_0-2000;
      default "30";
      units "slot";
    }
    leaf upUlThreshold {
      description "Threshold used for DCI-based BWP switch from sparse to dense BWP in uplink. If 0, switch is triggered as soon as uplink buffer is non-empty.; range 0..2000; Default value: 30.";
      type eytypes:int32_range_0-2000;
      default "30";
      units "slot";
    }
    leaf userLabel {
      description "Label for free use..";
      type string;
    }
  }
  grouping EndpointResource-attributes {
    leaf endpointResourceId {
      description "The value component of the RDN..";
      type string;
      mandatory true;
    }
    leaf-list reservedBy {
      description "Contains a list of MO instances that reserve this MO instance..";
      type string;
      min-elements 0;
    }
    leaf userLabel {
      description "Label for free use..";
      type string;
    }
  }
  grouping EnergyEfficiency-attributes {
    leaf energyEfficiencyId {
      description "The value component of the RDN..";
      type string;
      mandatory true;
    }
  }
  grouping EnergyOptPwrAlloc-attributes {
    leaf avgRbSymThresh {
      description "Threshold for disabling Energy-Optimized Power Allocation feature. Threshold is based on average downlink resource block symbol utilization. When average utilization is higher than this attribute value, then Energy-Optimized Power Allocation feature applies no digital power backoff. When average utilization is lower than or equal to this attribute value - 10 %, then Energy-Optimized Power Allocation feature applies digital power backoff.; range 30..100; Default value: 100.";
      type int32 {
        range "30..100";
      }
      default "100";
    }
    leaf energyOptPwrAllocCellMode {
      description "Whether Energy-Optimized Power Allocation feature in NRCellDU is enabled..";
      type enumeration {
        enum DISABLED;
        enum ENABLED;
      }
    }
    leaf energyOptPwrAllocId {
      description "The value component of the RDN..";
      type string;
      mandatory true;
    }
    leaf energyOptPwrAllocMode {
      description "Whether Energy Optimization Power Allocation feature in NRCellDU is enabled..";
      type enumeration {
        enum DISABLED;
        enum ENABLED;
      }
    }
    leaf rbExpansionTarget {
      description "Targeted resource block usage value. If estimated resource block usage in slot without power backoff is lower than target value, Energy-Optimized Power Allocation feature decrease output power and decrease MCS to match lowered power. To transfer data with decreased MCS, more resource blocks are required and target is to reach target value. If estimate resource block usage is higher than this attribute value, no backoff is performed. Resulting resource block allocation depends on traffic, SINR and more parameters, but this attribute value cannot be reached. In rare cases expansion can be higher than target value.; range 1..200; Default value: 70.";
      type int32 {
        range "1..200";
      }
      default "70";
    }
    leaf-list reservedBy {
      description "Contains a list of MO instances that reserve this MO instance..";
      type string;
      min-elements 0;
    }
    leaf ueConfGroupType {
      description "UE configuration group type. UE configuration group type that is applied in contained EnergyOptPwrAllocUeCfg instances..";
      type enumeration {
        enum UE_MOBILITY_GROUP;
        enum UE_SERVICE_GROUP;
        enum UE_ADMISSION_GROUP;
      }
    }
  }
  grouping EnergyOptPwrAllocUeCfg-attributes {
    leaf energyOptPwrAllocMode {
      description "Whether the Energy-Optimized Power Allocation feature is enabled for this profile in UE Groups..";
      type enumeration {
        enum DISABLED;
        enum ENABLED;
      }
    }
    leaf energyOptPwrAllocUeCfgId {
      description "The value component of the RDN..";
      type string;
      mandatory true;
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
  }
  grouping ExtCaPriority-attributes {
    leaf adjustedPriorityMode {
      description "Priority mode this SCell shall use when scheduling external data..";
      type enumeration {
        enum STATIC_PRIO_WITHOUT_POLICING;
        enum STATIC_PRIO_WITH_POLICING;
        enum DYNAMIC_PRIO;
      }
    }
    leaf extCaPriorityId {
      description "The value component of the RDN..";
      type string;
      mandatory true;
    }
    leaf priorityDomainBase {
      description "Priority Domain this SCell shall use when scheduling external data. Applicable when adjustedPriorityMode is STATIC_PRIO_WITH_POLICING or STATIC_PRIO_WITHOUT_POLICING.; range 1..64; Default value: 48.";
      type eytypes:int32_range_1-64;
      default "48";
    }
    leaf priorityDomainLimit {
      description "Highest priority of Priority Domains that SpCell is allowed to set. Used when prioritizing external data to this SCell. Applicable when adjustedPriorityMode is DYNAMIC_PRIO.; range 1..64; Default value: 1.";
      type eytypes:int32_range_1-64;
      default "1";
    }
    leaf relativePriorityBase {
      description "Relative Priority this SCell shall use when scheduling external data. Applicable when adjustedPriorityMode is STATIC_PRIO_WITH_POLICING or STATIC_PRIO_WITHOUT_POLICING.; range 1..256; Default value: 1.";
      type eytypes:int32_range_1-256;
      default "1";
    }
    leaf relativePriorityLimit {
      description "Maximum Relative Priority SpCell is allowed to set when prioritizing external data to this SCell. Applicable when adjustedPriorityMode is DYNAMIC_PRIO.; range 1..256; Default value: 256.";
      type eytypes:int32_range_1-256;
      default "256";
    }
    leaf-list reservedBy {
      description "Contains a list of MO instances that reserve this MO instance..";
      type string;
      min-elements 0;
    }
  }
  grouping ExtENodeBPartnerFunction-attributes {
    leaf eNbId {
      description "Identity of partner eNodeB within a PLMN.; range 0..1048575.";
      type eytypes:int32_range_0-1048575;
      mandatory true;
    }
    leaf extENodeBPartnerFunctionId {
      description "The value component of the RDN..";
      type string;
      mandatory true;
    }
    leaf locatedOnIntraMe {
      description "Whether partner eNodeB is located on same RAN Compute unit.; Default value: false.";
      type boolean;
      default "false";
    }
    leaf pimVlanPortRef {
      description "Reference to an instance of VlanPort MO. VlanPort instance that can be used to set up Elastic RAN link for PIM function. If empty, GNBDUFunction::pimVlanPortRef is used as default..";
      type string;
    }
  }
  grouping ExtGNBDUPartnerFunction-attributes {
    leaf caVlanPortRef {
      description "Reference to an instance of VlanPort MO used by the InterMeLink. Overrides value of GNBDUFunction::caVlanPortRef..";
      type string;
    }
    leaf extGNBDUPartnerFunctionId {
      description "The value component of the RDN..";
      type string;
      mandatory true;
    }
    leaf gNBDUId {
      description "Unique identifier for the 3GPP distributed unit in a partner gNodeB.; range 0..68719476735.";
      type eytypes:int64_range_0-68719476735;
      mandatory true;
    }
    leaf gNBDUName {
      description "Distributed unit name..";
      type string;
      config false;
    }
    leaf gNBId {
      description "Identity of partner gNodeB within a PLMN.; range 0..4294967295.";
      type eytypes:int64_range_0-4294967295;
      mandatory true;
    }
    leaf gNBIdLength {
      description "Length of gNBId bit string representation. Must be at least minimum bit length that can accommodate gNBId if gNBId bit representation exceeds 22 bits.; range 22..32; Default value: 22.";
      type eytypes:int32_range_22-32;
      default "22";
    }
  }
  grouping FlowLimit-attributes {
    leaf-list flowLimit5qiList {
      description "List of QoS Identifier values for which configured limits apply. If empty, configured limits apply for all QoS Identifier values. Only applicable if license for at least one of following features is present and feature is active: - NR Service Admission Control - Service Adaptive Admission and Preemption.";
      type eytypes:int32_range_1-255;
      ordered-by user;
      min-elements 0;
      max-elements 12;
    }
    leaf flowLimitId {
      description "The value component of the RDN..";
      type string;
      mandatory true;
    }
    leaf maxNoOfFlows {
      description "Maximum number of admitted QoS flows. If empty, number of QoS flows is not limited. Only applicable if license for at least one of following features is present and feature is active: - NR Service Admission Control - Service Adaptive Admission and Preemption; range 0..2147483647.";
      type eytypes:int32_range_0-2147483647;
    }
    leaf preemptionEnabled {
      description "Whether DRB preemption is enabled. NR Standalone DRB can preempt NR Standalone or EN-DC Secondary Node terminated DRB. EN-DC Secondary Node terminated or NR-DC Secondary Node terminated DRB cannot preempt other DRB. NR-DC Secondary Node terminated DRB cannot be preempted. Only applicable if license for Service Adaptive Admission and Preemption is present and feature is active.; Default value: false.";
      type boolean;
      default "false";
    }
    leaf softAdmissionEnabled {
      description "Whether QoS flow Soft Admission is enabled. Only applicable if license for NR Soft Admission is present and feature is active.; Default value: false.";
      type boolean;
      default "false";
    }
  }
  grouping GNBDUFunction-attributes {
    leaf activeF1Link {
      description "Active F1-C link used for traffic towards gNodeB-CU-CP..";
      type enumeration {
        enum NOT_ACTIVE;
        enum ACTIVE;
      }
      config false;
    }
    leaf altDepHMultCGPeriodEnabled {
      description "Whether alternative deprecation handling for uplink configured grant profiles is enabled. If true, following attribute is used: - ConfiguredGrantUeCfg::configuredGrantPeriodicity Otherwise, following attribute to be deprecated is used: - NRCellDU::configuredGrantPeriodicity Only applicable to Low-Band and Mid-Band cells..";
      type boolean;
    }
    leaf altDepHServAdapUPProfEnabled {
      description "Whether alternative deprecation handling for Service Adaptive User Plane Profiles is enabled. If enabled, following attributes are used: - DU5qi::drbUpRef - DrbUp::ueConfGroupType - DrbUpUeCfg::ueGroupList - DrbUpUeCfg::ueConfGroupList - DrbUpUeCfg::prefUeGroupList - DrbUpUeCfg::aqmCfgRef - AqmCfg::aqmMode - AqmCfg::estimatedE2ERTT - AqmCfg::tDiscardDl Otherwise, following deprecated attributes are used: - DU5qi::aqmMode - DU5qi::estimatedE2ERTT - DU5qi::packetDelayBudgetOffset; Default value: false.";
      type boolean;
      default "false";
    }
    leaf autoLockDelay {
      description "Delay after O&M connection loss detection when automatic cell locking is applied. Only applicable if license for NR Automatic Cell Lock at OAM Connection Outage is present and feature is active. Only relevant when NRCellDU::autoLockAction is IMMEDIATE_LOCK or SOFT_LOCK. No action is performed if O&M connection is restored before delay time elapses. If 0, automatic locking is applied immediately after O&M connection loss detection. Detection of lost O&M connection can take up to 10 minutes, therefore effective locking takes place maximally after 10 minutes plus value of this attribute.; range 0..60; Default value: 0.";
      type uint32 {
        range "0..60";
      }
      default "0";
      units "minute";
    }
    leaf capacityAllocationPolicy {
      description "Policy for allocation of Baseband capacity on hardware resources. Has impact on Baseband Power Savings function. If value is SYSTEM_SELECTED, Baseband Power Savings function is controlled by configuration in PowerSaving MO. For other values, configuration in PowerSaving MO is overridden and Baseband Power Savings function is deactivated..";
      type enumeration {
        enum SYSTEM_SELECTED;
        enum CAPACITY_PRIORITIZATION;
        enum CAPACITY_PRIORITIZATION_TDD;
      }
    }
    leaf capacityAllocationStatus {
      description "Value of capacityAllocationPolicy currently used..";
      type enumeration {
        enum SYSTEM_SELECTED;
        enum CAPACITY_PRIORITIZATION;
        enum CAPACITY_PRIORITIZATION_TDD;
      }
      config false;
    }
    leaf caVlanPortRef {
      description "Reference to an instance of VlanPort MO that can be used to set up InterMeLinks. Used as default when no value is specified for ExtGNBDUPartnerFunction::caVlanPortRef..";
      type string;
    }
    leaf configuredGrantConfMode {
      description "Configuration mode for configured grant periodicity. Whether configured grant periodicity is configured on cell level or on configured grant profile level. Only applicable to Low-Band and Mid-Band cells..";
      type enumeration {
        enum CELL_CG_PERIODICITY;
        enum CG_PROFILE_CG_PERIODICITY;
      }
    }
    leaf dlBbCapacityMaxLimit {
      description "Maximum downlink baseband capacity available on unlocked Baseband hardware. Maximum limit of downlink capacity that can be granted by baseband HWAC. This level sets the limit at emergency unlock.; range 0..65535.";
      type eytypes:int32_range_0-65535;
      config false;
      units "Mbps";
    }
    leaf dlBbCapacityNet {
      description "Granted downlink baseband capacity. Available capacity of corresponding Baseband HWAC property for all enabled Baseband HW.; range 0..65535.";
      type eytypes:int32_range_0-65535;
      config false;
      units "Mbps";
    }
    leaf dlBbCapacityTarget {
      description "Required amount of Baseband HWAC throughput capacity for downlink to be allocated to NR. The setting impacts installation and distribution of HUPs on the node. In LTE + NR mixed mode Baseband configuration, ENodeBFunction::dlBbCapacityTarget must also be considered in following cases: - If greater than or equal to 75 for just one RAT, the system attempts to allocate the required value to that RAT. Available excess capacity is allocated to the other RAT. - If greater than or equal to 75 on both RATs, an attempt to fulfill both requirements is made with priority to NR. Until requirements are met, HUPs are distributed proportionally. Afterwards, HUPs are distributed equally. - If undefined on both RATs (set to empty on NR and set to -1 on LTE), Baseband HWAC throughput capacity for downlink is equally allocated by the system to the extent allowed by HUPs, with priority to NR. With the Instantaneous Licensing feature activated, an undefined attribute setting gives a minimum requirement of 75 Mbps. Granted Baseband DL capacity is shown by dlBbCapacityNet. Granted Baseband uplink capacity is half of granted downlink capacity and is shown by ulBbCapacityNet. Information on installed Baseband HWACs and HUPs can be found in CapacityUsage::hupInfo.; range 75..65535.";
      type int32 {
        range "75..65535";
      }
      units "Mbps";
    }
    list dUpLMNId {
      config false;
      description "PLMN identifier used as part of PM Events data. Same value as GNBCUCPFunction::pLMNId. Value MCC=001, MNC=01 means PLMN is not initiated. This value cannot be used as a valid PLMN Identity..";
      uses PLMNId-struct;
    }
    leaf dynTACConfigEnabled {
      description "Whether dynamic configuration of NRCellDU::nRTAC and AdditionalPLMNInfo::nRTAC is enabled. Attribute nRTAC changed while value of this attribute is false takes effect when value is changed to true.; Default value: false.";
      type boolean;
      default "false";
    }
    leaf endpointResourceRef {
      description "Reference to an instance of EndpointResource MO. ResourcePartitionMember MO can also refer to EndpointResource instances only valid for specific PLMN or NSSAI. If ResourcePartitionMember::endpointResourceRef is empty, this reference is used..";
      type string;
    }
    leaf gNBDUFunctionId {
      description "The value component of the RDN..";
      type string;
      mandatory true;
    }
    leaf gNBDUId {
      description "Unique identifier for the DU within a gNodeB.; range 0..68719476735.";
      type eytypes:int64_range_0-68719476735;
      mandatory true;
    }
    leaf gNBDUName {
      description "Name of the gNodeB-DU. Allowed characters for value, are as follows: - a-z - A-Z - 0-9 - Space - Apostrophe (') - Left and right parenthesis ((,)) - Plus and minus sign (+,-) - Comma (,) - Full stop (.) - Forward slash (/) - Colon (:) - Equal sign (=) - Question mark (?) Character case is preserved. Length of name cannot exceed 150 characters. For more information, see PrintableString of ITU-T Rec X.680. If attribute contains invalid characters, each invalid one is replaced by a space before the string is sent to gNodeB-CU. If empty, gNBDU-Name is not sent to gNodeB-CU.; length 1..150.";
      type string {
        length "1..150";
      }
    }
    leaf gNBId {
      description "Identity of gNodeB within a PLMN.; range 0..4294967295.";
      type eytypes:int64_range_0-4294967295;
      mandatory true;
    }
    leaf gNBIdLength {
      description "Length of gNBId bit string representation. Must be at least minimum bit length that can accommodate gNBId if gNBId bit representation exceeds 22 bits. gNBId =< (2^gNBIdLength)-1; range 22..32; Default value: 22.";
      type eytypes:int32_range_22-32;
      default "22";
    }
    leaf measGapLengthMode {
      description "Whether measurement gap length (MGL) with 3 ms length instead of default 6 ms length is enabled. Measurement gap length 3 ms can be enabled for NR FR1 measurements, E-UTRAN measurements, or both. 6 ms gap is used even if 3 ms gap is enabled in following cases: - UE does not support 3 ms gap. - Both NR FR1 and E-UTRAN measurements are configured and 3 ms gap is only enabled for one of them. - FR2 measurement is configured, and UE does not support independent gaps. 3 ms gap corresponds to gap pattern (GP) GP2 and GP3. 6 ms gap corresponds to GP0 and GP1. GP0 and GP2 are only used for E-UTRAN measurements configured for the purpose of EPS fallback, otherwise GP1 and GP3 are used..";
      type enumeration {
        enum OFF;
        enum EUTRAN_3MS;
        enum NR_FR1_3MS;
        enum ALL_3MS;
      }
    }
    leaf mixedSrsModeEnabled {
      description "Whether support for both Periodic and Aperiodic SRS is simultaneously enabled in an NR cell. Only applicable to Mid-Band cells. Only applicable to RAN Compute group 5 and higher.; Default value: false.";
      type boolean;
      default "false";
    }
    leaf multiTddPatternSmEnabled {
      description "Whether multiple TDD patterns are enabled for NR Single Mode Baseband configurations. Must be false for High-Band cells.; Default value: false.";
      type boolean;
      default "false";
    }
    leaf noOfUsedPimAvoidEranPartners {
      description "Number of connected E-RAN PIM avoidance partners. If 4, new E5 tunnel for PIM avoidance cannot be established.; range 0..4.";
      type int32 {
        range "0..4";
      }
      config false;
    }
    leaf pimAutoDetectionEnabled {
      description "Whether automatic PIM Detection is activated in this gNodeB.; Default value: false; Status info: Since 24.Q1. Planned to be removed..";
      type boolean;
      status deprecated;
      default "false";
    }
    leaf pimCancAutoConfigEnabled {
      description "Whether automatic configuration for PIM cancellation is active. If true, - PimCancellationFunction instance and NRPimCancellationConfig instance are created automatically. - Automatically created MO instances are active in PIM cancellation. - Manually created instances are inactive. If false, - Automatically created MO instances are deleted.; Default value: false.";
      type boolean;
      default "false";
    }
    leaf pimVlanPortRef {
      description "Reference to an instance of VlanPort MO. VlanPort instances that can be used to set up Elastic RAN link for PIM function. Used as default value when no value is specified for ExtENodeBPartnerFunction::pimVlanPortRef. If empty, LteInterMeLink instances cannot be created..";
      type string;
    }
    leaf pwsEtwsPrimaryInd {
      description "Number of consecutive defaultPagingCycles during which ETWS primary notification is broadcast.; range 3..16; Default value: 8.";
      type int32 {
        range "3..16";
      }
      default "8";
    }
    leaf release {
      description "The product release of the ManagedFunction..";
      type string;
      config false;
    }
    leaf rimAggressorRSSetRef {
      description "Reference to an instance of RimRSSet MO. Used for aggressor set. If empty and setIdAllocation is CELL, no aggressor RimRSSet instance is used in this gNodeB. Only applicable if GNBDUFunction::setIdAllocation is G_NODE_B..";
      type string;
    }
    leaf rimVictimRSSetRef {
      description "Reference to an instance of RimRSSet MO. Used for victim set. If empty and setIdAllocation is CELL, no victim RimRSSet instance is used in this gNodeB. Only applicable if GNBDUFunction::setIdAllocation is G_NODE_B..";
      type string;
    }
    leaf servAdapUPProfDepHEnabled {
      description "Whether deprecation handling for downlink cell group switching attributes in NRCellDU is enabled. If true, updating any of following attributes to be deprecated in NRCellDU instance - endcDlLegSwitchEnabled - endcDlNrLowQualThresh - endcDlNrQualHyst also updates corresponding (replacing) attribute in corresponding CgSwitchCfg instance. If false, CgSwitchCfg MO instance is not updated. Node always uses attributes configured in used CgSwitchCfg instance. Updating that MO class never updates deprecated attributes. Disabling deprecation handling prevents attributes in CgSwitchCfg MO instance from being overwritten in new management system versions where CgSwitchCfg MO instance is visible and used instead of deprecated attributes.; Default value: true.";
      type boolean;
      default "true";
    }
    leaf servAdapUPProfUlDepHEnabled {
      description "Whether deprecation handling for attributes in NRCellDU is enabled. If true, updating any of following deprecated attributes in NRCellDU instance also updates corresponding attribute in corresponding UlCgSwitchCfg instance: - endcUlLegSwitchEnabled - endcUlNrLowQualThresh - endcUlNrQualHyst If false, UlCgSwitchCfg instance is not updated. Attributes in corresponding UlCgSwitchCfg instance are always applied. Updating attributes in UlCgSwitchCfg never updates corresponding deprecated attributes. Disabling deprecation handling prevents attributes in UlCgSwitchCfg instance from being overwritten in new management system versions where UlCgSwitchCfg instance is visible and used instead of deprecated attributes.; Default value: true.";
      type boolean;
      default "true";
    }
    leaf setIdAllocation {
      description "Whether RIM set ID is allocated on gNodeB or cell level..";
      type enumeration {
        enum G_NODE_B;
        enum CELL;
      }
    }
    leaf trafficDefinitionDepHEnabled {
      description "Whether deprecation handling for TrafficGroup and TrafficGroupMember is enabled. If true, updating any of following deprecated attributes in TrafficGroupMember instance also updates corresponding attribute in corresponding TrafficSet and TrafficSetMember instances under TrafficDefinitions instance: - TrafficSetMember::sNSSAIList - TrafficSetMember::plmnIdList - TrafficSetMember::spidRfspList - TrafficSetMember::trafficCategory - TrafficSet::sessionLimitRef If true, updating deprecated NRCellDU::trafficGroupRef also updates NRCellDU::trafficDefinitionRef. If false, NRCellDU:: trafficDefinitionRef and TrafficSet and TrafficSetMember instances are not updated. NRCellDU::trafficDefinitionRef and attributes in corresponding TrafficSet and TrafficSetMember instances are always applied. Updating NRCellDU::trafficDefinitionRef and attributes in TrafficSet and TrafficSetMember instances never updates corresponding deprecated attributes. Disabling deprecation handling prevents NRCellDU::trafficDefinitionRef and attributes in TrafficSet and TrafficSetMember instances from being overwritten in new management system versions where TrafficSet and TrafficSetMember instances are visible and used instead of deprecated attributes.; Default value: true.";
      type boolean;
      default "true";
    }
    leaf ulBbCapacityMaxLimit {
      description "Maximum uplink baseband capacity available on unlocked Baseband hardware. Maximum limit of uplink capacity that can be granted by baseband HWAC. This level sets the limit at emergency unlock.; range 0..65535.";
      type eytypes:int32_range_0-65535;
      config false;
      units "Mbps";
    }
    leaf ulBbCapacityNet {
      description "Granted uplink baseband capacity. Available capacity of corresponding Baseband HWAC property for all enabled Baseband HW.; range 0..65535.";
      type eytypes:int32_range_0-65535;
      config false;
      units "Mbps";
    }
    leaf ulServiceDepHEnabled {
      description "Whether deprecation handling for ulServicePacketInterval and ulServicePacketSize is enabled. Attributes ulServicePacketInterval and ulServicePacketSize are under UlLinkAdaptation instance. If true, deprecation handling as below apply: - At create/delete of UlLinkAdaptation instance Create/delete corresponding instance of UlService and its parent UlServiceDefinitionUeCfg using RDN of UlLinkAdaptation parent MO instance. - At set of UeBbProfileUeCfg::linkAdaptationUeCfgRef Set UeBbProfileUeCfg::ulServiceDefinitionUeCfgRef to corresponding instance of UlServiceDefinitionUeCfg - At update of deprecated ulServicePacketInterval or ulServicePacketSize in UlLinkAdaptation instance Update replacing attributes in corresponding UlService instance If false, no deprecation handling is applied for ulServicePacketInterval and ulServicePacketSize in UlLinkAdaptation instance. Node always uses ulServicePacketInterval and ulServicePacketSize configured in UlService instance. Updating UlService instance never updates deprecated attributes. Disabling deprecation handling prevents attributes in UlService instance from being overwritten in new management system versions where UlService instance is visible and used instead of deprecated attributes.; Default value: true.";
      type boolean;
      default "true";
    }
    leaf userLabel {
      description "Label for free use..";
      type string;
    }
    leaf pmPagF1ReceivedEdrx {
      description "Number of F1AP eDRX paging messages received in gNodeB-DU. Both Core Network paging and Radio Access Network paging are included. Subset of GNBDUFunction.pmPagF1Received PM counter. Unit: N/A.";
      type uint64;
      config false;
    }
    leaf pmLicDlSlotsHwacLimit {
      description "Aggregated number of downlink slots in which throughput HWAC limits scheduled data..";
      type uint64;
      config false;
    }
    leaf pmLic5MHzBwHwacFdd {
      description "Current level of HWACs of type NR AAS FDD Channel Bandwidth 5 MHz, allocated to FDD sector carriers. Unit: N/A.";
      type int64;
      config false;
    }
    leaf pmLicUlCapUsedSum {
      description "Accumulated sum of uplink Baseband throughput capacity usage over a ROP period. Unit: kbps.";
      type uint64;
      config false;
    }
    leaf-list pmFwkStreamDroppedEventSocketSetupFailDistr {
      description "Number of PM events dropped due to socket setup failure in each CTR stream in PM framework. Ranges: Bin[0]: Applicable for the Cell Trace Job ID 10000 Bin[1]: Applicable for the Cell Trace Job ID 10001 Bin[2]: Applicable for the Cell Trace Job ID 10002 Bin[3]: Applicable for the Cell Trace Job ID 10003 Bin[4]: Applicable for the Cell Trace Job ID 10004 Bin[5]: Applicable for the Cell Trace Job ID 10005.";
      type uint64;
      max-elements 6;
    }
    leaf pmFwkSampLostL2Sectorcarrier {
      description "Total number of lost or incomplete granularity level Sector Carrier samples in Layer 2. Unit: samples.";
      type uint64;
      config false;
    }
    leaf pmRimAggressorCellDetectedMax {
      description "Maximum number of unique aggressor cells which detect RS1..";
      type int64;
      config false;
    }
    leaf-list pmFwkStreamDroppedEventSocketConnectionFailDistr {
      description "Number of PM events dropped due to socket connection failure in each CTR stream in PM framework. Ranges: Bin[0]: Applicable for the Cell Trace Job ID 10000 Bin[1]: Applicable for the Cell Trace Job ID 10001 Bin[2]: Applicable for the Cell Trace Job ID 10002 Bin[3]: Applicable for the Cell Trace Job ID 10003 Bin[4]: Applicable for the Cell Trace Job ID 10004 Bin[5]: Applicable for the Cell Trace Job ID 10005.";
      type uint64;
      max-elements 6;
    }
    leaf pmLicDlCapUsedSum {
      description "Accumulated sum of downlink Baseband throughput capacity usage over a ROP period. Unit: kbps.";
      type uint64;
      config false;
    }
    leaf pmFwkSampLostL2Rb {
      description "Total number of lost or incomplete granularity level RB samples in Layer 2. Unit: samples.";
      type uint64;
      config false;
    }
    leaf pmLicDlSlotsData {
      description "Aggregated number of downlink slots with data to be scheduled..";
      type uint64;
      config false;
    }
    leaf pmRimVictimRiDetectedMax {
      description "Maximum number of unique victim cells detecting RI during reporting period..";
      type int64;
      config false;
    }
    leaf pmLicLteNrSpectrumSharingFdd {
      description "Current number of LTE-NR Spectrum Sharing Enabler capacity license units allocated to all FDD cells defined for ESS service on gNodeB. If no FDD cells that are defined for ESS service are unlocked on node, counter reports 0 value. For more information, refer to Feature Description for Ericsson Spectrum Sharing in CPI library. Unit: N/A.";
      type int64;
      config false;
    }
    leaf pmLic5Plus5MHzScTdd {
      description "Current number of licensed NR 5+5 MHz Sector Carrier capacity units allocated to all TDD sector carriers. A sector carrier is configured for TDD if NRSectorCarrier::arfcnDL and NRSectorCarrier::arfcnUL are equal. If node has no TDD sector carriers unlocked, counter reports 0 value. For more information, refer to Feature Description for NR 5+5 MHz Sector Carrier in CPI library. Unit: N/A.";
      type int64;
      config false;
    }
    leaf-list pmRadioPdschRimBlankSlotsMaxDistr {
      description "Maximum number of unique aggressor cells that perform slot muting or power control mitigation. Ranges: Bin[0]: Maximum number of unique aggressor cells that perform special slot downlink muting mitigation. Bin[1]: Maximum number of unique aggressor cells that perform special slot and preceding downlink slot muting mitigation. Bin[2]: Maximum number of unique aggressor cells that perform special slot and two preceding downlink slot muting mitigation. Bin[3]: Maximum number of unique aggressor cells that perform special slot muting and preceding downlink slot power control mitigation. Bin[4]: Maximum number of unique aggressor cells that perform special slot and preceding downlink slot muting mitigation and next preceding downlink slot power control mitigation. Bin[5]: Maximum number of unique aggressor cells that perform special slot and symbol-level downlink muting mitigation. Bin[6]: Maximum number of unique aggressor cells that perform special slot and preceding downlink slot muting mitigation, and next preceding downlink slot symbol-level muting mitigation. Bin[7]: Not used. Bin[8]: Not used. Bin[9]: Not used..";
      type int64;
      max-elements 10;
    }
    leaf pmMacVolDl {
      description "Shows accumulated sum of data volume of successfully transmitted downlink MAC PDUs for DRB or SRB using each Cell as PCell or SCell in GNBDUFunction. Unit: byte.";
      type ietfyang:mac-address;
      config false;
    }
    leaf pmLicDlCapUsedSamp {
      description "Total number of measured samples of downlink Baseband throughput capacity usage..";
      type uint64;
      config false;
    }
    leaf pmFwkSampLostL2Ue {
      description "Total number of lost or incomplete granularity level UE samples in Layer 2. Unit: samples.";
      type uint64;
      config false;
    }
    leaf pmFwkSampLostL2Cell {
      description "Total number of lost or incomplete granularity level Cell samples in Layer 2. Unit: samples.";
      type uint64;
      config false;
    }
    leaf pmLic25Plus25MHzScActual {
      description "Current number of licensed NR 25+25 MHz Sector Carrier capacity units allocated to all TDD sector carriers. If node has no TDD sector carriers unlocked, counter reports 0 value. For more information, refer to Feature Description for NR 25+25 MHz Sector Carrier in CPI library. Unit: N/A.";
      type int64;
      config false;
    }
    leaf pmPagF1DiscardedEdrx {
      description "Number of F1AP eDRX paging messages discarded and not routed to any cell. Both Core Network paging and Radio Access Network paging are included. Subset of GNBDUFunction.pmPagF1Discarded PM counter. Unit: N/A.";
      type uint64;
      config false;
    }
    leaf-list pmFwkStreamDroppedEventDistr {
      description "Total number of PM events dropped in each CTR stream in PM framework. Ranges: Bin[0]: Applicable for the Cell Trace Job ID 10000 Bin[1]: Applicable for the Cell Trace Job ID 10001 Bin[2]: Applicable for the Cell Trace Job ID 10002 Bin[3]: Applicable for the Cell Trace Job ID 10003 Bin[4]: Applicable for the Cell Trace Job ID 10004 Bin[5]: Applicable for the Cell Trace Job ID 10005.";
      type uint64;
      max-elements 6;
    }
    leaf pmFwkSampLostL2Cellplmn {
      description "Total number of lost or incomplete granularity level Cellplmn samples in Layer 2. Unit: samples.";
      type uint64;
      config false;
    }
    leaf pmRimVictimCellDetectedMax {
      description "Maximum number of unique victim cells which detect RS2..";
      type int64;
      config false;
    }
    leaf pmArcLinkDelayAboveCaSchedOptThres {
      description "Aggregated number of Advanced RAN Coordination partners that do not meet E5 link delay requirement to support NR Carrier Aggregation Scheduling Optimization for External SCells feature..";
      type uint64;
      config false;
    }
    leaf pmPagF1Discarded {
      description "Number of F1AP paging messages discarded and not routed to any cell. Both Core Network paging and Radio Access Network paging are included. Unit: N/A.";
      type uint64;
      config false;
    }
    leaf-list pmRadioPdschRimBlankSymbolMaxDistr {
      description "Maximum number of unique aggressor cells that perform symbol-level muting mitigation. Ranges: Bin[0]: Maximum number of unique aggressor cells that perform special slot and symbol-level downlink muting mitigation because of high-level interference. Bin[1]: Maximum number of unique aggressor cells that perform special slot and symbol-level downlink muting mitigation because of medium-level interference. Bin[2]: Maximum number of unique aggressor cells that perform special slot and symbol-level downlink muting mitigation because of low-level interference. Bin[3]: Maximum number of unique aggressor cells that perform special slot and preceding downlink slot muting mitigation, and next preceding downlink slot symbol-level downlink muting mitigation because of high-level interference. Bin[4]: Maximum number of unique aggressor cells that perform special slot and preceding downlink slot muting mitigation, and next preceding downlink slot symbol-level downlink muting mitigation because of medium-level interference. Bin[5]: Maximum number of unique aggressor cells that perform special slot and preceding downlink slot muting mitigation, and next preceding downlink slot symbol-level downlink muting mitigation because of low-level interference. Bin[6]: Not used. Bin[7]: Not used. Bin[8]: Not used. Bin[9]: Not used..";
      type int64;
      max-elements 10;
    }
    leaf pmLic5MHzBwHwacTdd {
      description "Current level of HWACs of type NR AAS TDD Channel Bandwidth 5 MHz, allocated to TDD sector carriers. Unit: N/A.";
      type int64;
      config false;
    }
    leaf pmLicEricssonRedCapAdvCellCapacity {
      description "Current number of cells with RedCap Advanced Cell Capacity enabled on gNodeB. If no operational cells are configured for RedCap Advanced Cell Capacity, the counter reports a value of 0. Disabled cells are disregarded by licensing. For more information, refer to CPI library. Unit: N/A.";
      type int64;
      config false;
    }
    leaf pmLic10MHzBwHwacTdd {
      description "Current level of HWACs of type NR AAS TDD Channel Bandwidth 10 MHz, allocated to TDD sector carriers. Unit: N/A.";
      type int64;
      config false;
    }
    leaf pmFwkSampLostL2Beam {
      description "Total number of lost or incomplete granularity level Beam samples in Layer 2. Unit: samples.";
      type uint64;
      config false;
    }
    leaf pmLicEricssonRedCapBasCellCapacity {
      description "Current number of cells with RedCap Basic Cell Capacity enabled on gNodeB. If no operational cells are configured for RedCap Basic Cell Capacity, the counter reports a value of 0. Disabled cells are disregarded by licensing. For more information, refer to CPI library. Unit: N/A.";
      type int64;
      config false;
    }
    leaf pmMacVolUl {
      description "Shows accumulated sum of data volume in MAC SDUs successfully received in uplink in all Cells as PCell or SCell in GNBDUFunction. Unit: byte.";
      type ietfyang:mac-address;
      config false;
    }
    leaf pmFwkSampLostL2Cellpartition {
      description "Total number of lost or incomplete granularity level Cellpartition samples in Layer 2. Unit: samples.";
      type uint64;
      config false;
    }
    leaf pmLicEricssonRedCapMaxCellCapacity {
      description "Current number of cells with RedCap Maximum Cell Capacity enabled on gNodeB. If no operational cells are configured for RedCap Maximum Cell Capacity, the counter reports a value of 0. Disabled cells are disregarded by licensing. For more information, refer to CPI library. Unit: N/A.";
      type int64;
      config false;
    }
    leaf pmLicDlCapUsedMax {
      description "Maximum value of downlink Baseband capacity usage. Counter works only with single mode NR configurations. Unit: kbps.";
      type int64;
      config false;
    }
    leaf pmUeConfigProfileOverwrite {
      description "Number of overwritten configuration profiles, which is caused by creation of UeBbProfileUeCfg MO class or value change of feature parameters referenced by UeBbProfileUeCfg MO class. Such an overwrite can lead to unintended UE treatment..";
      type uint64;
      config false;
    }
    leaf pmPagF1Received {
      description "Number of received F1AP paging messages in gNodeB-DU. Both Core Network paging and Radio Access Network paging are included. Unit: N/A.";
      type uint64;
      config false;
    }
    leaf pmLic5Plus5MHzScActual {
      description "Current number of licensed NR 5+5 MHz Sector Carrier capacity units allocated to all sector carriers of node. For more information, refer to Feature Description NR 5+5 MHz Sector Carrier in CPI library. Unit: N/A.";
      type int64;
      config false;
    }
    leaf-list pmFwkStreamDroppedEventSocketErrorDistr {
      description "Number of PM events dropped due to socket error in each CTR stream in PM framework. Ranges: Bin[0]: Applicable for the Cell Trace Job ID 10000 Bin[1]: Applicable for the Cell Trace Job ID 10001 Bin[2]: Applicable for the Cell Trace Job ID 10002 Bin[3]: Applicable for the Cell Trace Job ID 10003 Bin[4]: Applicable for the Cell Trace Job ID 10004 Bin[5]: Applicable for the Cell Trace Job ID 10005.";
      type uint64;
      max-elements 6;
    }
    leaf pmLicUlCapUsedMax {
      description "Maximum value of uplink Baseband capacity usage. Counter functions only with single mode NR configurations. Unit: kbps.";
      type int64;
      config false;
    }
    leaf-list pmFwkStreamProducedEventDistr {
      description "Total number of PM events produced in each CTR stream in PM framework. Ranges: Bin[0]: Applicable for the Cell Trace Job ID 10000 Bin[1]: Applicable for the Cell Trace Job ID 10001 Bin[2]: Applicable for the Cell Trace Job ID 10002 Bin[3]: Applicable for the Cell Trace Job ID 10003 Bin[4]: Applicable for the Cell Trace Job ID 10004 Bin[5]: Applicable for the Cell Trace Job ID 10005.";
      type uint64;
      max-elements 6;
    }
    leaf pmLic5Plus5MHzScFdd {
      description "Current number of licensed NR 5+5 MHz Sector Carrier capacity units allocated to all FDD sector carriers. A sector carrier is configured for FDD if NRSectorCarrier::arfcnDL and NRSectorCarrier::arfcnUL differ. If node has no FDD sector carriers unlocked, counter reports 0 value. For more information, refer to Feature Description for NR 5+5 MHz Sector Carrier in CPI library. Unit: N/A.";
      type int64;
      config false;
    }
    leaf pmLicUlSlotsHwacLimit {
      description "Aggregated number of uplink slots in which throughput HWAC limits scheduled data..";
      type uint64;
      config false;
    }
    leaf-list pmFwkStreamDroppedEventSlowStreamDistr {
      description "Number of PM events dropped due to slow stream in each CTR stream in PM framework. Ranges: Bin[0]: Applicable for the Cell Trace Job ID 10000 Bin[1]: Applicable for the Cell Trace Job ID 10001 Bin[2]: Applicable for the Cell Trace Job ID 10002 Bin[3]: Applicable for the Cell Trace Job ID 10003 Bin[4]: Applicable for the Cell Trace Job ID 10004 Bin[5]: Applicable for the Cell Trace Job ID 10005.";
      type uint64;
      max-elements 6;
    }
    leaf pmLic50MHzBwHwac {
      description "Current level of NR 50 MHz Channel Bandwidth HWACs allocated to sector carriers. Unit: N/A.";
      type int64;
      config false;
    }
    leaf pmLicUlCapUsedSamp {
      description "Total number of measured samples of uplink Baseband throughput capacity usage..";
      type uint64;
      config false;
    }
    leaf-list pmLicDlCapDistr {
      description "Shows utilization of downlink Baseband throughput capacity relative to minimum of installed license for DL Baseband Capacity or hardware capacity limit. Expressed as percentage of minimum of license limit or hardware capacity limit. Throughput is measured with a slot level granularity. Only valid PDSCH slots are considered. PDF ranges: Bin[0]: [0..5]%, Bin[1]: ]5..10]%, Bin[2]: ]10..15]%, Bin[3]: ]15..20]%, Bin[4]: ]20..25]%, Bin[5]: ]25..30]%, Bin[6]: ]30..35]%, Bin[7]: ]35..40]%, Bin[8]: ]40..45]%, Bin[9]: ]45..50]%, Bin[10]: ]50..55]%, Bin[11]: ]55..60]%, Bin[12]: ]60..65]%, Bin[13]: ]65..70]%, Bin[14]: ]70..75]%, Bin[15]: ]75..80]%, Bin[16]: ]80..85]%, Bin[17]: ]85..90]%, Bin[18]: ]90..95]%, Bin[19]: ]95..100]% Unit: %.";
      type uint64;
      max-elements 20;
    }
    leaf-list pmLicUlCapDistr {
      description "Shows utilization of uplink Baseband throughput capacity relative to minimum of installed license for UL Baseband Capacity or hardware capacity limit. Expressed as percentage of minimum of license limit or hardware capacity limit. Throughput is measured with a slot level granularity. Only valid PUSCH slots are considered. PDF ranges: Bin[0]: [0..5]%, Bin[1]: ]5..10]%, Bin[2]: ]10..15]%, Bin[3]: ]15..20]%, Bin[4]: ]20..25]%, Bin[5]: ]25..30]%, Bin[6]: ]30..35]%, Bin[7]: ]35..40]%, Bin[8]: ]40..45]%, Bin[9]: ]45..50]%, Bin[10]: ]50..55]%, Bin[11]: ]55..60]%, Bin[12]: ]60..65]%, Bin[13]: ]65..70]%, Bin[14]: ]70..75]%, Bin[15]: ]75..80]%, Bin[16]: ]80..85]%, Bin[17]: ]85..90]%, Bin[18]: ]90..95]%, Bin[19]: ]95..100]% Unit: %.";
      type uint64;
      max-elements 20;
    }
    leaf-list pmFwkStreamDroppedEventLicenseUnavailableDistr {
      description "Number of PM events dropped due to license unavailable in each CTR stream in PM framework Ranges: Bin[0]: Applicable for the Cell Trace Job ID 10000 Bin[1]: Applicable for the Cell Trace Job ID 10001 Bin[2]: Applicable for the Cell Trace Job ID 10002 Bin[3]: Applicable for the Cell Trace Job ID 10003 Bin[4]: Applicable for the Cell Trace Job ID 10004 Bin[5]: Applicable for the Cell Trace Job ID 10005.";
      type uint64;
      max-elements 6;
    }
    leaf pmLicUlSlotsData {
      description "Aggregated number of uplink slots with data to be scheduled..";
      type uint64;
      config false;
    }
    leaf pmLic10MHzBwHwacFdd {
      description "Current level of HWACs of type NR AAS FDD Channel Bandwidth 10 MHz, allocated to FDD sector carriers. Unit: N/A.";
      type int64;
      config false;
    }
    leaf pmFwkSampLostL2Qos {
      description "Total number of lost or incomplete granularity level QoS samples in Layer 2. Unit: samples.";
      type uint64;
      config false;
    }
    leaf pmArcPartnerSuspensionLinkDelay {
      description "Aggregated number of Advanced RAN Coordination partners that are in suspended state due to not meeting the E5 link delay requirement to set up a tunnel..";
      type uint64;
      config false;
    }
  }
  grouping Harq-attributes {
    leaf harqId {
      description "The value component of the RDN..";
      type string;
      mandatory true;
    }
  }
  grouping HarqUeCfg-attributes {
    leaf dlHarqMode {
      description "Defines HARQ mode in downlink. Only applicable to Low-Band and Mid-Band cells..";
      type enumeration {
        enum HARQ_NORMAL;
        enum HARQ_VONR;
        enum HARQ_ROBUST;
      }
    }
    leaf harqUeCfgId {
      description "The value component of the RDN..";
      type string;
      mandatory true;
    }
    leaf-list reservedBy {
      description "Contains a list of MO instances that reserve this MO instance..";
      type string;
      min-elements 0;
    }
    leaf ulHarqMode {
      description "Defines HARQ mode in uplink. Only applicable to Low-Band and Mid-Band cells..";
      type enumeration {
        enum HARQ_NORMAL;
        enum HARQ_VONR;
        enum HARQ_ROBUST;
      }
    }
  }
  grouping InterMeLink-attributes {
    leaf-list availabilityStatus {
      description "The availability status. It contains details about operationalState..";
      type AvailStatus;
      min-elements 0;
    }
    leaf caSchedOptActive {
      description "Whether optimized scheduling for external cells is active. Only applicable to InterMeLink instances that represent PCell client side. Value is true only if all tunnels on this InterMeLink instance allow optimized scheduling for external cells. Always empty for InterMeLink instances that represent external SCell server side..";
      type boolean;
      config false;
    }
    leaf interMeLinkId {
      description "The value component of the RDN..";
      type string;
      mandatory true;
    }
    leaf linkLatency15minHWM {
      description "Highest latency measured during last completed 15-minute period..";
      type int32;
      config false;
      units "microsecond";
    }
    leaf linkLatency1minAvg {
      description "Average latency measured during last 1-minute period..";
      type int32;
      config false;
      units "microsecond";
    }
    leaf linkLatency24hrsHWM {
      description "Highest latency measured during last 24 hours..";
      type int32;
      config false;
      units "microsecond";
    }
    leaf localEndpointIdentity {
      description "Local hardware board that terminates inter-ME link..";
      type string;
      config false;
    }
    leaf operationalState {
      description "The operational state..";
      type enumeration {
        enum DISABLED;
        enum ENABLED;
      }
      config false;
    }
    leaf remoteEndpointIdentity {
      description "Remote hardware board that terminates inter-ME link..";
      type string;
      config false;
    }
    leaf vlanId {
      description "VLAN ID in VLAN tag of packets transmitted over Ethernet..";
      type int32;
      config false;
    }
  }
  grouping L4sCfg-attributes {
    leaf l4sCfgId {
      description "The value component of the RDN..";
      type string;
      mandatory true;
    }
    leaf-list reservedBy {
      description "Contains a list of MO instances that reserve this MO instance..";
      type string;
      min-elements 0;
    }
    leaf ulL4sHighThresh {
      description "High threshold in L4S. Threshold above which L4S Congestion Experienced marking probability is 100 %.; range 5..100; Default value: 20.";
      type int32 {
        range "5..100";
      }
      default "20";
      units "ms";
    }
    leaf ulL4sLowThresh {
      description "Low threshold in L4S. Threshold below which L4S Congestion Experienced marking probability is 0 %.; range 1..50; Default value: 8.";
      type int32 {
        range "1..50";
      }
      default "8";
      units "ms";
    }
    leaf ulL4sMode {
      description "L4S mode in uplink. L4S mechanism reduces RLC latency, but can impact throughput. Only applicable to Low-Band and Mid-Band cells..";
      type enumeration {
        enum DISABLED;
        enum QUEUE_BASED;
      }
    }
    leaf userLabel {
      description "Label for free use..";
      type string;
    }
  }
  grouping LinkAdaptation-attributes {
    leaf linkAdaptationId {
      description "The value component of the RDN..";
      type string;
      mandatory true;
    }
  }
  grouping LinkAdaptationUeCfg-attributes {
    leaf dlMaxBitrate {
      description "Maximum allowed downlink bitrate. If -1, downlink bitrate is not limited. Not applicable to High-Band cells.; Default value: -1.";
      type int32 {
        range "-1 | 4..32";
      }
      default "-1";
      units "Mbps";
    }
    leaf dlMcsTable {
      description "MCS table to be used for downlink. LOW_SE_QAM64 is only applicable if license for at least one of following features is present and feature is active: - Link Adaptation with Low Spectral Efficiency MCS Table for Public RAN - Link Adaptation with Low Spectral Efficiency MCS Table for Dedicated RAN Otherwise handled as QAM64..";
      type enumeration {
        enum QAM64;
        enum QAM256;
        enum LOW_SE_QAM64;
      }
    }
    leaf linkAdaptationUeCfgId {
      description "The value component of the RDN..";
      type string;
      mandatory true;
    }
    leaf linkAdaptationUeMode {
      description "Link adaption mode applied on UE. GENERAL mode is applied to UE by default if configured mode is invalid, for example when feature license in gNodeB is missing. ROBUST_BASIC and ROBUST_HIGH are only applicable to High-Band cells..";
      type enumeration {
        enum GENERAL;
        enum ROBUST_BASIC;
        enum ROBUST_HIGH;
        enum CUSTOM;
        enum ROBUST_MCS;
      }
    }
    leaf-list reservedBy {
      description "Contains a list of MO instances that reserve this MO instance..";
      type string;
      min-elements 0;
    }
    leaf ulMcsTable {
      description "MCS table to be used for uplink. QAM256 is only applicable to Low-Band and Mid-Band cells. LOW_SE_QAM64 is only applicable if license for at least one of following features is present and feature is active: - Link Adaptation with Low Spectral Efficiency MCS Table for Public RAN - Link Adaptation with Low Spectral Efficiency MCS Table for Dedicated RAN Otherwise handled as QAM64..";
      type enumeration {
        enum QAM64;
        enum QAM256;
        enum LOW_SE_QAM64;
      }
    }
    leaf userLabel {
      description "Label for free use..";
      type string;
    }
  }
  grouping LocalIpEndpoint-attributes {
    leaf-list addressRef {
      description "Reference to an instance of AddressIPv4 or AddressIPv6 MO. Must be unique among LocalIpEndpoint instances under EndpointResource instance. Dual stack is not supported, only one IP address can be referenced..";
      type string;
      ordered-by user;
      min-elements 1;
      max-elements 2;
    }
    leaf-list interfaceList {
      description "List of user plane interfaces that use the referenced AddressIPv4 or AddressIPv6. Allowed value: F1. Interface must be unique across LocalIpEndpoint instances under EndpointResource instance..";
      type InterfaceName;
      min-elements 1;
      max-elements 2;
    }
    leaf localIpEndpointId {
      description "The value component of the RDN..";
      type string;
      mandatory true;
    }
  }
  grouping LocalSctpEndpoint-attributes {
    leaf interfaceUsed {
      description "Control plane interface that uses the referenced SctpEndpoint. Allowed value: F1. Interface must be unique across LocalSctpEndpoint instances under EndpointResource instance..";
      type enumeration {
        enum C5;
        enum E1;
        enum E6;
        enum F1;
        enum NG;
        enum S1;
        enum XN;
        enum X2;
      }
      mandatory true;
    }
    leaf localSctpEndpointId {
      description "The value component of the RDN..";
      type string;
      mandatory true;
    }
    leaf sctpEndpointRef {
      description "Reference to an instance of SctpEndpoint MO. Must be unique among LocalSctpEndpoint instances under EndpointResource instance..";
      type string;
      mandatory true;
    }
  }
  grouping LogicalChannel-attributes {
    leaf logicalChannelId {
      description "The value component of the RDN..";
      type string;
      mandatory true;
    }
    leaf-list reservedBy {
      description "Contains a list of MO instances that reserve this MO instance..";
      type string;
      min-elements 0;
    }
    leaf ueConfGroupType {
      description "UE configuration group type. UE configuration group type that is applied in contained LogicalChannelUeCfg instances..";
      type enumeration {
        enum UE_MOBILITY_GROUP;
        enum UE_SERVICE_GROUP;
        enum UE_ADMISSION_GROUP;
      }
    }
  }
  grouping LogicalChannelUeCfg-attributes {
    leaf bucketSizeDuration {
      description "Bucket size duration used in RRC logical channel configuration..";
      type enumeration {
        enum MS_5;
        enum MS_10;
        enum MS_20;
        enum MS_50;
        enum MS_100;
        enum MS_150;
        enum MS_300;
        enum MS_500;
        enum MS_1000;
      }
    }
    leaf logicalChannelGroup {
      description "Logical channel group used in RRC logical channel configuration. If empty, DU5qi::logicalChannelGroupId is used.; range 1..7.";
      type eytypes:int32_range_1-7;
    }
    leaf logicalChannelPriority {
      description "Priority of logical channel used in RRC logical channel configuration. Priorities 1, 2 and 3 are reserved for SRBs. If empty, value is set automatically based on DRB priority level and number of bearers.; range 4..16.";
      type int32 {
        range "4..16";
      }
    }
    leaf logicalChannelUeCfgId {
      description "The value component of the RDN..";
      type string;
      mandatory true;
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf prioritisedBitRate {
      description "Prioritized bit rate used in RRC logical channel configuration. If LogicalChannelUeCfg=Base instance under LogicalChannel=IMS_Voice instance is created automatically, value is KBPS_16..";
      type enumeration {
        enum KBPS_0;
        enum KBPS_8;
        enum KBPS_16;
        enum KBPS_32;
        enum KBPS_64;
        enum KBPS_128;
        enum KBPS_256;
        enum KBPS_512;
        enum KBPS_1024;
        enum KBPS_2048;
        enum KBPS_4096;
        enum KBPS_8192;
        enum KBPS_16384;
        enum KBPS_32768;
        enum KBPS_65536;
        enum INFINITY;
      }
    }
    leaf prioritisedBitRateFR2 {
      description "Prioritized bit rate for FR2 used in RRC logical channel configuration..";
      type enumeration {
        enum KBPS_0;
        enum KBPS_8;
        enum KBPS_16;
        enum KBPS_32;
        enum KBPS_64;
        enum KBPS_128;
        enum KBPS_256;
        enum KBPS_512;
        enum KBPS_1024;
        enum KBPS_2048;
        enum KBPS_4096;
        enum KBPS_8192;
        enum KBPS_16384;
        enum KBPS_32768;
        enum KBPS_65536;
        enum INFINITY;
      }
    }
    leaf srDelayTimerApplied {
      description "Whether delay timer for scheduling request transmission for logical channel is applied. RRC parameters logicalChannelSR-DelayTimerApplied and logicalChannelSR-DelayTimer are defined in 3GPP TS 38.331. If true and logicalChannelSR-DelayTimer in BSR-Config is excluded, logicalChannelSR-DelayTimerApplied is set to false for logical channel.; Default value: false.";
      type boolean;
      default "false";
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 16;
    }
    leaf-list ueGroupList {
      description "UE group list. List of UE group identifiers. If empty, MO instance matches all UE group identifiers..";
      type eytypes:int32_range_1-255;
      ordered-by user;
      min-elements 0;
      max-elements 16;
    }
  }
  grouping LteInterMeLink-attributes {
    leaf-list availabilityStatus {
      description "The availability status. It contains details about operationalState..";
      type AvailStatus;
      min-elements 0;
    }
    leaf linkLatency15minHWM {
      description "Highest latency measured during last completed 15-minute period..";
      type int32;
      config false;
      units "microsecond";
    }
    leaf linkLatency1minAvg {
      description "Average latency measured during last 1-minute period..";
      type int32;
      config false;
      units "microsecond";
    }
    leaf linkLatency24hrsHWM {
      description "Highest latency measured during last 24 hours..";
      type int32;
      config false;
      units "microsecond";
    }
    leaf localEndpointIdentity {
      description "Local hardware board that terminates inter-ME link..";
      type string;
      config false;
    }
    leaf lteInterMeLinkId {
      description "The value component of the RDN..";
      type string;
      mandatory true;
    }
    leaf operationalState {
      description "The operational state..";
      type enumeration {
        enum DISABLED;
        enum ENABLED;
      }
      config false;
    }
    leaf remoteEndpointIdentity {
      description "Remote hardware board that terminates inter-ME link..";
      type string;
      config false;
    }
    leaf vlanId {
      description "VLAN ID in VLAN tag of packets transmitted over Ethernet..";
      type int32;
      config false;
    }
  }
  grouping MassiveMimoSleep-attributes {
    leaf massiveMimoSleepId {
      description "The value component of the RDN..";
      type string;
      mandatory true;
    }
  }
  grouping MMimoSleepProfile-attributes {
    leaf mMimoSleepProfileId {
      description "The value component of the RDN..";
      type string;
      mandatory true;
    }
    leaf-list reservedBy {
      description "Contains a list of MO instances that reserve this MO instance..";
      type string;
      min-elements 0;
    }
    leaf sleepMode {
      description "Mode of massive MIMO sleep. Applicable if NRSectorCarrier::massiveMimoSleepEnabled is ENABLED or DETECTION. If license for NR Massive MIMO Sleep Mode is present and feature is active: - If massiveMimoSleepEnabled is ENABLED, value TXMUTE is applicable. If license for NR Massive MIMO Eco Mode is present and feature is active: - If massiveMimoSleepEnabled is ENABLED, values ECO and TXMUTE are applicable. If massiveMimoSleepEnabled is DETECTION, no licenses are required..";
      type enumeration {
        enum TXMUTE;
        enum ECO;
      }
    }
    leaf switchDownMonitorDurTimer {
      description "Massive MIMO Sleep TxMute mode detection duration for down-switching.; range 0..14400; Default value: 60.";
      type eytypes:int32_range_0-14400;
      default "60";
      units "s";
    }
    leaf switchDownMonitorDurTimerEco {
      description "Massive MIMO Sleep Eco mode detection duration for down-switching. Only applicable when sleepMode is ECO.; range 0..14400; Default value: 300.";
      type eytypes:int32_range_0-14400;
      default "300";
      units "s";
    }
    leaf switchDownPrbThreshDl {
      description "Down-switching downlink PRB usage TxMute threshold. Percentage of downlink PRB usage required during switchDownMonitorDurTimer period to activate Massive MIMO Sleep TxMute mode. If 0, Automated Energy Saver feature is never activated. If 100, threshold is deactivated.; range 0..100; Default value: 20.";
      type eytypes:int32_range_0-100;
      default "20";
      units "percent";
    }
    leaf switchDownPrbThreshDlEco {
      description "Down-switching downlink PRB usage Eco threshold. Percentage of downlink PRB usage required during switchDownMonitorDurTimerEco period to activate Massive MIMO Sleep Eco mode. If 0, Automated Energy Saver feature is never activated. If 100, threshold is deactivated. Only applicable when sleepMode is ECO.; range 0..100; Default value: 15.";
      type eytypes:int32_range_0-100;
      default "15";
      units "percent";
    }
    leaf switchDownPrbThreshUlEco {
      description "Down-switching uplink PRB usage Eco threshold. Percentage of uplink PRB usage required during switchDownMonitorDurTimerEco period to activate Massive MIMO Sleep Eco mode. Only applicable when sleepMode is ECO.; range 0..100; Default value: 10.";
      type eytypes:int32_range_0-100;
      default "10";
      units "percent";
    }
    leaf switchDownRrcConnThresh {
      description "Down-switching RRC connections TxMute threshold. Number of user connections required during switchDownMonitorDurTimer period to activate Massive MIMO Sleep TxMute mode. If 0, threshold is deactivated.; range 0..5000; Default value: 30.";
      type eytypes:int32_range_0-5000;
      default "30";
    }
    leaf switchDownRrcConnThreshEco {
      description "Down-switching RRC connections Eco threshold. Number of user connections required during switchDownMonitorDurTimerEco period to activate Massive MIMO Sleep Eco mode. If 0, threshold is deactivated. Only applicable when sleepMode is ECO.; range 0..5000; Default value: 30.";
      type eytypes:int32_range_0-5000;
      default "30";
    }
    leaf switchUpMonitorDurTimer {
      description "Massive MIMO Sleep TxMute mode detection duration for up-switching.; range 0..14400; Default value: 30.";
      type eytypes:int32_range_0-14400;
      default "30";
      units "s";
    }
    leaf switchUpMonitorDurTimerEco {
      description "Massive MIMO Sleep Eco mode detection duration for up-switching. Only applicable when sleepMode is ECO.; range 0..14400; Default value: 120.";
      type eytypes:int32_range_0-14400;
      default "120";
      units "s";
    }
    leaf switchUpPrbThreshDl {
      description "Up-switching downlink PRB usage TxMute threshold. Percentage of downlink PRB usage required during switchUpMonitorDurTimer period to deactivate Massive MIMO Sleep TxMute mode. If 0, Automated Energy Saver feature is never activated. If 100, threshold is deactivated.; range 0..100; Default value: 30.";
      type eytypes:int32_range_0-100;
      default "30";
      units "percent";
    }
    leaf switchUpPrbThreshDlEco {
      description "Up-switching downlink PRB usage Eco threshold. Percentage of downlink PRB usage required during switchUpMonitorDurTimerEco period to deactivate Massive MIMO Sleep Eco mode. If 0, Automated Energy Saver feature is never activated. If 100, threshold is deactivated. Only applicable when sleepMode is ECO.; range 0..100; Default value: 30.";
      type eytypes:int32_range_0-100;
      default "30";
      units "percent";
    }
    leaf switchUpPrbThreshUlEco {
      description "Up-switching uplink PRB usage Eco threshold. Percentage of uplink PRB usage required during switchUpMonitorDurTimerEco period to deactivate Massive MIMO Sleep Eco Mode. Only applicable when sleepMode is ECO.; range 0..100; Default value: 15.";
      type eytypes:int32_range_0-100;
      default "15";
      units "percent";
    }
    leaf switchUpRrcConnThresh {
      description "Up-switching RRC connections TxMute threshold. Number of user connections required during switchUpMonitorDurTimer period to deactivate Massive MIMO Sleep TxMute mode. If 0, threshold is deactivated.; range 0..5000; Default value: 50.";
      type eytypes:int32_range_0-5000;
      default "50";
    }
    leaf switchUpRrcConnThreshEco {
      description "Up-switching RRC connections Eco threshold. Number of user connections required during switchUpMonitorDurTimer period to deactivate Massive MIMO Sleep Eco Mode. If 0, threshold is deactivated. Only applicable when sleepMode is ECO.; range 0..5000; Default value: 50.";
      type eytypes:int32_range_0-5000;
      default "50";
    }
  }
  grouping MMimoSleepTimeGroup-attributes {
    leaf mMimoSleepTimeGroupId {
      description "The value component of the RDN..";
      type string;
      mandatory true;
    }
    leaf-list reservedBy {
      description "Contains a list of MO instances that reserve this MO instance..";
      type string;
      min-elements 0;
    }
  }
  grouping MMimoSleepTimeWindow-attributes {
    leaf daylightTimeOffsetApplied {
      description "Daylight saving time offset applied given as +/- hours:minutes.; length 0..6.";
      type string {
        length "0..6";
      }
      config false;
    }
    leaf-list dayOfWeek {
      description "Days in UTC when time window is applicable..";
      type DayOfWeek;
      min-elements 1;
      max-elements 7;
    }
    leaf mMimoSleepProfileRef {
      description "Reference to an instance of MMimoSleepProfile MO..";
      type string;
      mandatory true;
    }
    leaf mMimoSleepTimeWindowId {
      description "The value component of the RDN..";
      type string;
      mandatory true;
    }
    leaf startTime {
      description "Time of day in UTC when time window starts. Value ranges from 00:00 to 23:59 system time.; length 5..5; Default value: 02:00.";
      type string {
        length "5";
        pattern "([01][0-9]|2[0-3]):([0-5][0-9])";
      }
      default "02:00";
    }
    leaf stopTime {
      description "Time of day in UTC when time window ends. Value ranges from 00:00 to 23:59 system time.; length 5..5; Default value: 05:00.";
      type string {
        length "5";
        pattern "([01][0-9]|2[0-3]):([0-5][0-9])";
      }
      default "05:00";
    }
  }
  grouping NRCellDU-attributes {
    leaf actualPdcchRachBoost {
      description "Actual boost for PDCCH channel carrying Msg2, Msg3 retransmission, Msg4 and P2 refinement. This value can be less than pdcchRachBoost, depending on installed radio equipment and config mode. Only applicable to High-Band SpCells..";
      type int32;
      config false;
      units "dB";
    }
    leaf actualPdschRachBoost {
      description "Actual boost for PDSCH channel carrying Msg2. This value can be different from value of pdschRachBoost, depending on installed radio equipment and configuration mode. Only applicable to High-Band SpCells..";
      type int32;
      config false;
      units "dB";
    }
    leaf actualSsbPowerBoost {
      description "Actual boost for SSB. For Low-Band and Mid-Band cells, value can be less than ssbPowerBoost because of limitations of installed radio equipment. For High-Band, value is same as ssbPowerBoost..";
      type int32;
      config false;
      units "dB";
    }
    leaf additionalPucchForCaEnabled {
      description "Whether additional PUCCH resource is allocated in cell for Carrier Aggregation. Set value to true if cell is intended to be used as PCell for Carrier Aggregation. Only applicable to Low-Band and Mid-Band cells.; Default value: false.";
      type boolean;
      default "false";
    }
    leaf administrativeState {
      description "The administrative state. While set to SHUTTINGDOWN the cell is automatically barred. Set to LOCKED when all UEs have left the cell or timer maxOffloadDurationShutDown expires..";
      type enumeration {
        enum LOCKED;
        enum UNLOCKED;
        enum SHUTTINGDOWN;
      }
    }
    leaf advancedDlSuMimoEnabled {
      description "Whether Advanced Downlink Single-User MIMO Mid-Band feature is enabled in cell. Only applicable to Mid-Band cells.; Default value: false.";
      type boolean;
      default "false";
    }
    leaf advDlBfWhenAllSrsPortsUsable {
      description "Whether advanced downlink beamforming is allowed only when all SRS ports can be used. If true, reciprocity-based PDSCH beamforming is allowed only when gNodeB assesses that all SRS ports can be used. If gNodeB assesses that at least one SRS port is not usable, UE uses codebook-based PDSCH instead.; Default value: false.";
      type boolean;
      default "false";
    }
    leaf ailgBeamDirectionEnabled {
      description "Whether EMF Integrator Mid-Band feature is enabled. If true, Air Interface Load Generator (AILG) for PDSCH is beamformed according to PMIs set by ailgI11BeamDirection and ailgI12BeamDirection. Only applicable if value of ailgDlPrbLoadLevel is greater than 0. Only applicable to Mid-Band cells.; Default value: false.";
      type boolean;
      default "false";
    }
    leaf ailgDlPrbLoadLevel {
      description "Air Interface Load Generator (AILG) load level required for PDSCH. If 0, AILG for PDSCH is disabled.; range 0..100; Default value: 0.";
      type uint32 {
        range "0..100";
      }
      default "0";
      units "percent";
    }
    leaf ailgI11BeamDirection {
      description "The i11 PMI component of Air Interface Load Generator beam direction for PDSCH. Set according to highest CSI-RS configuration.; range 0..31; Default value: 0.";
      type eytypes:int32_range_0-31-13;
      default "0";
    }
    leaf ailgI12BeamDirection {
      description "The i12 PMI component of Air Interface Load Generator (AILG) beam direction for PDSCH. Set according to highest CSI-RS configuration.; range 0..15; Default value: 0.";
      type eytypes:int32_range_0-15;
      default "0";
    }
    leaf ailgModType {
      description "PDSCH Air Interface Load Generator (AILG) modulation type..";
      type enumeration {
        enum AILG_MOD_QPSK;
        enum AILG_MOD_16QAM;
        enum AILG_MOD_64QAM;
        enum AILG_MOD_256QAM;
      }
    }
    leaf ailgPdcchBeamDirectionEnabled {
      description "Whether EMF Integrator Mid-Band feature is enabled for PDCCH. If true, Air Interface Load Generator (AILG) for PDCCH is beamformed according to PMIs set by ailgI11BeamDirection and ailgI12BeamDirection. Only applicable if ailgPdcchLoadLevel is greater than 0. Only applicable to Mid-Band cells.; Default value: false.";
      type boolean;
      default "false";
    }
    leaf ailgPdcchLoadLevel {
      description "Air Interface Load Generator (AILG) load level required for PDCCH. If 0, AILG for PDCCH is disabled.; range 0..100; Default value: 0.";
      type uint32 {
        range "0..100";
      }
      default "0";
      units "percent";
    }
    leaf aperiodicSrsEnabled {
      description "Whether NR Aperiodic SRS Mid-Band feature is enabled. Only applicable to Mid-Band cells.; Default value: false.";
      type boolean;
      default "false";
    }
    leaf autoLockAction {
      description "Cell locking action that system performs automatically when lost O&M connection is detected. Only applicable if license for NR Automatic Cell Lock at OAM Connection Outage is present and feature is active..";
      type enumeration {
        enum NO_LOCK;
        enum IMMEDIATE_LOCK;
        enum SOFT_LOCK;
      }
    }
    leaf autoSelectedModeOffset {
      description "Offset for PUSCH closed-loop power control.; range -10..30; Default value: 6.";
      type int32 {
        range "-10..30";
      }
      default "6";
      units "dB";
    }
    leaf-list availabilityStatus {
      description "The availability status. It contains details about operational state..";
      type AvailStatus;
      min-elements 0;
    }
    leaf-list bandList {
      description "List of all NR bands the cells belongs to. Calculated by the system at cell unlock. If bandListManual is configured, it is used instead of bandList..";
      type eytypes:int32_range_1-1024;
      min-elements 0;
      max-elements 32;
    }
    leaf-list bandListManual {
      description "Configured list of bands to be used by cell. If present, this list is used instead of bandList. Bands specified in bandListManual must be intersection of possible bands for given cell configuration. Possible bands are displayed in bandList. Example, if bandList contains only bands 77 and 78, this attribute must contain 77, 78, or both. If a band specified in bandListManual does not match cell configuration, cell fails to unlock. Recommendation is that this list has same content as NRFrequency::bandListManual for cells with same frequency. This recommendation is for 3GPP compliance. Order of NR bands listed in bandListManual corresponds to order of bands in frequencyBandList in SIB1..";
      type int32 {
        range "1..3 | 5 | 7..8 | 12..14 | 18 | 20 | 24..26 | 28..31 | 34 | 38..41 | 46 | 48 | 50..51 | 53..54 | 65..67 | 70..72 | 74..86 | 89..102 | 104..106 | 109 | 257..262";
      }
      ordered-by user;
      min-elements 0;
      max-elements 32;
    }
    leaf bfrEnabled {
      description "Whether Beam Failure Recovery is enabled..";
      type boolean;
    }
    leaf-list bWPRef {
      description "References to instances of BWP MO. If non-empty at cell unlock and bWPSetRef is also non-empty, channel bandwidth from referenced MO instances are used. If empty at cell unlock and bWPSetRef is also empty, channel bandwidth according to NRSectorCarrier instance is used in this cell. Only applicable if license for NR Dynamic Power Optimizer or NR Reduced UE Bandwidth Support is present and feature is active..";
      type string;
      ordered-by user;
      min-elements 0;
    }
    leaf bWPSetRef {
      description "Reference to an instance of BWPSet MO. If non-empty at cell unlock and bWPRef is also non-empty, channel bandwidth from referenced MO instances are used. If empty at cell unlock and bWPRef is also empty, channel bandwidth according to NRSectorCarrier instance is used in this cell. Only applicable if license for NR Dynamic Power Optimizer or NR Reduced UE Bandwidth Support is present and feature is active..";
      type string;
    }
    leaf caBufferSplitThresh {
      description "Size of downlink Carrier Aggregation buffer splitting threshold. Defines whether volume of data in buffer is split into multiple activated cells. Only applicable to Low-Band and Mid-Band cells.; range 1..3000; Default value: 3.";
      type uint16 {
        range "1..3000";
      }
      default "3";
      units "byte";
    }
    leaf caPerCcFairnessWeightEnabled {
      description "Whether scheduler fairness for CA UE in each Component Carrier (CC) is enabled. Used with Carrier Aggregation feature and set on PCell node to improve scheduler fairness for CA UE in each CC, when enabled. If true, scheduling priority on one CC is not affected by scheduling activity on other CC. If false, scheduling activity on one CC affects scheduling priority on all CC. Not applicable to High-Band cells.; Default value: true.";
      type boolean;
      default "true";
    }
    leaf caPerCcFairnessWeightUlEnabled {
      description "Whether scheduler fairness for uplink carrier aggregation UEs in each component carrier is enabled. Used to improve uplink scheduler fairness for carrier aggregation UEs in each component carrier. Not applicable if NRSectorCarrier::txDirection is DL. Only applicable to Low-Band and Mid-Band cells.; Default value: false.";
      type boolean;
      default "false";
    }
    leaf caSCellHandlingRef {
      description "Reference to an instance of CaSCellHandling MO. If non-empty, attributes from referenced MO instance are used. If empty, attribute default values according to CaSCellHandling and CaSCellHandlingUeCfg MO class definitions are used..";
      type string;
    }
    leaf cbrsCellBandwidthPreferred {
      description "Preferred bandwidth for CBRS cell. Affects CBRS Domain Coordinator policies.; range 10000..100000; Default value: 20000.";
      type int32 {
        range "10000..100000";
      }
      default "20000";
      units "kHz";
    }
    leaf cbrsCellPriority {
      description "CBRS cell priority. Used together with cbrsCellPriorityRank. Affects CBRS Domain Coordinator policies..";
      type enumeration {
        enum NORMAL;
        enum HIGH;
      }
    }
    leaf cbrsCellPriorityRank {
      description "CBRS cell rank in priority group. If 1, lowest rank is prioritized. If 10, highest rank is prioritized. Used together with cbrsCellPriority. Affects CBRS Domain Coordinator policies.; range 1..10; Default value: 1.";
      type eytypes:int32_range_1-10;
      default "1";
    }
    leaf cbrsCellSsbControlEnabled {
      description "Whether optimization of SSB placement for CBRS cell is allowed. Affects CBRS Domain Coordinator policies.; Default value: false.";
      type boolean;
      default "false";
    }
    leaf cellBarred {
      description "Configuration for barring NR cell. If BARRED, cell is barred. If NOT_BARRED, cell can still be barred for other reasons. See cellBarredStatus..";
      type enumeration {
        enum BARRED;
        enum NOT_BARRED;
      }
    }
    leaf cellBarredReason {
      description "Reason why cell is barred. Cell can be barred for following reasons: - cellBarred is BARRED. - administrativeState is SHUTTINGDOWN, in NR Cell Soft Lock feature. - Barred by NR Booster Carrier Sleep feature for energy saving. If empty, cell is not barred..";
      type enumeration {
        enum MANUAL;
        enum CELL_SOFT_LOCK;
        enum BOOSTER_CARRIER_SLEEP;
      }
      config false;
    }
    leaf cellBarredStatus {
      description "Whether cell is currently barred. Cell can be barred for following reasons: - cellBarred is BARRED. - administrativeState is SHUTTINGDOWN, in NR Cell Soft Lock feature. - Barred by NR Booster Carrier Sleep feature for energy saving..";
      type enumeration {
        enum BARRED;
        enum NOT_BARRED;
      }
      config false;
    }
    leaf cellLocalId {
      description "Used together with gNodeB identifier to identify NR cell in PLMN. Must be unique in gNodeB. Used together with gNBId to form NCI.; range 0..16383.";
      type eytypes:int32_range_0-16383;
      mandatory true;
    }
    leaf cellPriorityShiftRef {
      description "Reference to an instance of CellPriorityShift MO. If non-empty, attributes from referenced MO instance are used. If empty, attribute default values according to CellPriorityShift MO class definitions are used..";
      type string;
    }
    leaf cellRange {
      description "Maximum signal path distance from BS where connection to UE can be set up and maintained. If empty, system configures 1100 m for High-Band cells and 1600 m for Low-Band or Mid-Band cells. Value greater than 15000 m when rachPreambleFormat is RACH_PREAMBLE_FORMAT_00 (F0) can cause random access performance degradation and interference to other channels.; range 1..100000.";
      type int32 {
        range "1..100000";
      }
      units "m";
    }
    leaf cellReservedForOperator {
      description "Whether the cell is reserved for operator use..";
      type enumeration {
        enum RESERVED;
        enum NOT_RESERVED;
      }
    }
    leaf cellResourceMappingRef {
      description "Reference to an instance of CellResourceMapping MO. Only applicable if nrRrpEnabled is true..";
      type string;
    }
    leaf cellSelectionWeightFactor {
      description "Factor for estimated cell weight. Scales cell weight contribution when selecting serving cells. A value less than 100 reduces the cell weight compared to maximum cell weight.; range 0..100; Default value: 100.";
      type uint32 {
        range "0..100";
      }
      default "100";
    }
    leaf cellState {
      description "Current cellState..";
      type enumeration {
        enum IDLE;
        enum INACTIVE;
        enum ACTIVE;
      }
      config false;
    }
    leaf cfraEnabled {
      description "Whether Contention-Free Random Access (CFRA) is enabled. If true, system allocates a portion of random access preambles for CFRA, to be used for incoming NR SA HO. If allocation fails, CBRA is performed.; Default value: false.";
      type boolean;
      default "false";
    }
    leaf configuredEpsTAC {
      description "EPS TAC, is not broadcast and differs from 5G System (5GS) TAC. If empty, gNodeB takes TAC from ENDCX2SetupRequest message and includes in ENDCX2SetupResponse or ENDCConfigurationTransfer message.; range 0..65535.";
      type eytypes:int32_range_0-65535-9;
    }
    leaf configuredGrantPeriodicity {
      description "Periodicity in slots for configured grant. For FDD, following values are applicable: 5, 10, 20, 40, 80, 160, 320, 640. For TDD, following values are applicable: 5, 10, 20, 40, 80, 160, 320, 640, 1280. Only applicable to Low-Band and Mid-Band cells.; Default value: 10.";
      type int32 {
        range "5 | 10 | 20 | 40 | 80 | 160 | 320 | 640 | 1280";
      }
      default "10";
    }
    leaf covOptUlSchedFr2Enabled {
      description "Whether Coverage-Optimized Uplink Scheduling High-Band is enabled. Only applicable if license for Coverage-Optimized Uplink Scheduling High-Band is present and feature is active. Only applicable to High-Band cells. Value must be false for Low-Band and Mid-Band cells.; Default value: false.";
      type boolean;
      default "false";
    }
    leaf csiReportFormat {
      description "Whether aperiodic CSI reports include subband or wideband feedback..";
      type enumeration {
        enum CQI_WB_PMI_WB;
        enum CQI_WB_PMI_SB;
        enum CQI_SB_PMI_WB;
        enum CQI_SB_PMI_SB;
      }
    }
    leaf-list csiRsActivePortConfig {
      description "Active CSI-RS resource configuration. The active CSI-RS resource configuration has been determined based on the preferred HW/SW configurations of gNodeB..";
      type CsiRsActivePortConfig;
      min-elements 0;
      max-elements 5;
    }
    list csiRsConfig16P {
      key "id";
      leaf id {
        type uint32;
        description "Synthetic key for struct attribute.";
      }
      description "Settings related to 16-port CSI and associated port to antenna mapping. Applies only to cells based on radios with at least 16 Tx branches. Otherwise, ignored. In standalone operation on radios with 8 or more Tx branches, 8-port CSI-RS is necessary to ensure that users with minimum allowed CSI measurement capability are served by cell. 8-port CSI-RS can be configured together with 16-port or 32-port on compatible AAS..";
      uses CsiRsConfig16P-struct;
    }
    list csiRsConfig2P {
      key "id";
      leaf id {
        type uint32;
        description "Synthetic key for struct attribute.";
      }
      description "Settings related to 2-port CSI and associated port to antenna mapping. Applies only to cells based on radios with two Tx branches or applies to cells based on radios with four TX branches if NRSectorCarrier::ueAssistedPrecodingOptEnabled is true. Otherwise, ignored..";
      uses CsiRsConfig2P-struct;
    }
    list csiRsConfig32P {
      key "id";
      leaf id {
        type uint32;
        description "Synthetic key for struct attribute.";
      }
      description "Settings related to 32-port CSI and associated port to antenna mapping. Applies only to cells based on radios with at least 32 Tx branches. Otherwise, ignored. In standalone operation on radios with 8 or more Tx branches, 8-port CSI-RS is necessary to ensure that users with minimum allowed CSI measurement capability are served by cell. 8-port CSI-RS can be configured together with 16-port or 32-port on compatible AAS..";
      uses CsiRsConfig32P-struct;
    }
    list csiRsConfig4P {
      key "id";
      leaf id {
        type uint32;
        description "Synthetic key for struct attribute.";
      }
      description "Settings related to 4-port CSI and associated port to antenna mapping. Applies only to cells based on radios with four Tx branches. Otherwise, ignored..";
      uses CsiRsConfig4P-struct;
    }
    list csiRsConfig8P {
      key "id";
      leaf id {
        type uint32;
        description "Synthetic key for struct attribute.";
      }
      description "Settings related to 8-port CSI and associated port to antenna mapping. Applies only to cells based on radios with at least eight Tx branches. Otherwise, ignored. In standalone operation on radios with 8 or more Tx branches, 8-port CSI-RS is necessary to ensure that users with minimum allowed CSI measurement capability are served by cell. 8-port CSI-RS can be configured together with 16-port or 32-port on compatible AAS..";
      uses CsiRsConfig8P-struct;
    }
    leaf csiRsPeriodicity {
      description "Periodicity of CSI-RS transmission.; Default value: 40.";
      type int32 {
        range "10 | 20 | 40 | 80 | 160 | 320 | 640";
      }
      default "40";
      units "slot";
    }
    leaf csiRsShiftingPrimary {
      description "Whether primary CSI-RS resource allocation shifting is activated..";
      type enumeration {
        enum DEACTIVATED;
        enum ACTIVATED_AUTOMATIC;
      }
    }
    leaf csiRsShiftingSecondary {
      description "Whether secondary CSI-RS resource allocation shifting is activated..";
      type enumeration {
        enum DEACTIVATED;
        enum ACTIVATED_AUTOMATIC;
      }
    }
    leaf dftSOfdmMsg3Enabled {
      description "Whether DFT-S-OFDM waveform support for Msg3 in the RACH process is enabled. Only applicable to Low-Band and Mid-Band cells.; Default value: false.";
      type boolean;
      default "false";
    }
    leaf dftSOfdmPuschEnabled {
      description "Whether DFT-S-OFDM waveform support for PUSCH is enabled.; Default value: false.";
      type boolean;
      default "false";
    }
    leaf dftSOfdmPuschStartRsrpThresh {
      description "UE starts on DFTS-OFDM when reported RSRP is below threshold in attribute value. RSRP is reported in 3GPP TS 38.331 CG-ConfigInfo. Applicable at secondary cell group addition. Only applicable to High-Band cells.; range -156..-29; Default value: -104.";
      type eytypes:int32_range_-156--29;
      default "-104";
      units "dBm";
    }
    leaf dl256QamEnabled {
      description "Enables 256 QAM support in downlink. Not applicable in High-Band cells.; Default value: true.";
      type boolean;
      default "true";
    }
    leaf dlAvailableCrbs {
      description "Total amount of CRBs available for downlink channels. Total downlink channel bandwidth corresponds to sum of downlink available CRBs and downlink blanked CRBs. Total downlink channel bandwidth is configured in NRSectorCarrier::bSChannelBwDL. Formula for conversion to number of CRBs is defined in 3GPP TS 38.211. If empty, there is no bandwidth restriction and no blanking in downlink. If 0, there is no available CRB, NR Channel Bandwidth is fixed to NRSectorCarrier::bSChannelBwDL.; range 0..272.";
      type eytypes:uint32_range_0-272;
    }
    leaf dlChannelScramblingIdentity {
      description "Downlink channel scrambling identity. Scrambling identity used for downlink physical channels and reference signals. Only applicable to High-Band cells..";
      type enumeration {
        enum PCI;
        enum GENERATED;
      }
    }
    leaf dlDmrsMuxSinrThresh {
      description "SINR threshold used by gNodeB to decide multiplexing PDSCH with DMRS for given PDSCH transmission. To avoid throughput degradation, gNodeB does not use Downlink Data and DMRS Multiplexing for a given UE when estimated UE SINR is below this threshold.; range -10..30; Default value: -10.";
      type int32 {
        range "-10..30";
      }
      default "-10";
      units "dB";
    }
    leaf dlMaxMuMimoLayers {
      description "Maximum number of codebook co-scheduled downlink MU-MIMO layers at cell level. Values greater than 8 are not supported. If value greater than 8 is configured, then maximum number of layers is 8. If 0, downlink MU-MIMO is disabled. Only used if license for Downlink Multi-User MIMO Low-Band or Mid-Band is present and feature is active. Only used if radio equipment supports AAS configuration. For High-Band cells, value must be 0.; Default value: 0.";
      type int32 {
        range "0 | 2 | 4 | 6 | 8 | 10 | 12 | 14 | 16";
      }
      default "0";
    }
    leaf dlMaxSupportedModOrder {
      description "Maximum modulation order supported by cell. Value is QAM_256 if radio unit supports 256 QAM and license for NR 256-QAM Downlink High-Band is present and feature is active. Otherwise, value is QAM_64. Only set when NRCellDU instance is unlocked. Only applicable to High-Band cells..";
      type enumeration {
        enum QAM_64;
        enum QAM_256;
      }
      config false;
    }
    leaf dlRobustLaEnabled {
      description "Whether downlink robust link adaptation is enabled. Only applicable if license for Critical IoT is present and the High-Band feature is active. Must be false for Low-Band and Mid-Band cells.; Default value: false; Takes effect: Next cell unlock; Status info: Since 25.Q2. Planned to be removed..";
      type boolean;
      status deprecated;
      default "false";
      reference "Takes effect: Next cell unlock.";
    }
    leaf dlScSpillover {
      description "Supported downlink subcarrier spill-over value of radio to which ESS cell pair is connected. Spill-over means that subcarrier or subcarriers of guard band NB-IoT PRB can exceed PRB subcarrier range of ESS NR cell. Spill-over value represents capability of radio which defines exceeding subcarrier number compared with outmost subcarrier of NR.; range 0..11; Default value: 0.";
      type int32 {
        range "0..11";
      }
      default "0";
      units "subcarrier";
    }
    leaf dlSmallDataRobustness {
      description "Robustness mode for downlink small data. Used to configure increased robustness of downlink small data. Not applicable to High-Band cells..";
      type enumeration {
        enum OFF;
        enum ON;
      }
    }
    leaf dlStartCrb {
      description "Start position of CRBs available for downlink channels. Blanked CRBs appear before start position and after the range of available CRBs.; range 0..272; Default value: 0.";
      type eytypes:uint32_range_0-272;
      default "0";
    }
    leaf drxEnable {
      description "Whether Connected Mode DRX feature to save energy in cell is enabled. If feature is disabled, Connected Mode DRX can still be activated in cell during CGI measurement..";
      type boolean;
    }
    leaf drxInactivityTimer {
      description "Duration after PDCCH ocassion in which PDCCH indicates new uplink or downlink transmission. Recommended value for High-Band is INACTIVITYTIMER_8MS..";
      type enumeration {
        enum INACTIVITYTIMER_0MS;
        enum INACTIVITYTIMER_1MS;
        enum INACTIVITYTIMER_2MS;
        enum INACTIVITYTIMER_3MS;
        enum INACTIVITYTIMER_4MS;
        enum INACTIVITYTIMER_5MS;
        enum INACTIVITYTIMER_6MS;
        enum INACTIVITYTIMER_8MS;
        enum INACTIVITYTIMER_10MS;
        enum INACTIVITYTIMER_20MS;
        enum INACTIVITYTIMER_30MS;
        enum INACTIVITYTIMER_40MS;
        enum INACTIVITYTIMER_50MS;
        enum INACTIVITYTIMER_60MS;
        enum INACTIVITYTIMER_80MS;
        enum INACTIVITYTIMER_100MS;
        enum INACTIVITYTIMER_200MS;
        enum INACTIVITYTIMER_300MS;
        enum INACTIVITYTIMER_500MS;
        enum INACTIVITYTIMER_750MS;
        enum INACTIVITYTIMER_1280MS;
        enum INACTIVITYTIMER_1920MS;
        enum INACTIVITYTIMER_2560MS;
      }
    }
    leaf drxLongCycle {
      description "Duration of one complete DRX cycle. Recommended value for High-Band is LONGCYCLE_80MS..";
      type enumeration {
        enum LONGCYCLE_10MS;
        enum LONGCYCLE_20MS;
        enum LONGCYCLE_32MS;
        enum LONGCYCLE_40MS;
        enum LONGCYCLE_60MS;
        enum LONGCYCLE_64MS;
        enum LONGCYCLE_70MS;
        enum LONGCYCLE_80MS;
        enum LONGCYCLE_128MS;
        enum LONGCYCLE_160MS;
        enum LONGCYCLE_256MS;
        enum LONGCYCLE_320MS;
        enum LONGCYCLE_512MS;
        enum LONGCYCLE_640MS;
        enum LONGCYCLE_1024MS;
        enum LONGCYCLE_1280MS;
        enum LONGCYCLE_2048MS;
        enum LONGCYCLE_2560MS;
        enum LONGCYCLE_5120MS;
        enum LONGCYCLE_10240MS;
      }
    }
    leaf drxOnDurationTimer {
      description "Number of consecutive slots or subframes at beginning of a DRX cycle..";
      type enumeration {
        enum ONDURATIONTIMER_1SUBMS;
        enum ONDURATIONTIMER_2SUBMS;
        enum ONDURATIONTIMER_3SUBMS;
        enum ONDURATIONTIMER_4SUBMS;
        enum ONDURATIONTIMER_5SUBMS;
        enum ONDURATIONTIMER_6SUBMS;
        enum ONDURATIONTIMER_7SUBMS;
        enum ONDURATIONTIMER_8SUBMS;
        enum ONDURATIONTIMER_9SUBMS;
        enum ONDURATIONTIMER_10SUBMS;
        enum ONDURATIONTIMER_11SUBMS;
        enum ONDURATIONTIMER_12SUBMS;
        enum ONDURATIONTIMER_13SUBMS;
        enum ONDURATIONTIMER_14SUBMS;
        enum ONDURATIONTIMER_15SUBMS;
        enum ONDURATIONTIMER_16SUBMS;
        enum ONDURATIONTIMER_17SUBMS;
        enum ONDURATIONTIMER_18SUBMS;
        enum ONDURATIONTIMER_19SUBMS;
        enum ONDURATIONTIMER_20SUBMS;
        enum ONDURATIONTIMER_21SUBMS;
        enum ONDURATIONTIMER_22SUBMS;
        enum ONDURATIONTIMER_23SUBMS;
        enum ONDURATIONTIMER_24SUBMS;
        enum ONDURATIONTIMER_25SUBMS;
        enum ONDURATIONTIMER_26SUBMS;
        enum ONDURATIONTIMER_27SUBMS;
        enum ONDURATIONTIMER_28SUBMS;
        enum ONDURATIONTIMER_29SUBMS;
        enum ONDURATIONTIMER_30SUBMS;
        enum ONDURATIONTIMER_31SUBMS;
        enum ONDURATIONTIMER_1MS;
        enum ONDURATIONTIMER_2MS;
        enum ONDURATIONTIMER_3MS;
        enum ONDURATIONTIMER_4MS;
        enum ONDURATIONTIMER_5MS;
        enum ONDURATIONTIMER_6MS;
        enum ONDURATIONTIMER_8MS;
        enum ONDURATIONTIMER_10MS;
        enum ONDURATIONTIMER_20MS;
        enum ONDURATIONTIMER_30MS;
        enum ONDURATIONTIMER_40MS;
        enum ONDURATIONTIMER_50MS;
        enum ONDURATIONTIMER_60MS;
        enum ONDURATIONTIMER_80MS;
        enum ONDURATIONTIMER_100MS;
        enum ONDURATIONTIMER_200MS;
        enum ONDURATIONTIMER_300MS;
        enum ONDURATIONTIMER_400MS;
        enum ONDURATIONTIMER_500MS;
        enum ONDURATIONTIMER_600MS;
        enum ONDURATIONTIMER_800MS;
        enum ONDURATIONTIMER_1000MS;
        enum ONDURATIONTIMER_1200MS;
        enum ONDURATIONTIMER_1600MS;
      }
    }
    leaf drxProfileEnabled {
      description "Whether DrxProfile MO class is used. If false, DRX attributes in NRCellDU instance are used. If true, appropriate attributes of DrxProfileUeCfg instance under DrxProfile instance referenced by drxProfileRef are used..";
      type boolean;
    }
    leaf drxProfileRef {
      description "Reference to an instance of DrxProfile MO. If non-empty, attributes from referenced MO instance are used. If empty, attribute default values according to DrxProfile and DrxProfileUeCfg MO class definitions are used..";
      type string;
    }
    leaf eDrxMode {
      description "Extended DRX mode. Only applicable if licenses for both following features are present and features are active: - Ericsson Reduced Capability Extended DRX Sector Carrier - Ericsson Reduced Capability Sector Carrier Value IDLE_AND_INACTIVE is only applicable if license for RRC Inactive State is present and feature is active. Only applicable to Low-Band and Mid-Band cells..";
      type enumeration {
        enum DISABLED;
        enum IDLE;
      }
    }
    leaf endcCgSwitchRef {
      description "Reference to an instance of CgSwitch MO. Automatically set to CgSwitch=Default instance, unless manually set to refer to another MO instance. Applicable to EN-DC..";
      type string;
    }
    leaf endcDlLegSwitchEnabled {
      description "Whether EN-DC downlink leg switching is enabled.; Default value: true; Takes effect: Next cell unlock; Status info: Since 24.Q1. Replaced by CgSwitchCfg::dlCgSwitchMode. Planned to be removed..";
      type boolean;
      status deprecated;
      default "true";
      reference "Takes effect: Next cell unlock.";
    }
    leaf endcDlNrLowQualThresh {
      description "NR radio quality level threshold used for SN terminated split bearer. Common for EN-DC and NR-DC. Below this threshold the SCG leg is not used for downlink user data transmission. SINR is used to represent quality. Value -16 corresponds to zero throughput, and lower values have no further impact.; range -40..40; Default value: 5; Takes effect: Next cell unlock; Status info: Since 24.Q1. Replaced by CgSwitchCfg::dlScgLowQualThresh. Planned to be removed..";
      type eytypes:int32_range_-40-40;
      status deprecated;
      default "5";
      units "dB";
      reference "Takes effect: Next cell unlock.";
    }
    leaf endcDlNrQualHyst {
      description "NR radio quality hysteresis used for SN terminated split bearer. Common for EN-DC and NR-DC. Quality needs to be hysteresis more than endcDlNrLowQualThresh to start using SCG leg for downlink user data transmission again. SINR is used to represent quality.; range 0..60; Default value: 5; Takes effect: Next cell unlock; Status info: Since 24.Q1. Replaced by CgSwitchCfg::dlScgLowQualHyst. Planned to be removed..";
      type eytypes:int32_range_0-60;
      status deprecated;
      default "5";
      units "dB";
      reference "Takes effect: Next cell unlock.";
    }
    leaf endcUlCgSwitchRef {
      description "Reference to an instance of UlCgSwitch MO. Automatically set to UlCgSwitch=Default instance, unless manually set to refer to another MO instance. Applicable to EN-DC..";
      type string;
    }
    leaf endcUlLegSwitchEnabled {
      description "Whether EN-DC or NR-DC uplink leg switching is enabled.; Default value: false; Takes effect: Next cell unlock; Status info: Since 24.Q4. Replaced by UlCgSwitchCfg::ulCgSwitchMode. Planned to be removed..";
      type boolean;
      status deprecated;
      default "false";
      reference "Takes effect: Next cell unlock.";
    }
    leaf endcUlNrLowQualThresh {
      description "NR radio quality level threshold used for SN Terminated split bearer. Below this threshold SCG is not used as primary uplink path. SINR is used to represent quality. Common for EN-DC and NR-DC.; range -40..145; Default value: 17; Takes effect: Next cell unlock; Status info: Since 24.Q4. Replaced by UlCgSwitchCfg::ulScgLowQualThresh. Planned to be removed..";
      type int32 {
        range "-40..145";
      }
      status deprecated;
      default "17";
      units "dB";
      reference "Takes effect: Next cell unlock.";
    }
    leaf endcUlNrQualHyst {
      description "NR radio quality hysteresis used for SN Terminated split bearer. Quality need to be hysteresis better than endcUlNrLowQualThresh to start using the SCG Radio Resources as primary uplink path again. SINR is used to represent quality. Common for EN-DC and NR-DC.; range 1..60; Default value: 6; Takes effect: Next cell unlock; Status info: Since 24.Q4. Replaced by UlCgSwitchCfg::ulScgLowQualHyst. Planned to be removed..";
      type int32 {
        range "1..60";
      }
      status deprecated;
      default "6";
      units "dB";
      reference "Takes effect: Next cell unlock.";
    }
    leaf energyOptPwrAllocRef {
      description "Reference to an instance of EnergyOptPwrAlloc MO. Automatically set to EnergyOptPwrAlloc=Default instance, unless manually set to refer to another MO instance..";
      type string;
    }
    leaf essMbsfnConfiguredSubframes {
      description "Decimal representation of bitmap for ESS MBSFN subframes in four consecutive radio frames. Each bit has one of following values: 1: Corresponding MBSFN subframe is configured for ESS. 0: Corresponding MBSFN subframe is not configured for ESS. Starting from first radio frame and from first or leftmost bit in bitmap, configuration applies to subframes #1, #2, #3, #6, #7, and #8 in sequence of four radio frames..";
      type uint32;
      config false;
    }
    leaf essMbsfnSubframeConfig {
      description "MBSFN subframe configuration for eNodeB using four frames. ESS NSA: 110000 000000 100000 000000 (decimal 12584960). ESS SA: 100100 000000 110100 000000 (decimal 9440512) or 100100 000000 111100 000000 (decimal 9441024)..";
      type uint32 {
        range "9440512 | 9441024 | 12584960";
      }
    }
    leaf essMbsfnSubframeVariant {
      description "MBSFN subframe configuration variant for ESS enabled cell..";
      type enumeration {
        enum NSA_BASIC;
        enum SA_BASIC;
        enum SA_SIB_ROBUST_15_PERCENT;
        enum NSA_25_PERCENT;
        enum SA_25_PERCENT;
        enum NSA_SA_35_PERCENT;
        enum NSA_SA_45_PERCENT;
        enum NSA_SA_55_PERCENT;
      }
    }
    leaf essPdschEarlyStartConfig {
      description "Configuration of PDSCH early start symbol for ESS enabled cell. Defines earliest possible start symbol for PDSCH. Only applicable if license for LTE-NR FDD Spectrum Sharing with Additional NR PDSCH Symbols is present and feature is active. Only applicable to Low-Band, ESS cells..";
      type enumeration {
        enum NO_PDSCH_EARLY_START;
        enum ADAPT_MIN_SECOND;
      }
    }
    leaf extCaPriorityRef {
      description "Reference to an instance of ExtCaPriority MO. Automatically set to ExtCaPriority=Default instance, unless manually set to refer to another MO instance..";
      type string;
    }
    leaf extendedBandN77TwoBwpEnabled {
      description "Whether UE capability extended-n77-2-r17 control the selection of partial or full bandwidth part. If true, UEs that indicate capability for extendedBand-n77-2-r17 can access full bandwidth part of cell. UEs that do not indicate capability for extendedBand-n77-2-r17 can access partial bandwidth part below 3650 MHz of cell. Only applicable if license for NR Overlapping Dual Band Support is present and feature is active.; Default value: false.";
      type boolean;
      default "false";
    }
    leaf externalConnectDelay {
      description "Additional round trip delay required for Indoor Connect 8855 or similar component. Value must be taken from external connecting system. Only applicable to Mid-Band cells.; Default value: 0.";
      type int32 {
        range "0 | 100..250";
      }
      default "0";
      units "microsecond";
    }
    leaf fixWideBeamsForPeriodicSr {
      description "Number of fixed wide beams for periodic SR in PRACH slot according to SSB relation. Only applicable to High-Band cells. For Low-Band and Mid-Band cells, value must be FIX_WB_FOR_PERIODIC_SR_NONE. Attribute is for 12 wide beam configuration and is scaled automatically for 24 wide beam support..";
      type enumeration {
        enum FIX_WB_FOR_PERIODIC_SR_NONE;
        enum FIX_WB_FOR_PERIODIC_SR_LOW;
        enum FIX_WB_FOR_PERIODIC_SR_MEDIUM;
        enum FIX_WB_FOR_PERIODIC_SR_HIGH;
      }
    }
    leaf improvedUlInSparseBwp {
      description "Whether additional uplink scheduling occasion is used in sparse BWP. If true, improved uplink performance is expected in sparse BWP by using more uplink scheduling occasions. Only applicable to 4+2+4, 4+1 and 8+2 TDD pattern. Only applicable to Mid-Band cells. Only applicable if license for NR Dynamic Power Optimizer is present and feature is active.; Default value: true.";
      type boolean;
      default "true";
    }
    leaf improvedUlLinkAdaptation {
      description "Whether Improved Uplink Link Adaptation feature is enabled for cell.; Default value: true.";
      type boolean;
      default "true";
    }
    leaf imsEmSupportEnabled {
      description "Whether NR cell supports emergency services for UEs in limited service mode. If true, attribute indicates by broadcasting ims-EmergencySupport in SIB1 that cell supports emergency services for UEs in limited service mode. If false, IMS emergency call is not supported by network in cell for UEs in limited service mode. Only applicable if license for NR Limited Service Mode Emergency Call Support is present and feature is active.; Default value: false.";
      type boolean;
      default "false";
    }
    leaf interferenceSensingEnabled {
      description "Whether Ericsson Interference Sensing feature is enabled. Only applicable to Mid-Band cells. Value true is only applicable to RAN Compute group 5 and higher.; Default value: false.";
      type boolean;
      default "false";
    }
    leaf intMitigationDlSched {
      description "Activation mode of NR Interference Mitigation for Downlink Scheduling feature. Only applicable to Low-Band cells..";
      type enumeration {
        enum DEACTIVATED;
        enum PM_ONLY;
        enum ACTIVATED;
      }
    }
    leaf maxNoOfAdvancedDlMuMimoLayers {
      description "Maximum number of advanced downlink MU-MIMO Mid-Band layers at cell level that are co-scheduled. Values higher than 8 are only applicable to RAN Compute group 5 and higher.; Default value: 0.";
      type int32 {
        range "0 | 2 | 4 | 6 | 8 | 10 | 12 | 14 | 16";
      }
      default "0";
    }
    leaf maxNoOfUeInSparseBwp {
      description "Maximum number of simultaneously supported UEs in sparse BWP per cell. If 0, DCI-based BWP switch is not allowed. Only applicable if license for NR Dynamic Power Optimizer is present, feature is active and configured in cell. Only applicable to Mid-Band cells.; range 0..5000; Default value: 900.";
      type eytypes:int32_range_0-5000;
      default "900";
    }
    leaf maxNoOfUeInSparseSssg {
      description "Maximum number of simultaneously supported UEs in sparse SSSG per cell. If 0, SSSG switch is not allowed. Only applicable if sssgSwitchRef is non-empty. Only applicable to Low-Band cells.; range 0..5000; Default value: 900.";
      type eytypes:int32_range_0-5000;
      default "900";
    }
    leaf maxOffloadDurationShutDown {
      description "Maximum time administrativeState is set to SHUTTINGDOWN for NR Cell Soft Lock functionality. Maximum offload duration time for NR Booster Carrier Sleep. Value -1 means wait forever.; Default value: 90.";
      type int32 {
        range "-1 | 10..1500";
      }
      default "90";
      units "s";
    }
    leaf maxPf3Resources {
      description "Maximum value possible for PUCCH format 3 resources to be allocated for downlink HARQs. Actual number configured might be adjusted by algorithm.; range 1..8; Default value: 2.";
      type eytypes:int32_range_1-8;
      default "2";
    }
    leaf maxUeSpeed {
      description "Expected maximum speed of moving UE. If empty, system configures a value depending on cell configuration. For High-Band, value is UP_TO_10KMPH. For Low-Band or Mid-Band, value is UP_TO_100KMPH. For High-Band, one of following values is allowed: - UP_TO_10KMPH - UP_TO_50KMPH - UP_TO_100KMPH - Empty For Low-Band and Mid-Band cells, one of following values is allowed: - UP_TO_100KMPH - UP_TO_200KMPH - UP_TO_350KMPH - UP_TO_500KMPH - Empty.";
      type enumeration {
        enum UP_TO_10KMPH;
        enum UP_TO_50KMPH;
        enum UP_TO_100KMPH;
        enum UP_TO_200KMPH;
        enum UP_TO_350KMPH;
        enum UP_TO_500KMPH;
      }
    }
    leaf maxUsersRachSchedPusch {
      description "Maximum number of connected users for scheduling PUSCH on RACH symbols. Maximum number of connected users for each cell to allow scheduling PUSCH on symbols configured for RACH. If 0, scheduling of PUSCH on symbols configured for RACH is not allowed. Only applicable when this cell is configured as PSCell.; range 0..100; Default value: 100.";
      type eytypes:int32_range_0-100-2;
      default "100";
    }
    leaf msg3MaxHarqTx {
      description "Maximum number of HARQ transmissions for Msg3. Only applicable to High-Band cells.; range 1..8; Default value: 4.";
      type uint32 {
        range "1..8";
      }
      default "4";
    }
    leaf nbIotCellDeployed {
      description "Whether NB-IoT cell is deployed with LTE and NR cells. Only applicable if license for LTE-NR FDD Spectrum Sharing with NB-IoT is present and feature is active.; Default value: false.";
      type boolean;
      default "false";
    }
    leaf nCI {
      description "NR Cell Identity..";
      type int64;
      config false;
    }
    leaf networkSignalValue {
      description "Network signaling value to adjust UE power.; Default value: 0.";
      type int32 {
        range "0..100 | 300 | 500 | 4300";
      }
      default "0";
    }
    leaf noOfCbraPreambles {
      description "Number of Contention-Based Random Access (CBRA) preambles. If rachRestrictedSetConfig is not UNRESTRICTED_SET, value 16 is used. Only applicable to Low-Band and Mid-Band cells.; range 16..64; Default value: 16.";
      type int32 {
        range "16..64";
      }
      default "16";
    }
    leaf nRCellDUId {
      description "The value component of the RDN..";
      type string;
      mandatory true;
    }
    leaf nrdcCgSwitchRef {
      description "Reference to an instance of CgSwitch MO. Automatically set to CgSwitch=Default instance, unless manually set to refer to another MO instance. Applicable to NR-DC..";
      type string;
    }
    leaf nrdcUlCgSwitchRef {
      description "Reference to an instance of UlCgSwitch MO. Automatically set to UlCgSwitch=Default instance, unless manually set to refer to another MO instance. Applicable to NR-DC..";
      type string;
    }
    leaf nrLteCoexistence {
      description "Whether NR cell is deployed in an LTE-NR coexistence in a Low-Band or Mid-Band cell. If true when using TDD, tddUlDlPattern settings are validated with respect to alignment to LTE TDD. Value of N_TA, offset is configured to 39936 x T_c to enable uplink frame alignment with an LTE TDD network. If true when using FDD, value of N_TA, offset is configured to 0 x T_c to enable uplink frame alignment with an LTE FDD network. If false, value of N_TA, offset is configured to: - 25600 x T_c, if ulCaTimeAlignmentMode is N_TA_O_STANDARD - 39936 x T_c, if ulCaTimeAlignmentMode is N_TA_O_39936 See 3GPP TS 38.133, 5G; NR; Requirements for support of radio resource management, chapter 7.1.2.; Default value: false.";
      type boolean;
      default "false";
    }
    leaf nRPCI {
      description "The Physical Cell Identity (PCI) of the NR cell.; range 0..1007.";
      type int32 {
        range "0..1007";
      }
      mandatory true;
    }
    leaf nrRrpEnabled {
      description "Whether NR radio resource partitioning is enabled. Only applicable if license for NR Radio Resource Partitioning is present and feature is active. Only applicable if cellResourceMappingRef is non-empty. Not applicable to High-Band cells.; Default value: false.";
      type boolean;
      default "false";
    }
    leaf-list nRSectorCarrierRef {
      description "References to instances of NRSectorCarrier MO. If empty, no SectorCarrier instance is used in this cell..";
      type string;
      ordered-by user;
      min-elements 0;
      max-elements 6;
    }
    leaf nrSrsDlBufferVolThr {
      description "Data size threshold used by gNodeB to label a user session as heavy traffic. SRS resources are only allocated to users with this label. If 0, data size is not considered, and SRS is allocated to users in order of arrival. Only applicable if license for Advanced Downlink Single-User MIMO Mid-Band is present and feature is active. Only applicable to Mid-Band cells.; range 0..30000; Default value: 0.";
      type eytypes:int32_range_0-30000;
      default "0";
      units "kB";
    }
    leaf nrSrsDlPacketAgeThr {
      description "Packet age threshold used by gNodeB to label a user session as heavy traffic. If 0, packet age is not considered for SRS allocation. Only data size is considered if nrSrsDlBufferVolThr value is non-zero. If values of this attribute and nrSrsDlBufferVolThr are both zero, SRS is allocated in order of arrival. Only applicable if license for Advanced Downlink Single-User MIMO Mid-Band is present and feature is active. Only applicable to Mid-Band cells.; range 0..1000; Default value: 0.";
      type eytypes:int32_range_0-1000;
      default "0";
      units "ms";
    }
    leaf nRTAC {
      description "NR Tracking Area Code (TAC). Values 0, 16777214, and 16777215 are not broadcast in SIB1.; range 0..16777215.";
      type eytypes:int32_range_0-16777215;
      mandatory true;
    }
    leaf nRTACInSib1Enabled {
      description "Whether nRTAC can be included in SIB1. If false, nRTAC is excluded from SIB1 and NR cell is not used as a PCell within any of the PLMNs in pLMNIdList. If true and secondaryCellOnly is false, nRTAC is included in SIB1..";
      type boolean;
    }
    leaf operationalState {
      description "The operational state..";
      type enumeration {
        enum DISABLED;
        enum ENABLED;
      }
      config false;
    }
    leaf-list pairwiseSrsCorrelationThresh {
      description "Correlation thresholds for different number of SRS ports. Used to determine which SRS ports can be used for reciprocity-based PDSCH beamforming. Value of first position (index 1) is used for cases when up to two SRS ports are deemed as valid from gNodeB. Value of second position (index 2) is used to validate correlation across all possible pairwise combinations from all SRS ports of UE. Value of this attribute is normalized correlation: If 0, no correlation. If 1000, full correlation. First value in pair must be lower than second value. Only applicable to Mid-Band cells.; Default values sequence: 850,990.";
      type uint32 {
        range "0..1000";
      }
      ordered-by user;
      min-elements 2;
      max-elements 2;
    }
    leaf pCellDlDataOffload {
      description "Whether PCell downlink data offloading is enabled. If true, cell is offloaded to SCells with larger pipe size. Can only be true for Low-Band cells.; Default value: false.";
      type boolean;
      default "false";
    }
    leaf pdcchCapacityBoostEnabled {
      description "Whether PDCCH capacity boosting is enabled. Only applicable if license for PDCCH Capacity Boost is present and feature is active.; Default value: false.";
      type boolean;
      default "false";
    }
    leaf pdcchLaBfGainFraction {
      description "Fraction of beamforming gain considered by PDCCH Link Adaptation to enhance PDCCH capacity. Decreasing from 100 to 0 shifts the emphasis of PDCCH Link Adaptation (LA) from PDCCH capacity enhancement to PDCCH robustness enhancement. If 0, PDCCH LA does not consider beamforming gain difference between codebook-based PDCCH beamforming and common channel PDCCH beamforming. PDCCH robustness improves. If 100, PDCCH LA fully consider beamforming gain difference between codebook-based PDCCH beamforming and common channel PDCCH beamforming. PDCCH LA is more aggressive in aggregation level selection. PDCCH capacity improves. If a value between 0 and 100, PDCCH LA partially considers beamforming gain difference between codebook-based PDCCH beamforming and common channel PDCCH beamforming. Only applicable if license for Coverage- and Capacity-Optimized PDCCH Beamforming is present and feature is active. Only applicable to Low-Band and Mid-Band cells.; range 0..100; Default value: 100.";
      type eytypes:int32_range_0-100-2;
      default "100";
    }
    leaf pdcchLaSinrOffset {
      description "SINR offset added to SINR estimated from CQI to determine PDCCH SINR. To determine aggregation level, PDCCH LA utilizes SINR offset. SINR offset accounts for link and beamforming compensations. Only applicable to Low-Band and Mid-Band cells.; range -30..30; Default value: -15.";
      type eytypes:int32_range_-30-30;
      default "-15";
      units "dB";
    }
    leaf pdcchOlaSelection {
      description "Determines how PDCCH outer loop adjustment is computed. Only applicable to Low-Band, ESS cells..";
      type enumeration {
        enum NO_OLA;
        enum PDSCH_OLA;
      }
    }
    leaf pdcchRachBoost {
      description "Amount of power boosting to PDCCH for initial access. This is applicable to following messages: - Msg2 - Msg3 retransmission - Msg4 - P2 refinement Only applicable to High-Band SpCells. Value must be 0 for Low-Band and Mid-Band cells. Attribute actualPdcchRachBoost shows actual boost.; range 0..6; Default value: 0.";
      type eytypes:int32_range_0-6;
      default "0";
      units "dB";
    }
    leaf pdcchReuseForPdschRef {
      description "Reference to an instance of PdcchReuseForPdsch MO. Automatically set to PdcchReuseForPdsch=Default instance, unless manually set to refer to another MO instance. Only applicable to Low-Band and Mid-Band cells..";
      type string;
    }
    leaf pdcchSymbConfig {
      description "Configuration for number of symbols used for PDCCH in each downlink slot. Value must be MINIMUM in following cases: - High-Band cells (TDD cells) - Low-Band cells with bandwidth larger than 50 MHz - Mid-Band cells (TDD cells) with bandwidth lower than 20 MHz or larger than 100 MHz Value can be MINIMUM or ADAPT_MAX_2 for ESS cells. Value can be MINIMUM, STATIC_2 or STATIC_3 for cells that are both FDD and non-ESS, with bandwidth of 5 MHz or 10 MHz when NR Flexible Channel Bandwidth in downlink is used (dlAvailableCrbs greater than 0). Value can be MINIMUM, STATIC_2, ADAPT_MAX_2, STATIC_3 or ADAPT_MAX_3 for cells that are both FDD and non-ESS, with bandwidth of 15, 20 MHz or 10 MHz when NR Flexible Channel Bandwidth in downlink is not used (dlAvailableCrbs equal to 0 or empty). Value can be MINIMUM, ADAPT_MAX_2 or ADAPT_MAX_3 for cells that are both FDD and non-ESS, with bandwidth of 25, 30, 35, 40 or 50 MHz. Value can be MINIMUM or ADAPT_MAX_2 for Mid-Band cells (TDD) with a bandwidth of 20, 30, 40, 50, 60, 70, 80, 90 or 100 MHz. Not applicable to High-Band cells..";
      type enumeration {
        enum MINIMUM;
        enum STATIC_2;
        enum ADAPT_MAX_2;
        enum ADAPT_MAX_3;
        enum STATIC_3;
      }
    }
    leaf pdschAllowedInDmrsSym {
      description "Whether DMRS symbols are allowed to be used for PDSCH data transmission. If true, PDSCH can be present in symbols carrying DMRS. gNodeB determines number of DMRS CDM groups without data for each PDSCH transmission. If false, PDSCH is not present in symbols carrying DMRS unless required by 3GPP TS 38.214, section 5.1.6.2. The gNodeB signals UE according to 3GPP TS 38.212, section 7.3.1.2. In ESS cell, only applicable if license for LTE-NR FDD Spectrum Sharing with Downlink Data and DMRS Multiplexing is present and feature is active. In non-ESS cell, only applicable - to FR1 frequencies - if license for Downlink Data and DMRS Multiplexing is present and feature is active.; Default value: false.";
      type boolean;
      default "false";
    }
    leaf pdschRachBoost {
      description "Amount of power boosting to PDSCH channel carrying Msg2. Only applicable to High-Band SpCells. Value must be 0 for Low-Band and Mid-Band cells. Attribute actualPdschRachBoost shows actual boost.; range 0..12; Default value: 0.";
      type eytypes:int32_range_0-12;
      default "0";
      units "dB";
    }
    leaf pdschStartPrbStrategy {
      description "Mitigate interference strategy that chooses one of following ways to allocate PRBs to UEs for downlink. - From lower frequency band edge, START_LOWER_EDGE. - From higher frequency band edge, START_HIGHER_EDGE. - Both from lower and higher frequency band edges by random for each slot, RANDOM_START_LOWER_OR_HIGHER. - Random starting point for each slot for interference spreading over the whole band, RANDOM_START_WITHIN_BAND..";
      type enumeration {
        enum START_LOWER_EDGE;
        enum START_HIGHER_EDGE;
        enum RANDOM_START_LOWER_OR_HIGHER;
        enum RANDOM_START_WITHIN_BAND;
      }
    }
    leaf pimaVictimCellId {
      description "Cell ID of victim cell performing PIM avoidance. If empty, cell is not aggressor cell.; range 0..255.";
      type eytypes:int32_range_0-255;
      config false;
    }
    leaf pimaVictimENodeBId {
      description "The eNodeB ID of victim cell performing PIM avoidance. If empty, cell is not aggressor cell.; range 0..1048575.";
      type eytypes:int32_range_0-1048575;
      config false;
    }
    leaf pimAvoidanceControllerEnabled {
      description "Whether Multi-Node PIM Avoidance is enabled. Cell can be victim, aggressor, or both. In case of victim cell, PIM power excess measurement is reported to aggressor cell. In case of aggressor cell, downlink CRBs are blanked to avoid PIM interference.; Default value: false.";
      type boolean;
      default "false";
    }
    leaf pimAvoidanceModeStatus {
      description "Multi-Node PIM Avoidance status. If empty, cell is not performing Multi-Node PIM Avoidance..";
      type enumeration {
        enum AGGRESSOR;
        enum VICTIM;
        enum AGGRESSOR_VICTIM;
      }
      config false;
    }
    leaf pimAvoidPeriodicPause {
      description "Whether periodic pause of PIM avoidance is enabled. Periodic pause is used to observe gain.; Default value: false.";
      type boolean;
      default "false";
    }
    leaf pimMinCrbReservedProportion {
      description "Minimum percentage of CRBs reserved for scheduling.; range 10..100; Default value: 10.";
      type eytypes:int32_range_10-100;
      default "10";
      units "percent";
    }
    leaf pimRunningVictimCellId {
      description "Cell ID of victim cell performing PIM avoidance. If empty, cell is not aggressor cell.; range 0..255.";
      type eytypes:int32_range_0-255;
      config false;
    }
    leaf pimRunningVictimENBId {
      description "The eNodeB ID of victim cell performing PIM avoidance. If empty, cell is not aggressor cell.; range 0..1048575.";
      type eytypes:int32_range_0-1048575;
      config false;
    }
    list pLMNIdList {
      key "id";
      leaf id {
        type uint32;
        description "Synthetic key for struct sequence entry.";
      }
      min-elements 1;
      max-elements 12;
      uses PLMNId-struct;
    }
    leaf pMax {
      description "Maximum UE uplink transmission power in serving cell. Corresponds to parameter PEMAX in 3GPP TS 38.101. All cells that belong to same frequency relation must be set to same value If empty or 1000, maximum uplink power of UE is limited by UE capabilities. Only applicable to Low-Band and Mid-Band cells.; Default value: 23.";
      type int32 {
        range "-30..33 | 1000";
      }
      default "23";
      units "dBm";
    }
    leaf pMaxCa {
      description "Maximum UE uplink transmission power over all serving cells. Corresponds to parameter PEMAXCA in 3GPP TS 38.101-1. If 1000, maximum uplink transmission power of UE in uplink carrier aggregation is limited by UE capabilities. Not applicable if NRSectorCarrier::txDirection is DL. Only applicable to Low-Band and Mid-Band cells.; Default value: 1000.";
      type int32 {
        range "-30..33 | 1000";
      }
      default "1000";
      units "dBm";
    }
    leaf pointAArfcnDlFdd {
      description "Common reference point for the resource block grid of the downlink carrier FDD cell. PointA value given by center frequency of resource element 0 in cell resource block 0 and indicated on a raster as NR-ARFCN. Computed from NRSectorCarrier::arfcnDL on cell unlock..";
      type int32;
      config false;
    }
    leaf pointAArfcnTdd {
      description "Common reference point for resource block grid within a cell. PointA value given by center frequency of resource element 0 in cell resource block 0 and indicated on a raster as NR-ARFCN. Computed from NRSectorCarrier::arfcnDL on cell unlock.; range 0..3279165.";
      type eytypes:int32_range_0-3279165;
      config false;
    }
    leaf pointAArfcnUlFdd {
      description "Common reference point for the resource block grid of the uplink carrier FDD cell. PointA value given by center frequency of resource element 0 in cell resource block 0 and indicated on a raster as NR-ARFCN. Computed from NRSectorCarrier::arfcnUL on cell unlock. Not applicable if NRSectorCarrier::txDirection is DL..";
      type int32;
      config false;
    }
    leaf pointAFrequencyDlFdd {
      description "Frequency representation of the NR-ARFCN used by pointAArfcnDlFdd..";
      type int32;
      config false;
      units "kHz";
    }
    leaf pointAFrequencyTdd {
      description "Frequency representation of the NR-ARFCN used by pointAArfcnTDD.; range 0..100000000.";
      type int32 {
        range "0..100000000";
      }
      config false;
      units "kHz";
    }
    leaf pointAFrequencyUlFdd {
      description "Frequency representation of the NR-ARFCN used by pointAArfcnUlFdd. Not applicable if NRSectorCarrier::txDirection is DL..";
      type int32;
      config false;
      units "kHz";
    }
    leaf poorRadioQualDciBwpSwitchThr {
      description "Threshold that defines poor radio quality for UE configured with DCI-based BWP switching. Radio quality is considered poor when below threshold. SINR is used to represent radio quality. Only applicable if license for NR Dynamic Power Optimizer is present, feature is active and configured in cell. Only applicable to Mid-Band cells.; range -40..40; Default value: 5.";
      type eytypes:int32_range_-40-40;
      default "5";
      units "dB";
    }
    leaf poorRadioQualSssgSwitchThresh {
      description "Threshold that defines poor radio quality for UE configured with SSSG switching. Radio quality is considered poor when below threshold. SINR is used to represent radio quality. Only applicable if sssgSwitchRef is non-empty. Only applicable to Low-Band cells.; range -40..40; Default value: 5.";
      type eytypes:int32_range_-40-40;
      default "5";
      units "dB";
    }
    leaf prachConfigIndex {
      description "PRACH configuration index. If empty, system configures: - 159 if tddUlDlPattern is TDD_ULDL_PATTERN_00, TDD_ULDL_PATTERN_02, TDD_ULDL_PATTERN_03 or TDD_ULDL_PATTERN_04. - 158 if tddUlDlPattern is TDD_ULDL_PATTERN_01 or TDD_ULDL_PATTERN_08. - 156 if tddUlDlPattern is TDD_ULDL_PATTERN_07. Only applicable to Mid-Band cells.; range 155..159.";
      type int32 {
        range "155..159";
      }
    }
    leaf primaryCellCapable {
      description "Whether UEs are allowed to connect to cell in standalone mode. If true, this attribute overrides setting of attribute secondaryCellOnly. Only applicable for High-Band cells..";
      type boolean;
    }
    leaf prioBoundaryCrb {
      description "CRB position indicating boundary between CRBs with higher and lower priority. Starting point for CRBs with lower priority. If empty, CRB position is not set. Only applicable to non-ESS Low-Band cells with downlink bandwidth of 10, 15, 20, 25, 30, or 35 MHz. Must be empty in other cells.; range 0..272.";
      type int32 {
        range "0..272";
      }
    }
    leaf puschAllowedInDmrsSym {
      description "Whether DMRS symbols can be used for PUSCH data transmission. If true, PUSCH can be present in symbols carrying DMRS. If false, PUSCH is not present in symbols carrying DMRS. See 3GPP TS 38.214, section 6.2.2 and 3GPP TS 38.212, section 7.3.1.1. Not applicable in High-Band cells. Will be used together with a feature license.; Default value: false.";
      type boolean;
      default "false";
    }
    leaf puschModeOnFddSCell {
      description "Usage of short PUSCH in Low-Band cells. Short PUSCH refers to time domain allocation of less than 14 symbols. Long PUSCH refers to time domain allocation of 14 symbols. Used in SCell. Only applicable if license for NR Uplink Carrier Aggregation is present and feature is active. Not applicable if NRSectorCarrier::txDirection is DL. Only applicable to Low-Band cells. Must be LONG in Mid-Band and High-Band cells..";
      type enumeration {
        enum LONG;
        enum SHORT_SRS_CONSEC_SL_OVERLAP;
        enum SHORT_SRS_OVERLAP;
        enum SHORT_CONSEC_SL_OVERLAP;
      }
    }
    leaf puschStartPrbStrategy {
      description "Mitigate interference strategy that chooses one of following ways to allocate PRBs to UEs for uplink. - From lower frequency band edge, START_LOWER_EDGE. - From higher frequency band edge, START_HIGHER_EDGE. - Both from lower and higher frequency band edges by random for each slot, RANDOM_START_LOWER_OR_HIGHER. - Random starting point for each slot for interference spreading over the whole band, RANDOM_START_WITHIN_BAND..";
      type enumeration {
        enum START_LOWER_EDGE;
        enum START_HIGHER_EDGE;
        enum RANDOM_START_LOWER_OR_HIGHER;
        enum RANDOM_START_WITHIN_BAND;
      }
    }
    leaf pwsBroadcastOngoing {
      description "Whether PWS broadcast is scheduled..";
      type boolean;
      config false;
    }
    leaf pZeroNomPucch {
      description "Power control parameter P0 Nominal for PUCCH transmissions. If 1000, system selects a P0 Nominal for PUCCH transmissions, which is presented in pZeroNomPucchAutoSelected. Value 1000 is only allowed for High-Band cells.; Default value: -114.";
      type int32 {
        range "-202..24 | 1000";
      }
      default "-114";
      units "dBm";
    }
    leaf pZeroNomPucchAutoSelected {
      description "Automatically selected P0 Nominal for PUCCH transmissions. System selected value if pZeroNomPucch is set to 1000. If empty while NRCellDU instance unlocked, automatic selection is not active..";
      type int32;
      config false;
      units "dBm";
    }
    leaf pZeroNomPuschAutoSelected {
      description "Automatically selected P0 Nominal for PUSCH transmissions with grant. System selected value if pZeroNomPuschGrant is set to 1000. If empty while NRCellDU instance unlocked, automatic selection is not active..";
      type int32;
      config false;
      units "dBm";
    }
    leaf pZeroNomPuschGrant {
      description "Power control parameter P0 Nominal for PUSCH transmissions with grant. If 1000, system selects a P0 Nominal for PUSCH transmissions with grant, which is presented in pZeroNomPuschAutoSelected.; Default value: -100.";
      type int32 {
        range "-202..24 | 1000";
      }
      default "-100";
      units "dBm";
    }
    leaf pZeroNomSrs {
      description "Power control parameter P0 nominal for SRS transmissions.; range -202..24; Default value: -110.";
      type int32 {
        range "-202..24";
      }
      default "-110";
      units "dBm";
    }
    leaf pZeroUePuschOffset256Qam {
      description "Power offset to target-received PUSCH PSD for 256-QAM-capable UEs. Relevant when 256-QAM MCS Table 5.1.3.1-2 in 3GPP TS 38.214 is used. Controls received SINR target. Only applicable if ul256QamEnabled is true.; range 0..15; Default value: 0.";
      type int32 {
        range "0..15";
      }
      default "0";
      units "dB";
    }
    leaf qQualMin {
      description "Minimum required quality level RSRQ in cell. If empty, value is not broadcast in SIB1.; range -43..-12.";
      type eytypes:int32_range_-43--12;
      units "dB";
    }
    leaf qQualMinOffset {
      description "Offset applied to signaled Qqualmin. If empty, value is not broadcast in SIB1, and UE applies default value of 0 dB for Qqualminoffset in 3GPP TS 38.304.; range 1..8.";
      type int32 {
        range "1..8";
      }
      units "dB";
    }
    leaf qRxLevMin {
      description "Required minimum received RSRP level in cell for cell selection or re-selection.; range -140..-44; Default value: -140.";
      type eytypes:int32_range_-140--44;
      default "-140";
      units "dBm";
    }
    leaf qRxLevMinOffset {
      description "Offset applied to signaled Qrxlevmin. If empty, value is not broadcast in SIB1, and UE applies default value of 0 dB for Qrxlevminoffset in 3GPP TS 38.304.; range 2..16.";
      type int32 {
        range "2..16";
      }
      units "dB";
    }
    leaf qualHystDciBwpSwitch {
      description "Hysteresis that defines good radio quality for UE configured with DCI-based BWP switching. Radio quality is considered good when greater than the sum of this value and threshold, where the threshold is value of poorRadioQualDciBwpSwitchThr. SINR is used to represent radio quality. Only applicable if license for NR Dynamic Power Optimizer is present, feature is active and configured in cell. Only applicable to Mid-Band cells.; range 0..60; Default value: 3.";
      type eytypes:int32_range_0-60;
      default "3";
      units "dB";
    }
    leaf qualHystSssgSwitch {
      description "Hysteresis that defines good radio quality for UE configured with SSSG switching. Radio quality is considered good when greater than sum of this value and threshold, where threshold is value of poorRadioQualSssgSwitchThresh. SINR is used to represent radio quality. Only applicable if sssgSwitchRef is non-empty. Only applicable to Low-Band cells.; range 0..60; Default value: 3.";
      type eytypes:int32_range_0-60;
      default "3";
      units "dB";
    }
    leaf rachPreambleDetThrFraction {
      description "Fraction applied to PRACH power level detection threshold. Value lower than 10 decreases PRACH power level detection threshold. Value higher than 10 increases PRACH power level detection threshold.; range 1..100; Default value: 10.";
      type eytypes:int32_range_1-100-3;
      default "10";
    }
    leaf rachPreambleFormat {
      description "RACH preamble format. If empty, system configures: For Low-Band, RACH_PREAMBLE_FORMAT_00 (F0) For Mid-Band, RACH_PREAMBLE_FORMAT_01 (B4) For High-Band, RACH_PREAMBLE_FORMAT_03 (A3). For Low-Band cells, RACH_PREAMBLE_FORMAT_00 (F0), RACH_PREAMBLE_FORMAT_01 (B4) and RACH_PREAMBLE_FORMAT_02 (F1) are allowed. For Mid-Band cells, RACH_PREAMBLE_FORMAT_00 (F0) and RACH_PREAMBLE_FORMAT_01 (B4) are allowed. For High-Band cells, RACH_PREAMBLE_FORMAT_03 (A3) and RACH_PREAMBLE_FORMAT_04 (C2) are allowed. Value RACH_PREAMBLE_FORMAT_01 (B4) is allowed for backward compatibility. System applies RACH_PREAMBLE_FORMAT_03 (A3)..";
      type enumeration {
        enum RACH_PREAMBLE_FORMAT_00;
        enum RACH_PREAMBLE_FORMAT_01;
        enum RACH_PREAMBLE_FORMAT_02;
        enum RACH_PREAMBLE_FORMAT_03;
        enum RACH_PREAMBLE_FORMAT_04;
      }
    }
    leaf rachPreambleRecTargetPower {
      description "Target random access preamble power level at network receiver side.; range -202..-60; Default value: -110.";
      type int32 {
        range "-202..-60";
      }
      default "-110";
      units "dBm";
    }
    leaf rachPreambleTransMax {
      description "Maximum number of random access preamble transmissions performed before declaring a failure.; Default value: 10.";
      type int32 {
        range "3..8 | 10 | 20 | 50 | 100 | 200";
      }
      default "10";
    }
    leaf rachRef {
      description "Reference to an instance of Rach MO. Automatically set to Rach=Default instance, unless manually set to refer to another MO instance..";
      type string;
    }
    leaf rachRestrictedSetConfig {
      description "Configuration of restricted sets for random access preamble. Configuration of unrestricted set, or one of two types of restricted sets for random access preamble..";
      type enumeration {
        enum UNRESTRICTED_SET;
        enum RESTRICTED_SET_TYPE_A;
        enum RESTRICTED_SET_TYPE_B;
      }
      config false;
    }
    leaf rachRootSequence {
      description "First root sequence index for random access preamble generation.; range 0..837; Default value: 1.";
      type eytypes:int32_range_0-837;
      default "1";
    }
    leaf radioRecIntPwrOffset {
      description "Negative offset for uplink interference and noise PM counters in Radio Dot System. The offset is applied in following PM counters: - pmRadioRecInterferencePwrSumPrbDistr - pmRadioRecInterferencePwrDistr - pmRadioRecInterferencePowerDistr - pmRadioRecInterferencePwrUlSlotXDistr, X=1..6 - pmRadioRecInterferencePwrSpecialSlotXDistr, X=1..4 The offset makes the PM counter represent the noise floor at one RU, consisting of IRU and connected Radio Dots (RD), instead of aggregated values from all RD connected to the IRU. Use only for cell in RDS.; range 0..3000; Default value: 0.";
      type int32 {
        range "0..3000";
      }
      default "0";
      units "dB";
    }
    leaf raResponseWindow {
      description "Msg2 random access response window in number of slots. If license for NR Uplink Carrier Aggregation is present and feature is active, system automatically overrides settings lower than 20 and uses 20. Only applicable to Mid-Band cells.; Default value: 10.";
      type int32 {
        range "10 | 20";
      }
      default "10";
    }
    leaf rdsUeAdvancedPosEnabled {
      description "Whether Advanced RDS Location Support for Dedicated RAN is enabled in cell. Only applicable if license for Advanced RDS Location Support for Dedicated RAN is present and feature is active. Only applicable to Mid-Band cells.; Default value: false.";
      type boolean;
      default "false";
    }
    leaf redCap1RxEnabled {
      description "Whether Reduced Capability 1Rx UE for cell is enabled. If true, IE cellBarredRedCap1Rx-r17 in SIB1 is set to notBarred and IE intraFreqReselectionRedCap-r17 in SIB1 is set to allowed. If false, IE cellBarredRedCap1Rx-r17 in SIB1 is set to barred. If both this attribute and redCap2RxEnabled are false, IE intraFreqReselectionRedCap-r17 is not transmitted in SIB1 and this disables Reduced Capability UE in cell. If both this attribute and redCap2RxEnabled are true, cell supports both types of UE. Only applicable to Low-Band and Mid-Band cells.; Default value: false.";
      type boolean;
      default "false";
    }
    leaf redCap2RxEnabled {
      description "Whether Reduced Capability 2Rx UE for cell is enabled. If true, IE cellBarredRedCap2Rx-r17 in SIB1 is set to notBarred and IE intraFreqReselectionRedCap-r17 in SIB1 is set to allowed. If false, IE cellBarredRedCap2Rx-r17 in SIB1 is set to barred. If both this attribute and redCap1RxEnabled are false, IE intraFreqReselectionRedCap-r17 is not transmitted in SIB1 and this disables Reduced Capability UE in cell. If both this attribute and redCap1RxEnabled are true, cell supports both types of UE. Only applicable to Low-Band and Mid-Band cells.; Default value: false.";
      type boolean;
      default "false";
    }
    leaf redCapUeLimit {
      description "Number of RedCap UEs that are allowed to enter cell. Only applicable to Low-Band and Mid-Band cells..";
      type enumeration {
        enum NONE;
        enum BASIC;
        enum ADVANCED;
        enum MAXIMUM;
      }
    }
    leaf resourceAllocTypeDlRef {
      description "Reference to an instance of ResourceAllocTypeDl MO. Automatically set to ResourceAllocTypeDl=Default instance, unless manually set to refer to another MO instance..";
      type string;
    }
    leaf rimAggressorRSSetRef {
      description "Reference to an instance of RimRSSet MO. Used for aggressor set. If empty, no aggressor RimRSSet instance is used in this cell, or RimRSSet instance is set on GNBDUFunction level. Only applicable if GNBDUFunction::setIdAllocation is CELL..";
      type string;
    }
    leaf rimBgNoiseThresh {
      description "Threshold defining background noise power to decide RIM slope detection. Assumed background noise power (dBm/PRB), which contributes to RIM detection decision. Background noise is thermal noise of receiver without any external interference impact.; range -125..-100; Default value: -110.";
      type int32 {
        range "-125..-100";
      }
      default "-110";
      units "dBm";
    }
    leaf rimCLPCHighIpnRSThresh {
      description "Threshold for triggering NR Uplink Closed Loop Power Control.; range -120..-90; Default value: -105.";
      type eytypes:int32_range_-120--90;
      default "-105";
      units "dBm";
    }
    leaf rimDetectedRS1State {
      description "Whether RIM-RS1 sequence is detected. Updated at intervals specified by rimRSDetectionTime..";
      type boolean;
      config false;
    }
    leaf rimDetectedRS2State {
      description "Whether RIM-RS2 sequence is detected. Updated at intervals specified by rimRSDetectionTime..";
      type boolean;
      config false;
    }
    leaf rimDetectedSlopeState {
      description "Whether slope state is detected. Only applicable if rimDetectionEnabled is true..";
      type boolean;
      config false;
    }
    leaf rimDetectionEnabled {
      description "Whether remote interference management detection is enabled. Only applicable to Mid-Band cells.; Default value: false.";
      type boolean;
      default "false";
    }
    leaf rimDLMitChangeSymThresh {
      description "Minimal portion of RIM-RS1 with \"Not enough\" indication to change symbol level downlink mitigation. Only valid RIM-RS1 is considered. Validity is based on set ID. See rimDLMitChangeTime. If 0, keep selected downlink mitigation. Only applicable if both following conditions are true: - sequenceDomainPara.enableEnoughNotEnoughIndication under RimRSGlobal instance is ENABLED. - tddUlDlPattern is TDD_ULDL_PATTERN_03.; range 0..100; Default value: 60.";
      type eytypes:int32_range_0-100;
      default "60";
      units "percent";
    }
    leaf rimDLMitChangeTime {
      description "Number of RIM RS detection periods before evaluating downlink mitigation selection. After this number of RIM RS detection periods has passed, a more aggressive downlink mitigation can be selected if ratio of RIM-RS1 with \"Not enough\" indication is above or equal to rimDLMitChangeSymThresh. Only applicable if sequenceDomainPara.enableEnoughNotEnoughIndication under RimRSGlobal instance is ENABLED.; range 2..10; Default value: 2.";
      type int32 {
        range "2..10";
      }
      default "2";
    }
    leaf rimHighIpnState {
      description "Whether high uplink interference state is detected. Only applicable if rimDetectionEnabled is true..";
      type boolean;
      config false;
    }
    leaf rimHighIpnThresh {
      description "Threshold for determining if IpN is too high.; range -125..-80; Default value: -105.";
      type int32 {
        range "-125..-80";
      }
      default "-105";
      units "dBm";
    }
    leaf rimLocationEnabled {
      description "Whether RIM location is enabled. If true, rimOffloadEnabled is overridden. Only applicable if license for NR Remote Interference Management is present and feature is active. Only applicable to Mid-Band cells.; Default value: false.";
      type boolean;
      default "false";
    }
    leaf rimMaxNoReportedSequences {
      description "Maximum number of RIM-RS sequences reported during rimRSReportInterval.; range 20..100; Default value: 50.";
      type int32 {
        range "20..100";
      }
      default "50";
    }
    leaf rimNotEnoughPortionThresh {
      description "Minimal portion of valid RIM-RS1 with \"Not enough\" indication. Above this threshold, downlink mitigation is triggered. Validity is based on set ID. Only applicable if sequenceDomainPara.enableEnoughNotEnoughIndication under RimRSGlobal instance is ENABLED.; range 0..100; Default value: 20.";
      type eytypes:int32_range_0-100;
      default "20";
      units "percent";
    }
    leaf rimOffloadEnabled {
      description "Whether remote interference triggered offload is enabled in cell.; Default value: false.";
      type boolean;
      default "false";
    }
    leaf rimOffloadHighIpNThresh {
      description "Threshold for average IpN. During RIM detect period this value is used by gNodeB to evaluate if start offloading and rimOffloadEnabled is true.; range -125..-80; Default value: -105.";
      type int32 {
        range "-125..-80";
      }
      default "-105";
      units "dBm";
    }
    leaf rimPdschSlotBlankDlOffset {
      description "Offset to control blanking and power control of second downlink slot in PDSCH slot blanking. Offset is applied to rimPdschSlotBlankDlSsThresh, for second downlink slot. Increasing value can lead to that blanking of second downlink slot is disabled.; range 0..10; Default value: 0.";
      type int32 {
        range "0..10";
      }
      default "0";
      units "dBm";
    }
    leaf rimPdschSlotBlankDlSsThresh {
      description "Threshold for triggering PDSCH special downlink slot and special slot blanking.; range -120..-90; Default value: -105.";
      type eytypes:int32_range_-120--90;
      default "-105";
      units "dBm";
    }
    leaf rimPdschSlotBlankMode {
      description "PDSCH slot blanking mode for remote interference mitigation. Only applicable to Mid-Band cells..";
      type enumeration {
        enum DISABLED;
        enum AUTO_MODE;
        enum SPECIAL_SLOT;
        enum SPECIAL_DL_SLOT;
        enum AUTO_RS1;
        enum SPECIAL_2DL_SLOT;
      }
    }
    leaf rimPdschSlotBlankSsThresh {
      description "Threshold for triggering PDSCH special slot blanking.; range -120..-90; Default value: -105.";
      type eytypes:int32_range_-120--90;
      default "-105";
      units "dBm";
    }
    leaf rimPdschSlotBlankStopThresh {
      description "Threshold for triggering PDSCH blanking fallback.; range -120..-90; Default value: -111.";
      type eytypes:int32_range_-120--90;
      default "-111";
      units "dBm";
    }
    leaf rimPdschSlotBlankTimer {
      description "Duration time of PDSCH slot blanking for remote interference mitigation. Used if rimPdschSlotBlankMode is AUTO_MODE. If 0, corresponding timer is disabled. Only applicable to Mid-Band cells.; range 0..86400; Default value: 1260.";
      type eytypes:int32_range_0-86400;
      default "1260";
      units "s";
    }
    leaf rimQRxLevMinConstant {
      description "Constant to calculate qRxLevMin for RIM offload. Only applicable if rimOffloadEnabled is true.; range 0..40; Default value: 0.";
      type uint32 {
        range "0..40";
      }
      default "0";
      units "dB";
    }
    leaf rimQRxLevMinIpNCompFactor {
      description "Compensation factor to calculate qRxLevMin for RIM offload. Only applicable if rimOffloadEnabled is true.; range 0..200; Default value: 100.";
      type uint32 {
        range "0..200";
      }
      default "100";
    }
    leaf rimRS1DetectedThresh {
      description "Threshold to define minimum number of valid victims based on set ID in one detection period.; range 0..214748647; Default value: 2.";
      type eytypes:uint32_range_0-214748647;
      default "2";
    }
    leaf rimRS1FarThresh {
      description "Threshold for blanking of special slot and of PDSCH two downlink slots before special slot. Special slot, and PDSCH two downlink slots before special slot, are blanked if ratio of valid RIM-RS1 with \"Far\" indication is greater than or equal to this value, and rimPdschSlotBlankDlSsThresh criteria is met. Validity of RIM-RS1 is based on set ID. Only applicable if timeDomainPara.enablenearfarIndicationRS1 under RimRSGlobal instance is ENABLED.; range 0..100; Default value: 30.";
      type eytypes:int32_range_0-100;
      default "30";
      units "percent";
    }
    leaf rimRS1NotEnoughDetectedThresh {
      description "Threshold to decide if RIM-RS1 with \"Not enough\" indication is detected. Threshold is defined in number of unique set IDs in RIM-RS1 with \"Not enough\".; range 0..214748647; Default value: 2.";
      type eytypes:uint32_range_0-214748647;
      default "2";
    }
    leaf rimRS1PortionStartDLMitThresh {
      description "Minimal portion of valid RIM-RS1 to start downlink mitigation. Portion is ratio of valid RIM-RS1 in relation to total number of valid RIM-RS1 and RIM-RS2. Validity is based on set ID.; range 0..100; Default value: 50.";
      type eytypes:int32_range_0-100;
      default "50";
      units "percent";
    }
    leaf rimRS1PortionStopDLMitThresh {
      description "Minimal portion of valid RIM-RS1 to stop downlink mitigation. Portion is ratio of valid RIM-RS1 in relation to total number of valid RIM-RS1 and RIM-RS2. Validity is based on set ID.; range 0..100; Default value: 20.";
      type eytypes:int32_range_0-100;
      default "20";
      units "percent";
    }
    leaf rimRS2DetectedThresh {
      description "Threshold to define minimum number of valid aggressors based on set ID in one detection period.; range 0..214748647; Default value: 2.";
      type eytypes:uint32_range_0-214748647;
      default "2";
    }
    leaf rimRS2TransEnabled {
      description "Whether RIM-RS2 transmission is enabled.; Default value: true.";
      type boolean;
      default "true";
    }
    leaf rimRS2TransStartThresh {
      description "Minimal portion of RIM-RS1 with \"Not enough\" indication to start RIM-RS2 transmission. Only applicable if sequenceDomainPara.enableEnoughNotEnoughIndication under RimRSGlobal instance is ENABLED.; range 0..100.";
      type eytypes:int32_range_0-100;
      units "percent";
    }
    leaf rimRS2TransStopThresh {
      description "Minimal portion of RIM-RS1 with \"Not enough\" indication to stop RIM-RS2 transmission. Only applicable if sequenceDomainPara.enableEnoughNotEnoughIndication under RimRSGlobal instance is ENABLED.; range 0..100.";
      type eytypes:int32_range_0-100;
      units "percent";
    }
    leaf rimRSDetectionThresholdOffset {
      description "Modifier for RIM-RS detection threshold. Increasing value can lead to lower false alarm rate and raise missed detection rate.; range 1..100; Default value: 10.";
      type eytypes:int32_range_1-100;
      default "10";
      units "percent";
    }
    leaf rimRSDetectionTime {
      description "Number of RIM RS transmission periods to detect RIM RS reception. Interval, measured in RIM RS transmission periods, at which RIM-RS1 and/or RIM-RS2 detection is determined.; range 1..30; Default value: 3.";
      type int32 {
        range "1..30";
      }
      default "3";
    }
    leaf rimRSReportInterval {
      description "Periodicity to generate and report RIM-RS Detection report.; range 1000..10000; Default value: 1000.";
      type int32 {
        range "1000..10000";
      }
      default "1000";
      units "ms";
    }
    leaf rimSlopeDetectPeriod {
      description "Slope detection period.; range 1..30; Default value: 10.";
      type int32 {
        range "1..30";
      }
      default "10";
      units "minute";
    }
    leaf rimSlopeFrontSymIndex {
      description "Symbol to be used as front symbol in slope detection. If SRS is activated, front symbol in special slot is activated SRS symbol..";
      type enumeration {
        enum SS_LAST_UL;
        enum SS_2LAST_UL;
        enum SS_3LAST_UL;
        enum SS_4LAST_UL;
        enum UL1_FRONT_DMRS;
        enum UL1_END_DMRS;
        enum UL2_FRONT_DMRS;
      }
    }
    leaf rimSlopePwrDiffThresh {
      description "Threshold for slope detection. Defined as interference power difference on front symbol and last symbol. Setting lower value increases slope detection report, and higher value decreases slope detection report.; range 1..8; Default value: 3.";
      type int32 {
        range "1..8";
      }
      default "3";
      units "dB";
    }
    leaf rimTransmittedRS1State {
      description "Whether RIM-RS1 sequence is transmitted..";
      type boolean;
      config false;
    }
    leaf rimTransmittedRS2State {
      description "Whether RIM-RS2 sequence is transmitted..";
      type boolean;
      config false;
    }
    leaf-list rimValidFrequencyOffsets {
      description "Frequency offsets for RIM RS corresponding to valid frequency positions in carrier. Frequency positions are considered valid if they fall inside carrier bandwidth and do not violate radio limitations. Only valid frequency positions are used for transmission or detection of RIM RS..";
      type int32 {
        range "0..549";
      }
      ordered-by user;
      min-elements 0;
      max-elements 4;
    }
    leaf rimVictimRSSetRef {
      description "Reference to an instance of RimRSSet MO. Used for victim set. If empty, no victim RimRSSet instance is used in this cell, or RimRSSet instance is set on GNBDUFunction level. Only applicable if GNBDUFunction::setIdAllocation is CELL..";
      type string;
    }
    leaf riOffloadHighIpnRSThresh {
      description "Threshold for triggering remote interference triggered offload.; range -120..-90; Default value: -110.";
      type eytypes:int32_range_-120--90;
      default "-110";
      units "dBm";
    }
    leaf secondaryCellOnly {
      description "Whether UEs are prevented from camping on cell. Changing this attribute can affect ssbFrequencyAutoSelected.; Default value: true.";
      type boolean;
      default "true";
    }
    leaf serviceState {
      description "Current service state..";
      type enumeration {
        enum OUT_OF_SERVICE;
        enum IN_SERVICE;
      }
      config false;
    }
    leaf sfnOffset {
      description "System Frame Number offset relative to GPS time. 1 radio frame is equal to 10 ms.; range -512..511; Default value: 0.";
      type int16 {
        range "-512..511";
      }
      default "0";
      units "radio frame";
    }
    leaf sib9BroadcastOngoing {
      description "Whether SIB9 broadcast is scheduled..";
      type boolean;
      config false;
    }
    list sibType2 {
      key "id";
      leaf id {
        type uint32;
        description "Synthetic key for struct attribute.";
      }
      description "Information needed for acquisition of System Information Block 2..";
      uses SibType-struct;
    }
    list sibType4 {
      key "id";
      leaf id {
        type uint32;
        description "Synthetic key for struct attribute.";
      }
      description "Information needed for acquisition of System Information Block 4..";
      uses SibType-struct;
    }
    list sibType5 {
      key "id";
      leaf id {
        type uint32;
        description "Synthetic key for struct attribute.";
      }
      description "Information needed for acquisition of System Information Block 5..";
      uses SibType-struct;
    }
    list sibType6 {
      key "id";
      leaf id {
        type uint32;
        description "Synthetic key for struct attribute.";
      }
      description "Information needed for acquisition of System Information Block 6 (SIB6). Contains PWS warning message for ETWS primary notification..";
      uses SibTypePws-struct;
    }
    list sibType7 {
      key "id";
      leaf id {
        type uint32;
        description "Synthetic key for struct attribute.";
      }
      description "Information needed for acquisition of System Information Block 7 (SIB7). Contains PWS warning message for ETWS secondary notification..";
      uses SibType-struct;
    }
    list sibType8 {
      key "id";
      leaf id {
        type uint32;
        description "Synthetic key for struct attribute.";
      }
      description "Information needed for acquisition of System Information Block 8 (SIB8). Contains PWS warning message for Wireless Emergency Alerts (WEA), also known as CMAS..";
      uses SibType-struct;
    }
    list sibType9 {
      key "id";
      leaf id {
        type uint32;
        description "Synthetic key for struct attribute.";
      }
      description "Information needed for acquisition of System Information Block 9 (SIB9)..";
      uses SibTypeSib9-struct;
    }
    leaf siWindowLength {
      description "Length of SI scheduling window in slots.; Default value: 20.";
      type int32 {
        range "5 | 10 | 20 | 40 | 80 | 160 | 320 | 640 | 1280";
      }
      default "20";
      units "slot";
    }
    list slotSpecificDlLaConfigList {
      key "id";
      leaf id {
        type uint32;
        description "Synthetic key for struct sequence entry.";
      }
      min-elements 0;
      max-elements 10;
      uses SlotSpecificLaConfig-struct;
    }
    list sNSSAIList {
      key "id";
      leaf id {
        type uint32;
        description "Synthetic key for struct sequence entry.";
      }
      min-elements 0;
      max-elements 1024;
      uses SliceSelectionAssistInfo-struct;
    }
    leaf speedAdvMuThresh {
      description "Effective UE speed threshold to decide if reciprocity-based MU-MIMO is used. Reciprocity-based MU-MIMO is allowed if effective UE speed is less than or equal to this threshold. Effective UE speed is estimated speed based on measured doppler in gNodeB. Applicable to periodic SRS and aperiodic SRS. Only applicable if advancedDlSuMimoEnabled is true and maxNoOfAdvancedDlMuMimoLayers is greater than 0. Values lower than 500 are only applicable to RAN Compute group 5 and higher.; range 0..500; Default value: 500.";
      type int32 {
        range "0..500";
      }
      default "500";
      units "km/h";
    }
    leaf speedAdvSuThresh {
      description "Effective UE speed threshold to decide if reciprocity-based SU-MIMO is used. Reciprocity-based SU-MIMO is allowed if effective UE speed is less than or equal to this threshold. Effective UE speed is estimated speed based on measured doppler in gNodeB. Applicable to periodic SRS and aperiodic SRS. Taken into consideration whether an SRS resource can be configured or released to a UE in case of periodic SRS and whether an SRS resource can be triggered to a UE in case of aperiodic SRS. Only applicable if advancedDlSuMimoEnabled is true. Values lower than 500 are only applicable to RAN Compute group 5 and higher.; range 0..500; Default value: 500.";
      type int32 {
        range "0..500";
      }
      default "500";
      units "km/h";
    }
    leaf srbPriorityRef {
      description "Reference to an instance of SrbPriority MO. Automatically set to SrbPriority=Default instance, unless manually set to refer to another MO instance. Applicable to Low-Band and Mid-Band cells if license for Adaptive SRB Priority is present and feature is active..";
      type string;
    }
    leaf srDetectHighEnabled {
      description "Whether high Scheduling Request (SR) detection threshold is enabled in cell. If true, two SRs are needed in a row before gNodeB further processes the SR for UE when SR is detected lower than high SR detection threshold. Only applicable to Low-Band and Mid-Band cells.; Default value: false.";
      type boolean;
      default "false";
    }
    leaf srPeriodicityPoolSetRef {
      description "Reference to an instance of SrPeriodicityPoolSet MO. If empty, for Low-Band and Mid-Band cells, cell is configured with short, common, and long pools with predefined values. If empty, for High-Band cells, cell is configured with default pool with predefined values. Applicable to Low-Band and Mid-Band cells if license NR Service-Adaptive SR Periodicity is present and feature is active. Applicable to High-Band cells if license Service-Adaptive SR Periodicity High-Band for Dedicated RAN or license Service-Adaptive SR Periodicity High-Band for Public RAN is present and feature is active..";
      type string;
    }
    leaf srPeriodicityRef {
      description "Reference to an instance of SrPeriodicity MO. Automatically set to SrPeriodicity=Default instance, unless manually set to refer to another MO instance. Applicable to Low-Band and Mid-Band cells if license NR Service-Adaptive SR Periodicity is present and feature is active. Applicable to High-Band cells if license Service-Adaptive SR Periodicity High-Band for Dedicated RAN or license Service-Adaptive SR Periodicity High-Band for Public RAN is present and feature is active..";
      type string;
    }
    leaf srsCapacityBoostEnabled {
      description "Whether NR SRS Capacity Boost Mid-Band feature is enabled. If true, it can be applicable for any type of SRS mode. Only applicable to Mid-Band cells.; Default value: false.";
      type boolean;
      default "false";
    }
    leaf srsHoppingBandwidth {
      description "SRS frequency hopping bandwidth..";
      type enumeration {
        enum FULL;
        enum HALF;
      }
    }
    leaf srsPeriodicity {
      description "SRS periodicity in slots in a Mid-Band cell.; Default value: 40.";
      type int32 {
        range "5 | 10 | 20 | 40 | 80";
      }
      default "40";
      units "slot";
    }
    leaf srsSymbolCombSelectionMode {
      description "Controls how uplink symbols and comb offsets are selected for SRS transmissions. Only applicable to Mid-Band cells. Value COMMON is only applicable to RAN Compute group 5 and higher..";
      type enumeration {
        enum DEFAULT;
        enum COMMON;
      }
    }
    leaf ssbDuration {
      description "Duration of SSB transmission. If empty, system selects SSB duration, which is presented in ssbDurationAutoSelected. For Low-Band cells, value must be empty, 1, or 2. For Mid-Band cells, value must be empty or 1. For High-Band cells, value must be empty, 3, 4, or 5.; range 1..5.";
      type eytypes:int32_range_1-5;
      units "ms";
    }
    leaf ssbDurationAutoSelected {
      description "Automatically selected SSB Duration. Calculated at cell unlock if ssbDuration is empty. Value is empty if ssbDuration is configured..";
      type int32;
      config false;
      units "ms";
    }
    leaf ssbFrequency {
      description "Frequency (NR-ARFCN) of the SSB transmission. The frequency identifies the position of resource element RE=#0 (subcarrier #0) of resource block RB#10 of the SS block. The frequency must be positioned on the NR global frequency raster, as defined in 3GPP TS 38.101, and within bSChannelBwDL. If 0, the system selects an SSB frequency, which is presented in ssbFrequencyAutoSelected.; range 0..3279165; Default value: 0.";
      type eytypes:int32_range_0-3279165;
      default "0";
    }
    leaf ssbFrequencyAutoSelected {
      description "Automatically selected SSB frequency (NR-ARFCN). Calculated at cell unlock if ssbFrequency is set to 0. Empty if ssbFrequency greater than 0. Changing secondaryCellOnly can affect this attribute..";
      type int32;
      config false;
    }
    leaf ssbGscn {
      description "GSCN of SSB. SSB location on synchronization raster (required for primary cell in stand-alone gNodeB). If empty, SSB is not placed on synchronization raster..";
      type int32;
      config false;
    }
    leaf ssbIndex {
      description "Configured SSB index. If empty, gNodeB selects SSB index value which is presented in ssbIndexAutoSelected. Only applicable to Mid-Band cells. Not applicable to ESS cells.; range 0..2.";
      type eytypes:int32_range_0-2;
    }
    leaf ssbIndexAutoSelected {
      description "Automatically selected SSB index. Empty if ssbIndex is non-empty. Only applicable to Mid-Band cells. Not applicable to ESS cells..";
      type int32;
      config false;
    }
    leaf ssbOffset {
      description "Offset of SSB transmission window. Corresponds to the SSB time domain position. If empty, the system selects an SSB duration, which is presented in ssbOffsetAutoSelected. For ESS Low-Band, values empty, 0 and 1 are allowed. Otherwise, values empty and 0 are allowed.; range 0..159.";
      type eytypes:int32_range_0-159;
      units "ms";
    }
    leaf ssbOffsetAutoSelected {
      description "Automatically selected SSB Offset. Calculated at cell unlock if ssbOffset is empty. Value is empty if ssbOffset is configured..";
      type int32;
      config false;
      units "ms";
    }
    leaf ssbPeriodicity {
      description "Periodicity of SSB transmission.; Default value: 20.";
      type int32 {
        range "5 | 10 | 20 | 40 | 80 | 160";
      }
      default "20";
      units "ms";
    }
    leaf ssbPowerBoost {
      description "Boost value to be applied to SSB power. Only applicable if license for SSB Power Boost is present and feature is active. For High-Band cells, values must be as follows: - For 100 MHz cells, less than or equal to 5. - For 50 MHz cells, less than or equal to 2. For Mid-Band cells, values must be as follows: - For 30, 40, 50, 60, 70, 80, 90, or 100 MHz, less than or equal to 6. - For 20 MHz, less than or equal to 4. - For 15 MHz, less than or equal to 3. - For 10 MHz, less than or equal to 1. - For other bandwidth, equal to 0. For Low-Band cells, values must be as follows: - For 25, 30, 35, 40, or 50 MHz, less than or equal to 6. - For 20 MHz, less than or equal to 4. - For 15 MHz, less than or equal to 3. - For 10 MHz, less than or equal to 1. - For other bandwidth, equal to 0. Actual boost is seen in actualSsbPowerBoost.; range 0..12; Default value: 0.";
      type eytypes:int32_range_0-12;
      default "0";
      units "dB";
    }
    leaf ssbPowerBoostMMimoSleep {
      description "Boost value applied to SSB power during massive MIMO sleep in addition to ssbPowerBoost. Used to compensate for SSB power lost during massive MIMO sleep. If empty, value of 0 is used. Combined value of ssbPowerBoost and this attribute must be as follows: - For 30, 40, 50, 60, 70, 80, 90, or 100 MHz, less than or equal to 6. - For 20 MHz, less than or equal to 4. - For 15 MHz, less than or equal to 3. - For 10 MHz, less than or equal to 1. - For other bandwidths, equal to 0. Actual boost is only seen in actualSsbPowerBoost when NR Massive MIMO Sleep Mode or NR Massive MIMO Eco Mode feature is in sleep state. Only applicable if license for one of following features is present and feature is active: - NR Massive MIMO Sleep Mode - NR Massive MIMO Eco Mode Only applicable to Mid-Band cells.; range 0..12.";
      type eytypes:int32_range_0-12;
      units "dB";
    }
    leaf ssbSubCarrierSpacing {
      description "Sub-carrier spacing of the SSB.; Default value: 120.";
      type int32 {
        range "15 | 30 | 120 | 240";
      }
      default "120";
      units "kHz";
    }
    leaf ssbTimeShiftEnabled {
      description "Whether NR SSB Time Shift feature is enabled. Only applicable if license for NR SSB Time Shift is present and feature is active. Only applicable to Mid-Band cells. Not applicable to ESS cells.; Default value: false.";
      type boolean;
      default "false";
    }
    leaf sssgSwitchRef {
      description "Reference to an instance of SssgSwitch MO. If non-empty at cell unlock, Flexible PDCCH Monitoring feature is enabled. If non-empty at cell unlock, it is required that license for Flexible PDCCH Monitoring feature is present and feature is active. Otherwise, Configuration Requires Feature Activation alarm or MO Configuration Requires Key Install and Feature Activation alarm is raised. If empty, Flexible PDCCH Monitoring is disabled in cell. Only applicable if license for Flexible PDCCH Monitoring feature is present and feature is active. Only applicable to non-ESS Low-Band cells with bandwidth greater than or equal to 10 MHz. Must be empty in other cells..";
      type string;
    }
    leaf subCarrierSpacing {
      description "Sub-carrier spacing for common elements at cell level.; Default value: 120.";
      type int32 {
        range "15 | 30 | 60 | 120";
      }
      default "120";
      units "kHz";
    }
    leaf tddBorderVersion {
      description "TDD border version. TDD border version can be used in certain geographic areas in different countries to mitigate downlink to uplink interference. Unaligned TDD patterns lead to cross-link interference when tddUlDlPattern and tddSpecialSlotPattern of adjacent cells have certain values. Both patterns must be adapted to avoid downlink and uplink in the same time slot. This means that this attribute must be set in both cells. Only applicable to Mid-Band cells..";
      type enumeration {
        enum DISABLED;
        enum VERSION_1;
      }
    }
    leaf tddSpecialSlotPattern {
      description "TDD special slot pattern. Defines the downlink, guard, and uplink symbols of special slot or slots for NR TDD in Mid-Band or High-Band cell. Configured special slot pattern must be applicable to Mid-Band in Mid-Band cells. Configured special slot pattern must be applicable to High-Band in High-Band cells. For High-Band cell, default value TDD_SPECIAL_SLOT_PATTERN_00 is overridden by the system to High-Band applicable special slot pattern TDD_SPECIAL_SLOT_PATTERN_02..";
      type enumeration {
        enum TDD_SPECIAL_SLOT_PATTERN_00;
        enum TDD_SPECIAL_SLOT_PATTERN_01;
        enum TDD_SPECIAL_SLOT_PATTERN_02;
        enum TDD_SPECIAL_SLOT_PATTERN_03;
        enum TDD_SPECIAL_SLOT_PATTERN_04;
        enum TDD_SPECIAL_SLOT_PATTERN_05;
        enum TDD_SPECIAL_SLOT_PATTERN_06;
      }
    }
    leaf tddUlDlPattern {
      description "TDD uplink-downlink pattern configuration. Defines downlink, uplink, and special slot pattern for NR TDD in Mid-Band or High-Band cell. Configured uplink-downlink pattern must be applicable to Mid-Band in Mid-Band cells. Configured uplink-downlink pattern must be applicable to High-Band in High-Band cells. Must be TDD_ULDL_PATTERN_00 in Low-Band cells. For High-Band cell, default value TDD_ULDL_PATTERN_00 is overridden by the system to High-Band applicable TDD pattern TDD_ULDL_PATTERN_02..";
      type enumeration {
        enum TDD_ULDL_PATTERN_00;
        enum TDD_ULDL_PATTERN_01;
        enum TDD_ULDL_PATTERN_02;
        enum TDD_ULDL_PATTERN_03;
        enum TDD_ULDL_PATTERN_04;
        enum TDD_ULDL_PATTERN_05;
        enum TDD_ULDL_PATTERN_06;
        enum TDD_ULDL_PATTERN_08;
      }
    }
    leaf totalNoOfRaPreambles {
      description "Total number of CBRA and CFRA preambles. If rachRestrictedSetConfig is not UNRESTRICTED_SET, value 17 is used. Only applicable to Low-Band and Mid-Band cells.; range 16..64; Default value: 17.";
      type int32 {
        range "16..64";
      }
      default "17";
    }
    leaf trafficDefinitionRef {
      description "Reference to an instance of TrafficDefinition MO. Automatically set to TrafficDefinition=Default instance, unless manually set to refer to another MO instance..";
      type string;
    }
    leaf trafficGroupRef {
      description "Reference to an instance of TrafficGroup MO. Automatically set to TrafficGroup=Default instance, unless manually set to refer to another MO instance.; MOM flags: isNillable=true; Status info: Since 25.Q2. Replaced by trafficDefinitionRef. Planned to be removed..";
      type string;
      status deprecated;
    }
    leaf trsConfigMode {
      description "TRS bandwidth configuration mode..";
      type enumeration {
        enum AUTO;
        enum FULL_BW;
        enum PRB_52;
        enum FULL_BW_MUTE;
      }
    }
    leaf trsModeSelected {
      description "Selected TRS mode. If empty, TRS mode is not selected..";
      type enumeration {
        enum AUTO;
        enum FULL_BW;
        enum PRB_52;
        enum FULL_BW_MUTE;
      }
      config false;
    }
    leaf trsPeriodicity {
      description "Periodicity of Channel State Information-Reference Signal (CSI-RS) used for tracking purpose.; Default value: 20.";
      type int32 {
        range "10 | 20 | 40 | 80";
      }
      default "20";
      units "ms";
    }
    leaf trsPowerBoosting {
      description "TRS power boosting. Selects different power boosting levels for CSI-RS transmission for tracking purposes. For Low-Band and Mid-Band cells, values 0, 3, 4, and 6 are allowed.; range 0..6; Default value: 0.";
      type int32 {
        range "0..6";
      }
      default "0";
    }
    leaf trsResourceShifting {
      description "Whether TRS resource allocation shifting is activated..";
      type enumeration {
        enum DEACTIVATED;
        enum ACTIVATED;
      }
    }
    leaf typeISinglePanelRiRestriction {
      description "Bit mask that indicates UE-specific rank restriction for codebook of Type1 single panel. Only applicable to Low-Band or Mid-Band cells. Following values can be applied: - Bitmap b00001111, no rank restriction, value 15. - Bitmap b00000001, rank restricted to 1, UE can only report rank 1, value 1. - Bitmap b00000010, rank restricted to 2, value is 2. - Bitmap b00000100, rank restricted to 3, value is 4. - Bitmap b00001000, rank restricted to 4, value is 8. - Bitmap b00000011, rank restricted to 1, or 2, value is 3. - Bitmap b00000101, rank restricted to 1, or 3, value is 5. - Bitmap b00001001, rank restricted to 1, or 4, value is 9. - Bitmap b00000110, rank restricted to 2, or 3, value is 6. - Bitmap b00001010, rank restricted to 2, or 4, value is 10. - Bitmap b00001100, rank restricted to 3, or 4, value is 12. - Bitmap b00000111, rank restricted to 1, 2, or 3, value is 7. - Bitmap b00001011, rank restricted to 1, 2, or 4, value is 11. - Bitmap b00001101, rank restricted to 1, 3, or 4, value is 13. - Bitmap b00001110, rank restricted to 2, 3, or 4, value is 14. Note that this is a configuration for all UEs in cell. However, if UE capability conflicts with the value, bitmap b00000001 will be set to this UE.; range 1..15; Default value: 15.";
      type eytypes:uint8_range_1-15;
      default "15";
    }
    leaf ueBbProfileRef {
      description "Reference to an instance of UeBbProfile MO. Automatically set to UeBbProfile=Default instance, unless manually set to refer to another MO instance..";
      type string;
    }
    leaf ueSpecificDrxMode {
      description "Mode of UE specific DRX. If ENABLED, following apply: - If UE-specific DRX cycle is provided in paging message from AMF, that is shorter than value of Paging::defaultPagingCycle, then value from AMF overrides value in RBS. - If UE-specific DRX cycle is provided in Core Network Assistance Information from AMF, it is used for RAN initiated paging, and value from AMF overrides value in RBS..";
      type enumeration {
        enum ENABLED;
        enum DISABLED;
      }
    }
    leaf ul256QamEnabled {
      description "Whether 256-QAM support in uplink is enabled. Only applicable to Low-Band and Mid-Band cells. For High-Band cells, value must be false. Only applicable if license for 256-QAM Uplink Low/Mid-Band is present and feature is active.; Default value: false.";
      type boolean;
      default "false";
    }
    leaf ulAvailableCrbs {
      description "Total amount of CRBs available for uplink channels. Total uplink channel bandwidth corresponds to sum of uplink available CRBs and uplink blanked CRBs. Total uplink channel bandwidth is configured in NRSectorCarrier::bSChannelBwUL. Formula for conversion to number of CRBs is defined in 3GPP TS 38.211. If empty, there is no bandwidth restriction and no blanking in uplink. If 0, there is no available CRB, NR Channel Bandwidth is fixed to NRSectorCarrier::bSChannelBwUL.; range 0..272.";
      type eytypes:uint32_range_0-272;
    }
    leaf ulCaTimeAlignmentMode {
      description "Timing advance offset configuration in Low-Band cells. Only applicable if license for NR Uplink Carrier Aggregation is present and feature is active. Not applicable if NRSectorCarrier::txDirection is DL. Only applicable to non-ESS Low-Band cells..";
      type enumeration {
        enum N_TA_O_STANDARD;
        enum N_TA_O_39936;
      }
    }
    leaf ulMaxMuMimoLayers {
      description "Maximum number of co-scheduled uplink MU-MIMO layers at cell level. Uplink MU-MIMO is disabled when value is 0. Only used if Control Channel Beamforming feature is configured. Only used if radio equipment supports AAS configuration. For High-Band cells, value must be 0. For Mid-Band cells, values 0, 2 and 4 are allowed. For Low-Band cells, values 0, 2 and 4 are allowed.; Default value: 0.";
      type int32 {
        range "0 | 2 | 4 | 6 | 8";
      }
      default "0";
    }
    leaf ulRobustLaEnabled {
      description "Whether uplink robust link adaptation is enabled. Only applicable if license for Critical IoT is present and the High-Band feature is active. Must be false for Low-Band and Mid-Band cells.; Default value: false; Takes effect: Next cell unlock; Status info: Since 25.Q2. Planned to be removed..";
      type boolean;
      status deprecated;
      default "false";
      reference "Takes effect: Next cell unlock.";
    }
    leaf ulScSpillover {
      description "Supported uplink subcarrier spill-over value of radio to which ESS cell pair is connected. Spill-over means that subcarrier or subcarriers of guard band NB-IoT PRB can exceed PRB subcarrier range of ESS NR cell. Spill-over value represents capability of radio which defines exceeding subcarrier number compared with outmost subcarrier of NR.; range 0..11; Default value: 0.";
      type int32 {
        range "0..11";
      }
      default "0";
      units "subcarrier";
    }
    leaf ulStartCrb {
      description "Start position of CRBs available for uplink channels. Blanked CRBs appear before start position and after the range of available CRBs.; range 0..272; Default value: 0.";
      type eytypes:uint32_range_0-272;
      default "0";
    }
    leaf ulTxSwitchingEnabled {
      description "Whether NR Switched Uplink for Throughput Boost feature is enabled in cell. Only applicable to Low-Band and Mid-Band cells. For High-Band cells, value must be false. Only applicable if license for NR Switched Uplink for Throughput Boost is present and feature is active.; Default value: false.";
      type boolean;
      default "false";
    }
    leaf userLabel {
      description "Label for free use..";
      type string;
    }
    leaf-list pmMacSchedSlotDlSCellActivatedDistr {
      description "Aggregated number of scheduled downlink slots when SCells are active. Measured when this cell is used as PSCell. Unit: N/A Ranges: Bin[0]: Scheduled DL slots with 0 SCells activated. Bin[1]: Scheduled DL slots with 1 SCell activated. Bin[2]: Scheduled DL slots with 2 SCells activated. Bin[3]: Scheduled DL slots with 3 SCells activated. Bin[4]: Scheduled DL slots with 4 SCells activated. Bin[5]: Scheduled DL slots with 5 SCells activated. Bin[6]: Scheduled DL slots with 6 SCells activated. Bin[7]: Scheduled DL slots with 7 SCells activated..";
      type ietfyang:mac-address;
      max-elements 8;
    }
    leaf pmMacRBSymAvailPdcch {
      description "Aggregated number of resource block symbols configured for PDCCH during complete ROP. Unit: N/A.";
      type ietfyang:mac-address;
      config false;
    }
    leaf-list pmMacVolDlSCellExtBwp {
      description "Aggregated volume of successfully transmitted downlink MAC PDUs for DRB or SRB using this cell as external inter-gNodeB SCell, inter-capacity module SCell, or inter-DU SCell. BWP value is always zero for uplink. PDF ranges: Bin[0]: Aggregated volume of successfully transmitted downlink MAC PDUs for DRB or SRB using this cell as external inter-gNodeB SCell, inter-capacity module SCell, or inter-DU SCell in first BWP referenced in NRCellDU MO by BWPSet.allBWPRegularRef attribute. Bin[1]: Aggregated volume of successfully transmitted downlink MAC PDUs for DRB or SRB using this cell as external inter-gNodeB SCell, inter-capacity module SCell, or inter-DU SCell in second BWP referenced in NRCellDU MO by BWPSet.allBWPRegularRef attribute. Bin[2]: Aggregated volume of successfully transmitted downlink MAC PDUs for DRB or SRB using this cell as external inter-gNodeB SCell, inter-capacity module SCell, or inter-DU SCell in third BWP referenced in NRCellDU MO by BWPSet.allBWPRegularRef attribute. ... Bin[15]: Aggregated volume of successfully transmitted downlink MAC PDUs for DRB or SRB using this cell as external inter-gNodeB SCell, inter-capacity module SCell, or inter-DU SCell in sixteenth BWP referenced in NRCellDU MO by BWPSet.allBWPRegularRef attribute. Unit: Bytes.";
      type ietfyang:mac-address;
      max-elements 16;
    }
    leaf pmMacVolUlUnresUe {
      description "Data volume in MAC SDUs successfully received in uplink and not restricted by air interface. Unit: byte.";
      type ietfyang:mac-address;
      config false;
    }
    leaf pmRadioRaCfAttMsg2 {
      description "Number of CFRA Msg2 scheduling attempts. Unit: messages.";
      type uint64;
      config false;
    }
    leaf pmPuschSchedActivityDynSlotAggr {
      description "Number of slots where at least one MAC SDU is received on PUSCH with dynamic slot aggregation. Unit: N/A.";
      type uint64;
      config false;
    }
    leaf-list pmMacHarqDlNack64QamInitSlotDistr {
      description "For each downlink slot, bin that corresponds to number of unsuccessful initial HARQ PDSCH transmissions using 64-QAM modulation in slot is incremented. HARQ transmissions used for BWP DCI switch Scheduling Request (SR) are not pegged. Unit: N/A Ranges: Bin[0]: Total number of unsuccessful initial downlink HARQ transmissions using 64-QAM on slot 0. Bin[1]: Total number of unsuccessful initial downlink HARQ transmissions using 64-QAM on slot 1. Bin[2]: Total number of unsuccessful initial downlink HARQ transmissions using 64-QAM on slot 2. Bin[3]: Total number of unsuccessful initial downlink HARQ transmissions using 64-QAM on slot 3. Bin[4]: Total number of unsuccessful initial downlink HARQ transmissions using 64-QAM on slot 4. Bin[5]: Total number of unsuccessful initial downlink HARQ transmissions using 64-QAM on slot 5. Bin[6]: Total number of unsuccessful initial downlink HARQ transmissions using 64-QAM on slot 6. Bin[7]: Total number of unsuccessful initial downlink HARQ transmissions using 64-QAM on slot 7. Bin[8]: Total number of unsuccessful initial downlink HARQ transmissions using 64-QAM on slot 8. Bin[9]: Total number of unsuccessful initial downlink HARQ transmissions using 64-QAM on slot 9. Bin[10]: Total number of unsuccessful initial downlink HARQ transmissions using 64-QAM on slot 10. Bin[11]: Total number of unsuccessful initial downlink HARQ transmissions using 64-QAM on slot 11. Bin[12]: Total number of unsuccessful initial downlink HARQ transmissions using 64-QAM on slot 12. Bin[13]: Total number of unsuccessful initial downlink HARQ transmissions using 64-QAM on slot 13. Bin[14]: Total number of unsuccessful initial downlink HARQ transmissions using 64-QAM on slot 14. Bin[15]: Total number of unsuccessful initial downlink HARQ transmissions using 64-QAM on slot 15. Bin[16]: Total number of unsuccessful initial downlink HARQ transmissions using 64-QAM on slot 16. Bin[17]: Total number of unsuccessful initial downlink HARQ transmissions using 64-QAM on slot 17. Bin[18]: Total number of unsuccessful initial downlink HARQ transmissions using 64-QAM on slot 18. Bin[19]: Total number of unsuccessful initial downlink HARQ transmissions using 64-QAM on slot 19..";
      type ietfyang:mac-address;
      max-elements 20;
    }
    leaf pmMacHarqDlNack256QamInit {
      description "Total number of unsuccessful initial downlink HARQ transmissions using 256-QAM modulation. Initial transmission is first transmission on HARQ process. Unit: N/A.";
      type ietfyang:mac-address;
      config false;
    }
    leaf-list pmMacVolDlBwp {
      description "Aggregated volume of successfully transmitted downlink MAC PDUs for DRB or SRB using cell as PCell, PSCell. For uplink BWP value is always zero. PDF ranges: Bin[0]: Aggregated volume of successfully transmitted downlink MAC PDUs for DRB or SRB in the first BWP referenced in NRCellDU MO by BWPSet.allBWPRegularRef attribute Bin[1]: Aggregated volume of successfully transmitted downlink MAC PDUs for DRB or SRB in the second BWP referenced in NRCellDU MO by BWPSet.allBWPRegularRef attribute Bin[2]: Aggregated volume of successfully transmitted downlink MAC PDUs for DRB or SRB in the third BWP referenced in NRCellDU MO by BWPSet.allBWPRegularRef attribute ... Bin[15]: Aggregated volume of successfully transmitted downlink MAC PDUs for DRB or SRB in the sixteenth BWP referenced in NRCellDU MO by BWPSet.allBWPRegularRef attribute Unit: 100 bytes.";
      type ietfyang:mac-address;
      max-elements 16;
    }
    leaf-list pmMacPdcchCongestionUlExclPreschedDistr {
      description "Distribution of uplink PDCCH congestion rate, excluding uplink prescheduling, averaged over one second. Ranges Bin[0]: [0..5] % Bin[1]: [6..10] % Bin[2]: [11..15] % Bin[3]: [16..20] % Bin[4]: [21..25] % Bin[5]: [26..30] % Bin[6]: [31..35] % Bin[7]: [36..40] % Bin[8]: [41..45] % Bin[9]: [46..50] % Bin[10]: [51..55] % Bin[11]: [56..60] % Bin[12]: [61..65] % Bin[13]: [66..70] % Bin[14]: [71..75] % Bin[15]: [76..80] % Bin[16]: [81..85] % Bin[17]: [86..90] % Bin[18]: [91..95] % Bin[19]: [96..] % Unit: N/A.";
      type ietfyang:mac-address;
      max-elements 20;
    }
    leaf pmMacRBSymUsedPdcchTypeBAggrLvl4 {
      description "Number of resource block symbols used by PDCCH with aggregation level 4 for scheduling of PDSCH or PUSCH using mapping type B. This includes DMRS and PTRS embedded in resources scheduling. Unit: N/A.";
      type ietfyang:mac-address;
      config false;
    }
    leaf pmRadioRaCbAttMsg2 {
      description "Number of CBRA Msg2 scheduling attempts. Unit: messages.";
      type uint64;
      config false;
    }
    leaf-list pmRimDetectedAggressorDistanceMaxDistr {
      description "Number of aggressor-victim pairs detecting remote interference within specified distance. Ranges: Bin[0]: [0..100] km Bin[1]: [101..250] km Bin[2]: [251..450] km Bin[3]: [451..] km.";
      type int64;
      max-elements 4;
    }
    leaf-list pmMacBsrLcg4Distr {
      description "Distribution of highest possible buffer size reported in BSRs in MAC Control Elements in UL LCG ID 4. Unit: N/A Ranges: Bin[0]: 0 bytes Bin[1]: [1..19] bytes Bin[2]: [20..36] bytes Bin[3]: [37..66] bytes Bin[4]: [67..124] bytes Bin[5]: [125..233] bytes Bin[6]: [234..436] bytes Bin[7]: [437..817] bytes Bin[8]: [818..1532] bytes Bin[9]: [1533..2873] bytes Bin[10]: [2874..5387] bytes Bin[11]: [5388..10104] bytes Bin[12]: [10105..18951] bytes Bin[13]: [18952..35543] bytes Bin[14]: [35544..66663] bytes Bin[15]: [66664..125030] bytes Bin[16]: [125031..] bytes.";
      type ietfyang:mac-address;
      max-elements 17;
    }
    leaf pmPimAvoidMutedCrbSamp {
      description "Number of slots when muting is performed..";
      type uint64;
      config false;
    }
    leaf pmSessionTimeUeBwpSamp {
      description "Number of times corresponding pmSessionTimeUeBwpSumDistr counter is incremented. Unit: N/A.";
      type uint64;
      config false;
    }
    leaf pmMacThpUlUeMax {
      description "Maximum UE throughput achieved when restricted by air interface. Unit: kbps.";
      type ietfyang:mac-address;
      config false;
    }
    leaf pmRadioPdschEmptySlots {
      description "Number of downlink slots without PDSCH traffic. Shows PDSCH use in time domain. Unit: N/A.";
      type uint64;
      config false;
    }
    leaf-list pmMacContentionDelayDlDistr {
      description "Distribution of downlink MAC contention delay. Time for HARQ initial transmission scheduling of DRB on PDSCH since last scheduled DRB (delta time between scheduling occasions). Unit: N/A Ranges: Bin[0]: [ 0..125[ microseconds Bin[1]: [125..250[ microseconds Bin[2]: [250..375[ microseconds Bin[3]: [375..500[ microseconds Bin[4]: [500..625[ microseconds Bin[5]: [625..750[ microseconds Bin[6]: [750..875[ microseconds Bin[7]: [875..1000[ microseconds Bin[8]: [1000..1125[ microseconds Bin[9]: [1125..1250[ microseconds Bin[10]: [1250..1375[ microseconds Bin[11]: [1375..1500[ microseconds Bin[12]: [1500..1625[ microseconds Bin[13]: [1625..1750[ microseconds Bin[14]: [1750..1875[ microseconds Bin[15]: [1875..2000[ microseconds Bin[16]: [2000..3000[ microseconds Bin[17]: [3000..4000[ microseconds Bin[18]: [4000..5000[ microseconds Bin[19]: [5000..10000[ microseconds Bin[20]: [10000..] us.";
      type ietfyang:mac-address;
      max-elements 21;
    }
    leaf pmMacVolDlDrbSingleBurst {
      description "Aggregated volume of downlink MAC SDUs for single-burst cases that are transmitted for HARQ initial transmission for each DRB. Single-burst case is when new packet arrives to empty buffer and buffer is drained by single scheduling occasion. HARQ retransmission is excluded. Unit: bytes.";
      type ietfyang:mac-address;
      config false;
    }
    leaf pmPuschAvailTime {
      description "Total duration of slots where gNodeB scheduler can schedule on PUSCH. Unit: 125 microseconds.";
      type uint64;
      config false;
    }
    leaf pmRadioMacDftsTransUl {
      description "Total number of UE uplink transmissions on DFT-s-OFDM in each cell. Unit: N/A.";
      type ietfyang:mac-address;
      config false;
    }
    leaf-list pmMacVolDlDrbSingleSlotShortBurstQoS {
      description "Aggregated volume of downlink MAC SDUs for single slot short burst cases that are transmitted for HARQ initial transmission for each QoS. Single slot short burst case is when new packet arrives to empty buffer and buffer is drained by single scheduling occasion on each active component carrier. HARQ retransmission is excluded. Unit: bytes Compressed: True.";
      type ietfyang:mac-address;
      max-elements 256;
    }
    leaf pmRadioRaCfFailMsg1Ooc {
      description "Number of CFRA preambles discarded because timing offset corresponds to a greater distance than configured cell range. Unit: N/A.";
      type uint64;
      config false;
    }
    leaf pmRadioRaCfUnassignedFalse {
      description "Number of detected CFRA preambles that are not allocated to any UE. Unit: N/A.";
      type uint64;
      config false;
    }
    leaf pmMacHarqUlDtx64Qam {
      description "Total number of occasions when no HARQ is received in gNodeB uplink when the following conditions apply: - Uplink grant is meant for HARQ transmission of transport block that uses 64-QAM modulation. - DTX is considered the reason for no reception. Unit: N/A.";
      type ietfyang:mac-address;
      config false;
    }
    leaf pmMacRBSymUsedNrEfficiency {
      description "Aggregated number of resource block symbols used for PDSCH during a complete result output period that cannot be used without one of following features: - LTE-NR FDD Spectrum Sharing with Downlink Data and DMRS Multiplexing - Downlink Data and DMRS Multiplexing - LTE-NR FDD Spectrum Sharing with Rate Matching around LTE Synchronization Signal and PBCH - NR Downlink Data and PDCCH Multiplexing Unit: N/A.";
      type ietfyang:mac-address;
      config false;
    }
    leaf pmMacVolDl {
      description "Aggregated volume of successfully transmitted downlink MAC PDUs for DRB or SRB using cell as PCell, SCell, or PSCell. Unit: bytes.";
      type ietfyang:mac-address;
      config false;
    }
    leaf pmMacHarqDlNack64Qam {
      description "Total number of unsuccessful downlink HARQ transmissions using 64-QAM modulation. Unit: N/A.";
      type ietfyang:mac-address;
      config false;
    }
    leaf pmPagReceived {
      description "Number of requests for RRC paging routed to cell. Both core network paging and RAN paging are included. Unit: N/A.";
      type uint64;
      config false;
    }
    leaf pmActiveUeUlSamp {
      description "Number of times corresponding pmActiveUeUlSum counter is incremented. Unit: N/A.";
      type uint64;
      config false;
    }
    leaf pmActiveUeDlTrueSamp {
      description "Number of times corresponding pmActiveUeDlSum counter is updated, regardless if there are any active UEs, that is, once every slot. Unit: N/A.";
      type uint64;
      config false;
    }
    leaf pmBwpUeConfSamp {
      description "Number of times pmBwpUeConfSumDistr counter accumulates new sample..";
      type uint64;
      config false;
    }
    leaf pmRlcDelayTimeDl {
      description "Aggregated RLC delay time. For each DRB packet, measures time in milliseconds from packet arrival in gNodeB RLC layer to when last byte of this packet is scheduled and drained from RLC layer for transmission over air. Also PDCP SDU queue time (if any) is included on RAN Compute group 5 and earlier. Unit: milliseconds.";
      type uint64;
      config false;
    }
    leaf pmRlcArqUlAck {
      description "Total number of successful RLC SDU transmissions (ACKs) in uplink (UL). Only applicable to RLC AM bearers. In NR, RLC SN is associated with RLC SDUs and not RLC PDUs. The arq_ul_ack and arq_ul_nack are related to RLC SDUs ACKed and RLC PDU or RLC SDU segments NACKed. When carrier aggregation is used, total number of successful RLC SDU transmissions (ACKs) in UL is registered on PCell of UE..";
      type uint64;
      config false;
    }
    leaf-list pmRadioUeRepCqi64QamLowSeRank1Distr {
      description "Distribution of UE-reported CQI values with low Spectral Efficiency related to rank 1 transmissions when highest modulation order supported in downlink (DL) in NR cell is 64-QAM. CQI values and interpretations correspond to entries in Table 5.2.2.1-4 in 3GPP 38.214 for reporting CQI based on QPSK, 16-QAM, and 64-QAM. Unit: N/A Ranges: Bin[0]: CQI = 0 Bin[1]: CQI = 1 Bin[2]: CQI = 2 Bin[3]: CQI = 3 Bin[4]: CQI = 4 Bin[5]: CQI = 5 Bin[6]: CQI = 6 Bin[7]: CQI = 7 Bin[8]: CQI = 8 Bin[9]: CQI = 9 Bin[10]: CQI = 10 Bin[11]: CQI = 11 Bin[12]: CQI = 12 Bin[13]: CQI = 13 Bin[14]: CQI = 14 Bin[15]: CQI = 15.";
      type uint64;
      max-elements 16;
    }
    leaf pmActiveUeUlMax {
      description "Peak number of active UE instances that have DRB or SRB data in UE uplink buffer. Value is maximum of a set of samples, where following conditions apply: . Throughout measurement period, each sample is an average of active UE instances. Rounding method can cause counter to show one less than the real number of UE instances. . Sample is taken every second. Unit: N/A.";
      type int64;
      config false;
    }
    leaf-list pmRadioUeRepPmiSecondaryCsiRsRank2Distr {
      description "Distribution of precoding weights reported by UE for rank 2 codebook associated with secondary CSI-RS. Indicates spatial distribution of UEs using cell as PCell. Type 1 single-panel codebooks are defined in 3GPP TS 38.214. Represents distribution of requested departure angles from AAS-capable radio unit as estimated from UE CSI feedback, specifically main and diversity direction of PMI values. It is not recommended to use this PM counter for Remote radio units. For more information, see Massive MIMO Mid-Band and Manage Massive MIMO NR in CPI library. Unit: N/A Compressed: True.";
      type uint64;
      max-elements 256;
    }
    leaf-list pmRadioRecInterferencePwrUlSlot6Distr {
      description "Absolute power for each symbol in uplink slot 6 in one radio frame. Bins correspond to uplink symbol 2 and uplink symbol 11 respectively. To get average interference power for each bin across a Result Output Period (ROP), divide by NRCellDU.pmRadioRecInterferencePwrSlotSamp. Unit: 0.1 dBm/PRB.";
      type uint64;
      max-elements 2;
    }
    leaf pmMacVolDlDrb {
      description "Aggregated volume of downlink MAC SDUs transmitted for HARQ initial transmission for each DRB. HARQ retransmission is excluded. Unit: bytes.";
      type ietfyang:mac-address;
      config false;
    }
    leaf pmRadioPucchFailSr {
      description "Number of received Scheduling Requests (SRs) over RACH due to failure of UE to access node with SR over PUCCH. Unit: N/A.";
      type uint64;
      config false;
    }
    leaf-list pmMacBsrLcg0Distr {
      description "Distribution of highest possible buffer size reported in BSRs in MAC Control Elements in UL LCG ID 0. Unit: N/A Ranges: Bin[0]: 0 bytes Bin[1]: [1..19] bytes Bin[2]: [20..36] bytes Bin[3]: [37..66] bytes Bin[4]: [67..124] bytes Bin[5]: [125..233] bytes Bin[6]: [234..436] bytes Bin[7]: [437..817] bytes Bin[8]: [818..1532] bytes Bin[9]: [1533..2873] bytes Bin[10]: [2874..5387] bytes Bin[11]: [5388..10104] bytes Bin[12]: [10105..18951] bytes Bin[13]: [18952..35543] bytes Bin[14]: [35544..66663] bytes Bin[15]: [66664..125030] bytes Bin[16]: [125031..] bytes.";
      type ietfyang:mac-address;
      max-elements 17;
    }
    leaf-list pmRadioServingBeamDlDistr {
      description "Number of measurement reports for serving beam, identified by logical SSB index. Measured when this cell is used as PSCell. Unit: N/A Ranges: Bin[0]: SSB index 1. Bin[1]: SSB index 2. Bin[2]: SSB index 3. Bin[3]: SSB index 4. Bin[4]: SSB index 5. Bin[5]: SSB index 6. Bin[6]: SSB index 7. Bin[7]: SSB index 8. Bin[8]: SSB index 9. Bin[9]: SSB index 10. Bin[10]: SSB index 11. Bin[11]: SSB index 12. Bin[12]: SSB index 13. Bin[13]: SSB index 14. Bin[14]: SSB index 15. Bin[15]: SSB index 16. Bin[16]: SSB index 17. Bin[17]: SSB index 18. Bin[18]: SSB index 19. Bin[19]: SSB index 20. Bin[20]: SSB index 21. Bin[21]: SSB index 22. Bin[22]: SSB index 23. Bin[23]: SSB index 24..";
      type uint64;
      max-elements 24;
    }
    leaf pmPdschSchedActivityLowPrioArea {
      description "Total duration of slots with downlink PDSCH in low priority area. Unit: 125 microseconds.";
      type uint64;
      config false;
    }
    leaf pmMacVolUlResUeLate {
      description "Data volume in MAC SDUs successfully received in uplink after being restricted by air interface. Received after last slot of burst. Unit: byte.";
      type ietfyang:mac-address;
      config false;
    }
    leaf-list pmDrbEstabSoftAdmissionQos {
      description "Number of soft-admitted DRB establishments per QoS. Compressed: True.";
      type uint64;
      max-elements 256;
    }
    leaf pmMacTimeDlDrbSamp {
      description "Aggregated number of samples for measuring time for HARQ initial transmission scheduling of downlink DRB while there is data in buffer. Unit: N/A.";
      type ietfyang:mac-address;
      config false;
    }
    leaf pmMacHarqUlAck16QamInit {
      description "Total number of successful initial HARQ transmissions in uplink using 16-QAM modulation. Initial transmission is first transmission on HARQ process, where NDI bit in DCI message is toggled. Unit: N/A.";
      type ietfyang:mac-address;
      config false;
    }
    leaf-list pmUeCtxtModAttWvfSwitchDistr {
      description "Counts each RRC Reconfiguration attempt during UE Context Modification procedure for UE uplink waveform switch. Unit: N/A Ranges: Bin[0]: NR SA MCG CP-OFDM Bin[1]: EN-DC SCG CP-OFDM Bin[2]: NR-DC SCG CP-OFDM Bin[3]: NR SA MCG DFTs-OFDM Bin[4]: EN-DC SCG DFTs-OFDM Bin[5]: NR-DC SCG DFTs-OFDM.";
      type uint64;
      max-elements 6;
    }
    leaf-list pmMacRBSymUsedPdschAdvMimoUserDistr {
      description "Distribution of aggregated number of resource block symbols used for PDSCH by different number of users as a result of advanced beamforming. DMRS and PTRS embedded in PDSCH resources are included. Unit: N/A Ranges: Bin[0]: Distribution of aggregated number of resource block symbols for one user case. Bin[1]: Distribution of aggregated number of resource block symbols for two users case. Bin[2]: Distribution of aggregated number of resource block symbols for three users case. Bin[3]: Distribution of aggregated number of resource block symbols for four users case. Bin[4]: Distribution of aggregated number of resource block symbols for five users case. Bin[5]: Distribution of aggregated number of resource block symbols for six users case. Bin[6]: Distribution of aggregated number of resource block symbols for seven users case. Bin[7]: Distribution of aggregated number of resource block symbols for eight users case. Bin[8]: Reserved for future MU-MIMO. Bin[9]: Reserved for future MU-MIMO. Bin[10]: Reserved for future MU-MIMO. Bin[11]: Reserved for future MU-MIMO. Bin[12]: Reserved for future MU-MIMO. Bin[13]: Reserved for future MU-MIMO. Bin[14]: Reserved for future MU-MIMO. Bin[15]: Reserved for future MU-MIMO..";
      type ietfyang:mac-address;
      max-elements 16;
    }
    leaf-list pmPdcchDciSwitchBwp {
      description "Shows accumulated number of outgoing DCI switches in BWP in NRCellDU. Only DL bins are pegged. PDF ranges: Bin[0]: Accumulated number of outgoing DCI switches out of the first BWP referenced in NRCellDU by BWPSet.allBWPRegularRef Bin[1]: Accumulated number of outgoing DCI switches out of the second BWP referenced in NRCellDU by BWPSet.allBWPRegularRef Bin[2]: Accumulated number of outgoing DCI switches out of the third BWP referenced in NRCellDU by BWPSet.allBWPRegularRef ... Bin[15]: Accumulated number of outgoing DCI switches out of the sixteenth BWP referenced in NRCellDU by BWPSet.allBWPRegularRef.";
      type uint64;
      max-elements 16;
    }
    leaf pmMacOverlapTimeDlDrbExtSCell {
      description "Counter that records time overlap between carrier aggregation data bursts, where original data burst time is overlapped with subsequent data burst times due to scheduling delay on external SCell. This time is subtracted from other counters intended for user throughput calculation. Unit: 125 microseconds.";
      type ietfyang:mac-address;
      config false;
    }
    leaf-list pmMacRBSymUsedPdschAdvEisSuMimoTxRankDistr {
      description "Distribution of aggregated number of resource block symbols used for PDSCH by sounding antennas and downlink rank as a result of reciprocity-based Ericsson Interference Sensing (EIS) SU-MIMO. DMRS and PTRS embedded in PDSCH resources are included. Unit: N/A Ranges: Bin[0]: Number of resource block symbols scheduled with 1TX/4RX R1. Bin[1]: Number of resource block symbols scheduled with 1TX/4RX R2. Bin[2]: Number of resource block symbols scheduled with 1TX/4RX R3. Bin[3]: Number of resource block symbols scheduled with 1TX/4RX R4. Bin[4]: Number of resource block symbols scheduled with 2TX/4RX R1. Bin[5]: Number of resource block symbols scheduled with 2TX/4RX R2. Bin[6]: Number of resource block symbols scheduled with 2TX/4RX R3. Bin[7]: Number of resource block symbols scheduled with 2TX/4RX R4. Bin[8]: Number of resource block symbols scheduled with 4TX/4RX R1. Bin[9]: Number of resource block symbols scheduled with 4TX/4RX R2. Bin[10]: Number of resource block symbols scheduled with 4TX/4RX R3. Bin[11]: Number of resource block symbols scheduled with 4TX/4RX R4. Bin[12]: Number of resource block symbols scheduled with 1TX/2RX R1. Bin[13]: Number of resource block symbols scheduled with 1TX/2RX R2. Bin[14]: Number of resource block symbols scheduled with 2TX/2RX R1. Bin[15]: Number of resource block symbols scheduled with 2TX/2RX R2. Bin[16]: Number of resource block symbols scheduled with 1TX/1RX R1..";
      type ietfyang:mac-address;
      max-elements 17;
    }
    leaf-list pmMacVolUlSCellBwp {
      description "Data volume in MAC SDUs successfully received in uplink when cell is used as SCell. BWP value is always zero for downlink. PDF ranges: Bin[0]: Data volume in MAC SDUs successfully received in uplink when cell is used as Scell in first BWP referenced in NRCellDU MO by BWPSet.allBWPRegularRef attribute. Bin[1]: Data volume in MAC SDUs successfully received in uplink when cell is used as Scell in second BWP referenced in NRCellDU MO by BWPSet.allBWPRegularRef attribute. Bin[2]: Data volume in MAC SDUs successfully received in uplink when cell is used as Scell in third BWP referenced in NRCellDU MO by BWPSet.allBWPRegularRef attribute. ... Bin[15]: Data volume in MAC SDUs successfully received in uplink when cell is used as Scell in sixteenth BWP referenced in NRCellDU MO by BWPSet.allBWPRegularRef attribute. Unit: Bytes.";
      type ietfyang:mac-address;
      max-elements 16;
    }
    leaf pmMacActiveSrsUe {
      description "Total number of active SRS UE. This counter shall steps when the UE PDSCH is RAT(Reciprocity assistant transmission) mode. Include both P-SRS and AP-SRS..";
      type ietfyang:mac-address;
      config false;
    }
    leaf pmPuschSchedActivityPCellCa {
      description "Total duration of slots where at least one MAC SDU is received on PUSCH using cell as PCell. Only count in carrier aggregation UEs using cell as PCell, including uplink carrier aggregation and uplink Tx Switching UEs. Unit: 125 microseconds.";
      type uint64;
      config false;
    }
    leaf pmUeCtxtAllocatedSamp {
      description "Number of times pmUeCtxtAllocatedSum is stepped..";
      type uint64;
      config false;
    }
    leaf-list pmRlcDelayPktTransmitDlQos {
      description "Aggregated number of samples for downlink Radio Link Control RLC delay measurements for each QoS. Unit: N/A Compressed: True.";
      type uint64;
      max-elements 256;
    }
    leaf pmDuCellDownLockMan {
      description "Number of times cell is locked due to operator-initiated action..";
      type uint64;
      config false;
    }
    leaf-list pmDrbModSoftAdmissionQos {
      description "Number of soft-admitted DRB modifications per QoS. Compressed: True.";
      type uint64;
      max-elements 256;
    }
    leaf-list pmMacTimeDlDrbSingleSlotShortBurstQoS {
      description "Aggregated time for HARQ initial transmission scheduling of single slot short burst cases of downlink DRB while there is data in buffer. Accumulates measured time from all DRBs with same QoS. HARQ retransmission is excluded. Unit: 125 microseconds Compressed: True.";
      type ietfyang:mac-address;
      max-elements 256;
    }
    leaf-list pmRadioUeRepCqi64QamRank2Distr {
      description "Distribution of UE-reported CQI values related to rank 2 transmissions when highest modulation order supported in downlink (DL) in NR cell is 64-QAM. CQI values and interpretations correspond to entries in Table 5.2.2.1-2 in 3GPP 38.214 for reporting CQI based on QPSK, 16-QAM, and 64-QAM. Unit: N/A Ranges: Bin[0]: CQI = 0 Bin[1]: CQI = 1 Bin[2]: CQI = 2 Bin[3]: CQI = 3 Bin[4]: CQI = 4 Bin[5]: CQI = 5 Bin[6]: CQI = 6 Bin[7]: CQI = 7 Bin[8]: CQI = 8 Bin[9]: CQI = 9 Bin[10]: CQI = 10 Bin[11]: CQI = 11 Bin[12]: CQI = 12 Bin[13]: CQI = 13 Bin[14]: CQI = 14 Bin[15]: CQI = 15.";
      type uint64;
      max-elements 16;
    }
    leaf pmRadioRaCfPreambles {
      description "Number of detected CFRA preambles (Msg1). Unit: messages.";
      type uint64;
      config false;
    }
    leaf-list pmMacRBSymUsedPdschMimoUserDistr {
      description "Distribution of aggregated number of resource block symbols used for PDSCH by different number of users as a result of SU-MIMO or MU-MIMO. DMRS and PTRS embedded in PDSCH resources are included. Unit: N/A Ranges: Bin[0]: Number of resource block symbols scheduled with 1 user. Bin[1]: Number of resource block symbols scheduled with 2 users. Bin[2]: Number of resource block symbols scheduled with 3 users. Bin[3]: Number of resource block symbols scheduled with 4 users. Bin[4]: Number of resource block symbols scheduled with 5 users. Bin[5]: Number of resource block symbols scheduled with 6 users. Bin[6]: Number of resource block symbols scheduled with 7 users. Bin[7]: Number of resource block symbols scheduled with 8 users. Bin[8]: Number of resource block symbols scheduled with 9 users. Bin[9]: Number of resource block symbols scheduled with 10 users. Bin[10]: Number of resource block symbols scheduled with 11 users. Bin[11]: Number of resource block symbols scheduled with 12 users. Bin[12]: Number of resource block symbols scheduled with 13 users. Bin[13]: Number of resource block symbols scheduled with 14 users. Bin[14]: Number of resource block symbols scheduled with 15 users. Bin[15]: Number of resource block symbols scheduled with 16 users..";
      type ietfyang:mac-address;
      max-elements 16;
    }
    leaf-list pmRadioPdschTable1MbsfnMcsDistr {
      description "Distribution of MCS used for PDSCH transmissions in MBSFN subframes where MCS index table 1 is applied, and UE instances are enabled with up to 64-QAM. For more information, see 3GPP TS 38.214, Table 5.1.3.1-1. Each bin represents a specific MCS. Unit: N/A Ranges: Bin[0]: MCS = 0 Bin[1]: MCS = 1 Bin[2]: MCS = 2 Bin[3]: MCS = 3 Bin[4]: MCS = 4 Bin[5]: MCS = 5 Bin[6]: MCS = 6 Bin[7]: MCS = 7 Bin[8]: MCS = 8 Bin[9]: MCS = 9 Bin[10]: MCS = 10 Bin[11]: MCS = 11 Bin[12]: MCS = 12 Bin[13]: MCS = 13 Bin[14]: MCS = 14 Bin[15]: MCS = 15 Bin[16]: MCS = 16 Bin[17]: MCS = 17 Bin[18]: MCS = 18 Bin[19]: MCS = 19 Bin[20]: MCS = 20 Bin[21]: MCS = 21 Bin[22]: MCS = 22 Bin[23]: MCS = 23 Bin[24]: MCS = 24 Bin[25]: MCS = 25 Bin[26]: MCS = 26 Bin[27]: MCS = 27 Bin[28]: MCS = 28 Bin[29]: MCS = 29 Bin[30]: MCS = 30 Bin[31]: MCS = 31.";
      type uint64;
      max-elements 32;
    }
    leaf pmMacRBSymAvailUl {
      description "Aggregated number of resource block symbols available for uplink transmission during complete ROP. Unit: N/A.";
      type ietfyang:mac-address;
      config false;
    }
    leaf pmDrxTotalTime {
      description "Total duration of DRX time for all UEs. Unit: 125 microseconds.";
      type uint64;
      config false;
    }
    leaf pmPagDiscardedEdrx {
      description "Number of eDRX RRC paging messages discarded and not broadcasted in cell. Both Core Network paging and Radio Access Network paging are included. This counter is a subset of NRCellDU.pmPagDiscarded PM counter. Unit: NA.";
      type uint64;
      config false;
    }
    leaf-list pmRadioSinrPuschHarqFailDistr {
      description "Total number of PUSCH HARQ failure counts pegged at SINR values for each PUSCH transmission. Ranges: Bin[0]: [..-11] dB Bin[1]: ]-11..-8] dB Bin[2]: ]-8..-5] dB Bin[3]: ]-5..-2] dB Bin[4]: ]-2..1] dB Bin[5]: ]1..4] dB Bin[6]: ]4..7] dB Bin[7]: ]7..10] dB Bin[8]: ]10..13] dB Bin[9]: ]13..16] dB Bin[10]: ]16..] dB.";
      type uint64;
      max-elements 11;
    }
    leaf-list pmRadioPreambleSinrMsg3SuccTx2Distr {
      description "Total number of successful Msg3 counts for second transmission attempt for a preamble SINR bin. Ranges: Bin[0]: [..-15] dB Bin[1]: ]-15..-12] dB Bin[2]: ]-12..-9] dB Bin[3]: ]-9..-6] dB Bin[4]: ]-6..-3] dB Bin[5]: ]-3..] dB.";
      type uint64;
      max-elements 6;
    }
    leaf pmMacRBSymUsedPusch1Port1Layer {
      description "Aggregated number of resource block symbols scheduled in uplink for one-layer transmission with one port. Unit: N/A.";
      type ietfyang:mac-address;
      config false;
    }
    leaf pmMacRBSymUsedPusch2Port1Layer {
      description "Aggregated number of resource block symbols scheduled in uplink for one-layer transmission with two ports. Unit: N/A.";
      type ietfyang:mac-address;
      config false;
    }
    leaf pmUeCtxtSetupAtt {
      description "Number of UE Context Setup attempts..";
      type uint64;
      config false;
    }
    leaf pmMacRBSymUsedPdcchAilg {
      description "Total number of resource block symbols generated for PDCCH by artificial load generator. Unit: N/A.";
      type ietfyang:mac-address;
      config false;
    }
    leaf-list pmMacTimeDlDrbLastSlotQos {
      description "Aggregated time for last slot of burst scheduling of downlink DRB since last scheduled DRB (delta time between scheduling occasions). It is considered last slot if all data in DRB buffer is drained. It is considered part of a burst if there is at least one previous DL scheduling occasion that does not fully empty buffer. HARQ initial transmission is measured. HARQ retransmission is excluded. Time is accumulated from all DRBs with same QoS. Unit: 125 microseconds Compressed: True.";
      type ietfyang:mac-address;
      max-elements 256;
    }
    leaf-list pmRadioRecInterferencePwrUlSlot8Distr {
      description "Absolute power for each symbol in uplink slot 8 in one radio frame. Bins correspond to uplink symbol 2 and uplink symbol 11 respectively. To get average interference power for each bin across a Result Output Period (ROP), divide by NRCellDU.pmRadioRecInterferencePwrSlotSamp. Unit: 0.1 dBm/PRB.";
      type uint64;
      max-elements 2;
    }
    leaf-list pmMacRBSymUsedPdcchTypeAAggrLvl16Bwp {
      description "Number of resource block symbols used by PDCCH with aggregation level 16 for scheduling of PDSCH or PUSCH using mapping type A in BWP. This includes DMRS and PTRS embedded in resources. PDF ranges: Bin[0]: Accumulated downlink resource block symbols used by PDCCH with aggregation level 16 in the first BWP referenced in NRCellDU MO by BWPSet.allBWPRegularRef attribute Bin[1]: Accumulated downlink resource block symbols used by PDCCH with aggregation level 16 in the second BWP referenced in NRCellDU MO by BWPSet.allBWPRegularRef attribute Bin[2]: Accumulated downlink resource block symbols used by PDCCH with aggregation level 16 in the third BWP referenced in NRCellDU MO by BWPSet.allBWPRegularRef attribute ... Bin[15]: Accumulated downlink resource block symbols used by PDCCH with aggregation level 16 in the sixteenth BWP referenced in NRCellDU MO by BWPSet.allBWPRegularRef attribute Unit: N/A.";
      type ietfyang:mac-address;
      max-elements 16;
    }
    leaf pmRadioRecInterferencePwrSlotSamp {
      description "Aggregated number of radio frames, during which uplink interference and noise in each uplink slot or in each special slot is measured. Unit: N/A.";
      type uint64;
      config false;
    }
    leaf pmMacOffloadVolDlSCellExt {
      description "Aggregated volume of successfully transmitted DL MAC PDUs for DRB or SRB offloaded to external inter-gNodeB SCells, inter-Capacity module SCell, or inter-DU SCell when this cell is used as PCell. Unit: bytes.";
      type ietfyang:mac-address;
      config false;
    }
    leaf pmMacHarqUlDtx64QamInit {
      description "Number of DTX detections for initial HARQ transmissions in uplink using 64-QAM modulation. Initial transmission is first transmission on HARQ process, where NDI bit in DCI message is toggled. Unit: N/A.";
      type ietfyang:mac-address;
      config false;
    }
    leaf-list pmRadioRaCfPreambleFailedUlCaDistr {
      description "Number of failed CFRA preamble allocations for uplink carrier aggregation UEs for each PRACH period during measurement period. Unit: N/A Ranges: Bin[0]: One failed preamble assignment for uplink carrier aggregation. Bin[1]: Two failed preamble assignments for uplink carrier aggregation. Bin[2]: Three failed preamble assignments for uplink carrier aggregation. Bin[3]: More than three failed preamble assignments for uplink carrier aggregation..";
      type uint64;
      max-elements 4;
    }
    leaf-list pmRadioMacLongPsrSinrDistr {
      description "Distribution of SINR values as measured at time of decision to switch scheduling request on PUCCH periodicity to longer periodicity. Ranges: Bin[0]: [..-1] dB Bin[1]: ]-1..1] dB Bin[2]: ]1..3] dB Bin[3]: ]3..5] dB Bin[4]: ]5..7] dB Bin[5]: ]7..9] dB Bin[6]: ]9..11] dB Bin[7]: ]11..13] dB Bin[8]: ]13..15] dB Bin[9]: ]15..17] dB Bin[10]: ]17..19] dB Bin[11]: ]19..21] dB Bin[12]: ]21..23] dB Bin[13]: ]23..25] dB Bin[14]: ]25..] dB Unit: N/A.";
      type ietfyang:mac-address;
      max-elements 15;
    }
    leaf-list pmRadioUeRepPmiPrimaryCsiRsRank2Distr {
      description "Distribution of precoding weights reported by UE for rank 2 codebook associated with primary CSI-RS. Indicates spatial distribution of UEs using cell as PCell. Type 1 single-panel codebooks are defined in 3GPP TS 38.214. Represents distribution of requested departure angles from AAS-capable radio unit as estimated from UE CSI feedback, specifically main and diversity direction of PMI values. It is not recommended to use this PM counter for Remote radio units. For more information, see Massive MIMO Mid-Band and Manage Massive MIMO NR in CPI library. Unit: N/A Compressed: True.";
      type uint64;
      max-elements 256;
    }
    leaf pmMacHarqUlNack16Qam {
      description "Total number of unsuccessful HARQ transmissions in uplink using 16-QAM modulation. Unit: N/A.";
      type ietfyang:mac-address;
      config false;
    }
    leaf-list pmRadioRecInterferencePwrSumPrbDistr {
      description "Aggregated absolute power value for each PRB in units of 0.1 dBm. For example, a value of 1130 corresponds to an interference plus noise power of -113 dBm/PRB. Bins correspond to individual PRBs. Subsequent values are summed. To extract average across a ROP, divide by corresponding bins in pmRadioRecInterferenceNoOfEventsPrbDistr. Number of bins (273) corresponds to maximum number that might appear. Therefore, not all bins can be pegged for most combinations of bandwidth and numerology. Unit: dBm/PRB.";
      type uint64;
      max-elements 273;
    }
    leaf pmRadioRaCfSucc {
      description "The number of successfully completed CFRA procedures, i.e., Msg2 is successfully received at UE side. It is measured by non-DTX detection of PUSCH scheduled by RAR UL grant at gNB side. Unit: messages.";
      type uint64;
      config false;
    }
    leaf pmMacHarqDlResAllocType0Dci11 {
      description "Aggregated number of HARQ transmissions and retransmissions scheduled with resource allocation Type 0 with DCI format 1_1. Unit: N/A.";
      type ietfyang:mac-address;
      config false;
    }
    leaf-list pmRadioUeRepRankDistr {
      description "UE-reported ranks in a distribution. Unit: N/A Ranges: Bin[0]: Rank = 1 Bin[1]: Rank = 2 Bin[2]: Rank = 3 Bin[3]: Rank = 4.";
      type uint64;
      max-elements 4;
    }
    leaf-list pmMacRBSymUsedPdcchTypeADciSwitchBwp {
      description "Aggregated number of resource block symbols used by PDCCH for scheduling of PDSCH or PUSCH using mapping type A in BWP for DCI switches. This includes DMRS and PTRS embedded in resources. PDF ranges: Bin[0]: Aggregated number of resource block symbols used by PDCCH for scheduling of PDSCH or PUSCH using mapping type A for DCI switches in the first BWP referenced in NRCellDU by BWPSet.allBWPRegularRef Bin[1]: Aggregated number of resource block symbols used by PDCCH for scheduling of PDSCH or PUSCH using mapping type A for DCI switches in the second BWP referenced in NRCellDU by BWPSet.allBWPRegularRef Bin[2]: Aggregated number of resource block symbols used by PDCCH for scheduling of PDSCH or PUSCH using mapping type A for DCI switches in the third BWP referenced in NRCellDU by BWPSet.allBWPRegularRef ... Bin[15]: Aggregated number of resource block symbols used by PDCCH for scheduling of PDSCH or PUSCH using mapping type A for DCI switches in the sixteenth BWP referenced in NRCellDU by BWPSet.allBWPRegularRef Unit: N/A.";
      type ietfyang:mac-address;
      max-elements 16;
    }
    leaf pmMacPduVolDlUeSCell {
      description "Aggregated volume of HARQ initially transmitted and retransmitted downlink MAC PDUs for DRB using cell as SCell. Unit: bytes.";
      type ietfyang:mac-address;
      config false;
    }
    leaf pmMacHighPrioPreschedGrants {
      description "Number of high-priority prescheduling grants given in uplink across cell..";
      type ietfyang:mac-address;
      config false;
    }
    leaf pmMacOffloadVolUlSCell {
      description "MAC SDU volume successfully received through SCells when cell is used as PCell. Unit: bytes.";
      type ietfyang:mac-address;
      config false;
    }
    leaf-list pmRadioPuschPwrSpectralDensityDistr {
      description "Distribution of PUSCH power spectral density. Unit: N/A Ranges: Bin[0]: [..-120] dBm/prb Bin[1]: ]-120..-115] dBm/prb Bin[2]: ]-115..-110] dBm/prb Bin[3]: ]-110..-105] dBm/prb Bin[4]: ]-105..-100] dBm/prb Bin[5]: ]-100..-97] dBm/prb Bin[6]: ]-97..-94] dBm/prb Bin[7]: ]-94..-91] dBm/prb Bin[8]: ]-91..-88] dBm/prb Bin[9]: ]-88..-85] dBm/prb Bin[10]: ]-85..-82] dBm/prb Bin[11]: ]-82..-79] dBm/prb Bin[12]: ]-79..-76] dBm/prb Bin[13]: ]-76..-71] dBm/prb Bin[14]: ]-71..-66] dBm/prb Bin[15]: ]-66..-61] dBm/prb Bin[16]: ]-61..] dBm/prb.";
      type uint64;
      max-elements 17;
    }
    leaf-list pmRadioSinrPucchF0Distr {
      description "Distribution of SINR values calculated for PUCCH format 0. Unit: N/A Bin[0]: [..-15] dB Bin[1]: ]-15..-12] dB Bin[2]: ]-12..-9] dB Bin[3]: ]-9..-6] dB Bin[4]: ]-6..-3] dB Bin[5]: ]-3..0] dB Bin[6]: ]0..3] dB Bin[7]: ]3..6] dB Bin[8]: ]6..9] dB Bin[9]: ]9..] dB.";
      type uint64;
      max-elements 10;
    }
    leaf-list pmRadioUeRepPmiSecondaryCsiRsRank3Distr {
      description "Distribution of precoding weights reported by UE for rank 3 codebook associated with secondary CSI-RS. Indicates spatial distribution of UEs using cell as PCell. Type 1 single-panel codebooks are defined in 3GPP TS 38.214. Represents distribution of requested departure angles from AAS-capable radio unit as estimated from UE CSI feedback, specifically main and diversity direction of PMI values. It is not recommended to use this PM counter for Remote radio units. For more information, see Massive MIMO Mid-Band and Manage Massive MIMO NR in CPI library. Unit: N/A Compressed: True.";
      type uint64;
      max-elements 256;
    }
    leaf pmMacHighPrioPreschedGrantsUsed {
      description "Number of high-priority prescheduling grants used in uplink across cell..";
      type ietfyang:mac-address;
      config false;
    }
    leaf-list pmMacUaiOhIndSCellDistr {
      description "Aggregated number of unique UAI Overheating indications when SCells are active. Measured when this cell is used as PCell for SA or PSCell for ENDC/NRDC. Unit: N/A Bin[0]: Unique UAI Overheating indications with 0 SCells activated. Bin[1]: Unique UAI Overheating indications with 1 SCells activated. Bin[2]: Unique UAI Overheating indications with 2 SCells activated. Bin[3]: Unique UAI Overheating indications with 3 SCells activated. Bin[4]: Unique UAI Overheating indications with 4 SCells activated. Bin[5]: Unique UAI Overheating indications with 5 SCells activated. Bin[6]: Unique UAI Overheating indications with 6 SCells activated. Bin[7]: Unique UAI Overheating indications with 7 SCells activated..";
      type ietfyang:mac-address;
      max-elements 8;
    }
    leaf pmMacRBSymUsedPdcchTypeAAggrLvl8 {
      description "Number of resource block symbols used by PDCCH with aggregation level 8 for scheduling of PDSCH or PUSCH using mapping type A. This includes DMRS and PTRS embedded in resources. Unit: N/A.";
      type ietfyang:mac-address;
      config false;
    }
    leaf pmCellUptime {
      description "Length of time the cell is in-service. Unit: seconds.";
      type uint64;
      config false;
    }
    leaf-list pmMeasGapDurationDistr {
      description "Number of milliseconds while UE is configured with measurement gaps. Unit: ms Ranges: Bin[0]: [0..200] ms Bin[1]: [201..500] ms Bin[2]: [501..800] ms Bin[3]: [801..1000] ms Bin[4]: [1001..1500] ms Bin[5]: [1501..2000] ms Bin[6]: [2001..2500] ms Bin[7]: [2501..3000] ms Bin[8]: [3001..4000] ms Bin[9]: [4001..5000] ms Bin[10]: [5001..10000] ms Bin[11]: [10001..15000] ms Bin[12]: [15001..30000] ms Bin[13]: [30001..60000] ms Bin[14]: [60001..120000] ms Bin[15]: [120001..] ms.";
      type uint64;
      max-elements 16;
    }
    leaf pmBwpSwitchDciDropped {
      description "Number of dropped BWP switch DCIs in a cell because only one switch DCI can be sent in each slot. Unit: N/A.";
      type uint64;
      config false;
    }
    leaf pmMacHarqDlDtx64Qam {
      description "Total number of occasions when downlink HARQ feedback for a HARQ transmission using 64-QAM modulation could not be detected from UE. Unit: N/A.";
      type ietfyang:mac-address;
      config false;
    }
    leaf-list pmMacRBSymUsedPdschSuMimoLayerDistr {
      description "Distribution of aggregated number of resource block symbols used for PDSCH by a variable number of co-scheduled layers as a result of code-book based SU-MIMO. DMRS and PTRS embedded in PDSCH resources are included. Unit: N/A Ranges: Bin[0]: Number of resource block symbols scheduled with one layer. Bin[1]: Number of resource block symbols scheduled with two layers. Bin[2]: Number of resource block symbols scheduled with three layers. Bin[3]: Number of resource block symbols scheduled with four layers. Bin[4]: Reserved for future MIMO. Bin[5]: Reserved for future MIMO. Bin[6]: Reserved for future MIMO. Bin[7]: Reserved for future MIMO..";
      type ietfyang:mac-address;
      max-elements 8;
    }
    leaf pmMacVolDlCaDrb {
      description "Aggregated volume of downlink MAC SDUs transmitted for HARQ initial transmission for each DRB, classified as carrier aggregation bursts. HARQ retransmission is excluded. Unit: bytes.";
      type ietfyang:mac-address;
      config false;
    }
    leaf pmUeCtxtAllocatedMax {
      description "Maximum number of allocated UE contexts during reporting period..";
      type int64;
      config false;
    }
    leaf pmMacHarqDlAck16Qam {
      description "Total number of successful downlink HARQ transmissions using 16-QAM modulation. Unit: N/A.";
      type ietfyang:mac-address;
      config false;
    }
    leaf pmActiveUeUlSum {
      description "Number of UE instances considered active in uplink direction. UE is considered to have DRB or SRB data in its buffer. Unit: N/A.";
      type uint64;
      config false;
    }
    leaf pmMacHarqUlDtxQpsk {
      description "Total number of occasions when no HARQ is received in gNodeB uplink when the following conditions apply: - Uplink grant is meant for HARQ transmission of transport block that uses QPSK modulation. - DTX is considered the reason for no reception. Unit: N/A.";
      type ietfyang:mac-address;
      config false;
    }
    leaf pmMacHarqDlNack256Qam {
      description "Total number of unsuccessful downlink HARQ transmissions using 256-QAM modulation. Unit: N/A.";
      type ietfyang:mac-address;
      config false;
    }
    leaf-list pmPagBundledUeDistr {
      description "Number of UE instances paged or bundled for each PO. Both Core Network paging and Radio Access Network paging are included. Unit: N/A Ranges: Bin[0]: PO Index = 0 Bin[1]: PO Index = 1 Bin[2]: PO Index = 2 Bin[3]: PO Index = 3.";
      type uint64;
      max-elements 4;
    }
    leaf pmMacRBSymCsiRs {
      description "Aggregated number of resource block symbols used for CSI-RS, TRS, and CSI-IM during complete ROP. Unit: N/A.";
      type ietfyang:mac-address;
      config false;
    }
    leaf-list pmMacBsrLcg3Distr {
      description "Distribution of highest possible buffer size reported in BSRs in MAC Control Elements in UL LCG ID 3. Unit: N/A Ranges: Bin[0]: 0 bytes Bin[1]: [1..19] bytes Bin[2]: [20..36] bytes Bin[3]: [37..66] bytes Bin[4]: [67..124] bytes Bin[5]: [125..233] bytes Bin[6]: [234..436] bytes Bin[7]: [437..817] bytes Bin[8]: [818..1532] bytes Bin[9]: [1533..2873] bytes Bin[10]: [2874..5387] bytes Bin[11]: [5388..10104] bytes Bin[12]: [10105..18951] bytes Bin[13]: [18952..35543] bytes Bin[14]: [35544..66663] bytes Bin[15]: [66664..125030] bytes Bin[16]: [125031..] bytes.";
      type ietfyang:mac-address;
      max-elements 17;
    }
    leaf-list pmMacRBSymUsedPdschMimoSinrThresUserDistr {
      description "Distribution of aggregated number of resource block symbols used for PDSCH by a variable number of users that meet preset SINR thresholding conditions as a result of codebook SU-MIMO or MU-MIMO. This PM counter can be used together with NRCellDU.pmMacVolPdschMimoSinrThresUserDistr PM counter to calculate codebook resource block spectral efficiency. DMRS and PTRS embedded in PDSCH resources are included. Unit: N/A Ranges: Bin[0]: Number of resource block symbols scheduled with one user. Bin[1]: Number of resource block symbols scheduled with two users. Bin[2]: Number of resource block symbols scheduled with three users. Bin[3]: Number of resource block symbols scheduled with four users. Bin[4]: Reserved for future MU-MIMO. Bin[5]: Reserved for future MU-MIMO. Bin[6]: Reserved for future MU-MIMO. Bin[7]: Reserved for future MU-MIMO..";
      type ietfyang:mac-address;
      max-elements 8;
    }
    leaf pmMacRBSymUsedPdschTypeA {
      description "Aggregated number of resource block symbols used for PDSCH mapping type A during complete ROP. DMRS and PTRS embedded in PDSCH resources are included. Unit: N/A.";
      type ietfyang:mac-address;
      config false;
    }
    leaf pmRadioRaCbFailMsg3Dtx {
      description "Number of RACH attempts failed due to DTX detected. Unit: messages.";
      type uint64;
      config false;
    }
    leaf-list pmRadioMacLongPsrRsrpDistr {
      description "Distribution of last measured widebeam RSRP values at time of decision to switch scheduling request on PUCCH periodicity to longer periodicity. Ranges: Bin[0]: [..-120] dBm Bin[1]: ]-120..-118] dBm Bin[2]: ]-118..-116] dBm Bin[3]: ]-116..-114] dBm Bin[4]: ]-114..-112] dBm Bin[5]: ]-112..-110] dBm Bin[6]: ]-110..-108] dBm Bin[7]: ]-108..-106] dBm Bin[8]: ]-106..-104] dBm Bin[9]: ]-104..-102] dBm Bin[10]: ]-102..-100] dBm Bin[11]: ]-100..-98] dBm Bin[12]: ]-98..-96] dBm Bin[13]: ]-96..-94] dBm Bin[14]: ]-94..] dBm Unit: N/A.";
      type ietfyang:mac-address;
      max-elements 15;
    }
    leaf-list pmMacLatTimeDlDrxSyncSampQos {
      description "Aggregated number of samples for downlink MAC latency measurements for each QoS with DRX impact but without out-of-sync impact. DL MAC latency measures MAC scheduling latency between reception of packet in empty DL buffer and transmission of first packet. Unit: N/A Compressed: True.";
      type ietfyang:mac-address;
      max-elements 256;
    }
    leaf-list pmMacLatTimeDlNoDrxSyncQos {
      description "Aggregated time for downlink MAC latency measurement for each QoS without DRX impact and out-of-sync impact. DL MAC latency measures MAC scheduling latency between reception of packet in an empty DL buffer and transmission of first packet. Unit: 125 microseconds Compressed: True.";
      type ietfyang:mac-address;
      max-elements 256;
    }
    leaf-list pmMacBsrLcg6Distr {
      description "Distribution of highest possible buffer size reported in BSRs in MAC Control Elements in UL LCG ID 6. Unit: N/A Ranges: Bin[0]: 0 bytes Bin[1]: [1..19] bytes Bin[2]: [20..36] bytes Bin[3]: [37..66] bytes Bin[4]: [67..124] bytes Bin[5]: [125..233] bytes Bin[6]: [234..436] bytes Bin[7]: [437..817] bytes Bin[8]: [818..1532] bytes Bin[9]: [1533..2873] bytes Bin[10]: [2874..5387] bytes Bin[11]: [5388..10104] bytes Bin[12]: [10105..18951] bytes Bin[13]: [18952..35543] bytes Bin[14]: [35544..66663] bytes Bin[15]: [66664..125030] bytes Bin[16]: [125031..] bytes.";
      type ietfyang:mac-address;
      max-elements 17;
    }
    leaf-list pmMacRBSymUsedPdschAdvEisMuMimoLayerDistr {
      description "Distribution of aggregated number of resource block symbols used for PDSCH by different number of coscheduled layers as a result of reciprocity-based Ericsson Interference Sensing (EIS) MU-MIMO. DMRS and PTRS embedded in PDSCH resources are included. Unit: N/A Ranges: Bin[0]: Reserved - Not Used. Bin[1]: Number of resource block symbols scheduled with 2 layers. Bin[2]: Number of resource block symbols scheduled with 3 layers. Bin[3]: Number of resource block symbols scheduled with 4 layers. Bin[4]: Number of resource block symbols scheduled with 5 layers. Bin[5]: Number of resource block symbols scheduled with 6 layers. Bin[6]: Number of resource block symbols scheduled with 7 layers. Bin[7]: Number of resource block symbols scheduled with 8 layers. Bin[8]: Number of resource block symbols scheduled with 9 layers. Bin[9]: Number of resource block symbols scheduled with 10 layers. Bin[10]: Number of resource block symbols scheduled with 11 layers. Bin[11]: Number of resource block symbols scheduled with 12 layers. Bin[12]: Number of resource block symbols scheduled with 13 layers. Bin[13]: Number of resource block symbols scheduled with 14 layers. Bin[14]: Number of resource block symbols scheduled with 15 layers. Bin[15]: Number of resource block symbols scheduled with 16 layers..";
      type ietfyang:mac-address;
      max-elements 16;
    }
    leaf-list pmRadioRecInterferencePwrUlSlot2Distr {
      description "Absolute power for each symbol in uplink slot 2 in one radio frame. Bins correspond to uplink symbol 2 and uplink symbol 11 respectively. To get average interference power for each bin across a Result Output Period (ROP), divide by NRCellDU.pmRadioRecInterferencePwrSlotSamp. Unit: 0.1 dBm/PRB.";
      type uint64;
      max-elements 2;
    }
    leaf pmPdschPimBlankedSlot {
      description "Number of PDSCH-blanked slots when PIM related blanking requests are accepted. Unit: N/A.";
      type uint64;
      config false;
    }
    leaf pmMacHarqUlDtx256Qam {
      description "Total number of times when no HARQ is received in gNodeB uplink when the following conditions apply: - UL grant is meant for HARQ transmission of transport block that uses 256-QAM modulation. - DTX is considered the reason for no reception. Unit: N/A.";
      type ietfyang:mac-address;
      config false;
    }
    leaf-list pmMacRBSymUsedPdschCbRatDistr {
      description "Number of resource block symbols used for PDSCH for codebook and reciprocity beamforming. DMRS and PTRS embedded in PDSCH resources are included. Unit: N/A Ranges: Bin[0]: UE configured with SRS and PDSCH is reciprocity-based Bin[1]: UE configured with SRS and PDSCH is codebook-based Bin[2]: UE not configured with SRS and PDSCH is codebook-based Bin[3]: UE configured with SRS and PDSCH is configured with common beamforming weights.";
      type ietfyang:mac-address;
      max-elements 4;
    }
    leaf pmMacRBSymAvailPucch {
      description "Aggregated number of resource block symbols configured for PUCCH during complete ROP. Unit: N/A.";
      type ietfyang:mac-address;
      config false;
    }
    leaf pmMacTimeDlCaDrbActivity {
      description "Aggregated time for HARQ initial transmission scheduling activity of downlink DRB for data volume classified as carrier aggregation bursts. Scheduling activity refers to time interval from first scheduling occasion of a burst until all data in DRB buffer is drained. Unit: 125 microseconds.";
      type ietfyang:mac-address;
      config false;
    }
    leaf-list pmRimPdschActionSpecialSlotDistr {
      description "Histogram of applied RIM mitigation actions on PDSCH transmissions. Considers mitigation actions taken in special slot. Unit: N/A Ranges: Bin[0]: UE not scheduled due to blanking Bin[1]: UE not scheduled due to low load Bin[2]: UE not scheduled due to low SINR Bin[3]: UE is backed off with low power value Bin[4]: UE is backed off with high power value.";
      type uint64;
      max-elements 5;
    }
    leaf-list pmRadioPreambleSinrMsg3DtxAllTxDistr {
      description "Total number of occurances when all attempts of Msg3 transimissions resulted in DTX for a preamble SINR bin. Ranges: Bin[0]: [..-15] dB Bin[1]: ]-15..-12] dB Bin[2]: ]-12..-9] dB Bin[3]: ]-9..-6] dB Bin[4]: ]-6..-3] dB Bin[5]: ]-3..] dB.";
      type uint64;
      max-elements 6;
    }
    leaf pmMacRBSymUsedPdschTypeB {
      description "Aggregated number of resource block symbols used by PDSCH mapping type B. This includes DMRS and PTRS embedded in resources. Unit: N/A.";
      type ietfyang:mac-address;
      config false;
    }
    leaf-list pmRadioRecInterferencePowerDistr {
      description "Measured noise and interference power on PUSCH. Unit: N/A Ranges: Bin[0]: [..-130] dBm/PRB Bin[1]: ]-130..-128] dBm/PRB Bin[2]: ]-128..-126] dBm/PRB Bin[3]: ]-126..-124] dBm/PRB Bin[4]: ]-124..-122] dBm/PRB Bin[5]: ]-122..-121] dBm/PRB Bin[6]: ]-121..-120] dBm/PRB Bin[7]: ]-120..-119] dBm/PRB Bin[8]: ]-119..-118] dBm/PRB Bin[9]: ]-118..-117] dBm/PRB Bin[10]: ]-117..-116] dBm/PRB Bin[11]: ]-116..-115] dBm/PRB Bin[12]: ]-115..-114] dBm/PRB Bin[13]: ]-114..-113] dBm/PRB Bin[14]: ]-113..-112] dBm/PRB Bin[15]: ]-112..-108] dBm/PRB Bin[16]: ]-108..-104] dBm/PRB Bin[17]: ]-104..-100] dBm/PRB Bin[18]: ]-100..-96] dBm/PRB Bin[19]: ]-96..-92] dBm/PRB Bin[20]: ]-92..] dBm/PRB.";
      type uint64;
      max-elements 21;
    }
    leaf pmMacOffloadVolUlSCellExt {
      description "MAC SDU volume successfully received through external inter-gNodeB SCells and inter-capacity module SCells when cell is used as PCell. Unit: bytes.";
      type ietfyang:mac-address;
      config false;
    }
    leaf pmMacVolDlDrbLastSlot {
      description "Aggregated volume of downlink MAC SDUs transmitted for HARQ initial transmission in last slot of burst when buffer is emptied for each DRB. HARQ retransmission is excluded. Unit: bytes.";
      type ietfyang:mac-address;
      config false;
    }
    leaf pmMacTimeDlDrbSingleSlotShortBurst {
      description "Aggregated time for HARQ initial transmission scheduling of single slot short burst cases of downlink DRB while there is data in buffer. HARQ retransmission is excluded. Unit: 125 microseconds.";
      type ietfyang:mac-address;
      config false;
    }
    leaf pmMacVolUlUnresUePreemptGrant {
      description "Data volume in MAC SDUs successfully received in uplink, unrestricted by air interface. Sent using one preemptive grant given by gNodeB to anticipate need of sending PUCCH scheduling request by UE. Unit: byte.";
      type ietfyang:mac-address;
      config false;
    }
    leaf-list pmMacVolPdschMimoSinrThresUserDistr {
      description "Shows accumulated sum of data volume for first downlink transmission by a variable number of users that meet preset SINR thresholding conditions as a result of codebook SU-MIMO or MU-MIMO. This PM counter can be used together with NRCellDU.pmMacRBSymUsedPdschMimoSinrThresUserDistr PM counter to calculate codebook resource block spectral efficiency. Unit: byte Ranges: Bin[0]: Accumulated sum of data volume for first downlink transmission for one user. Bin[1]: Accumulated sum of data volume for first downlink transmission for two users. Bin[2]: Accumulated sum of data volume for first downlink transmission for three users. Bin[3]: Accumulated sum of data volume for first downlink transmission for four users. Bin[4]: Reserved for future MU-MIMO. Bin[5]: Reserved for future MU-MIMO. Bin[6]: Reserved for future MU-MIMO. Bin[7]: Reserved for future MU-MIMO..";
      type ietfyang:mac-address;
      max-elements 8;
    }
    leaf-list pmMacBsrLcg5Distr {
      description "Distribution of highest possible buffer size reported in BSRs in MAC Control Elements in UL LCG ID 5. Unit: N/A Ranges: Bin[0]: 0 bytes Bin[1]: [1..19] bytes Bin[2]: [20..36] bytes Bin[3]: [37..66] bytes Bin[4]: [67..124] bytes Bin[5]: [125..233] bytes Bin[6]: [234..436] bytes Bin[7]: [437..817] bytes Bin[8]: [818..1532] bytes Bin[9]: [1533..2873] bytes Bin[10]: [2874..5387] bytes Bin[11]: [5388..10104] bytes Bin[12]: [10105..18951] bytes Bin[13]: [18952..35543] bytes Bin[14]: [35544..66663] bytes Bin[15]: [66664..125030] bytes Bin[16]: [125031..] bytes.";
      type ietfyang:mac-address;
      max-elements 17;
    }
    leaf pmRadioMacWvfSwitchSuccUlDfts {
      description "Total number of successful UE uplink waveform switching attempts from CP-OFDM to DFT-s-OFDM in each cell. Unit: N/A.";
      type ietfyang:mac-address;
      config false;
    }
    leaf-list pmMacHarqDlAck16QamInitSlotDistr {
      description "For each downlink slot, bin that corresponds to number of successful initial HARQ PDSCH transmissions using 16-QAM modulation in slot is incremented. HARQ transmissions used for BWP DCI switch Scheduling Request (SR) are not pegged. Unit: N/A Ranges: Bin[0]: Total number of successful initial downlink HARQ transmissions using 16-QAM on slot 0. Bin[1]: Total number of successful initial downlink HARQ transmissions using 16-QAM on slot 1. Bin[2]: Total number of successful initial downlink HARQ transmissions using 16-QAM on slot 2. Bin[3]: Total number of successful initial downlink HARQ transmissions using 16-QAM on slot 3. Bin[4]: Total number of successful initial downlink HARQ transmissions using 16-QAM on slot 4. Bin[5]: Total number of successful initial downlink HARQ transmissions using 16-QAM on slot 5. Bin[6]: Total number of successful initial downlink HARQ transmissions using 16-QAM on slot 6. Bin[7]: Total number of successful initial downlink HARQ transmissions using 16-QAM on slot 7. Bin[8]: Total number of successful initial downlink HARQ transmissions using 16-QAM on slot 8. Bin[9]: Total number of successful initial downlink HARQ transmissions using 16-QAM on slot 9. Bin[10]: Total number of successful initial downlink HARQ transmissions using 16-QAM on slot 10. Bin[11]: Total number of successful initial downlink HARQ transmissions using 16-QAM on slot 11. Bin[12]: Total number of successful initial downlink HARQ transmissions using 16-QAM on slot 12. Bin[13]: Total number of successful initial downlink HARQ transmissions using 16-QAM on slot 13. Bin[14]: Total number of successful initial downlink HARQ transmissions using 16-QAM on slot 14. Bin[15]: Total number of successful initial downlink HARQ transmissions using 16-QAM on slot 15. Bin[16]: Total number of successful initial downlink HARQ transmissions using 16-QAM on slot 16. Bin[17]: Total number of successful initial downlink HARQ transmissions using 16-QAM on slot 17. Bin[18]: Total number of successful initial downlink HARQ transmissions using 16-QAM on slot 18. Bin[19]: Total number of successful initial downlink HARQ transmissions using 16-QAM on slot 19..";
      type ietfyang:mac-address;
      max-elements 20;
    }
    leaf-list pmRadioMacShortPsrRsrpDistr {
      description "Distribution of last measured widebeam RSRP values at time of decision to switch scheduling request on PUCCH periodicity to shorter periodicity. Ranges: Bin[0]: [..-116] dBm Bin[1]: ]-116..-114] dBm Bin[2]: ]-114..-112] dBm Bin[3]: ]-112..-110] dBm Bin[4]: ]-110..-108] dBm Bin[5]: ]-108..-106] dBm Bin[6]: ]-106..-104] dBm Bin[7]: ]-104..-102] dBm Bin[8]: ]-102..-100] dBm Bin[9]: ]-100..-98] dBm Bin[10]: ]-98..-96] dBm Bin[11]: ]-96..-94] dBm Bin[12]: ]-94..-92] dBm Bin[13]: ]-92..-90] dBm Bin[14]: ]-90..] dBm Unit: N/A.";
      type ietfyang:mac-address;
      max-elements 15;
    }
    leaf-list pmMacRBSymUsedPdschAdvSuMimoLayerDistr {
      description "Distribution of aggregated number of resource block symbols used for PDSCH by different number of coscheduled layers as a result of reciprocity-based SU-MIMO. DMRS and PTRS embedded in PDSCH resources are included. Unit: N/A Ranges: Bin[0]: Number of resource block symbols scheduled with 1 layer. Bin[1]: Number of resource block symbols scheduled with 2 layers. Bin[2]: Number of resource block symbols scheduled with 3 layers. Bin[3]: Number of resource block symbols scheduled with 4 layers. Bin[4]: Number of resource block symbols scheduled with 5 layers. Bin[5]: Number of resource block symbols scheduled with 6 layers. Bin[6]: Number of resource block symbols scheduled with 7 layers. Bin[7]: Number of resource block symbols scheduled with 8 layers..";
      type ietfyang:mac-address;
      max-elements 8;
    }
    leaf pmMacRBSymUsedPdcchTypeBAggrLvl8 {
      description "Number of resource block symbols used by PDCCH with aggregation level 8 for scheduling of PDSCH or PUSCH using mapping type B. This includes DMRS and PTRS embedded in resources scheduling. Unit: N/A.";
      type ietfyang:mac-address;
      config false;
    }
    leaf pmRimDetectedVictimSetIDsMax {
      description "Number of unique setIDs reported by aggressor cells with RS1 detection..";
      type int64;
      config false;
    }
    leaf pmMacVolDlAdvEis {
      description "Aggregated volume of successfully transmitted downlink MAC PDUs for all reciprocity-based Ericsson Interference Sensing (EIS) transmissions. Unit: bytes.";
      type ietfyang:mac-address;
      config false;
    }
    leaf pmMacVolUlSCellExt {
      description "Data volume in MAC SDUs successfully received in uplink when cell is used as external inter-gNodeB SCell and inter-capacity module SCell. Unit: byte.";
      type ietfyang:mac-address;
      config false;
    }
    leaf pmRadioMacCpofdmTransUl {
      description "Total number of UE uplink transmissions on CP-OFDM in each cell. Unit: N/A.";
      type ietfyang:mac-address;
      config false;
    }
    leaf pmPagReceivedEdrx {
      description "Number of requests for eDRX RRC paging routed to cell. Both core network paging and RAN paging are included. Counter is a subset of NRCellDU.pmPagReceived PM counter. Unit: N/A.";
      type uint64;
      config false;
    }
    leaf pmMacHarqDlDtx64QamInit {
      description "Total number of occasions when downlink HARQ feedback for initial HARQ transmission using 64-QAM modulation could not be detected from UE. Initial transmission is first transmission on HARQ process. Unit: N/A.";
      type ietfyang:mac-address;
      config false;
    }
    leaf-list pmMacRBSymUsedPdcchTypeAAggrLvl4Bwp {
      description "Number of resource block symbols used by PDCCH with aggregation level 4 for scheduling of PDSCH or PUSCH using mapping type A in BWP. This includes DMRS and PTRS embedded in resources. PDF ranges: Bin[0]: Accumulated downlink resource block symbols used by PDCCH with aggregation level 4 in the first BWP referenced in NRCellDU MO by BWPSet.allBWPRegularRef attribute Bin[1]: Accumulated downlink resource block symbols used by PDCCH with aggregation level 4 in the second BWP referenced in NRCellDU MO by BWPSet.allBWPRegularRef attribute Bin[2]: Accumulated downlink resource block symbols used by PDCCH with aggregation level 4 in the third BWP referenced in NRCellDU MO by BWPSet.allBWPRegularRef attribute ... Bin[15]: Accumulated downlink resource block symbols used by PDCCH with aggregation level 4 in the sixteenth BWP referenced in NRCellDU MO by BWPSet.allBWPRegularRef attribute Unit: N/A.";
      type ietfyang:mac-address;
      max-elements 16;
    }
    leaf pmPdschPimBlankingReq {
      description "Number of slots sending blanking request when PIM is detected and there are UEs vulnerable to PIM. Unit: N/A.";
      type uint64;
      config false;
    }
    leaf-list pmSssgUeConfSumDistr {
      description "Bin[0]: Number of UEs not capable of search space set group switching. Bin[1]: Number of UEs capable of and configured with search space set group switching. Bin[2]: Number of UEs capable of but not configured with search space set group switching..";
      type uint64;
      max-elements 3;
    }
    leaf-list pmRadioPdschTable3McsDistr {
      description "Distribution of MCS used for PDSCH transmissions where MCS index Table 3 is applied and UE instances are enabled. For more information, see 3GPP TS 38.214, Table 5.1.3.1-3. Each bin represents a specific MCS. Unit: N/A Ranges: Bin[0]: MCS = 0 Bin[1]: MCS = 1 Bin[2]: MCS = 2 Bin[3]: MCS = 3 Bin[4]: MCS = 4 Bin[5]: MCS = 5 Bin[6]: MCS = 6 Bin[7]: MCS = 7 Bin[8]: MCS = 8 Bin[9]: MCS = 9 Bin[10]: MCS = 10 Bin[11]: MCS = 11 Bin[12]: MCS = 12 Bin[13]: MCS = 13 Bin[14]: MCS = 14 Bin[15]: MCS = 15 Bin[16]: MCS = 16 Bin[17]: MCS = 17 Bin[18]: MCS = 18 Bin[19]: MCS = 19 Bin[20]: MCS = 20 Bin[21]: MCS = 21 Bin[22]: MCS = 22 Bin[23]: MCS = 23 Bin[24]: MCS = 24 Bin[25]: MCS = 25 Bin[26]: MCS = 26 Bin[27]: MCS = 27 Bin[28]: MCS = 28 Bin[29]: MCS = 29 Bin[30]: MCS = 30 Bin[31]: MCS = 31.";
      type uint64;
      max-elements 32;
    }
    leaf pmMacHarqDlDtxQpsk {
      description "Total number of occasions when downlink HARQ feedback for a HARQ transmission using QPSK modulation could not be detected from UE. Unit: N/A.";
      type ietfyang:mac-address;
      config false;
    }
    leaf pmDrxSleepTime {
      description "Total duration of DRX sleep slots for all UEs. Unit: 125 microseconds.";
      type uint64;
      config false;
    }
    leaf pmMacVolUlUeLastSlot {
      description "Data volume in MAC SDUs successfully received in uplink while not restricted by air interface. Received in last slot of burst. Unit: byte.";
      type ietfyang:mac-address;
      config false;
    }
    leaf pmMacTimeDlCaDrb {
      description "Aggregated time for HARQ initial transmission scheduling of downlink DRB for data volume classified as carrier aggregation bursts, with data in buffer. Unit: 125 microseconds.";
      type ietfyang:mac-address;
      config false;
    }
    leaf-list pmDrbEstabFailAdmissionRejQos {
      description "Number of DRB establishments rejected by Service Admission Control feature per QoS. DRB is rejected because of limit configured in FlowLimit.maxNoOfFlows attribute. For more information, check Feature Description for Service Admission Control feature. Compressed: True.";
      type uint64;
      max-elements 256;
    }
    leaf pmRlcArqUlNack {
      description "Total number of unsuccessful RLC SDU and RLC SDU segment transmissions (NACKs) in uplink (UL). Only applicable to RLC AM bearers. In NR, RLC SN is associated with RLC SDUs and not RLC PDUs. The arq_ul_ack and arq_ul_nack are related to RLC SDUs and RLC PDU or RLC SDU segments NACKed. When carrier aggregation is used, total number of unsuccessful RLC SDU and RLC SDU segment transmissions (NACKs) in UL is registered on PCell of UE..";
      type uint64;
      config false;
    }
    leaf-list pmRadioMacShortPsrSinrDistr {
      description "Distribution of SINR values as measured at time of decision to switch scheduling request on PUCCH periodicity to shorter periodicity. Ranges: Bin[0]: [..13] dB Bin[1]: ]13..15] dB Bin[2]: ]15..17] dB Bin[3]: ]17..19] dB Bin[4]: ]19..21] dB Bin[5]: ]21..23] dB Bin[6]: ]23..25] dB Bin[7]: ]25..27] dB Bin[8]: ]27..29] dB Bin[9]: ]29..31] dB Bin[10]: ]31..33] dB Bin[11]: ]33..35] dB Bin[12]: ]35..37] dB Bin[13]: ]37..39] dB Bin[14]: ]39..] dB Unit: N/A.";
      type ietfyang:mac-address;
      max-elements 15;
    }
    leaf pmSssgSwitchDciDropped {
      description "Number of dropped search space set group switch DCIs in a cell because only one switch DCI can be sent in each slot. Unit: N/A.";
      type uint64;
      config false;
    }
    leaf pmPdschAvailTime {
      description "Total duration of slots where gNodeB scheduler can schedule on PDSCH. Unit: 125 microseconds.";
      type uint64;
      config false;
    }
    leaf-list pmBwpUeConfSumDistr {
      description "Shows distribution of UEs configured with BWP for PCell in NRCellDU MO by BWPSet.allBWPRegularRef attribute PDF ranges: Bin[0]: Number of UEs configured with first BWP for PCell referenced in NRCellDU MO by BWPSet.allBWPRegularRef attribute Bin[1]: Number of UEs configured with second BWP for PCell referenced in NRCellDU MO by BWPSet.allBWPRegularRef attribute Bin[2]: Number of UEs configured with third BWP for PCell referenced in NRCellDU MO by BWPSet.allBWPRegularRef attribute ... Bin[15]: Number of UEs configured with sixteenth BWP for PCell referenced in NRCellDU MO by BWPSet.allBWPRegularRef attribute.";
      type uint64;
      max-elements 16;
    }
    leaf-list pmRadioRecInterferencePwrUlSlot4Distr {
      description "Absolute power for each symbol in uplink slot 4 in one radio frame. Bins correspond to uplink symbol 2 and uplink symbol 11 respectively. To get average interference power for each bin across a Result Output Period (ROP), divide by NRCellDU.pmRadioRecInterferencePwrSlotSamp. Unit: 0.1 dBm/PRB.";
      type uint64;
      max-elements 2;
    }
    leaf pmMassiveMimoSleepTimeTxMute {
      description "Accumulates actual amount of time a cell is set to TXMUTE state. Unit: seconds.";
      type uint64;
      config false;
    }
    leaf-list pmRadioPreambleSinrMsg3SuccTx3Distr {
      description "Total number of successful Msg3 counts for third transmission attempt for a preamble SINR bin. Ranges: Bin[0]: [..-15] dB Bin[1]: ]-15..-12] dB Bin[2]: ]-12..-9] dB Bin[3]: ]-9..-6] dB Bin[4]: ]-6..-3] dB Bin[5]: ]-3..] dB.";
      type uint64;
      max-elements 6;
    }
    leaf pmPagReceivedRan {
      description "Number of requests for RAN paging routed to cell. Counter is a subset of NRCellDU.pmPagReceived PM counter. Unit: N/A.";
      type uint64;
      config false;
    }
    leaf pmRrcAccessFailBbIntens {
      description "Number of failed RRC Connection procedures because of connection intensity control. RRC connection procedures can be one of the following options: - RRC Setup Request - RRC Resume Request - RRC Reestablishment Request.";
      type uint64;
      config false;
    }
    leaf pmMacPdcchBlockingPuschOccasionsExclPresched {
      description "Number of scheduling occasions when PDCCH limits number of sessions served by PUSCH, excluding uplink prescheduling scheduling requests. Scheduling occasion is when any number of requests are allocated PDCCH, PDSCH and PUSCH. Unit: N/A.";
      type ietfyang:mac-address;
      config false;
    }
    leaf-list pmMacTempAlarmSCellDistr {
      description "Aggregated number of unique UE temperature alarms when SCells are active. Measured when this cell is used as PSCell. Unit: N/A Ranges: Bin[0]: Unique UE temperature alarms with 0 SCells activated. Bin[1]: Unique UE temperature alarms with 1 SCells activated. Bin[2]: Unique UE temperature alarms with 2 SCells activated. Bin[3]: Unique UE temperature alarms with 3 SCells activated. Bin[4]: Unique UE temperature alarms with 4 SCells activated. Bin[5]: Unique UE temperature alarms with 5 SCells activated. Bin[6]: Unique UE temperature alarms with 6 SCells activated. Bin[7]: Unique UE temperature alarms with 7 SCells activated..";
      type ietfyang:mac-address;
      max-elements 8;
    }
    leaf-list pmMacPucchSrPuschGrantLatDistr {
      description "Distribution of latency between reception of PUCCH scheduling request from UE and grant on PDCCH for transmission on PUSCH for that UE. Unit: N/A Ranges: Bin[0]: [0..0.5[ ms Bin[1]: [0.5..1[ ms Bin[2]: [1..2[ ms Bin[3]: [2..3[ ms Bin[4]: [3..4[ ms Bin[5]: [4..5[ ms Bin[6]: [5..6[ ms Bin[7]: [6..7[ ms Bin[8]: [7..8[ ms Bin[9]: [8..9[ ms Bin[10]: [9..10[ ms Bin[11]: [10..20[ ms Bin[12]: [20..40[ ms Bin[13]: [40..60[ ms Bin[14]: [60..80[ ms Bin[15]: [80..100[ ms Bin[16]: [100..200[ ms Bin[17]: [200..300[ ms Bin[18]: [300..400[ ms Bin[19]: [400..500[ ms Bin[20]: [500..] ms.";
      type ietfyang:mac-address;
      max-elements 21;
    }
    leaf-list pmRadioUeRepCqi64QamLowSeRank2Distr {
      description "Distribution of UE-reported CQI values with low Spectral Efficiency related to rank 2 transmissions when highest modulation order supported in downlink (DL) in NR cell is 64-QAM. CQI values and interpretations correspond to entries in Table 5.2.2.1-4 in 3GPP 38.214 for reporting CQI based on QPSK, 16-QAM, and 64-QAM. Unit: N/A Ranges: Bin[0]: CQI = 0 Bin[1]: CQI = 1 Bin[2]: CQI = 2 Bin[3]: CQI = 3 Bin[4]: CQI = 4 Bin[5]: CQI = 5 Bin[6]: CQI = 6 Bin[7]: CQI = 7 Bin[8]: CQI = 8 Bin[9]: CQI = 9 Bin[10]: CQI = 10 Bin[11]: CQI = 11 Bin[12]: CQI = 12 Bin[13]: CQI = 13 Bin[14]: CQI = 14 Bin[15]: CQI = 15.";
      type uint64;
      max-elements 16;
    }
    leaf-list pmRlcDelayTimeDlQos {
      description "Aggregated RLC delay time for each QoS. For each DRB packet, measures time in milliseconds from packet arrival in gNodeB RLC layer to when last byte of this packet is scheduled and drained from RLC layer for transmission over air. Also PDCP SDU queue time (if any) is included on RAN Compute group 5 and earlier. Unit: milliseconds Compressed: True.";
      type uint64;
      max-elements 256;
    }
    leaf pmMacHarqDlAck64Qam {
      description "Total number of successful downlink HARQ transmissions using 64-QAM modulation. Unit: N/A.";
      type ietfyang:mac-address;
      config false;
    }
    leaf pmMacVolUl {
      description "Aggregated volume of successfully received uplink MAC SDUs for DRB or SRB using cell as PCell, SCell, or PSCell. Unit: byte.";
      type ietfyang:mac-address;
      config false;
    }
    leaf pmRadioBeamSwitchTargetNotAvailable {
      description "Number of times when beam is not available as target for beam switch. Unit: N/A.";
      type uint64;
      config false;
    }
    leaf pmMacHarqUlAck256Qam {
      description "Total number of successful HARQ transmissions with 256-QAM uplink. Unit: N/A.";
      type ietfyang:mac-address;
      config false;
    }
    leaf pmMacHarqUlNackQpsk {
      description "Total number of unsuccessful HARQ transmissions in uplink using QPSK modulation. Unit: N/A.";
      type ietfyang:mac-address;
      config false;
    }
    leaf pmMacVolUlPCellCa {
      description "Aggregated volume of successfully received uplink MAC SDUs for DRB or SRB using cell as PCell. Only includes volume from carrier aggregation UEs using cell as PCell, including uplink carrier aggregation and uplink Tx Switching UEs. Unit: byte.";
      type ietfyang:mac-address;
      config false;
    }
    leaf-list pmPdcchDciSwitchSssg {
      description "Accumulated number of outgoing DCI switches by search space set group for NRCellDU MO. PDF ranges: Bin[0]: Accumulated number of outgoing DCI switches for UEs that are not configured with search space set group switching. Bin[1]: Accumulated number of outgoing DCI switches for UEs configured with search space set group switching. Value of SssgSwitchUeCfg.sssgSwitchPmIdentity attribute must be 1 for UEs configured with a dense search space set group. Bin[2]: Accumulated number of outgoing DCI switches for UEs configured with search space set group switching. Value of SssgSwitchUeCfg.sssgSwitchPmIdentity attribute must be 1 for UEs configured with a sparse search space set group. Bin[3]: Accumulated number of outgoing DCI switches for UEs configured with search space set group switching. Value of SssgSwitchUeCfg.sssgSwitchPmIdentity attribute must be 2 for UEs configured with a dense search space set group. ... Bin[15]: Accumulated number of outgoing DCI switches for UEs configured with search space set group switching. Value of SssgSwitchUeCfg.sssgSwitchPmIdentity attribute must be 8 for UEs configured with a dense search space set group. Bin[16]: Accumulated number of outgoing DCI switches for UEs configured with search space set group switching. Value of SssgSwitchUeCfg.sssgSwitchPmIdentity attribute must be 8 for UEs configured with a sparse search space set group..";
      type uint64;
      max-elements 17;
    }
    leaf-list pmMacRBSymUsedPdcchTypeAAggrLvl16Sssg {
      description "Number of resource block symbols used by PDCCH with aggregation level 16 for scheduling of PDSCH or PUSCH using mapping type A in search space set group. Includes DMRS and PTRS embedded in resources. PDF ranges: Bin[0]: Accumulated downlink resource block symbols that use PDCCH with aggregation level 16 for UEs that are not configured with search space set group switching. Bin[1]: Accumulated downlink resource block symbols that use PDCCH with aggregation level 16 for UEs configured with search space set group switching. Value of SssgSwitchUeCfg.sssgSwitchPmIdentity attribute must be 1 for UEs configured with a dense search space set group. Bin[2]: Accumulated downlink resource block symbols that use PDCCH with aggregation level 16 for UEs configured with search space set group switching. Value of SssgSwitchUeCfg.sssgSwitchPmIdentity attribute must be 1 for UEs configured with a sparse search space set group. Bin[3]: Accumulated downlink resource block symbols that use PDCCH with aggregation level 16 for UEs configured with search space set group switching. Value of SssgSwitchUeCfg.sssgSwitchPmIdentity attribute must be 2 for UEs configured with a dense search space set group. ... Bin[15]: Accumulated downlink resource block symbols that use PDCCH with aggregation level 16 for UEs configured with search space set group switching. Value of SssgSwitchUeCfg.sssgSwitchPmIdentity attribute must be 8 for UEs configured with a dense search space set group. Bin[16]: Accumulated downlink resource block symbols that use PDCCH with aggregation level 16 for UEs configured with search space set group switching. Value of SssgSwitchUeCfg.sssgSwitchPmIdentity attribute must be 8 for UEs configured with a sparse search space set group. Unit: N/A.";
      type ietfyang:mac-address;
      max-elements 17;
    }
    leaf-list pmPdschSchedActivitySssg {
      description "Total duration of slots with downlink PDSCH scheduling activity. PDF ranges: Bin[0]: Total duration of slots with downlink PDSCH scheduling activity for UEs that are not configured with search space set group switching. Bin[1]: Total duration of slots with downlink PDSCH scheduling activity for UEs configured with search space set group switching. Value of SssgSwitchUeCfg.sssgSwitchPmIdentity attribute must be 1 for UEs configured with a dense search space set group. Bin[2]: Total duration of slots with downlink PDSCH scheduling activity for UEs configured with search space set group switching. Value of SssgSwitchUeCfg.sssgSwitchPmIdentity attribute must be 1 for UEs configured with a sparse search space set group. Bin[3]: Total duration of slots with downlink PDSCH scheduling activity for UEs configured with search space set group switching. Value of SssgSwitchUeCfg.sssgSwitchPmIdentity attribute must be 2 for UEs configured with a dense search space set group. ... Bin[15]: Total duration of slots with downlink PDSCH scheduling activity for UEs configured with search space set group switching. Value of SssgSwitchUeCfg.sssgSwitchPmIdentity attribute must be 8 for UEs configured with a dense search space set group. Bin[16]: Total duration of slots with downlink PDSCH scheduling activity for UEs configured with search space set group switching. Value of SssgSwitchUeCfg.sssgSwitchPmIdentity attribute must be 8 for UEs configured with a sparse search space set group. Unit: 125 microseconds.";
      type uint64;
      max-elements 17;
    }
    leaf pmMacRBSymUtilDlMax {
      description "Maximum utilization of downlink resource block symbols in ROP sampled every 1 second. Unit: N/A.";
      type ietfyang:mac-address;
      config false;
    }
    leaf-list pmRadioRecInterferencePwrSpecialSlot3Distr {
      description "Absolute power value of SRS comb offsets in each uplink symbol of special slot 3. The absolute power value is expressed in units of 0.1 dBm. Bins correspond to SRS comb offsets in each uplink symbol. This ensures compatibility between the lengths of uplink symbols in a special slot. To extract average interference power for each bin across a ROP, divide by pmRadioRecInterferencePwrSlotSamp. Number of bins corresponds to maximum six uplink symbols in a special slot and four comb offsets in each uplink symbol. Bins support the following symbol number and comb offset combinations: Bin[0]: First comb offset in last uplink symbol of special slot Bin[1]: Second comb offset in last uplink symbol of special slot Bin[2]: Third comb offset in last uplink symbol of special slot Bin[3]: Fourth comb offset in last uplink symbol of special slot Bin[4]: First comb offset in second uplink symbol from last of special slot Bin[5]: Second comb offset in second uplink symbol from last of special slot .... Bin[22]: Third comb offset in sixth uplink symbol from last of special slot Bin[23]: Fourth comb offset in sixth uplink symbol from last of special slot Note: For TDD UL-DL pattern 'DDSSUUDDDD DDSSUUDDDD', there's no ul symbol in the first and the third S slot. Only the second and the fourth S slot will be pegged. So, only pmRadioRecInterferencePwrSpecialSlot1Distr and pmRadioRecInterferencePwrSpecialSlot2Distr will be used..";
      type uint64;
      max-elements 24;
    }
    leaf-list pmMacSchedSlotUlSCellActivatedDistr {
      description "Aggregated number of scheduled uplink slots when uplink-configured SCells are active. Measured when cell is used as PSCell. Pre-scheduling is not included. Unit: N/A Ranges: Bin[0]: Scheduled uplink slots with 0 SCells activated. Bin[1]: Scheduled uplink slots with 1 SCells activated. Bin[2]: Scheduled uplink slots with 2 SCells activated. Bin[3]: Scheduled uplink slots with 3 SCells activated. Bin[4]: Scheduled uplink slots with 4 SCells activated. Bin[5]: Scheduled uplink slots with 5 SCells activated. Bin[6]: Scheduled uplink slots with 6 SCells activated. Bin[7]: Scheduled uplink slots with 7 SCells activated..";
      type ietfyang:mac-address;
      max-elements 8;
    }
    leaf-list pmMacHarqDlNackQpskInitSlotDistr {
      description "For each downlink slot, bin that corresponds to number of unsuccessful initial HARQ PDSCH transmissions using QPSK modulation in slot is incremented. HARQ transmissions used for BWP DCI switch Scheduling Request (SR) are not pegged. Unit: N/A Ranges: Bin[0]: Total number of unsuccessful initial downlink HARQ transmissions using QPSK on slot 0. Bin[1]: Total number of unsuccessful initial downlink HARQ transmissions using QPSK on slot 1. Bin[2]: Total number of unsuccessful initial downlink HARQ transmissions using QPSK on slot 2. Bin[3]: Total number of unsuccessful initial downlink HARQ transmissions using QPSK on slot 3. Bin[4]: Total number of unsuccessful initial downlink HARQ transmissions using QPSK on slot 4. Bin[5]: Total number of unsuccessful initial downlink HARQ transmissions using QPSK on slot 5. Bin[6]: Total number of unsuccessful initial downlink HARQ transmissions using QPSK on slot 6. Bin[7]: Total number of unsuccessful initial downlink HARQ transmissions using QPSK on slot 7. Bin[8]: Total number of unsuccessful initial downlink HARQ transmissions using QPSK on slot 8. Bin[9]: Total number of unsuccessful initial downlink HARQ transmissions using QPSK on slot 9. Bin[10]: Total number of unsuccessful initial downlink HARQ transmissions using QPSK on slot 10. Bin[11]: Total number of unsuccessful initial downlink HARQ transmissions using QPSK on slot 11. Bin[12]: Total number of unsuccessful initial downlink HARQ transmissions using QPSK on slot 12. Bin[13]: Total number of unsuccessful initial downlink HARQ transmissions using QPSK on slot 13. Bin[14]: Total number of unsuccessful initial downlink HARQ transmissions using QPSK on slot 14. Bin[15]: Total number of unsuccessful initial downlink HARQ transmissions using QPSK on slot 15. Bin[16]: Total number of unsuccessful initial downlink HARQ transmissions using QPSK on slot 16. Bin[17]: Total number of unsuccessful initial downlink HARQ transmissions using QPSK on slot 17. Bin[18]: Total number of unsuccessful initial downlink HARQ transmissions using QPSK on slot 18. Bin[19]: Total number of unsuccessful initial downlink HARQ transmissions using QPSK on slot 19..";
      type ietfyang:mac-address;
      max-elements 20;
    }
    leaf pmCellSleepTimeEnergySaving {
      description "Time cell is disabled due to energy saving mode. NRCellDU.OperationalState is set to disabled and NRCellDU.AvailabilityStatus is set to OFF_DUTY by system Unit: seconds.";
      type uint64;
      config false;
    }
    leaf-list pmMacInitSchedDelayUlMaxQos {
      description "Maximum initial scheduling delay in uplink for each QoS. Unit: 125 microseconds Compressed: True.";
      type ietfyang:mac-address;
      max-elements 256;
    }
    leaf pmMacVolUlUnresUePucchSrGrant {
      description "Data volume in MAC SDUs successfully received in uplink and not restricted by air interface. Sent using one grant given by gNodeB to answer PUCCH scheduling request. Unit: byte.";
      type ietfyang:mac-address;
      config false;
    }
    leaf-list pmMacRBSymUsedPdschAdvMuMimoTxRankDistr {
      description "Distribution of aggregated number of resource block symbols used for PDSCH by sounding antennas and downlink rank as a result of reciprocity-based MU-MIMO. DMRS and PTRS embedded in PDSCH resources are included. Unit: N/A Ranges: Bin[0]: Number of resource block symbols scheduled with 1TX/4RX R1 in MU-MIMO. Bin[1]: Number of resource block symbols scheduled with 1TX/4RX R2 in MU-MIMO. Bin[2]: Number of resource block symbols scheduled with 1TX/4RX R3 in MU-MIMO. Bin[3]: Number of resource block symbols scheduled with 1TX/4RX R4 in MU-MIMO. Bin[4]: Number of resource block symbols scheduled with 2TX/4RX R1 in MU-MIMO. Bin[5]: Number of resource block symbols scheduled with 2TX/4RX R2 in MU-MIMO. Bin[6]: Number of resource block symbols scheduled with 2TX/4RX R3 in MU-MIMO. Bin[7]: Number of resource block symbols scheduled with 2TX/4RX R4 in MU-MIMO. Bin[8]: Number of resource block symbols scheduled with 4TX/4RX R1 in MU-MIMO. Bin[9]: Number of resource block symbols scheduled with 4TX/4RX R2 in MU-MIMO. Bin[10]: Number of resource block symbols scheduled with 4TX/4RX R3 in MU-MIMO. Bin[11]: Number of resource block symbols scheduled with 4TX/4RX R4 in MU-MIMO. Bin[12]: Number of resource block symbols scheduled with 1TX/2RX R1 in MU-MIMO. Bin[13]: Number of resource block symbols scheduled with 1TX/2RX R2 in MU-MIMO. Bin[14]: Number of resource block symbols scheduled with 2TX/2RX R1 in MU-MIMO. Bin[15]: Number of resource block symbols scheduled with 2TX/2RX R2 in MU-MIMO. Bin[16]: Number of resource block symbols scheduled with 1TX/1RX R1..";
      type ietfyang:mac-address;
      max-elements 17;
    }
    leaf pmMacRBSymUtilUlMax {
      description "Maximum utilization of uplink resource block symbols in ROP sampled every 1 second. Unit: N/A.";
      type ietfyang:mac-address;
      config false;
    }
    leaf-list pmMacRBSymPowerBackoffDistr {
      description "Represents mapping of all resource block symbols for UEs that were included in backoff calculations for appropriate backoff ranges. Unit: N/A Ranges: Bin[0]: 0 resource block symbol Bin[1]: 1 resource block symbol Bin[2]: 2 resource block symbol Bin[3]: 3 resource block symbol Bin[4]: 4 resource block symbol Bin[5]: 5 resource block symbol Bin[6]: 6 resource block symbol Bin[7]: 7 resource block symbol Bin[8]: 8 resource block symbol Bin[9]: 9 resource block symbol.";
      type ietfyang:mac-address;
      max-elements 10;
    }
    leaf pmMacHarqUlDtx16QamInit {
      description "Number of DTX detections for initial HARQ transmissions in uplink using 16-QAM modulation. Initial transmission is first transmission on HARQ process, where NDI bit in DCI message is toggled. Unit: N/A.";
      type ietfyang:mac-address;
      config false;
    }
    leaf-list pmRadioRaSuccTaRelDistr {
      description "Distribution of measured timing advance (TA) values at successful random access. TA values are expressed as a percentage of TAs that correspond to configured cell range. Unit: N/A Ranges: Bin[0]: [0..4] % Bin[1]: [5..9] % Bin[2]: [10..14] % Bin[3]: [15..19] % Bin[4]: [20..24] % Bin[5]: [25..29] % Bin[6]: [30..34] % Bin[7]: [35..39] % Bin[8]: [40..44] % Bin[9]: [45..49] % Bin[10]: [50..54] % Bin[11]: [55..59] % Bin[12]: [60..64] % Bin[13]: [65..69] % Bin[14]: [70..74] % Bin[15]: [75..79] % Bin[16]: [80..84] % Bin[17]: [85..89] % Bin[18]: [90..94] % Bin[19]: [95..99] % Bin[20]: [100..104] % Bin[21]: [105..109] % Bin[22]: [110..] %.";
      type uint64;
      max-elements 23;
    }
    leaf-list pmRadioPdschTable2MbsfnMcsDistr {
      description "Distribution of MCS used for PDSCH transmissions in MBSFN subframes where MCS index table 2 is applied, and UE instances are enabled with up to 256-QAM. For more information, see 3GPP TS 38.214, Table 5.1.3.1-2. Each bin represents a specific MCS. Unit: N/A Ranges: Bin[0]: MCS = 0 Bin[1]: MCS = 1 Bin[2]: MCS = 2 Bin[3]: MCS = 3 Bin[4]: MCS = 4 Bin[5]: MCS = 5 Bin[6]: MCS = 6 Bin[7]: MCS = 7 Bin[8]: MCS = 8 Bin[9]: MCS = 9 Bin[10]: MCS = 10 Bin[11]: MCS = 11 Bin[12]: MCS = 12 Bin[13]: MCS = 13 Bin[14]: MCS = 14 Bin[15]: MCS = 15 Bin[16]: MCS = 16 Bin[17]: MCS = 17 Bin[18]: MCS = 18 Bin[19]: MCS = 19 Bin[20]: MCS = 20 Bin[21]: MCS = 21 Bin[22]: MCS = 22 Bin[23]: MCS = 23 Bin[24]: MCS = 24 Bin[25]: MCS = 25 Bin[26]: MCS = 26 Bin[27]: MCS = 27 Bin[28]: MCS = 28 Bin[29]: MCS = 29 Bin[30]: MCS = 30 Bin[31]: MCS = 31.";
      type uint64;
      max-elements 32;
    }
    leaf pmMacRBSymUsedPdcchTypeAAggrLvl1 {
      description "Number of resource block symbols used by PDCCH with aggregation level 1 for scheduling of PDSCH or PUSCH using mapping type A. This includes DMRS and PTRS embedded in resources. Unit: N/A.";
      type ietfyang:mac-address;
      config false;
    }
    leaf-list pmMacLatTimeDlNoDrxSyncSampQos {
      description "Aggregated number of samples for downlink MAC latency measurements for each QoS without DRX and out-of-sync impact. DL MAC latency measures MAC scheduling latency between reception of packet in empty DL buffer and transmission of first packet. Unit: N/A Compressed: True.";
      type ietfyang:mac-address;
      max-elements 256;
    }
    leaf-list pmMacRBSymUsedPuschMimoUserDistr {
      description "Distribution of aggregated number of resource block symbols used for PUSCH by different number of users as a result of SU-MIMO or MU-MIMO. DMRS and PTRS embedded in PUSCH resources are included. Unit: N/A Ranges: Bin[0]: Number of resource block symbols scheduled with 1 user. Bin[1]: Number of resource block symbols scheduled with 2 users. Bin[2]: Number of resource block symbols scheduled with 3 users. Bin[3]: Number of resource block symbols scheduled with 4 users. Bin[4]: Number of resource block symbols scheduled with 5 users. Bin[5]: Number of resource block symbols scheduled with 6 users. Bin[6]: Number of resource block symbols scheduled with 7 users. Bin[7]: Number of resource block symbols scheduled with 8 users..";
      type ietfyang:mac-address;
      max-elements 8;
    }
    leaf-list pmMacRBSymUsedPdcchTypeADciSwitchSssg {
      description "Aggregated number of resource block symbols used by PDCCH for scheduling of PDSCH or PUSCH using mapping type A in search space set group for DCI switches. Includes DMRS and PTRS embedded in resources. PDF ranges: Bin[0]: Aggregated number of resource block symbols used by PDCCH for scheduling of PDSCH or PUSCH using mapping type A for DCI switches for UEs that are not configured with search space set group switching. Bin[1]: Aggregated number of resource block symbols used by PDCCH for scheduling of PDSCH or PUSCH using mapping type A for DCI switches for UEs configured with search space set group switching. Value of SssgSwitchUeCfg.sssgSwitchPmIdentity attribute must be 1 for UEs configured with a dense search space set group. Bin[2]: Aggregated number of resource block symbols used by PDCCH for scheduling of PDSCH or PUSCH using mapping type A for DCI switches for UEs configured with search space set group switching. Value of SssgSwitchUeCfg.sssgSwitchPmIdentity attribute must be 1 for UEs configured with a sparse search space set group. Bin[3]: Aggregated number of resource block symbols used by PDCCH for scheduling of PDSCH or PUSCH using mapping type A for DCI switches for UEs configured with search space set group switching. Value of SssgSwitchUeCfg.sssgSwitchPmIdentity attribute must be 2 for UEs configured with a dense search space set group. ... Bin[15]: Aggregated number of resource block symbols used by PDCCH for scheduling of PDSCH or PUSCH using mapping type A for DCI switches for UEs configured with search space set group switching. Value of SssgSwitchUeCfg.sssgSwitchPmIdentity attribute must be 8 for UEs configured with a dense search space set group. Bin[16]: Aggregated number of resource block symbols used by PDCCH for scheduling of PDSCH or PUSCH using mapping type A for DCI switches for UEs configured with search space set group switching. Value of SssgSwitchUeCfg.sssgSwitchPmIdentity attribute must be 8 for UEs configured with a sparse search space set group. Unit: N/A.";
      type ietfyang:mac-address;
      max-elements 17;
    }
    leaf pmMacHarqDlAckQpskInit {
      description "Total number of successful initial downlink HARQ transmissions using QPSK modulation. Initial transmission is first transmission on HARQ process. Unit: N/A.";
      type ietfyang:mac-address;
      config false;
    }
    leaf pmRadioBeamSwitchSuccMacCe {
      description "Number of successful wide beam switch commands. Beam switch command is sent to UE in MAC Control Element. Measured when this cell is used as PSCell. Unit: N/A.";
      type ietfyang:mac-address;
      config false;
    }
    leaf-list pmMacServingDelayUlUeDistr {
      description "The delay between consecutive occurrences of following events: - Uplink grant for data transmission - PUCCH scheduling request received from UE is 0 Unit: N/A Ranges: Bin[0]: [0..1] ms Bin[1]: ]1..2] ms Bin[2]: ]2..5] ms Bin[3]: ]5..10] ms Bin[4]: ]10..20] ms Bin[5]: ]20..40] ms Bin[6]: ]40..80] ms Bin[7]: ]80..160] ms Bin[8]: ]160..320] ms Bin[9]: ]320..] ms.";
      type ietfyang:mac-address;
      max-elements 10;
    }
    leaf pmMacHarqDlNackQpskInit {
      description "Total number of unsuccessful initial downlink HARQ transmissions using QPSK modulation. Initial transmission is first transmission on HARQ process. Unit: N/A.";
      type ietfyang:mac-address;
      config false;
    }
    leaf-list pmRadioUeRepPmiPrimaryCsiRsRank3Distr {
      description "Distribution of precoding weights reported by UE for rank 3 codebook associated with primary CSI-RS. Indicates spatial distribution of UEs using cell as PCell. Type 1 single-panel codebooks are defined in 3GPP TS 38.214. Represents distribution of requested departure angles from AAS-capable radio unit as estimated from UE CSI feedback, specifically main and diversity direction of PMI values. It is not recommended to use this PM counter for Remote radio units. For more information, see Massive MIMO Mid-Band and Manage Massive MIMO NR in CPI library. Unit: N/A Compressed: True.";
      type uint64;
      max-elements 256;
    }
    leaf pmMacVolDlDrbSingleSlotShortBurst {
      description "Aggregated volume of downlink MAC SDUs for single slot short burst cases that are transmitted for HARQ initial transmission for each DRB. Single slot short burst case is when new packet arrives to empty buffer and buffer is drained by single scheduling occasion on each active component carrier. HARQ retransmission is excluded. Unit: bytes.";
      type ietfyang:mac-address;
      config false;
    }
    leaf pmUeCtxtRelAbnormalGnbDuPnr {
      description "Total number of abnormal UE context releases triggered by gNodeB-DU because of partial node restart, that is, NR baseband reset. Unit: N/A.";
      type uint64;
      config false;
    }
    leaf-list pmRadioPdschTable1McsDistr {
      description "Distribution of MCS used for PDSCH transmissions where MCS index table 1 is applied and UE instances are enabled with up to 64-QAM. For more information, see 3GPP TS 38.214, Table 5.1.3.1-1. Each bin represents a specific MCS. Unit: N/A Ranges: Bin[0]: MCS = 0 Bin[1]: MCS = 1 Bin[2]: MCS = 2 Bin[3]: MCS = 3 Bin[4]: MCS = 4 Bin[5]: MCS = 5 Bin[6]: MCS = 6 Bin[7]: MCS = 7 Bin[8]: MCS = 8 Bin[9]: MCS = 9 Bin[10]: MCS = 10 Bin[11]: MCS = 11 Bin[12]: MCS = 12 Bin[13]: MCS = 13 Bin[14]: MCS = 14 Bin[15]: MCS = 15 Bin[16]: MCS = 16 Bin[17]: MCS = 17 Bin[18]: MCS = 18 Bin[19]: MCS = 19 Bin[20]: MCS = 20 Bin[21]: MCS = 21 Bin[22]: MCS = 22 Bin[23]: MCS = 23 Bin[24]: MCS = 24 Bin[25]: MCS = 25 Bin[26]: MCS = 26 Bin[27]: MCS = 27 Bin[28]: MCS = 28 Bin[29]: MCS = 29 Bin[30]: MCS = 30 Bin[31]: MCS = 31.";
      type uint64;
      max-elements 32;
    }
    leaf-list pmRadioRecInterferencePwrUlSlot3Distr {
      description "Absolute power for each symbol in uplink slot 3 in one radio frame. Bins correspond to uplink symbol 2 and uplink symbol 11 respectively. To get average interference power for each bin across a Result Output Period (ROP), divide by NRCellDU.pmRadioRecInterferencePwrSlotSamp. Unit: 0.1 dBm/PRB.";
      type uint64;
      max-elements 2;
    }
    leaf pmMacHarqDlFail {
      description "Number of complete downlink HARQ failures. When HARQ transmission reaches maximum number of retransmissions, it is not retransmitted again and is regarded as scheduling activity complete HARQ failure. Unit: N/A.";
      type ietfyang:mac-address;
      config false;
    }
    leaf-list pmRadioUeRepPmiPrimaryCsiRsRank1Distr {
      description "Distribution of precoding weights reported by UE for rank 1 codebook associated with primary CSI-RS. Indicates spatial distribution of UEs using cell as PCell. Type 1 single-panel codebooks are defined in 3GPP TS 38.214. Represents distribution of requested departure angles from AAS-capable radio unit as estimated from UE CSI feedback, specifically main and diversity direction of PMI values. It is not recommended to use this PM counter for Remote radio units. For more information, see Massive MIMO Mid-Band and Manage Massive MIMO NR in CPI library. Unit: N/A Compressed: True.";
      type uint64;
      max-elements 256;
    }
    leaf-list pmMacVolUlSssg {
      description "Aggregated volume of successfully received uplink MAC SDUs for DRB or SRB using cell as PCell or PSCell. PDF ranges: Bin[0]: Aggregated volume of successfully received uplink MAC SDUs for UEs that are not configured with search space set group switching. Bin[1]: Aggregated volume of successfully received uplink MAC SDUs for UEs configured with search space set group switching. Value of SssgSwitchUeCfg.sssgSwitchPmIdentity attribute must be 1 for UEs configured with a dense search space set group. Bin[2]: Aggregated volume of successfully received uplink MAC SDUs for UEs configured with search space set group switching. Value of SssgSwitchUeCfg.sssgSwitchPmIdentity attribute must be 1 for UEs configured with a sparse search space set group. Bin[3]: Aggregated volume of successfully received uplink MAC SDUs for UEs configured with search space set group switching. Value of SssgSwitchUeCfg.sssgSwitchPmIdentity attribute must be 2 for UEs configured with a dense search space set group. ... Bin[15]: Aggregated volume of successfully received uplink MAC SDUs for UEs configured with search space set group switching. Value of SssgSwitchUeCfg.sssgSwitchPmIdentity attribute must be 8 for UEs configured with a dense search space set group. Bin[16]: Aggregated volume of successfully received uplink MAC SDUs for UEs configured with search space set group switching. Value of SssgSwitchUeCfg.sssgSwitchPmIdentity attribute must be 8 for UEs configured with a sparse search space set group. Unit: 100 bytes.";
      type ietfyang:mac-address;
      max-elements 17;
    }
    leaf-list pmMacRBSymReservedPdcchCapacityBoostOfdmSymDistr {
      description "Distribution of aggregated number of resource block symbols reserved for PDCCH Capacity Boost feature. Ranges Bin[0]: Accumulated downlink resource block symbols reserved by PDCCH Capacity Boost feature on OFDM symbol 0. Bin[1]: Accumulated downlink resource block symbols reserved by PDCCH Capacity Boost feature on OFDM symbol 1. ... Bin[12]: Accumulated downlink resource block symbols reserved by PDCCH Capacity Boost feature on OFDM symbol 12. Bin[13]: Accumulated downlink resource block symbols reserved by PDCCH Capacity Boost feature on OFDM symbol 13. Unit: N/A.";
      type ietfyang:mac-address;
      max-elements 14;
    }
    leaf-list pmPuschSchedEntityDistr {
      description "For each uplink slot, bin that corresponds to number of PUSCH scheduled entities is incremented. Includes Msg3 but excludes prescheduling. For High-Band, only uplink-capable cells, where value of NRSectorCarrier.txDirection attribute is DL_AND_UL, are incremented. Unit: N/A Ranges: Bin[0]: Zero PUSCH scheduled entities in uplink slot. Bin[1]: One PUSCH scheduled entity in uplink slot. Bin[2]: Two PUSCH scheduled entities in uplink slot. Bin[3]: Three PUSCH scheduled entities in uplink slot. Bin[4]: Four PUSCH scheduled entities in uplink slot. Bin[5]: Five PUSCH scheduled entities in uplink slot. Bin[6]: Six PUSCH scheduled entities in uplink slot. Bin[7]: Seven PUSCH scheduled entities in uplink slot. Bin[8]: Eight PUSCH scheduled entities in uplink slot. Bin[9]: Nine PUSCH scheduled entities in uplink slot. Bin[10]: 10 PUSCH scheduled entities in uplink slot. Bin[11]: 11 PUSCH scheduled entities in uplink slot. Bin[12]: 12 PUSCH scheduled entities in uplink slot. Bin[13]: 13 PUSCH scheduled entities in uplink slot. Bin[14]: 14 PUSCH scheduled entities in uplink slot. Bin[15]: 15 PUSCH scheduled entities in uplink slot. Bin[16]: 16 PUSCH scheduled entities in uplink slot. Bin[17]: 17 PUSCH scheduled entities in uplink slot. Bin[18]: 18 PUSCH scheduled entities in uplink slot. Bin[19]: 19 PUSCH scheduled entities in uplink slot. Bin[20]: 20 PUSCH scheduled entities in uplink slot. Bin[21]: 21 PUSCH scheduled entities in uplink slot. Bin[22]: 22 PUSCH scheduled entities in uplink slot. Bin[23]: 23 PUSCH scheduled entities in uplink slot. Bin[24]: 24 PUSCH scheduled entities in uplink slot. Bin[25]: 25 PUSCH scheduled entities in uplink slot. Bin[26]: 26 PUSCH scheduled entities in uplink slot. Bin[27]: 27 PUSCH scheduled entities in uplink slot. Bin[28]: 28 PUSCH scheduled entities in uplink slot. Bin[29]: 29 PUSCH scheduled entities in uplink slot. Bin[30]: 30 PUSCH scheduled entities in uplink slot. Bin[31]: 31 PUSCH scheduled entities in uplink slot. Bin[32]: 32 PUSCH scheduled entities in uplink slot. Bin[33]: 33 PUSCH scheduled entities in uplink slot. Bin[34]: 34 PUSCH scheduled entities in uplink slot. Bin[35]: 35 PUSCH scheduled entities in uplink slot. Bin[36]: 36 PUSCH scheduled entities in uplink slot..";
      type uint64;
      max-elements 37;
    }
    leaf pmPduSessionEstabFailAdmissionRej {
      description "Number of PDU Session establishments rejected by Service Admission Control feature. PDU Session is rejected because of limit configured in SessionLimit.maxNoOfSessions attribute. For more information, check Feature Description for Service Admission Control feature..";
      type uint64;
      config false;
    }
    leaf pmMacVolUlResCaUe {
      description "Data volume in MAC SDUs successfully received in uplink as part of a carrier aggregation burst while being restricted by air interface, excluding data volume received in last slot in burst. Unit: byte.";
      type ietfyang:mac-address;
      config false;
    }
    leaf-list pmMeasGapUeMnSumDistr {
      description "Sum of active UEs that have measurement gap configured by MN which impacts SN during dual connectivity. Sample is taken every 5 seconds. Unit: N/A Ranges: Bin[0]: Gap pattern 0 Bin[1]: Gap pattern 1 Bin[2]: Gap pattern 2 Bin[3]: Gap pattern 3 Bin[4]: Not used Bin[5]: Not used Bin[6]: Not used Bin[7]: Not used Bin[8]: Not used Bin[9]: Not used Bin[10]: Not used Bin[11]: Not used Bin[12]: Not used Bin[13]: Not used Bin[14]: Gap pattern 14 Bin[15]: Not used Bin[16]: Not used Bin[17]: Not used Bin[18]: Not used Bin[19]: Not used Bin[20]: Not used Bin[21]: Not used Bin[22]: Not used Bin[23]: Not used Compressed: True.";
      type uint64;
      max-elements 24;
    }
    leaf pmActiveUeUlTrueSamp {
      description "Number of times corresponding pmActiveUeUlSum counter is updated, regardless if there are any active UEs, that is, once every slot. Unit: N/A.";
      type uint64;
      config false;
    }
    leaf pmMacRBSymUsedPdcchTypeBAggrLvl16 {
      description "Number of resource block symbols used by PDCCH with aggregation level 16 for scheduling of PDSCH or PUSCH using mapping type B. This includes DMRS and PTRS embedded in resources scheduling. Unit: N/A.";
      type ietfyang:mac-address;
      config false;
    }
    leaf pmActiveUeDlMax {
      description "Peak number of active UE instances that have DRB data in UE dedicated downlink buffer. Value is maximum of a set of samples, where following conditions apply: . Throughout measurement period, each sample is an average of active UE instances. Rounding method can cause counter to show one less than the real number of UE instances. . Sample is taken every second. Unit: N/A.";
      type int64;
      config false;
    }
    leaf-list pmRimPdschAction2LastDlSlotDistr {
      description "Histogram of applied RIM mitigation actions on PDSCH transmissions. Considers mitigation actions taken in second downlink slot before special slot. Unit: N/A Ranges: Bin[0]: UE not scheduled due to blanking Bin[1]: UE not scheduled due to low load Bin[2]: UE not scheduled due to low SINR Bin[3]: UE is backed off with low power value Bin[4]: UE is backed off with high power value.";
      type uint64;
      max-elements 5;
    }
    leaf-list pmMacSchedSlotUlCellSchedDistr {
      description "Aggregated number of scheduled uplink slots when uplink-configured cells are scheduled. Measured when cell is used as PSCell. Pre-scheduling is not included. Unit: N/A Ranges: Bin[0]: Scheduled uplink slots with 1 cell scheduled. Bin[1]: Scheduled uplink slots with 2 cells scheduled. Bin[2]: Scheduled uplink slots with 3 cells scheduled. Bin[3]: Scheduled uplink slots with 4 cells scheduled. Bin[4]: Scheduled uplink slots with 5 cells scheduled. Bin[5]: Scheduled uplink slots with 6 cells scheduled. Bin[6]: Scheduled uplink slots with 7 cells scheduled. Bin[7]: Scheduled uplink slots with 8 cells scheduled..";
      type ietfyang:mac-address;
      max-elements 8;
    }
    leaf-list pmRadioSinrPdschDistr {
      description "Distribution of SINR values calculated for PDSCH transmissions. Unit: N/A Ranges: Bin[0]: [..-5] dB Bin[1]: ]-5..-2] dB Bin[2]: ]-2..1] dB Bin[3]: ]1..4] dB Bin[4]: ]4..7] dB Bin[5]: ]7..10] dB Bin[6]: ]10..13] dB Bin[7]: ]13..16] dB Bin[8]: ]16..19] dB Bin[9]: ]19..22] dB Bin[10]: ]22..25] dB Bin[11]: ]25..] dB.";
      type uint64;
      max-elements 12;
    }
    leaf pmMacRBSymUsedPdcchTypeAAggrLvl2 {
      description "Number of resource block symbols used by PDCCH with aggregation level 2 for scheduling of PDSCH or PUSCH using mapping type A. This includes DMRS and PTRS embedded in resources. Unit: N/A.";
      type ietfyang:mac-address;
      config false;
    }
    leaf pmMacHarqUlAckQpsk {
      description "Total number of successful HARQ transmissions in uplink using QPSK modulation. Unit: N/A.";
      type ietfyang:mac-address;
      config false;
    }
    leaf pmMacTimeUlResCaUe {
      description "Transfer time of restricted uplink data volume of carrier aggregation burst records. Unit: 125 microseconds.";
      type ietfyang:mac-address;
      config false;
    }
    leaf pmMacRBSymUsedPdschAilg {
      description "Total number of resource blocks symbols generated by artificial load generator for PDSCH for artificial load. Unit: N/A.";
      type ietfyang:mac-address;
      config false;
    }
    leaf-list pmMacRBSymUtilUlDistr {
      description "Distribution of utilization for uplink resource block symbols averaged over 1 second. Unit: N/A Ranges: Bin[0]: [0..5] % Bin[1]: [6..10] % Bin[2]: [11..15] % Bin[3]: [16..20] % Bin[4]: [21..25] % Bin[5]: [26..30] % Bin[6]: [31..35] % Bin[7]: [36..40] % Bin[8]: [41..45] % Bin[9]: [46..50] % Bin[10]: [51..55] % Bin[11]: [56..60] % Bin[12]: [61..65] % Bin[13]: [66..70] % Bin[14]: [71..75] % Bin[15]: [76..80] % Bin[16]: [81..85] % Bin[17]: [86..90] % Bin[18]: [91..95] % Bin[19]: [96..100] %.";
      type ietfyang:mac-address;
      max-elements 20;
    }
    leaf pmRadioPdschEmptySlotsForced {
      description "Number of PDSCH slots (shown by NRCellDU.pmRadioPdschEmptySlots PM counter) forced to be empty to fulfill maximum PDSCH use ratio set by radio units of cell. Unit: N/A.";
      type uint64;
      config false;
    }
    leaf pmMacHarqUlNack64QamInit {
      description "Total number of unsuccessful initial HARQ transmissions in uplink using 64-QAM modulation. Initial transmission is first transmission on HARQ process, where NDI bit in DCI message is toggled. Unit: N/A.";
      type ietfyang:mac-address;
      config false;
    }
    leaf-list pmMacPdcchCongestionDlDistr {
      description "Distribution of downlink PDCCH congestion rate averaged over one second. Ranges Bin[0]: [0..5] % Bin[1]: [6..10] % Bin[2]: [11..15] % Bin[3]: [16..20] % Bin[4]: [21..25] % Bin[5]: [26..30] % Bin[6]: [31..35] % Bin[7]: [36..40] % Bin[8]: [41..45] % Bin[9]: [46..50] % Bin[10]: [51..55] % Bin[11]: [56..60] % Bin[12]: [61..65] % Bin[13]: [66..70] % Bin[14]: [71..75] % Bin[15]: [76..80] % Bin[16]: [81..85] % Bin[17]: [86..90] % Bin[18]: [91..95] % Bin[19]: [96..100] % Unit: N/A.";
      type ietfyang:mac-address;
      max-elements 20;
    }
    leaf pmMacHarqDlResAllocType1Dci11 {
      description "Aggregated number of HARQ transmissions and retransmissions scheduled with resource allocation Type 1 with DCI format 1_1. Unit: N/A.";
      type ietfyang:mac-address;
      config false;
    }
    leaf-list pmMacRBSymUsedPdschAdvMuMimoLayersDistr {
      description "Distribution of aggregated number of resource block symbols used for PDSCH by different number of co-scheduled layers as a result of reciprocity-based MU-MIMO. DMRS and PTRS embedded in PDSCH resources are included. Unit: N/A Ranges: Bin[0]: Reserved - Not Used. Bin[1]: Number of resource block symbols scheduled with 2 layers. Bin[2]: Number of resource block symbols scheduled with 3 layers. Bin[3]: Number of resource block symbols scheduled with 4 layers. Bin[4]: Number of resource block symbols scheduled with 5 layers. Bin[5]: Number of resource block symbols scheduled with 6 layers. Bin[6]: Number of resource block symbols scheduled with 7 layers. Bin[7]: Number of resource block symbols scheduled with 8 layers. Bin[8]: Number of resource block symbols scheduled with 9 layers. Bin[9]: Number of resource block symbols scheduled with 10 layers. Bin[10]: Number of resource block symbols scheduled with 11 layers. Bin[11]: Number of resource block symbols scheduled with 12 layers. Bin[12]: Number of resource block symbols scheduled with 13 layers. Bin[13]: Number of resource block symbols scheduled with 14 layers. Bin[14]: Number of resource block symbols scheduled with 15 layers. Bin[15]: Number of resource block symbols scheduled with 16 layers..";
      type ietfyang:mac-address;
      max-elements 16;
    }
    leaf pmMacHarqDlAck16QamInit {
      description "Total number of successful initial downlink HARQ transmissions using 16-QAM modulation. Initial transmission is first transmission on HARQ process. Unit: N/A.";
      type ietfyang:mac-address;
      config false;
    }
    leaf-list pmMacRBSymUsedPdschAdvEisSuMimoLayerDistr {
      description "Distribution of aggregated number of resource block symbols used for PDSCH by different number of coscheduled layers as a result of reciprocity-based Ericsson Interference Sensing (EIS) SU-MIMO. DMRS and PTRS embedded in PDSCH resources are included. Unit: N/A Ranges: Bin[0]: Number of resource block symbols scheduled with 1 layer. Bin[1]: Number of resource block symbols scheduled with 2 layers. Bin[2]: Number of resource block symbols scheduled with 3 layers. Bin[3]: Number of resource block symbols scheduled with 4 layers. Bin[4]: Number of resource block symbols scheduled with 5 layers. Bin[5]: Number of resource block symbols scheduled with 6 layers. Bin[6]: Number of resource block symbols scheduled with 7 layers. Bin[7]: Number of resource block symbols scheduled with 8 layers..";
      type ietfyang:mac-address;
      max-elements 8;
    }
    leaf pmMacTimeUlResUe {
      description "Transfer time of restricted uplink data volume. Unit: 125 microseconds.";
      type ietfyang:mac-address;
      config false;
    }
    leaf pmRadioMacSrPeriodicitySwitchLimitedCoverage {
      description "Indicates number of scheduling request on PUCCH periodicity reconfigurations to longer duration. Unit: N/A.";
      type ietfyang:mac-address;
      config false;
    }
    leaf-list pmRadioUeRepCqi256QamRank1Distr {
      description "Distribution of UE-reported CQI values related to rank 1 transmissions when highest modulation order supported in downlink (DL) in NR cell is configured to be 256-QAM. CQI values and interpretations correspond to entries in Table 5.2.2.1-3 in 3GPP 38.214 for reporting CQI based on QPSK, 16-QAM, 64-QAM, and 256-QAM. Unit: N/A Ranges: Bin[0]: CQI = 0 Bin[1]: CQI = 1 Bin[2]: CQI = 2 Bin[3]: CQI = 3 Bin[4]: CQI = 4 Bin[5]: CQI = 5 Bin[6]: CQI = 6 Bin[7]: CQI = 7 Bin[8]: CQI = 8 Bin[9]: CQI = 9 Bin[10]: CQI = 10 Bin[11]: CQI = 11 Bin[12]: CQI = 12 Bin[13]: CQI = 13 Bin[14]: CQI = 14 Bin[15]: CQI = 15.";
      type uint64;
      max-elements 16;
    }
    leaf pmMacRBSymPucchSchedPusch {
      description "Number of resource block symbols in uplink slots where PSCell is configured for PUCCH but the symbols are used for scheduling on PUSCH. Unit: N/A.";
      type ietfyang:mac-address;
      config false;
    }
    leaf-list pmMacRBSymUsedPdcchTypeAAggrLvl2Bwp {
      description "Number of resource block symbols used by PDCCH with aggregation level 2 for scheduling of PDSCH or PUSCH using mapping type A in BWP. This includes DMRS and PTRS embedded in resources. PDF ranges: Bin[0]: Accumulated downlink resource block symbols used by PDCCH with aggregation level 2 in the first BWP referenced in NRCellDU MO by BWPSet.allBWPRegularRef attribute Bin[1]: Accumulated downlink resource block symbols used by PDCCH with aggregation level 2 in the second BWP referenced in NRCellDU MO by BWPSet.allBWPRegularRef attribute Bin[2]: Accumulated downlink resource block symbols used by PDCCH with aggregation level 2 in the third BWP referenced in NRCellDU MO by BWPSet.allBWPRegularRef attribute ... Bin[15]: Accumulated downlink resource block symbols used by PDCCH with aggregation level 2 in the sixteenth BWP referenced in NRCellDU MO by BWPSet.allBWPRegularRef attribute Unit: N/A.";
      type ietfyang:mac-address;
      max-elements 16;
    }
    leaf-list pmPuschSchedActivitySssg {
      description "Total duration of slots where at least one MAC SDU is received on PUSCH. PDF ranges: Bin[0]: Duration of slots where at least one MAC SDU is received on PUSCH for UEs that are not configured with search space set group switching. Bin[1]: Duration of slots where at least one MAC SDU is received on PUSCH for UEs configured with search space set group switching. Value of SssgSwitchUeCfg.sssgSwitchPmIdentity attribute must be 1 for UEs configured with a dense search space set group. Bin[2]: Duration of slots where at least one MAC SDU is received on PUSCH for UEs configured with search space set group switching. Value of SssgSwitchUeCfg.sssgSwitchPmIdentity attribute must be 1 for UEs configured with a sparse search space set group. Bin[3]: Duration of slots where at least one MAC SDU is received on PUSCH for UEs configured with search space set group switching. Value of SssgSwitchUeCfg.sssgSwitchPmIdentity attribute must be 2 for UEs configured with a dense search space set group. ... Bin[15]: Duration of slots where at least one MAC SDU is received on PUSCH for UEs configured with search space set group switching. Value of SssgSwitchUeCfg.sssgSwitchPmIdentity attribute must be 8 for UEs configured with a dense search space set group. Bin[16]: Duration of slots where at least one MAC SDU is received on PUSCH for UEs configured with search space set group switching. Value of SssgSwitchUeCfg.sssgSwitchPmIdentity attribute must be 8 for UEs configured with a sparse search space set group. Unit: 125 microseconds.";
      type uint64;
      max-elements 17;
    }
    leaf pmRadioMacTransUl1LayerSinrDelta {
      description "Total number of single-layer uplink transmissions due to high difference in SINR between two layers. Unit: N/A.";
      type ietfyang:mac-address;
      config false;
    }
    leaf-list pmMacContentionDelayUlDistr {
      description "Distribution of MAC contention delay in uplink data bursts when volume is restricted by air interface. Unit: N/A Ranges: Bin[0]: [ 0..125[ us Bin[1]: [125..250[ us Bin[2]: [250..375[ us Bin[3]: [375..500[ us Bin[4]: [500..625[ us Bin[5]: [625..750[ us Bin[6]: [750..875[ us Bin[7]: [875..1000[ us Bin[8]: [1000..1125[ us Bin[9]: [1125..1250[ us Bin[10]: [1250..1375[ us Bin[11]: [1375..1500[ us Bin[12]: [1500..1625[ us Bin[13]: [1625..1750[ us Bin[14]: [1750..1875[ us Bin[15]: [1875..2000[ us Bin[16]: [2000..3000[ us Bin[17]: [3000..4000[ us Bin[18]: [4000..5000[ us Bin[19]: [5000..10000[ us Bin[20]: [10000..] us.";
      type ietfyang:mac-address;
      max-elements 21;
    }
    leaf-list pmMacRBSymUtilDlDistr {
      description "Distribution of utilization for downlink resource block symbols averaged over 1 second. Unit: N/A Ranges: Bin[0]: [0..5] % Bin[1]: [6..10] % Bin[2]: [11..15] % Bin[3]: [16..20] % Bin[4]: [21..25] % Bin[5]: [26..30] % Bin[6]: [31..35] % Bin[7]: [36..40] % Bin[8]: [41..45] % Bin[9]: [46..50] % Bin[10]: [51..55] % Bin[11]: [56..60] % Bin[12]: [61..65] % Bin[13]: [66..70] % Bin[14]: [71..75] % Bin[15]: [76..80] % Bin[16]: [81..85] % Bin[17]: [86..90] % Bin[18]: [91..95] % Bin[19]: [96..100] %.";
      type ietfyang:mac-address;
      max-elements 20;
    }
    leaf pmMacHarqUlNack16QamInit {
      description "Total number of unsuccessful initial HARQ transmissions in uplink using 16-QAM modulation. Initial transmission is first transmission on HARQ process, where NDI bit in DCI message is toggled. Unit: N/A.";
      type ietfyang:mac-address;
      config false;
    }
    leaf-list pmRadioRaAttTaDistr {
      description "Distribution of measured Timing Advance (TA) values from all detected random access attempts. TA values are expressed as percentage of maximum possible TA value in cell. Unit: N/A Ranges: Bin[0]: [0..9] % Bin[1]: [10..19] % Bin[2]: [20..29] % Bin[3]: [30..39] % Bin[4]: [40..49] % Bin[5]: [50..59] % Bin[6]: [60..69] % Bin[7]: [70..79] % Bin[8]: [80..89] % Bin[9]: [90..99] % Bin[10]: [100..109] % Bin[11]: [110..] %.";
      type uint64;
      max-elements 12;
    }
    leaf pmRadioRaCbFailMsg1Ooc {
      description "Number of CBRA preambles discarded because timing offset corresponds to a greater distance than the configured cell range. Unit: messages.";
      type uint64;
      config false;
    }
    leaf pmRadioSrsResUsedAntSwitching {
      description "Accumulates number of SRS resources used for SRS antenna switching from every SRS slot. Each SRS resource is a combination of symbol, comb, and cyclic shift. Unit: N/A.";
      type uint64;
      config false;
    }
    leaf pmMacRBSymReservedPdcchCapacityBoost {
      description "Aggregated number of resource block symbols reserved for PDCCH Capacity Boost feature. Unit: N/A.";
      type ietfyang:mac-address;
      config false;
    }
    leaf-list pmMacRBSymUsedPdschAdvMuMimoLayerDistr {
      description "Distribution of aggregated number of resource block symbols used for PDSCH by different number of co-scheduled layers as a result of reciprocity-based MU-MIMO. DMRS and PTRS embedded in PDSCH resources are included. Unit: N/A Ranges: Bin[0]: Reserved - Not Used. Bin[1]: Number of resource block symbols scheduled with 2 layers. Bin[2]: Number of resource block symbols scheduled with 3 layers. Bin[3]: Number of resource block symbols scheduled with 4 layers. Bin[4]: Number of resource block symbols scheduled with 5 layers. Bin[5]: Number of resource block symbols scheduled with 6 layers. Bin[6]: Number of resource block symbols scheduled with 7 layers. Bin[7]: Number of resource block symbols scheduled with 8 layers. Deprecated: Since 23.Q2. Planned to be removed. Replaced by NRCellDU::pmMacRBSymUsedPdschAdvMuMimoLayersDistr.; MOM flags: noNotification.";
      type ietfyang:mac-address;
      max-elements 8;
    }
    leaf pmMacTimeDlDrbLastSlot {
      description "Aggregated time for last slot of burst scheduling of downlink DRB since last scheduled DRB (delta time between scheduling occasions). It is considered last slot if all data in DRB buffer is drained. It is considered part of a burst if there is at least one previous DL scheduling occasion that does not fully empty buffer. HARQ initial transmission is measured. HARQ retransmission is excluded. Unit: 125 microseconds.";
      type ietfyang:mac-address;
      config false;
    }
    leaf-list pmMacVolDlSCellBwp {
      description "Aggregated volume of successfully transmitted downlink MAC PDUs for DRB or SRB using cell as SCell. BWP value is always zero for uplink. PDF ranges: Bin[0]: Aggregated volume of successfully transmitted downlink MAC PDUs for DRB or SRB in first BWP referenced in NRCellDU MO by BWPSet.allBWPRegularRef attribute. Bin[1]: Aggregated volume of successfully transmitted downlink MAC PDUs for DRB or SRB in second BWP referenced in NRCellDU MO by BWPSet.allBWPRegularRef attribute. Bin[2]: Aggregated volume of successfully transmitted downlink MAC PDUs for DRB or SRB in third BWP referenced in NRCellDU MO by BWPSet.allBWPRegularRef attribute. ... Bin[15]: Aggregated volume of successfully transmitted downlink MAC PDUs for DRB or SRB in sixteenth BWP referenced in NRCellDU MO by BWPSet.allBWPRegularRef attribute. Unit: Bytes.";
      type ietfyang:mac-address;
      max-elements 16;
    }
    leaf pmMassiveMimoSleepTimeEcoPending {
      description "Amount of time a cell is in EcoPending state. Timer starts when EcoPending indication is received and stops when sleep confirmation, for example TxMute or wake-up is received. Unit: seconds.";
      type uint64;
      config false;
    }
    leaf-list pmRadioRecInterferenceNoOfEventsPrbDistr {
      description "Number of events that are summed in each bin of pmRadioRecInterferencePwrSumPrbDistr. Unit: N/A.";
      type uint64;
      max-elements 273;
    }
    leaf pmRlcArqDlNack {
      description "Total number of unsuccessful RLC SDU and RLC SDU segment transmissions (NACKs) in downlink (DL). Only applicable to RLC AM bearers. In NR, the RLC SN is associated with RLC SDUs and not RLC PDUs. The arq_dl_ack and arq_dl_nack are related to RLC SDUs and RLC PDU or RLC SDU segments NACKed. When carrier aggregation is used, total number of unsuccessful RLC SDU and RLC SDU segment transmissions (NACKs) in DL is registered on PCell of UE..";
      type uint64;
      config false;
    }
    leaf-list pmDrbModFailAdmissionRejQos {
      description "Number of DRB modifications rejected by Service Admission Control feature per QoS. DRB is rejected because of limit configured in FlowLimit.maxNoOfFlows attribute. For more information, check Feature Description for Service Admission Control feature. Compressed: True.";
      type uint64;
      max-elements 256;
    }
    leaf pmUeCtxtSetupSucc {
      description "Number of successful UE Context Setup procedures..";
      type uint64;
      config false;
    }
    leaf-list pmRimPdschActionLastDlSlotDistr {
      description "Histogram of applied RIM mitigation actions on PDSCH transmissions. Considers mitigation actions taken in first downlink slot before special slot. Unit: N/A Ranges: Bin[0]: UE not scheduled due to blanking Bin[1]: UE not scheduled due to low load Bin[2]: UE not scheduled due to low SINR Bin[3]: UE is backed off with low power value Bin[4]: UE is backed off with high power value.";
      type uint64;
      max-elements 5;
    }
    leaf-list pmMacHarqDlAck256QamInitSlotDistr {
      description "For each downlink slot, bin that corresponds to number of successful initial HARQ PDSCH transmissions using 256-QAM modulation in slot is incremented. HARQ transmissions used for BWP DCI switch Scheduling Request (SR) are not pegged. Unit: N/A Ranges: Bin[0]: Total number of successful initial downlink HARQ transmissions using 256-QAM on slot 0. Bin[1]: Total number of successful initial downlink HARQ transmissions using 256-QAM on slot 1. Bin[2]: Total number of successful initial downlink HARQ transmissions using 256-QAM on slot 2. Bin[3]: Total number of successful initial downlink HARQ transmissions using 256-QAM on slot 3. Bin[4]: Total number of successful initial downlink HARQ transmissions using 256-QAM on slot 4. Bin[5]: Total number of successful initial downlink HARQ transmissions using 256-QAM on slot 5. Bin[6]: Total number of successful initial downlink HARQ transmissions using 256-QAM on slot 6. Bin[7]: Total number of successful initial downlink HARQ transmissions using 256-QAM on slot 7. Bin[8]: Total number of successful initial downlink HARQ transmissions using 256-QAM on slot 8. Bin[9]: Total number of successful initial downlink HARQ transmissions using 256-QAM on slot 9. Bin[10]: Total number of successful initial downlink HARQ transmissions using 256-QAM on slot 10. Bin[11]: Total number of successful initial downlink HARQ transmissions using 256-QAM on slot 11. Bin[12]: Total number of successful initial downlink HARQ transmissions using 256-QAM on slot 12. Bin[13]: Total number of successful initial downlink HARQ transmissions using 256-QAM on slot 13. Bin[14]: Total number of successful initial downlink HARQ transmissions using 256-QAM on slot 14. Bin[15]: Total number of successful initial downlink HARQ transmissions using 256-QAM on slot 15. Bin[16]: Total number of successful initial downlink HARQ transmissions using 256-QAM on slot 16. Bin[17]: Total number of successful initial downlink HARQ transmissions using 256-QAM on slot 17. Bin[18]: Total number of successful initial downlink HARQ transmissions using 256-QAM on slot 18. Bin[19]: Total number of successful initial downlink HARQ transmissions using 256-QAM on slot 19..";
      type ietfyang:mac-address;
      max-elements 20;
    }
    leaf pmMacVolUlUnresUeBsrGrant {
      description "Data volume in MAC SDUs successfully received in uplink, unrestricted by air interface. Sent using one grant given by gNodeB to empty UE buffer. Unit: byte.";
      type ietfyang:mac-address;
      config false;
    }
    leaf pmRlcDelayPktTransmitDl {
      description "Aggregated number of samples for downlink RLC delay measurements. Unit: N/A.";
      type uint64;
      config false;
    }
    leaf-list pmMacBsrLcg2Distr {
      description "Distribution of highest possible buffer size reported in BSRs in MAC Control Elements in UL LCG ID 2. Unit: N/A Ranges: Bin[0]: 0 bytes Bin[1]: [1..19] bytes Bin[2]: [20..36] bytes Bin[3]: [37..66] bytes Bin[4]: [67..124] bytes Bin[5]: [125..233] bytes Bin[6]: [234..436] bytes Bin[7]: [437..817] bytes Bin[8]: [818..1532] bytes Bin[9]: [1533..2873] bytes Bin[10]: [2874..5387] bytes Bin[11]: [5388..10104] bytes Bin[12]: [10105..18951] bytes Bin[13]: [18952..35543] bytes Bin[14]: [35544..66663] bytes Bin[15]: [66664..125030] bytes Bin[16]: [125031..] bytes.";
      type ietfyang:mac-address;
      max-elements 17;
    }
    leaf pmRimDetectedAggressorSetIDsMax {
      description "Number of unique setIDs reported by aggressor cells with RS2 detection..";
      type int64;
      config false;
    }
    leaf pmMassiveMimoSleepOppTimeEco {
      description "Accumulates potential amount of time a cell can be in ECO state. Unit: seconds.";
      type uint64;
      config false;
    }
    leaf-list pmMeasGapUeMaxDistr {
      description "Peak number of active UEs that have measurement gap configured by NRCellDU. Sample is taken every 5 seconds. Unit: N/A Ranges: Bin[0]: Gap pattern 0 Bin[1]: Gap pattern 1 Bin[2]: Gap pattern 2 Bin[3]: Gap pattern 3 Bin[4]: Not used Bin[5]: Not used Bin[6]: Not used Bin[7]: Not used Bin[8]: Not used Bin[9]: Not used Bin[10]: Not used Bin[11]: Not used Bin[12]: Not used Bin[13]: Not used Bin[14]: Gap pattern 14 Bin[15]: Not used Bin[16]: Not used Bin[17]: Not used Bin[18]: Not used Bin[19]: Not used Bin[20]: Not used Bin[21]: Not used Bin[22]: Not used Bin[23]: Not used Compressed: True.";
      type int64;
      max-elements 24;
    }
    leaf-list pmMacRBSymUsedPdcchTypeAAggrLvl1Sssg {
      description "Number of resource block symbols used by PDCCH with aggregation level 1 for scheduling of PDSCH or PUSCH using mapping type A in search space set group. Includes DMRS and PTRS embedded in resources. PDF ranges: Bin[0]: Accumulated downlink resource block symbols that use PDCCH with aggregation level 1 for UEs that are not configured with search space set group switching. Bin[1]: Accumulated downlink resource block symbols that use PDCCH with aggregation level 1 for UEs configured with search space set group switching. Value of SssgSwitchUeCfg.sssgSwitchPmIdentity attribute must be 1 for UEs configured with a dense search space set group. Bin[2]: Accumulated downlink resource block symbols that use PDCCH with aggregation level 1 for UEs configured with search space set group switching. Value of SssgSwitchUeCfg.sssgSwitchPmIdentity attribute must be 1 for UEs configured with a sparse search space set group. Bin[3]: Accumulated downlink resource block symbols that use PDCCH with aggregation level 1 for UEs configured with search space set group switching. Value of SssgSwitchUeCfg.sssgSwitchPmIdentity attribute must be 2 for UEs configured with a dense search space set group. ... Bin[15]: Accumulated downlink resource block symbols that use PDCCH with aggregation level 1 for UEs configured with search space set group switching. Value of SssgSwitchUeCfg.sssgSwitchPmIdentity attribute must be 8 for UEs configured with a dense search space set group. Bin[16]: Accumulated downlink resource block symbols that use PDCCH with aggregation level 1 for UEs configured with search space set group switching. Value of SssgSwitchUeCfg.sssgSwitchPmIdentity attribute must be 8 for UEs configured with a sparse search space set group. Unit: N/A.";
      type ietfyang:mac-address;
      max-elements 17;
    }
    leaf-list pmRadioSinrPuschNackDistr {
      description "Total number of PUSCH NACK counts pegged at SINR values for each PUSCH transmission. Ranges: Bin[0]: [..-11] dB Bin[1]: ]-11..-8] dB Bin[2]: ]-8..-5] dB Bin[3]: ]-5..-2] dB Bin[4]: ]-2..1] dB Bin[5]: ]1..4] dB Bin[6]: ]4..7] dB Bin[7]: ]7..10] dB Bin[8]: ]10..13] dB Bin[9]: ]13..16] dB Bin[10]: ]16..] dB.";
      type uint64;
      max-elements 11;
    }
    leaf-list pmRadioRecEffectiveIpNPwrDistr {
      description "Measured noise and interference power on PUSCH. Observes effect of PIM avoidance. Sampling is done at every transmission. Unit: dBm/PRB Ranges: Bin[0]: [..-130] dBm/PRB Bin[1]: ]-130..-128] dBm/PRB Bin[2]: ]-128..-126] dBm/PRB Bin[3]: ]-126..-124] dBm/PRB Bin[4]: ]-124..-122] dBm/PRB Bin[5]: ]-122..-121] dBm/PRB Bin[6]: ]-121..-120] dBm/PRB Bin[7]: ]-120..-119] dBm/PRB Bin[8]: ]-119..-118] dBm/PRB Bin[9]: ]-118..-117] dBm/PRB Bin[10]: ]-117..-116] dBm/PRB Bin[11]: ]-116..-115] dBm/PRB Bin[12]: ]-115..-114] dBm/PRB Bin[13]: ]-114..-113] dBm/PRB Bin[14]: ]-113..-112] dBm/PRB Bin[15]: ]-112..-108] dBm/PRB Bin[16]: ]-108..-104] dBm/PRB Bin[17]: ]-104..-100] dBm/PRB Bin[18]: ]-100..-96] dBm/PRB Bin[19]: ]-96..-92] dBm/PRB Bin[20]: ]-92..] dBm/PRB.";
      type uint64;
      max-elements 21;
    }
    leaf-list pmMacBsrLcg1Distr {
      description "Distribution of highest possible buffer size reported in BSRs in MAC Control Elements in UL LCG ID 1. Unit: N/A Ranges: Bin[0]: 0 bytes Bin[1]: [1..19] bytes Bin[2]: [20..36] bytes Bin[3]: [37..66] bytes Bin[4]: [67..124] bytes Bin[5]: [125..233] bytes Bin[6]: [234..436] bytes Bin[7]: [437..817] bytes Bin[8]: [818..1532] bytes Bin[9]: [1533..2873] bytes Bin[10]: [2874..5387] bytes Bin[11]: [5388..10104] bytes Bin[12]: [10105..18951] bytes Bin[13]: [18952..35543] bytes Bin[14]: [35544..66663] bytes Bin[15]: [66664..125030] bytes Bin[16]: [125031..] bytes.";
      type ietfyang:mac-address;
      max-elements 17;
    }
    leaf pmPimAvoidMutedCrbSum {
      description "Accumulation of muted CRBs in slot when muting is performed..";
      type uint64;
      config false;
    }
    leaf pmMeasGapUeSamp {
      description "Number of times pmMeasGapUeSumDistr and pmMeasGapUeMnSumDistr are stepped..";
      type uint64;
      config false;
    }
    leaf-list pmRimDetectedVictimDistanceMaxDistr {
      description "Number of victim-agressor pairs detecting remote interference within specified distance. Ranges: Bin[0]: [0..100] km Bin[1]: [101..250] km Bin[2]: [251..450] km Bin[3]: [451..] km.";
      type int64;
      max-elements 4;
    }
    leaf pmMacVolUlSCell {
      description "Data volume in MAC SDUs successfully received in uplink when cell is used as SCell. Unit: byte.";
      type ietfyang:mac-address;
      config false;
    }
    leaf-list pmMacHarqDlAck64QamInitSlotDistr {
      description "For each downlink slot, bin that corresponds to number of successful initial HARQ PDSCH transmissions using 64-QAM modulation in slot is incremented. HARQ transmissions used for BWP DCI switch Scheduling Request (SR) are not pegged. Unit: N/A Ranges: Bin[0]: Total number of successful initial downlink HARQ transmissions using 64-QAM on slot 0. Bin[1]: Total number of successful initial downlink HARQ transmissions using 64-QAM on slot 1. Bin[2]: Total number of successful initial downlink HARQ transmissions using 64-QAM on slot 2. Bin[3]: Total number of successful initial downlink HARQ transmissions using 64-QAM on slot 3. Bin[4]: Total number of successful initial downlink HARQ transmissions using 64-QAM on slot 4. Bin[5]: Total number of successful initial downlink HARQ transmissions using 64-QAM on slot 5. Bin[6]: Total number of successful initial downlink HARQ transmissions using 64-QAM on slot 6. Bin[7]: Total number of successful initial downlink HARQ transmissions using 64-QAM on slot 7. Bin[8]: Total number of successful initial downlink HARQ transmissions using 64-QAM on slot 8. Bin[9]: Total number of successful initial downlink HARQ transmissions using 64-QAM on slot 9. Bin[10]: Total number of successful initial downlink HARQ transmissions using 64-QAM on slot 10. Bin[11]: Total number of successful initial downlink HARQ transmissions using 64-QAM on slot 11. Bin[12]: Total number of successful initial downlink HARQ transmissions using 64-QAM on slot 12. Bin[13]: Total number of successful initial downlink HARQ transmissions using 64-QAM on slot 13. Bin[14]: Total number of successful initial downlink HARQ transmissions using 64-QAM on slot 14. Bin[15]: Total number of successful initial downlink HARQ transmissions using 64-QAM on slot 15. Bin[16]: Total number of successful initial downlink HARQ transmissions using 64-QAM on slot 16. Bin[17]: Total number of successful initial downlink HARQ transmissions using 64-QAM on slot 17. Bin[18]: Total number of successful initial downlink HARQ transmissions using 64-QAM on slot 18. Bin[19]: Total number of successful initial downlink HARQ transmissions using 64-QAM on slot 19..";
      type ietfyang:mac-address;
      max-elements 20;
    }
    leaf pmRadioMacWvfSwitchAttUlCpofdm {
      description "Total number of UE uplink waveform switching attempts from DFT-s-OFDM to CP-OFDM in each cell. Unit: N/A.";
      type ietfyang:mac-address;
      config false;
    }
    leaf pmRadioMacTransUl1Layer {
      description "Total number of single-layer uplink transmissions in each cell. Unit: N/A.";
      type ietfyang:mac-address;
      config false;
    }
    leaf-list pmRadioUeRepCqi64QamLowSeRank4Distr {
      description "Distribution of UE-reported CQI values with low Spectral Efficiency related to rank 4 transmissions when highest modulation order supported in downlink (DL) in NR cell is 64-QAM. CQI values and interpretations correspond to entries in Table 5.2.2.1-4 in 3GPP 38.214 for reporting CQI based on QPSK, 16-QAM, and 64-QAM. Unit: N/A Ranges: Bin[0]: CQI = 0 Bin[1]: CQI = 1 Bin[2]: CQI = 2 Bin[3]: CQI = 3 Bin[4]: CQI = 4 Bin[5]: CQI = 5 Bin[6]: CQI = 6 Bin[7]: CQI = 7 Bin[8]: CQI = 8 Bin[9]: CQI = 9 Bin[10]: CQI = 10 Bin[11]: CQI = 11 Bin[12]: CQI = 12 Bin[13]: CQI = 13 Bin[14]: CQI = 14 Bin[15]: CQI = 15.";
      type uint64;
      max-elements 16;
    }
    leaf pmMacHarqDlDtx16QamInit {
      description "Total number of occasions when downlink HARQ feedback for initial HARQ transmission using 16-QAM modulation could not be detected from UE. Initial transmission is first transmission on HARQ process. Unit: N/A.";
      type ietfyang:mac-address;
      config false;
    }
    leaf pmMacVolDlSCellExt {
      description "Aggregated volume of successfully transmitted downlink MAC PDUs for DRB or SRB using this cell as external inter-gNodeB SCell, inter-capacity module SCell, or inter-DU SCell. Unit: bytes.";
      type ietfyang:mac-address;
      config false;
    }
    leaf-list pmRadioPreambleSinrMsg3NackDistr {
      description "Total number of Msg3 NACK counts for a preamble SINR range. Ranges: Bin[0]: [..-15] dB Bin[1]: ]-15..-12] dB Bin[2]: ]-12..-9] dB Bin[3]: ]-9..-6] dB Bin[4]: ]-6..-3] dB Bin[5]: ]-3..] dB.";
      type uint64;
      max-elements 6;
    }
    leaf pmRadioRaCbFailMsg3Crc {
      description "Number of RACH attempts failed due to Msg3 received with wrong CRC. Unit: messages.";
      type uint64;
      config false;
    }
    leaf-list pmMacVolUlBwp {
      description "Aggregated volume of successfully received uplink MAC SDUs for DRB or SRB using cell as PCell, PSCell. For downlink BWP value is always zero. PDF ranges: Bin[0]: MAC SDUs successfully received in uplink in the first BWP referenced in NRCellDU MO by BWPSet.allBWPRegularRef attribute Bin[1]: MAC SDUs successfully received in uplink in the second BWP referenced in NRCellDU MO by BWPSet.allBWPRegularRef attribute Bin[2]: MAC SDUs successfully received in uplink in the third BWP referenced in NRCellDU MO by BWPSet.allBWPRegularRef attribute ... Bin[15]: MAC SDUs successfully received in uplink in the sixteenth BWP referenced in NRCellDU MO by BWPSet.allBWPRegularRef attribute Unit: 100 bytes.";
      type ietfyang:mac-address;
      max-elements 16;
    }
    leaf-list pmMacSchedSlotDlCellSchedDistr {
      description "Aggregated number of scheduled downlink slots when cells are scheduled. Measured when this cell is used as PSCell. Unit: N/A Ranges: Bin[0]: Scheduled DL slots with 1 cell scheduled. Bin[1]: Scheduled DL slots with 2 cells scheduled. Bin[2]: Scheduled DL slots with 3 cells scheduled. Bin[3]: Scheduled DL slots with 4 cells scheduled. Bin[4]: Scheduled DL slots with 5 cells scheduled. Bin[5]: Scheduled DL slots with 6 cells scheduled. Bin[6]: Scheduled DL slots with 7 cells scheduled. Bin[7]: Scheduled DL slots with 8 cells scheduled..";
      type ietfyang:mac-address;
      max-elements 8;
    }
    leaf pmMacRBSymUsedPdcchTypeAAggrLvl4 {
      description "Number of resource block symbols used by PDCCH with aggregation level 4 for scheduling of PDSCH or PUSCH using mapping type A. This includes DMRS and PTRS embedded in resources. Unit: N/A.";
      type ietfyang:mac-address;
      config false;
    }
    leaf-list pmMacSchedSlotUlTempAlarmSCellDistr {
      description "Aggregated number of uplink slots when UL-configured SCells are active and UE temperature alarm is detected. Measured when this cell is used as PSCell. Pre-scheduling is not included. Unit: N/A Ranges: Bin[0]: Scheduled UL slots when UE temperature alarm is detected with 0 SCells activated. Bin[1]: Scheduled UL slots when UE temperature alarm is detected with 1 SCells activated. Bin[2]: Scheduled UL slots when UE temperature alarm is detected with 2 SCells activated. Bin[3]: Scheduled UL slots when UE temperature alarm is detected with 3 SCells activated. Bin[4]: Scheduled UL slots when UE temperature alarm is detected with 4 SCells activated. Bin[5]: Scheduled UL slots when UE temperature alarm is detected with 5 SCells activated. Bin[6]: Scheduled UL slots when UE temperature alarm is detected with 6 SCells activated. Bin[7]: Scheduled UL slots when UE temperature alarm is detected with 7 SCells activated..";
      type ietfyang:mac-address;
      max-elements 8;
    }
    leaf-list pmRadioPdschTable2McsDistr {
      description "Distribution of MCS used for PDSCH transmissions where MCS index table 2 is applied and UE instances are enabled with up to 256-QAM. For more information, see 3GPP TS 38.214, Table 5.1.3.1-2. Each bin represents a specific MCS. Unit: N/A Ranges: Bin[0]: MCS = 0 Bin[1]: MCS = 1 Bin[2]: MCS = 2 Bin[3]: MCS = 3 Bin[4]: MCS = 4 Bin[5]: MCS = 5 Bin[6]: MCS = 6 Bin[7]: MCS = 7 Bin[8]: MCS = 8 Bin[9]: MCS = 9 Bin[10]: MCS = 10 Bin[11]: MCS = 11 Bin[12]: MCS = 12 Bin[13]: MCS = 13 Bin[14]: MCS = 14 Bin[15]: MCS = 15 Bin[16]: MCS = 16 Bin[17]: MCS = 17 Bin[18]: MCS = 18 Bin[19]: MCS = 19 Bin[20]: MCS = 20 Bin[21]: MCS = 21 Bin[22]: MCS = 22 Bin[23]: MCS = 23 Bin[24]: MCS = 24 Bin[25]: MCS = 25 Bin[26]: MCS = 26 Bin[27]: MCS = 27 Bin[28]: MCS = 28 Bin[29]: MCS = 29 Bin[30]: MCS = 30 Bin[31]: MCS = 31.";
      type uint64;
      max-elements 32;
    }
    leaf pmPagDiscardedRan {
      description "Number of Radio Access Network RRC paging messages discarded and not broadcasted in cell. This counter is a subset of NRCellDU.pmPagDiscarded PM counter. Unit: NA.";
      type uint64;
      config false;
    }
    leaf-list pmMacSymUsedPdcchDistr {
      description "Distribution of number of symbols used for PDCCH. Unit: N/A Ranges: Bin[0]: Number of slots with 1 PDCCH symbol used. Bin[1]: Number of slots with 2 PDCCH symbols used. Bin[2]: Number of slots with 3 PDCCH symbols used..";
      type ietfyang:mac-address;
      max-elements 3;
    }
    leaf pmMacVolUlResUe {
      description "Data volume in MAC SDUs successfully received in uplink as part of a burst while being restricted by air interface, excluding data volume received in last slot in burst. Unit: byte.";
      type ietfyang:mac-address;
      config false;
    }
    leaf-list pmRadioMaxDeltaIpNDistr {
      description "Measures maximum deltaIpN among each UL slot within SFN in 1 second. Unit: N/A Ranges: Bin[0]: [..1] dB/PRB Bin[1]: ]1..3] dB/PRB Bin[2]: ]3..5] dB/PRB Bin[3]: ]5..10] dB/PRB Bin[4]: ]10..] dB/PRB.";
      type uint64;
      max-elements 5;
    }
    leaf-list pmMacHarqDlNack256QamInitSlotDistr {
      description "For each downlink slot, bin that corresponds to number of unsuccessful initial HARQ PDSCH transmissions using 256-QAM modulation in slot is incremented. HARQ transmissions used for BWP DCI switch Scheduling Request (SR) are not pegged. Unit: N/A Ranges: Bin[0]: Total number of unsuccessful initial downlink HARQ transmissions using 256-QAM on slot 0. Bin[1]: Total number of unsuccessful initial downlink HARQ transmissions using 256-QAM on slot 1. Bin[2]: Total number of unsuccessful initial downlink HARQ transmissions using 256-QAM on slot 2. Bin[3]: Total number of unsuccessful initial downlink HARQ transmissions using 256-QAM on slot 3. Bin[4]: Total number of unsuccessful initial downlink HARQ transmissions using 256-QAM on slot 4. Bin[5]: Total number of unsuccessful initial downlink HARQ transmissions using 256-QAM on slot 5. Bin[6]: Total number of unsuccessful initial downlink HARQ transmissions using 256-QAM on slot 6. Bin[7]: Total number of unsuccessful initial downlink HARQ transmissions using 256-QAM on slot 7. Bin[8]: Total number of unsuccessful initial downlink HARQ transmissions using 256-QAM on slot 8. Bin[9]: Total number of unsuccessful initial downlink HARQ transmissions using 256-QAM on slot 9. Bin[10]: Total number of unsuccessful initial downlink HARQ transmissions using 256-QAM on slot 10. Bin[11]: Total number of unsuccessful initial downlink HARQ transmissions using 256-QAM on slot 11. Bin[12]: Total number of unsuccessful initial downlink HARQ transmissions using 256-QAM on slot 12. Bin[13]: Total number of unsuccessful initial downlink HARQ transmissions using 256-QAM on slot 13. Bin[14]: Total number of unsuccessful initial downlink HARQ transmissions using 256-QAM on slot 14. Bin[15]: Total number of unsuccessful initial downlink HARQ transmissions using 256-QAM on slot 15. Bin[16]: Total number of unsuccessful initial downlink HARQ transmissions using 256-QAM on slot 16. Bin[17]: Total number of unsuccessful initial downlink HARQ transmissions using 256-QAM on slot 17. Bin[18]: Total number of unsuccessful initial downlink HARQ transmissions using 256-QAM on slot 18. Bin[19]: Total number of unsuccessful initial downlink HARQ transmissions using 256-QAM on slot 19..";
      type ietfyang:mac-address;
      max-elements 20;
    }
    leaf-list pmRadioUeRepPmiSecondaryCsiRsRank4Distr {
      description "Distribution of precoding weights reported by UE for rank 4 codebook associated with secondary CSI-RS. Indicates spatial distribution of UEs using cell as PCell. Type 1 single-panel codebooks are defined in 3GPP TS 38.214. Represents distribution of requested departure angles from AAS-capable radio unit as estimated from UE CSI feedback, specifically main and diversity direction of PMI values. It is not recommended to use this PM counter for Remote radio units. For more information, see Massive MIMO Mid-Band and Manage Massive MIMO NR in CPI library. Unit: N/A Compressed: True.";
      type uint64;
      max-elements 256;
    }
    leaf pmMacRBSymUsedPusch2Port2Layer {
      description "Aggregated number of resource block symbols scheduled in uplink for two-layer transmission with two ports. Unit: N/A.";
      type ietfyang:mac-address;
      config false;
    }
    leaf pmRadioRaCbPreambles {
      description "Number of detected CBRA preambles (Msg1). Unit: messages.";
      type uint64;
      config false;
    }
    leaf pmMacHarqDlDtx256QamInit {
      description "Total number of occasions when downlink HARQ feedback for initial HARQ transmission using 256-QAM modulation could not be detected from UE. Initial transmission is first transmission on HARQ process. Unit: N/A.";
      type ietfyang:mac-address;
      config false;
    }
    leaf-list pmRadioSchedUlSuMimoRankDistr {
      description "Scheduled uplink rank distribution for SU-MIMO. Unit: N/A Ranges: Bin[0]: Rank = 1 Bin[1]: Rank = 2 Bin[2]: spare Bin[3]: spare.";
      type uint64;
      max-elements 4;
    }
    leaf pmRadioMacWvfSwitchSuccUlCpofdm {
      description "Total number of successful UE uplink waveform switching attempts from DFT-s-OFDM to CP-OFDM in each cell. Unit: N/A.";
      type ietfyang:mac-address;
      config false;
    }
    leaf-list pmPimAvoidMutedCrbDistr {
      description "Distribution of the percentage which is number of muted CRBs and number of CRBs in system bandwidth. Unit: N/A Ranges: Bin[0]: [0..4] % Bin[1]: ]4..8] % Bin[2]: ]8..12] % Bin[3]: ]12..16] % Bin[4]: ]16..20] % Bin[5]: ]20..24] % Bin[6]: ]24..28] % Bin[7]: ]28..32] % Bin[8]: ]32..36] % Bin[9]: ]36..40] % Bin[10]: ]40..44] % Bin[11]: ]44..48] % Bin[12]: ]48..52] % Bin[13]: ]52..56] % Bin[14]: ]56..60] % Bin[15]: ]60..64] % Bin[16]: ]64..68] % Bin[17]: ]68..72] % Bin[18]: ]72..76] % Bin[19]: ]76..80] % Bin[20]: ]80..84] % Bin[21]: ]84..88] % Bin[22]: ]88..92] % Bin[23]: ]92..96] % Bin[24]: ]96..100] %.";
      type uint64;
      max-elements 25;
    }
    leaf pmRadioMacWvfSwitchAttUlDfts {
      description "Total number of UE uplink waveform switching attempts from CP-OFDM to DFT-s-OFDM in each cell. Unit: N/A.";
      type ietfyang:mac-address;
      config false;
    }
    leaf pmMacVolDlPCellCa {
      description "Aggregated volume of successfully transmitted downlink MAC PDUs for DRB or SRB using cell as PCell. Only includes volume from Carrier Aggregation UEs using cell as PCell. Unit: bytes.";
      type ietfyang:mac-address;
      config false;
    }
    leaf-list pmRadioRaSuccTaAbsDistr {
      description "Distribution of timing advance (TA) values at successful random access. TA values are expressed as distance between UE and antenna site. Unit: N/A Ranges: Bin[0]: [0..49] m Bin[1]: [50..99] m Bin[2]: [100..149] m Bin[3]: [150..199] m Bin[4]: [200..299] m Bin[5]: [300..399] m Bin[6]: [400..499] m Bin[7]: [500..599] m Bin[8]: [600..699] m Bin[9]: [700..799] m Bin[10]: [800..999] m Bin[11]: [1000..1199] m Bin[12]: [1200..1399] m Bin[13]: [1400..1599] m Bin[14]: [1600..1799] m Bin[15]: [1800..1999] m Bin[16]: [2000..2499] m Bin[17]: [2500..2999] m Bin[18]: [3000..3499] m Bin[19]: [3500..3999] m Bin[20]: [4000..4999] m Bin[21]: [5000..5999] m Bin[22]: [6000..6999] m Bin[23]: [7000..7999] m Bin[24]: [8000..8999] m Bin[25]: [9000..9999] m Bin[26]: [10000..10999] m Bin[27]: [11000..11999] m Bin[28]: [12000..12999] m Bin[29]: [13000..13999] m Bin[30]: [14000..14999] m Bin[31]: [15000..] m.";
      type uint64;
      max-elements 32;
    }
    leaf-list pmMacTimeDlDrbSampQos {
      description "Aggregated number of samples for measuring time for HARQ initial transmission scheduling of downlink DRB while there is data in buffer. Accumulates samples from all DRBs with same QoS. Unit: N/A Compressed: True.";
      type ietfyang:mac-address;
      max-elements 256;
    }
    leaf-list pmMacRBSymUsedPdcchTypeAAggrLvl8Sssg {
      description "Number of resource block symbols used by PDCCH with aggregation level 8 for scheduling of PDSCH or PUSCH using mapping type A in search space set group. Includes DMRS and PTRS embedded in resources. PDF ranges: Bin[0]: Accumulated downlink resource block symbols that use PDCCH with aggregation level 8 for UEs that are not configured with search space set group switching. Bin[1]: Accumulated downlink resource block symbols that use PDCCH with aggregation level 8 for UEs configured with search space set group switching. Value of SssgSwitchUeCfg.sssgSwitchPmIdentity attribute must be 1 for UEs configured with a dense search space set group. Bin[2]: Accumulated downlink resource block symbols that use PDCCH with aggregation level 8 for UEs configured with search space set group switching. Value of SssgSwitchUeCfg.sssgSwitchPmIdentity attribute must be 1 for UEs configured with a sparse search space set group. Bin[3]: Accumulated downlink resource block symbols that use PDCCH with aggregation level 8 for UEs configured with search space set group switching. Value of SssgSwitchUeCfg.sssgSwitchPmIdentity attribute must be 2 for UEs configured with a dense search space set group. ... Bin[15]: Accumulated downlink resource block symbols that use PDCCH with aggregation level 8 for UEs configured with search space set group switching. Value of SssgSwitchUeCfg.sssgSwitchPmIdentity attribute must be 8 for UEs configured with a dense search space set group. Bin[16]: Accumulated downlink resource block symbols that use PDCCH with aggregation level 8 for UEs configured with search space set group switching. Value of SssgSwitchUeCfg.sssgSwitchPmIdentity attribute must be 8 for UEs configured with a sparse search space set group. Unit: N/A.";
      type ietfyang:mac-address;
      max-elements 17;
    }
    leaf-list pmRadioRaCfPreambleFailedDistr {
      description "Number of failed allocations of CFRA preambles for each PRACH period during measurement period. Unit: N/A Ranges: Bin[0]: One failed preamble assignment. Bin[1]: Two failed preamble assignments. Bin[2]: Three failed preamble assignments. Bin[3]: More than three failed preamble assignments. Deprecated: Since 25.Q1. Planned to be removed. Replaced by NRCellDU::pmRadioRaCfPreambleFailedUlCaDistr and NRCellDU::pmRadioRaCfPreambleFailedHoDistr; MOM flags: noNotification.";
      type uint64;
      max-elements 4;
    }
    leaf pmMacHarqDlNack16QamInit {
      description "Total number of unsuccessful initial downlink HARQ transmissions using 16-QAM modulation. Initial transmission is first transmission on HARQ process. Unit: N/A.";
      type ietfyang:mac-address;
      config false;
    }
    leaf pmMacPdcchBlockingPdschOccasions {
      description "Incremented for each scheduling occasion when PDCCH limits number of sessions served by PDSCH. A scheduling occasion is when any number of requests are allocated PDCCH, PDSCH and PUSCH. Unit: N/A.";
      type ietfyang:mac-address;
      config false;
    }
    leaf-list pmRadioUeRepCqi256QamRank4Distr {
      description "Distribution of UE-reported CQI values related to rank 4 transmissions when highest modulation order supported in downlink (DL) in NR cell is configured to be 256-QAM. CQI values and interpretations correspond to entries in Table 5.2.2.1-3 in 3GPP 38.214 for reporting CQI based on QPSK, 16-QAM, 64-QAM, and 256-QAM. Unit: N/A Ranges: Bin[0]: CQI = 0 Bin[1]: CQI = 1 Bin[2]: CQI = 2 Bin[3]: CQI = 3 Bin[4]: CQI = 4 Bin[5]: CQI = 5 Bin[6]: CQI = 6 Bin[7]: CQI = 7 Bin[8]: CQI = 8 Bin[9]: CQI = 9 Bin[10]: CQI = 10 Bin[11]: CQI = 11 Bin[12]: CQI = 12 Bin[13]: CQI = 13 Bin[14]: CQI = 14 Bin[15]: CQI = 15.";
      type uint64;
      max-elements 16;
    }
    leaf pmCellTimeSamp {
      description "Number of times corresponding cell downtime and uptime counters accumulate new sample..";
      type uint64;
      config false;
    }
    leaf-list pmSessionTimeUeBwpSumDistr {
      description "Shows accumulated time sessions of UEs with BWP in NRCellDU MO by BWPSet MO. PDF ranges: Bin[0]: Accumulated time sessions of UEs with first BWP referenced in NRCellDU MO by BWPSet.allBWPRegularRef attribute Bin[1]: Accumulated time sessions of UEs with second BWP referenced in NRCellDU MO by BWPSet.allBWPRegularRef attribute Bin[2]: Accumulated time sessions of UEs with third BWP referenced in NRCellDU MO by BWPSet.allBWPRegularRef attribute ... Bin[15]: Accumulated time sessions of UEs with sixteenth BWP referenced in NRCellDU MO by BWPSet.allBWPRegularRef attribute.";
      type uint64;
      max-elements 16;
    }
    leaf pmMacTimeDlDrb {
      description "Aggregated time for HARQ initial transmission scheduling of downlink DRB, while there is data in buffer. Unit: 125 microseconds.";
      type ietfyang:mac-address;
      config false;
    }
    leaf pmPuschAvailSlot {
      description "Total number of slots where gNodeB scheduler can schedule on PUSCH. Unit: N/A.";
      type uint64;
      config false;
    }
    leaf pmMacHarqUlFail {
      description "Number of complete uplink HARQ failures. When HARQ transmission reaches maximum number of retransmissions, it is not retransmitted again and is regarded as scheduling activity with complete HARQ failure. Unit: N/A.";
      type ietfyang:mac-address;
      config false;
    }
    leaf-list pmUeCtxtModSuccWvfSwitchDistr {
      description "Counts successful RRC Reconfiguration attempts during UE Context Modification procedure for UE uplink waveform switch. Unit: N/A Ranges: Bin[0]: NR SA MCG CP-OFDM Bin[1]: EN-DC SCG CP-OFDM Bin[2]: NR-DC SCG CP-OFDM Bin[3]: NR SA MCG DFTs-OFDM Bin[4]: EN-DC SCG DFTs-OFDM Bin[5]: NR-DC SCG DFTs-OFDM.";
      type uint64;
      max-elements 6;
    }
    leaf pmCellDowntimeAuto {
      description "Length of time the cell is automatically disabled. Unit: seconds.";
      type uint64;
      config false;
    }
    leaf-list pmMacPdcchCongestionUlDistr {
      description "Distribution of uplink PDCCH congestion rate averaged over one second. Ranges Bin[0]: [0..5] % Bin[1]: [6..10] % Bin[2]: [11..15] % Bin[3]: [16..20] % Bin[4]: [21..25] % Bin[5]: [26..30] % Bin[6]: [31..35] % Bin[7]: [36..40] % Bin[8]: [41..45] % Bin[9]: [46..50] % Bin[10]: [51..55] % Bin[11]: [56..60] % Bin[12]: [61..65] % Bin[13]: [66..70] % Bin[14]: [71..75] % Bin[15]: [76..80] % Bin[16]: [81..85] % Bin[17]: [86..90] % Bin[18]: [91..95] % Bin[19]: [96..] % Unit: N/A.";
      type ietfyang:mac-address;
      max-elements 20;
    }
    leaf pmMacVolDlDrbSingleBurstSamp {
      description "Aggregated number of samples when new downlink packet arrives to empty buffer. Buffer is drained by single scheduling occasion. Unit: N/A.";
      type ietfyang:mac-address;
      config false;
    }
    leaf-list pmMacVolDlDrbSingleBurstSampQos {
      description "Aggregated number of samples when new downlink packet arrives to empty buffer for each QoS. Buffer is drained by single scheduling occasion. Unit: N/A Compressed: True.";
      type ietfyang:mac-address;
      max-elements 256;
    }
    leaf pmRadioRaCbFailMsg3Crnti {
      description "Number of RACH attempts failed due to Msg3 received with wrong CRNTI. Unit: messages.";
      type uint64;
      config false;
    }
    leaf pmMacThpDlDrbMax {
      description "Maximum downlink MAC DRB throughput achieved when restricted by air interface. Unit: kbps.";
      type ietfyang:mac-address;
      config false;
    }
    leaf-list pmRadioPuschTable2McsDistr {
      description "Distribution of MCS used for PUSCH transmissions where MCS index table 2 is applied and UE instances are enabled with up to 256-QAM. For more information, see 3GPP TS 38.214, Table 5.1.3.1-2. Each bin represents a specific MCS. Unit: N/A Ranges: Bin[0]: MCS = 0 Bin[1]: MCS = 1 Bin[2]: MCS = 2 Bin[3]: MCS = 3 Bin[4]: MCS = 4 Bin[5]: MCS = 5 Bin[6]: MCS = 6 Bin[7]: MCS = 7 Bin[8]: MCS = 8 Bin[9]: MCS = 9 Bin[10]: MCS = 10 Bin[11]: MCS = 11 Bin[12]: MCS = 12 Bin[13]: MCS = 13 Bin[14]: MCS = 14 Bin[15]: MCS = 15 Bin[16]: MCS = 16 Bin[17]: MCS = 17 Bin[18]: MCS = 18 Bin[19]: MCS = 19 Bin[20]: MCS = 20 Bin[21]: MCS = 21 Bin[22]: MCS = 22 Bin[23]: MCS = 23 Bin[24]: MCS = 24 Bin[25]: MCS = 25 Bin[26]: MCS = 26 Bin[27]: MCS = 27 Bin[28]: MCS = 28 Bin[29]: MCS = 29 Bin[30]: MCS = 30 Bin[31]: MCS = 31.";
      type uint64;
      max-elements 32;
    }
    leaf pmMacPduVolDlUePCell {
      description "Aggregated volume of HARQ initially transmitted and retransmitted downlink MAC PDUs for DRB or SRB using cell as PCell or PSCell. Unit: bytes.";
      type ietfyang:mac-address;
      config false;
    }
    leaf-list pmMeasGapUeMnMaxDistr {
      description "Peak number of active UEs that have measurement gap configured by MN which impacts SN during dual connectivity. Sample is taken every 5 seconds. Unit: N/A Ranges: Bin[0]: Gap pattern 0 Bin[1]: Gap pattern 1 Bin[2]: Gap pattern 2 Bin[3]: Gap pattern 3 Bin[4]: Not used Bin[5]: Not used Bin[6]: Not used Bin[7]: Not used Bin[8]: Not used Bin[9]: Not used Bin[10]: Not used Bin[11]: Not used Bin[12]: Not used Bin[13]: Not used Bin[14]: Gap pattern 14 Bin[15]: Not used Bin[16]: Not used Bin[17]: Not used Bin[18]: Not used Bin[19]: Not used Bin[20]: Not used Bin[21]: Not used Bin[22]: Not used Bin[23]: Not used Compressed: True.";
      type int64;
      max-elements 24;
    }
    leaf pmPdschAvailSlot {
      description "Total number of slots where gNodeB scheduler can schedule on PDSCH. Unit: N/A.";
      type uint64;
      config false;
    }
    leaf pmMacRBSymEstimatedPdschTypeA {
      description "Aggregated number of resource block symbols estimated for PDSCH mapping type A during a complete Result Output Period (ROP) without use of Energy-Optimized Power Allocation feature. Unit: N/A.";
      type ietfyang:mac-address;
      config false;
    }
    leaf-list pmMacRBSymUsedPdschAdvMimoSinrThresUserDistr {
      description "Distribution of aggregated number of resource block symbols used for PDSCH by a variable number of users that meet preset SINR thresholding conditions as a result of advanced beamforming. This PM counter can be used together with NRCellDU.pmMacVolPdschAdvMimoSinrThresUserDistr PM counter to calculate SRS reciprocity resource block spectral efficiency. DMRS and PTRS embedded in PDSCH resources are included. Unit: N/A Ranges: Bin[0]: Distribution of aggregated number of resource block symbols for one user. Bin[1]: Distribution of aggregated number of resource block symbols for two users. Bin[2]: Distribution of aggregated number of resource block symbols for three users. Bin[3]: Distribution of aggregated number of resource block symbols for four users. Bin[4]: Distribution of aggregated number of resource block symbols for five users. Bin[5]: Distribution of aggregated number of resource block symbols for six users. Bin[6]: Distribution of aggregated number of resource block symbols for seven users. Bin[7]: Distribution of aggregated number of resource block symbols for eight users. Bin[8]: Reserved for future MU-MIMO. Bin[9]: Reserved for future MU-MIMO. Bin[10]: Reserved for future MU-MIMO. Bin[11]: Reserved for future MU-MIMO. Bin[12]: Reserved for future MU-MIMO. Bin[13]: Reserved for future MU-MIMO. Bin[14]: Reserved for future MU-MIMO. Bin[15]: Reserved for future MU-MIMO..";
      type ietfyang:mac-address;
      max-elements 16;
    }
    leaf-list pmRadioRaCfPreambleUnusedDistr {
      description "Number of unused CFRA preambles during a PRACH period. If there is failed allocation for HO, this counter is not stepped. But it can be stepped if there is failed allocation for UL CA. Unit: N/A Ranges: Bin[0]: All CFRA preambles are in use and no preamble assignment failures. Bin[1]: One unused CFRA preamble, no preamble assignment failures. Bin[2]: Two unused CFRA preambles, no preamble assignment failures. Bin[3]: Three unused CFRA preambles, no preamble assignment failures. Bin[4]: Four unused CFRA preambles, no preamble assignment failures. Bin[5]: Five unused CFRA preambles, no preamble assignment failures. Bin[6]: Six unused CFRA preambles, no preamble assignment failures. Bin[7]: Seven unused CFRA preambles, no preamble assignment failures. Bin[8]: Eight unused CFRA preambles, no preamble assignment failures. Bin[9]: Nine unused CFRA preambles, no preamble assignment failures. Bin[10]: Ten unused CFRA preambles, no preamble assignment failures. Bin[11]: Eleven unused CFRA preambles, no preamble assignment failures. Bin[12]: Twelve unused CFRA preambles, no preamble assignment failures. Bin[13]: More than twelve available CFRA preambles, no preamble assignment failures..";
      type uint64;
      max-elements 14;
    }
    leaf pmMassiveMimoSleepTimeEco {
      description "Accumulates actual amount of time a cell is set to ECO state. Unit: seconds.";
      type uint64;
      config false;
    }
    leaf-list pmRadioRaCfPreambleFailedHoDistr {
      description "Number of failed CFRA preamble allocations for handover UEs for each PRACH period during measurement period. Unit: N/A Ranges: Bin[0]: One failed preamble assignment for handover. Bin[1]: Two failed preamble assignments for handover. Bin[2]: Three failed preamble assignments for handover. Bin[3]: More than three failed preamble assignments for handover..";
      type uint64;
      max-elements 4;
    }
    leaf-list pmRadioPdschTable3MbsfnMcsDistr {
      description "Distribution of MCS used for PDSCH transmissions in MBSFN subframes where MCS index table 3 is applied, and UE instances are enabled with up to 64-QAM. For more information, see 3GPP TS 38.214, Table 5.1.3.1-3. Each bin represents a specific MCS. Unit: N/A Ranges: Bin[0]: MCS = 0 Bin[1]: MCS = 1 Bin[2]: MCS = 2 Bin[3]: MCS = 3 Bin[4]: MCS = 4 Bin[5]: MCS = 5 Bin[6]: MCS = 6 Bin[7]: MCS = 7 Bin[8]: MCS = 8 Bin[9]: MCS = 9 Bin[10]: MCS = 10 Bin[11]: MCS = 11 Bin[12]: MCS = 12 Bin[13]: MCS = 13 Bin[14]: MCS = 14 Bin[15]: MCS = 15 Bin[16]: MCS = 16 Bin[17]: MCS = 17 Bin[18]: MCS = 18 Bin[19]: MCS = 19 Bin[20]: MCS = 20 Bin[21]: MCS = 21 Bin[22]: MCS = 22 Bin[23]: MCS = 23 Bin[24]: MCS = 24 Bin[25]: MCS = 25 Bin[26]: MCS = 26 Bin[27]: MCS = 27 Bin[28]: MCS = 28 Bin[29]: MCS = 29 Bin[30]: MCS = 30 Bin[31]: MCS = 31.";
      type uint64;
      max-elements 32;
    }
    leaf-list pmMacVolDlDrbLastSlotQos {
      description "Aggregated volume of downlink MAC SDUs transmitted for HARQ initial transmission in last slot of burst when buffer is emptied for each QoS. HARQ retransmission is excluded. Unit: bytes Compressed: True.";
      type ietfyang:mac-address;
      max-elements 256;
    }
    leaf-list pmMacVolDlSssg {
      description "Aggregated volume of successfully transmitted downlink MAC PDUs for DRB or SRB using cell as PCell or PSCell. PDF ranges: Bin[0]: Aggregated volume of successfully transmitted downlink MAC PDUs for DRB or SRB for UEs that are not configured with search space set group switching. Bin[1]: Aggregated volume of successfully transmitted downlink MAC PDUs for DRB or SRB for UEs configured with search space set group switching. Value of SssgSwitchUeCfg.sssgSwitchPmIdentity attribute must be 1 for UEs configured with a dense search space set group. Bin[2]: Aggregated volume of successfully transmitted downlink MAC PDUs for DRB or SRB for UEs configured with search space set group switching. Value of SssgSwitchUeCfg.sssgSwitchPmIdentity attribute must be 1 for UEs configured with a sparse search space set group. Bin[3]: Aggregated volume of successfully transmitted downlink MAC PDUs for DRB or SRB for UEs configured with search space set group switching. Value of SssgSwitchUeCfg.sssgSwitchPmIdentity attribute must be 2 for UEs configured with a dense search space set group. ... Bin[15]: Aggregated volume of successfully transmitted downlink MAC PDUs for DRB or SRB for UEs configured with search space set group switching. Value of SssgSwitchUeCfg.sssgSwitchPmIdentity attribute must be 8 for UEs configured with a dense search space set group. Bin[16]: Aggregated volume of successfully transmitted downlink MAC PDUs for DRB or SRB for UEs configured with search space set group switching. Value of SssgSwitchUeCfg.sssgSwitchPmIdentity attribute must be 8 for UEs configured with a sparse search space set group. Unit: 100 bytes.";
      type ietfyang:mac-address;
      max-elements 17;
    }
    leaf-list pmMacRBSymUsedPdcchTypeAAggrLvl4Sssg {
      description "Number of resource block symbols used by PDCCH with aggregation level 4 for scheduling of PDSCH or PUSCH using mapping type A in search space set group. Includes DMRS and PTRS embedded in resources. PDF ranges: Bin[0]: Accumulated downlink resource block symbols that use PDCCH with aggregation level 4 for UEs that are not configured with search space set group switching. Bin[1]: Accumulated downlink resource block symbols that use PDCCH with aggregation level 4 for UEs configured with search space set group switching. Value of SssgSwitchUeCfg.sssgSwitchPmIdentity attribute must be 1 for UEs configured with a dense search space set group. Bin[2]: Accumulated downlink resource block symbols that use PDCCH with aggregation level 4 for UEs configured with search space set group switching. Value of SssgSwitchUeCfg.sssgSwitchPmIdentity attribute must be 1 for UEs configured with a sparse search space set group. Bin[3]: Accumulated downlink resource block symbols that use PDCCH with aggregation level 4 for UEs configured with search space set group switching. Value of SssgSwitchUeCfg.sssgSwitchPmIdentity attribute must be 2 for UEs configured with a dense search space set group. ... Bin[15]: Accumulated downlink resource block symbols that use PDCCH with aggregation level 4 for UEs configured with search space set group switching. Value of SssgSwitchUeCfg.sssgSwitchPmIdentity attribute must be 8 for UEs configured with a dense search space set group. Bin[16]: Accumulated downlink resource block symbols that use PDCCH with aggregation level 4 for UEs configured with search space set group switching. Value of SssgSwitchUeCfg.sssgSwitchPmIdentity attribute must be 8 for UEs configured with a sparse search space set group. Unit: N/A.";
      type ietfyang:mac-address;
      max-elements 17;
    }
    leaf pmMacHarqDlNack64QamInit {
      description "Total number of unsuccessful initial downlink HARQ transmissions using 64-QAM modulation. Initial transmission is first transmission on HARQ process. Unit: N/A.";
      type ietfyang:mac-address;
      config false;
    }
    leaf pmRadioBeamSwitchSucc {
      description "Number of wide beam switches with successful uplink decoding after quasi co-location (QCL) switch. Measured when this cell is used as PSCell. Unit: N/A.";
      type uint64;
      config false;
    }
    leaf-list pmRadioUeRepCqi64QamRank1Distr {
      description "Distribution of UE-reported CQI values related to rank 1 transmissions when highest modulation order supported in downlink (DL) in NR cell is 64-QAM. CQI values and interpretations correspond to entries in Table 5.2.2.1-2 in 3GPP 38.214 for reporting CQI based on QPSK, 16-QAM, and 64-QAM. Unit: N/A Ranges: Bin[0]: CQI = 0 Bin[1]: CQI = 1 Bin[2]: CQI = 2 Bin[3]: CQI = 3 Bin[4]: CQI = 4 Bin[5]: CQI = 5 Bin[6]: CQI = 6 Bin[7]: CQI = 7 Bin[8]: CQI = 8 Bin[9]: CQI = 9 Bin[10]: CQI = 10 Bin[11]: CQI = 11 Bin[12]: CQI = 12 Bin[13]: CQI = 13 Bin[14]: CQI = 14 Bin[15]: CQI = 15.";
      type uint64;
      max-elements 16;
    }
    leaf pmMacThpDlMax {
      description "Maximum throughput of successfully transmitted downlink MAC PDUs for DRB or SRB using cell as PCell, SCell, or PSCell. In the case of carrier aggregation, counter value is a combination of PCell (PSCell) and SCell and is accumulated in PCell (PSCell). Time period is fixed at one second. Unit: bytes per second.";
      type ietfyang:mac-address;
      config false;
    }
    leaf pmPuschSchedActivity {
      description "Total duration of slots where at least one MAC SDU is received on PUSCH. Unit: 125 microseconds.";
      type uint64;
      config false;
    }
    leaf-list pmRadioNarrowBeamAcqTimeDistr {
      description "Number of instances when time between PRACH and P2 refinement falls within a specific time range. P2 refinement means successful switch from wide beam to narrow beam. Unit: N/A Ranges: Bin[0]: [0..1] ms Bin[1]: ]1..2] ms Bin[2]: ]2..3] ms Bin[3]: ]3..4] ms Bin[4]: ]4..5] ms Bin[5]: ]5..6] ms Bin[6]: ]6..7] ms Bin[7]: ]7..8] ms Bin[8]: ]8..9] ms Bin[9]: ]9..10] ms Bin[10]: ]10..20] ms Bin[11]: ]20..30] ms Bin[12]: ]30..40] ms Bin[13]: ]40..50] ms Bin[14]: ]50..60] ms Bin[15]: ]60..70] ms Bin[16]: ]70..80] ms Bin[17]: ]80..90] ms Bin[18]: ]90..100] ms Bin[19]: ]100..] ms.";
      type uint64;
      max-elements 20;
    }
    leaf-list pmRadioRecInterferencePwrSpecialSlot4Distr {
      description "Absolute power value of SRS comb offsets in each uplink symbol of special slot 4. The absolute power value is expressed in units of 0.1 dBm. Bins correspond to SRS comb offsets in each uplink symbol. This ensures compatibility between the lengths of uplink symbols in a special slot. To extract average interference power for each bin across a ROP, divide by pmRadioRecInterferencePwrSlotSamp. Number of bins corresponds to maximum six uplink symbols in a special slot and four comb offsets in each uplink symbol. Bins support the following symbol number and comb offset combinations: Bin[0]: First comb offset in last uplink symbol of special slot Bin[1]: Second comb offset in last uplink symbol of special slot Bin[2]: Third comb offset in last uplink symbol of special slot Bin[3]: Fourth comb offset in last uplink symbol of special slot Bin[4]: First comb offset in second uplink symbol from last of special slot Bin[5]: Second comb offset in second uplink symbol from last of special slot .... Bin[22]: Third comb offset in sixth uplink symbol from last of special slot Bin[23]: Fourth comb offset in sixth uplink symbol from last of special slot Note: For TDD UL-DL pattern 'DDSSUUDDDD DDSSUUDDDD', there's no ul symbol in the first and the third S slot. Only the second and the fourth S slot will be pegged. So, only pmRadioRecInterferencePwrSpecialSlot1Distr and pmRadioRecInterferencePwrSpecialSlot2Distr will be used..";
      type uint64;
      max-elements 24;
    }
    leaf pmMacHarqUlNack256Qam {
      description "Total number of unsuccessful HARQ transmissions with 256-QAM UL. Unit: N/A.";
      type ietfyang:mac-address;
      config false;
    }
    leaf pmMacVolDlSCell {
      description "Aggregated volume of successfully transmitted DL MAC PDUs for DRB or SRB using cell as SCell. Unit: bytes.";
      type ietfyang:mac-address;
      config false;
    }
    leaf pmMacHarqDlAckQpsk {
      description "Total number of successful downlink HARQ transmissions using QPSK modulation. Unit: N/A.";
      type ietfyang:mac-address;
      config false;
    }
    leaf-list pmMacLatTimeDlDrxSyncQos {
      description "Aggregated time for downlink MAC latency measurement for each QoS with DRX impact but without out-of-sync impact. DL MAC latency measures MAC scheduling latency between reception of packet in empty DL buffer and transmission of first packet. Unit: 125 microseconds Compressed: True.";
      type ietfyang:mac-address;
      max-elements 256;
    }
    leaf pmMacHarqDlDtx16Qam {
      description "Total number of occasions when downlink HARQ feedback for HARQ transmission using 16-QAM modulation could not be detected from UE. Unit: N/A.";
      type ietfyang:mac-address;
      config false;
    }
    leaf-list pmMacHarqDlNack16QamInitSlotDistr {
      description "For each downlink slot, bin that corresponds to number of unsuccessful initial HARQ PDSCH transmissions using 16-QAM modulation in slot is incremented. HARQ transmissions used for BWP DCI switch Scheduling Request (SR) are not pegged. Unit: N/A Ranges: Bin[0]: Total number of unsuccessful initial downlink HARQ transmissions using 16-QAM on slot 0. Bin[1]: Total number of unsuccessful initial downlink HARQ transmissions using 16-QAM on slot 1. Bin[2]: Total number of unsuccessful initial downlink HARQ transmissions using 16-QAM on slot 2. Bin[3]: Total number of unsuccessful initial downlink HARQ transmissions using 16-QAM on slot 3. Bin[4]: Total number of unsuccessful initial downlink HARQ transmissions using 16-QAM on slot 4. Bin[5]: Total number of unsuccessful initial downlink HARQ transmissions using 16-QAM on slot 5. Bin[6]: Total number of unsuccessful initial downlink HARQ transmissions using 16-QAM on slot 6. Bin[7]: Total number of unsuccessful initial downlink HARQ transmissions using 16-QAM on slot 7. Bin[8]: Total number of unsuccessful initial downlink HARQ transmissions using 16-QAM on slot 8. Bin[9]: Total number of unsuccessful initial downlink HARQ transmissions using 16-QAM on slot 9. Bin[10]: Total number of unsuccessful initial downlink HARQ transmissions using 16-QAM on slot 10. Bin[11]: Total number of unsuccessful initial downlink HARQ transmissions using 16-QAM on slot 11. Bin[12]: Total number of unsuccessful initial downlink HARQ transmissions using 16-QAM on slot 12. Bin[13]: Total number of unsuccessful initial downlink HARQ transmissions using 16-QAM on slot 13. Bin[14]: Total number of unsuccessful initial downlink HARQ transmissions using 16-QAM on slot 14. Bin[15]: Total number of unsuccessful initial downlink HARQ transmissions using 16-QAM on slot 15. Bin[16]: Total number of unsuccessful initial downlink HARQ transmissions using 16-QAM on slot 16. Bin[17]: Total number of unsuccessful initial downlink HARQ transmissions using 16-QAM on slot 17. Bin[18]: Total number of unsuccessful initial downlink HARQ transmissions using 16-QAM on slot 18. Bin[19]: Total number of unsuccessful initial downlink HARQ transmissions using 16-QAM on slot 19..";
      type ietfyang:mac-address;
      max-elements 20;
    }
    leaf pmCellDowntimeMan {
      description "Length of time the cell is manually disabled. Unit: seconds.";
      type uint64;
      config false;
    }
    leaf-list pmRadioPreambleSinrMsg3SuccTx4Distr {
      description "Total number of successful Msg3 counts for fourth transmission attempt for a preamble SINR bin. Ranges: Bin[0]: [..-15] dB Bin[1]: ]-15..-12] dB Bin[2]: ]-12..-9] dB Bin[3]: ]-9..-6] dB Bin[4]: ]-6..-3] dB Bin[5]: ]-3..] dB.";
      type uint64;
      max-elements 6;
    }
    leaf pmMacHarqDlDtx256Qam {
      description "Total number of occasions when downlink HARQ feedback for HARQ transmission using 256-QAM modulation could not be detected from UE. Unit: N/A.";
      type ietfyang:mac-address;
      config false;
    }
    leaf pmRadioRaCfFailMsg1DiscSched {
      description "Number of CFRA preambles that are discarded because number of scheduled Random Access Msg3 transmissions exceeds maximum. For CFRA, Msg3 is PUSCH scheduled by RAR uplink grant. Unit: N/A.";
      type uint64;
      config false;
    }
    leaf-list pmRadioUeRepCqi64QamRank3Distr {
      description "Distribution of UE-reported CQI values related to rank 3 transmissions when highest modulation order supported in downlink (DL) in NR cell is 64-QAM. CQI values and interpretations correspond to entries in Table 5.2.2.1-2 in 3GPP 38.214 for reporting CQI based on QPSK, 16-QAM, and 64-QAM. Unit: N/A Ranges: Bin[0]: CQI = 0 Bin[1]: CQI = 1 Bin[2]: CQI = 2 Bin[3]: CQI = 3 Bin[4]: CQI = 4 Bin[5]: CQI = 5 Bin[6]: CQI = 6 Bin[7]: CQI = 7 Bin[8]: CQI = 8 Bin[9]: CQI = 9 Bin[10]: CQI = 10 Bin[11]: CQI = 11 Bin[12]: CQI = 12 Bin[13]: CQI = 13 Bin[14]: CQI = 14 Bin[15]: CQI = 15.";
      type uint64;
      max-elements 16;
    }
    leaf pmMacRBSymUsedPdcchTypeA {
      description "Aggregated number of resource block symbols used by PDCCH for scheduling of PDSCH or PUSCH using mapping type A. This includes DMRS and PTRS embedded in resources. Unit: N/A.";
      type ietfyang:mac-address;
      config false;
    }
    leaf pmRlcArqDlAck {
      description "Total number of successful RLC SDU transmissions (ACKs) in downlink (DL). Only applicable to RLC AM bearers. In NR, the RLC SN is associated with RLC SDUs and not RLC PDUs. The arq_dl_ack and arq_dl_nack are related to RLC SDUs ACKed and RLC PDU or RLC SDU segments NACKed. When carrier aggregation is used, total number of successful RLC SDU transmissions (ACKs) in DL is registered on PCell of UE..";
      type uint64;
      config false;
    }
    leaf-list pmRadioPuschTable1McsDistr {
      description "Distribution of MCS used for PUSCH transmissions where MCS index table 1 is applied and UE instances are enabled with up to 64-QAM. For more information, see 3GPP TS 38.214, Table 6.1.4.1-1 and Table 5.1.3.1-1 (depending on whether Transform Precoding is enabled/disabled). Each bin represents a specific MCS. Unit: N/A Ranges: Bin[0]: MCS = 0 Bin[1]: MCS = 1 Bin[2]: MCS = 2 Bin[3]: MCS = 3 Bin[4]: MCS = 4 Bin[5]: MCS = 5 Bin[6]: MCS = 6 Bin[7]: MCS = 7 Bin[8]: MCS = 8 Bin[9]: MCS = 9 Bin[10]: MCS = 10 Bin[11]: MCS = 11 Bin[12]: MCS = 12 Bin[13]: MCS = 13 Bin[14]: MCS = 14 Bin[15]: MCS = 15 Bin[16]: MCS = 16 Bin[17]: MCS = 17 Bin[18]: MCS = 18 Bin[19]: MCS = 19 Bin[20]: MCS = 20 Bin[21]: MCS = 21 Bin[22]: MCS = 22 Bin[23]: MCS = 23 Bin[24]: MCS = 24 Bin[25]: MCS = 25 Bin[26]: MCS = 26 Bin[27]: MCS = 27 Bin[28]: MCS = 28 Bin[29]: MCS = 29 Bin[30]: MCS = 30 Bin[31]: MCS = 31.";
      type uint64;
      max-elements 32;
    }
    leaf pmMacHarqDlAck256QamInit {
      description "Total number of successful initial downlink HARQ transmissions using 256-QAM modulation. Initial transmission is first transmission on HARQ process. Unit: N/A.";
      type ietfyang:mac-address;
      config false;
    }
    leaf pmPdschSchedActivity {
      description "Total duration of slots with downlink PDSCH scheduling activity. Unit: 125 microseconds.";
      type uint64;
      config false;
    }
    leaf-list pmRadioPreambleSinrMsg3SuccTx1Distr {
      description "Total number of successful Msg3 counts for first transmission attempt for a preamble SINR bin. Ranges: Bin[0]: [..-15] dB Bin[1]: ]-15..-12] dB Bin[2]: ]-12..-9] dB Bin[3]: ]-9..-6] dB Bin[4]: ]-6..-3] dB Bin[5]: ]-3..] dB.";
      type uint64;
      max-elements 6;
    }
    leaf pmActiveUeDlSum {
      description "Number of active UE instances that have DRB data in UE-dedicated downlink buffer. Unit: N/A.";
      type uint64;
      config false;
    }
    leaf-list pmMacVolDlDrbSingleBurstQos {
      description "Aggregated volume of downlink MAC SDUs for single-burst cases that are transmitted for HARQ initial transmission for each DRB for each QoS. Single-burst case is when new packet arrives to empty buffer and buffer is drained by single scheduling occasion. HARQ retransmission is excluded. Unit: bytes Compressed: True.";
      type ietfyang:mac-address;
      max-elements 256;
    }
    leaf pmMacHarqUlAck64QamInit {
      description "Total number of successful initial HARQ transmissions in uplink using 64-QAM modulation. Initial transmission is first transmission on HARQ process, where NDI bit in DCI message is toggled. Unit: N/A.";
      type ietfyang:mac-address;
      config false;
    }
    leaf-list pmMeasGapUeSumDistr {
      description "Sum of active UEs with measurement gap configured by NRCellDU. Sample is taken every 5 seconds. Unit: N/A Ranges: Bin[0]: Gap pattern 0 Bin[1]: Gap pattern 1 Bin[2]: Gap pattern 2 Bin[3]: Gap pattern 3 Bin[4]: Not used Bin[5]: Not used Bin[6]: Not used Bin[7]: Not used Bin[8]: Not used Bin[9]: Not used Bin[10]: Not used Bin[11]: Not used Bin[12]: Not used Bin[13]: Not used Bin[14]: Gap pattern 14 Bin[15]: Not used Bin[16]: Not used Bin[17]: Not used Bin[18]: Not used Bin[19]: Not used Bin[20]: Not used Bin[21]: Not used Bin[22]: Not used Bin[23]: Not used Compressed: True.";
      type uint64;
      max-elements 24;
    }
    leaf-list pmMacRBSymUsedPdschMuMimoLayerDistr {
      description "Distribution of aggregated number of resource block symbols used for PDSCH by a variable number of co-scheduled layers as a result of code-book based MU-MIMO. DMRS and PTRS embedded in PDSCH resources are included. Unit: N/A Ranges: Bin[0]: Reserved - Not Used. Bin[1]: Number of resource block symbols scheduled with two layers. Bin[2]: Number of resource block symbols scheduled with three layers. Bin[3]: Number of resource block symbols scheduled with four layers. Bin[4]: Number of resource block symbols scheduled with five layers. Bin[5]: Number of resource block symbols scheduled with six layers. Bin[6]: Number of resource block symbols scheduled with seven layers. Bin[7]: Number of resource block symbols scheduled with eight layers. Bin[8]: Reserved for future MU-MIMO. Bin[9]: Reserved for future MU-MIMO. Bin[10]: Reserved for future MU-MIMO. Bin[11]: Reserved for future MU-MIMO. Bin[12]: Reserved for future MU-MIMO. Bin[13]: Reserved for future MU-MIMO. Bin[14]: Reserved for future MU-MIMO. Bin[15]: Reserved for future MU-MIMO..";
      type ietfyang:mac-address;
      max-elements 16;
    }
    leaf-list pmRadioSinrPucchF2Distr {
      description "Distribution of SINR values calculated for PUCCH format 2. Unit: N/A Bin[0]: [..-15] dB Bin[1]: ]-15..-12] dB Bin[2]: ]-12..-9] dB Bin[3]: ]-9..-6] dB Bin[4]: ]-6..-3] dB Bin[5]: ]-3..0] dB Bin[6]: ]0..3] dB Bin[7]: ]3..6] dB Bin[8]: ]6..9] dB Bin[9]: ]9..] dB.";
      type uint64;
      max-elements 10;
    }
    leaf pmMacOffloadVolDlSCell {
      description "Aggregated volume of successfully transmitted DL MAC PDUs for DRB or SRB offloaded to intra-gNodeB SCells and external inter-gNodeB SCells when this cell is used as PCell. Unit: bytes.";
      type ietfyang:mac-address;
      config false;
    }
    leaf pmMacRBSymUsedPdschTypeABroadcasting {
      description "Aggregated number of resource block symbols used for PDSCH mapping type A broadcasting during complete ROP. DMRS and PTRS embedded in PDSCH resources are included. Unit: N/A.";
      type ietfyang:mac-address;
      config false;
    }
    leaf pmMacHarqUlNack64Qam {
      description "Total number of unsuccessful HARQ transmissions in uplink using 64-QAM modulation. Unit: N/A.";
      type ietfyang:mac-address;
      config false;
    }
    leaf-list pmPuschSchedEntityInclPreschedDistr {
      description "For each uplink slot, bin that corresponds to number of PUSCH scheduled entities is incremented. Includes prescheduling. For High-Band, only uplink-capable cells, where value of NRSectorCarrier.txDirection attribute is DL_AND_UL, are incremented. Unit: N/A Ranges: Bin[0]: Zero PUSCH scheduled entities in uplink slot. Bin[1]: One PUSCH scheduled entity in uplink slot. Bin[2]: Two PUSCH scheduled entities in uplink slot. Bin[3]: Three PUSCH scheduled entities in uplink slot. Bin[4]: Four PUSCH scheduled entities in uplink slot. Bin[5]: Five PUSCH scheduled entities in uplink slot. Bin[6]: Six PUSCH scheduled entities in uplink slot. Bin[7]: Seven PUSCH scheduled entities in uplink slot. Bin[8]: Eight PUSCH scheduled entities in uplink slot. Bin[9]: Nine PUSCH scheduled entities in uplink slot. Bin[10]: 10 PUSCH scheduled entities in uplink slot. Bin[11]: 11 PUSCH scheduled entities in uplink slot. Bin[12]: 12 PUSCH scheduled entities in uplink slot. Bin[13]: 13 PUSCH scheduled entities in uplink slot. Bin[14]: 14 PUSCH scheduled entities in uplink slot. Bin[15]: 15 PUSCH scheduled entities in uplink slot. Bin[16]: 16 PUSCH scheduled entities in uplink slot. Bin[17]: 17 PUSCH scheduled entities in uplink slot. Bin[18]: 18 PUSCH scheduled entities in uplink slot. Bin[19]: 19 PUSCH scheduled entities in uplink slot. Bin[20]: 20 PUSCH scheduled entities in uplink slot. Bin[21]: 21 PUSCH scheduled entities in uplink slot. Bin[22]: 22 PUSCH scheduled entities in uplink slot. Bin[23]: 23 PUSCH scheduled entities in uplink slot. Bin[24]: 24 PUSCH scheduled entities in uplink slot. Bin[25]: 25 PUSCH scheduled entities in uplink slot. Bin[26]: 26 PUSCH scheduled entities in uplink slot. Bin[27]: 27 PUSCH scheduled entities in uplink slot. Bin[28]: 28 PUSCH scheduled entities in uplink slot. Bin[29]: 29 PUSCH scheduled entities in uplink slot. Bin[30]: 30 PUSCH scheduled entities in uplink slot. Bin[31]: 31 PUSCH scheduled entities in uplink slot. Bin[32]: 32 PUSCH scheduled entities in uplink slot. Bin[33]: 33 PUSCH scheduled entities in uplink slot. Bin[34]: 34 PUSCH scheduled entities in uplink slot. Bin[35]: 35 PUSCH scheduled entities in uplink slot. Bin[36]: 36 PUSCH scheduled entities in uplink slot..";
      type uint64;
      max-elements 37;
    }
    leaf pmMacHarqUlAck64Qam {
      description "Total number of successful HARQ transmissions in uplink using 64-QAM modulation. Unit: N/A.";
      type ietfyang:mac-address;
      config false;
    }
    leaf pmEeAllResBlockUsed {
      description "Aggregated number of times where all resource blocks in slot are used. Unit: N/A.";
      type uint64;
      config false;
    }
    leaf pmMacHarqDlNack16Qam {
      description "Total number of unsuccessful downlink HARQ transmissions using 16-QAM modulation. Unit: N/A.";
      type ietfyang:mac-address;
      config false;
    }
    leaf pmMacRBSymUsedPdcchTypeAAggrLvl16 {
      description "Number of resource block symbols used by PDCCH with aggregation level 16 for scheduling of PDSCH or PUSCH using mapping type A. This includes DMRS and PTRS embedded in resources. Unit: N/A.";
      type ietfyang:mac-address;
      config false;
    }
    leaf pmRadioSsbBeamSwitch {
      description "Number of SSB beam switches in cell. Measured when this cell is used as PSCell..";
      type uint32;
      config false;
    }
    leaf pmMacHarqDlAck256Qam {
      description "Total number of successful downlink HARQ transmissions using 256-QAM modulation. Unit: N/A.";
      type ietfyang:mac-address;
      config false;
    }
    leaf-list pmMacRBSymUsedPdcchTypeAAggrLvl1Bwp {
      description "Number of resource block symbols used by PDCCH with aggregation level 1 for scheduling of PDSCH or PUSCH using mapping type A in BWP. This includes DMRS and PTRS embedded in resources. PDF ranges: Bin[0]: Accumulated downlink resource block symbols used by PDCCH with aggregation level 1 in the first BWP referenced in NRCellDU MO by BWPSet.allBWPRegularRef attribute Bin[1]: Accumulated downlink resource block symbols used by PDCCH with aggregation level 1 in the second BWP referenced in NRCellDU MO by BWPSet.allBWPRegularRef attribute Bin[2]: Accumulated downlink resource block symbols used by PDCCH with aggregation level 1 in the third BWP referenced in NRCellDU MO by BWPSet.allBWPRegularRef attribute ... Bin[15]: Accumulated downlink resource block symbols used by PDCCH with aggregation level 1 in the sixteenth BWP referenced in NRCellDU MO by BWPSet.allBWPRegularRef attribute Unit: N/A.";
      type ietfyang:mac-address;
      max-elements 16;
    }
    leaf-list pmRadioUeRepCqi64QamRank4Distr {
      description "Distribution of UE-reported CQI values related to rank 4 transmissions when highest modulation order supported in downlink (DL) in NR cell is 64-QAM. CQI values and interpretations correspond to entries in Table 5.2.2.1-2 in 3GPP 38.214 for reporting CQI based on QPSK, 16-QAM, and 64-QAM. Unit: N/A Ranges: Bin[0]: CQI = 0 Bin[1]: CQI = 1 Bin[2]: CQI = 2 Bin[3]: CQI = 3 Bin[4]: CQI = 4 Bin[5]: CQI = 5 Bin[6]: CQI = 6 Bin[7]: CQI = 7 Bin[8]: CQI = 8 Bin[9]: CQI = 9 Bin[10]: CQI = 10 Bin[11]: CQI = 11 Bin[12]: CQI = 12 Bin[13]: CQI = 13 Bin[14]: CQI = 14 Bin[15]: CQI = 15.";
      type uint64;
      max-elements 16;
    }
    leaf-list pmMacVolUlSCellExtBwp {
      description "Data volume in MAC SDUs successfully received in uplink when cell is used as external inter-gNodeB SCell and inter-capacity module SCell differentiated by BWP. BWP value is always zero for downlink. PDF ranges: Bin[0]: Data volume in MAC SDUs successfully received in uplink when cell is used as external inter-gNodeB SCell and inter-capacity module SCell in first BWP referenced in NRCellDU MO by BWPSet.allBWPRegularRef attribute. Bin[1]: Data volume in MAC SDUs successfully received in uplink when cell is used as external inter-gNodeB SCell and inter-capacity module SCell in second BWP referenced in NRCellDU MO by BWPSet.allBWPRegularRef attribute. Bin[2]: Data volume in MAC SDUs successfully received in uplink when cell is used as external inter-gNodeB SCell and inter-capacity module SCell in third BWP referenced in NRCellDU MO by BWPSet.allBWPRegularRef attribute. ... Bin[15]: Data volume in MAC SDUs successfully received in uplink when cell is used as external inter-gNodeB SCell and inter-capacity module SCell in sixteenth BWP referenced in NRCellDU MO by BWPSet.allBWPRegularRef attribute..";
      type ietfyang:mac-address;
      max-elements 16;
    }
    leaf-list pmRadioUeRepCqi256QamRank3Distr {
      description "Distribution of UE-reported CQI values related to rank 3 transmissions when highest modulation order supported in downlink (DL) in NR cell is configured to be 256-QAM. CQI values and interpretations correspond to entries in Table 5.2.2.1-3 in 3GPP 38.214 for reporting CQI based on QPSK, 16-QAM, 64-QAM, and 256-QAM. Unit: N/A Ranges: Bin[0]: CQI = 0 Bin[1]: CQI = 1 Bin[2]: CQI = 2 Bin[3]: CQI = 3 Bin[4]: CQI = 4 Bin[5]: CQI = 5 Bin[6]: CQI = 6 Bin[7]: CQI = 7 Bin[8]: CQI = 8 Bin[9]: CQI = 9 Bin[10]: CQI = 10 Bin[11]: CQI = 11 Bin[12]: CQI = 12 Bin[13]: CQI = 13 Bin[14]: CQI = 14 Bin[15]: CQI = 15.";
      type uint64;
      max-elements 16;
    }
    leaf pmRimRS1EnoughNotEnoughRatioMax {
      description "Ratio of RS1 with not_enough indication from total detected RS1 reported by aggressor cells with RS1 detection..";
      type int64;
      config false;
    }
    leaf-list pmRadioPreambleSinrMsg3SuccBeyondTx4Distr {
      description "Total number of successful Msg3 counts for more than four transmission attempts for a preamble SINR bin. Ranges: Bin[0]: [..-15] dB Bin[1]: ]-15..-12] dB Bin[2]: ]-12..-9] dB Bin[3]: ]-9..-6] dB Bin[4]: ]-6..-3] dB Bin[5]: ]-3..] dB.";
      type uint64;
      max-elements 6;
    }
    leaf pmMassiveMimoSleepOppTimeTxMute {
      description "Accumulates potential amount of time a cell can be in TXMUTE state. Unit: seconds.";
      type uint64;
      config false;
    }
    leaf pmRadioRaCbSuccMsg3 {
      description "Number of successfully detected random access Msg3 messages for CBRA. Unit: messages.";
      type uint64;
      config false;
    }
    leaf-list pmRadioUeRepPmiSecondaryCsiRsRank1Distr {
      description "Distribution of precoding weights reported by UE for rank 1 codebook associated with secondary CSI-RS. Indicates spatial distribution of UEs using cell as PCell. Type 1 single-panel codebooks are defined in 3GPP TS 38.214. Represents distribution of requested departure angles from AAS-capable radio unit as estimated from UE CSI feedback, specifically main and diversity direction of PMI values. It is not recommended to use this PM counter for Remote radio units. For more information, see Massive MIMO Mid-Band and Manage Massive MIMO NR in CPI library. Unit: N/A Compressed: True.";
      type uint64;
      max-elements 256;
    }
    leaf pmMacThpUlMax {
      description "Maximum UL MAC SDU throughput achieved in Cell during ROP. Time period is fixed at one second. Unit: bytes per second.";
      type ietfyang:mac-address;
      config false;
    }
    leaf-list pmMacVolDlDrbOverlapLastSlotQoS {
      description "Aggregated volume of downlink MAC SDUs transmitted for HARQ initial transmission in last slot of the burst that overlaps with subsequent burst when buffer is emptied for each QoS. HARQ retransmission is excluded. Unit: bytes Compressed: True.";
      type ietfyang:mac-address;
      max-elements 256;
    }
    leaf-list pmPagBundledUeSampDistr {
      description "Number of RRC paging messages constructed for each PO. Both Core Network paging and Radio Access Network paging are included. Unit: N/A Ranges: Bin[0]: PO Index = 0 Bin[1]: PO Index = 1 Bin[2]: PO Index = 2 Bin[3]: PO Index = 3.";
      type uint64;
      max-elements 4;
    }
    leaf-list pmRadioPucchSrResourcesRestoredDistr {
      description "Distribution represents Scheduling Request (SR) on RACH triggered RRC reconfigurations. Indicates number of restored PUCCH SR resources between attach and release on NR leg. Unit: N/A Bin[0]: 0 PUCCH SR resources restored. Bin[1]: 1 PUCCH SR resources restored. Bin[2]: 2 PUCCH SR resources restored. Bin[3]: 3-4 PUCCH SR resources restored. Bin[4]: 5-6 PUCCH SR resources restored. Bin[5]: 7-8 PUCCH SR resources restored. Bin[6]: 9-10 PUCCH SR resources restored. Bin[7]: 11-12 PUCCH SR resources restored. Bin[8]: More than 12 PUCCH SR resources restored..";
      type uint32;
      max-elements 9;
    }
    leaf pmRadioMacSrPeriodicitySwitchGoodCoverage {
      description "Indicates number of scheduling request on PUCCH periodicity reconfigurations to shorter duration. Unit: N/A.";
      type ietfyang:mac-address;
      config false;
    }
    leaf-list pmMacRBSymUsedPdschAdvSuMimoTxRankDistr {
      description "Distribution of aggregated number of resource block symbols used for PDSCH by sounding antennas and DL rank as a result of reciprocity-based SU-MIMO. DMRS and PTRS embedded in PDSCH resources are included. Unit: N/A Ranges: Bin[0]: Number of resource block symbols scheduled with 1TX/4RX R1. Bin[1]: Number of resource block symbols scheduled with 1TX/4RX R2. Bin[2]: Number of resource block symbols scheduled with 1TX/4RX R3. Bin[3]: Number of resource block symbols scheduled with 1TX/4RX R4. Bin[4]: Number of resource block symbols scheduled with 2TX/4RX R1. Bin[5]: Number of resource block symbols scheduled with 2TX/4RX R2. Bin[6]: Number of resource block symbols scheduled with 2TX/4RX R3. Bin[7]: Number of resource block symbols scheduled with 2TX/4RX R4. Bin[8]: Number of resource block symbols scheduled with 4TX/4RX R1. Bin[9]: Number of resource block symbols scheduled with 4TX/4RX R2. Bin[10]: Number of resource block symbols scheduled with 4TX/4RX R3. Bin[11]: Number of resource block symbols scheduled with 4TX/4RX R4. Bin[12]: Number of resource block symbols scheduled with 1TX/2RX R1. Bin[13]: Number of resource block symbols scheduled with 1TX/2RX R2. Bin[14]: Number of resource block symbols scheduled with 2TX/2RX R1. Bin[15]: Number of resource block symbols scheduled with 2TX/2RX R2. Bin[16]: Number of resource block symbols scheduled with 1TX/1RX R1..";
      type ietfyang:mac-address;
      max-elements 17;
    }
    leaf pmPagDiscarded {
      description "Number of RRC paging messages discarded and not broadcast in cell. Both Core Network paging and Radio Access Network paging are included. Unit: NA.";
      type uint64;
      config false;
    }
    leaf-list pmMacRBSymUsedPdschAdvEisMuMimoTxRankDistr {
      description "Distribution of aggregated number of resource block symbols used for PDSCH by sounding antennas and downlink rank as a result of reciprocity-based Ericsson Interference Sensing (EIS) MU-MIMO. DMRS and PTRS embedded in PDSCH resources are included. Unit: N/A Ranges: Bin[0]: Number of resource block symbols scheduled with 1TX/4RX R1 in MU-MIMO. Bin[1]: Number of resource block symbols scheduled with 1TX/4RX R2 in MU-MIMO. Bin[2]: Number of resource block symbols scheduled with 1TX/4RX R3 in MU-MIMO. Bin[3]: Number of resource block symbols scheduled with 1TX/4RX R4 in MU-MIMO. Bin[4]: Number of resource block symbols scheduled with 2TX/4RX R1 in MU-MIMO. Bin[5]: Number of resource block symbols scheduled with 2TX/4RX R2 in MU-MIMO. Bin[6]: Number of resource block symbols scheduled with 2TX/4RX R3 in MU-MIMO. Bin[7]: Number of resource block symbols scheduled with 2TX/4RX R4 in MU-MIMO. Bin[8]: Number of resource block symbols scheduled with 4TX/4RX R1 in MU-MIMO. Bin[9]: Number of resource block symbols scheduled with 4TX/4RX R2 in MU-MIMO. Bin[10]: Number of resource block symbols scheduled with 4TX/4RX R3 in MU-MIMO. Bin[11]: Number of resource block symbols scheduled with 4TX/4RX R4 in MU-MIMO. Bin[12]: Number of resource block symbols scheduled with 1TX/2RX R1 in MU-MIMO. Bin[13]: Number of resource block symbols scheduled with 1TX/2RX R2 in MU-MIMO. Bin[14]: Number of resource block symbols scheduled with 2TX/2RX R1 in MU-MIMO. Bin[15]: Number of resource block symbols scheduled with 2TX/2RX R2 in MU-MIMO. Bin[16]: Number of resource block symbols scheduled with 1TX/1RX R1..";
      type ietfyang:mac-address;
      max-elements 17;
    }
    leaf pmMacRBSymRachSchedPusch {
      description "Number of resource block symbols where PSCell is configured for RACH but the symbols are used for scheduling on PUSCH. Unit: N/A.";
      type ietfyang:mac-address;
      config false;
    }
    leaf-list pmMacRBSymUsedPuschMimoLayerDistr {
      description "Distribution of aggregated number of resource block symbols used for PUSCH by different number of coscheduled layers as a result of SU-MIMO or MU-MIMO. DMRS and PTRS embedded in PUSCH resources are included. Unit: N/A Ranges: Bin[0]: Number of resource block symbols scheduled with 1 layer. Bin[1]: Number of resource block symbols scheduled with 2 layers. Bin[2]: Number of resource block symbols scheduled with 3 layers. Bin[3]: Number of resource block symbols scheduled with 4 layers. Bin[4]: Number of resource block symbols scheduled with 5 layers. Bin[5]: Number of resource block symbols scheduled with 6 layers. Bin[6]: Number of resource block symbols scheduled with 7 layers. Bin[7]: Number of resource block symbols scheduled with 8 layers..";
      type ietfyang:mac-address;
      max-elements 8;
    }
    leaf-list pmMacSrsPdschAgeDistr {
      description "Distribution of the elapsed time between the latest received sounding reference signal (SRS) and current PDSCH. Unit: N/A Ranges: Bin[0]: [0..4] slot Bin[1]: [5..9] slot Bin[2]: [10..14] slot Bin[3]: [15..19] slot Bin[4]: [20..24] slot Bin[5]: [25..29] slot Bin[6]: [30..34] slot Bin[7]: [35..39] slot Bin[8]: [40..44] slot Bin[9]: [45..49] slot Bin[10]: [50..54] slot Bin[11]: [55..59] slot Bin[12]: [60..64] slot Bin[13]: [65..69] slot Bin[14]: [70..74] slot Bin[15]: [75..79] slot Bin[16]: [80..] slot.";
      type ietfyang:mac-address;
      max-elements 17;
    }
    leaf-list pmMacVolDlDrbQos {
      description "Aggregated volume of downlink MAC SDUs transmitted for HARQ initial transmission for each QoS. HARQ retransmission is excluded. Unit: bytes Compressed: True.";
      type ietfyang:mac-address;
      max-elements 256;
    }
    leaf pmMacRBSymUsedPdcchTypeB {
      description "Aggregated number of resource block symbols used by PDCCH for scheduling of PDSCH or PUSCH using mapping type B. This includes DMRS and PTRS embedded in resources. Unit: N/A.";
      type ietfyang:mac-address;
      config false;
    }
    leaf-list pmRadioSymbolDeltaIpnDistr {
      description "First and last symbols for delta IpN calculation are same as symbols used for rim detection. Measures delta IpN between first and last symbol for each TDD uplink-downlink switching period. Positive delta IpN value indicates that interference on first symbol is higher than on last symbol. Unit: dB Ranges: Bin[0]: [..-10] dB Bin[1]: ]-10..-5] dB Bin[2]: ]-5..-3] dB Bin[3]: ]-3..-1] dB Bin[4]: ]-1..1] dB Bin[5]: ]1..3] dB Bin[6]: ]3..5] dB Bin[7]: ]5..10] dB Bin[8]: ]10..] dB.";
      type uint64;
      max-elements 9;
    }
    leaf-list pmMacContentionDelayDlMaxQos {
      description "Maximum downlink MAC contention delay for each QoS. Time for HARQ initial transmission scheduling of DRB on PDSCH since last scheduled DRB (delta time between scheduling occasions). Unit: 125 microseconds Compressed: True.";
      type ietfyang:mac-address;
      max-elements 256;
    }
    leaf pmCellDowntimeManCbrs {
      description "Length of time CBRS-enabled cell is locked by Domain Coordinator due to reconfiguration. Unit: seconds.";
      type uint64;
      config false;
    }
    leaf pmDuCellDownUnlockMan {
      description "Number of times cell is successfully unlocked..";
      type uint64;
      config false;
    }
    leaf pmMacHarqDlDtxQpskInit {
      description "Total number of occasions when downlink HARQ feedback for initial HARQ transmission using QPSK modulation could not be detected from UE. Initial transmission is first transmission on HARQ process. Unit: N/A.";
      type ietfyang:mac-address;
      config false;
    }
    leaf pmMacTimeDlDrbLastSlotSamp {
      description "Aggregated number of samples for measuring time for last slot of burst scheduling of downlink DRB since last scheduled DRB (delta time between scheduling occasions). It is considered last slot if all data in DRB buffer is drained. It is considered part of a burst if there is at least one previous DL scheduling occasion that does not fully empty buffer. HARQ initial transmission is measured. HARQ retransmission is excluded. Unit: N/A.";
      type ietfyang:mac-address;
      config false;
    }
    leaf-list pmUeEffDopplerSpeedDistr {
      description "Distribution of measured effective speed values from all measured effective speeds. Ranges Bin[0]: Number of speed measurements within [0..20] km/h. Bin[1]: Number of speed measurements within ]20..40] km/h. Bin[2]: Number of speed measurements within ]40..60] km/h. Bin[3]: Number of speed measurements within ]60..80] km/h. Bin[4]: Number of speed measurements within ]80..100] km/h. Bin[5]: Number of speed measurements within ]100..120] km/h. Bin[6]: Number of speed measurements within ]120..140] km/h. Bin[7]: Number of speed measurements within ]140..160] km/h. Bin[8]: Number of speed measurements within ]160..180] km/h. Bin[9]: Number of speed measurements within ]180..200] km/h. Bin[10]: Number of speed measurements within ]200..220] km/h. Bin[11]: Number of speed measurements within ]220..240] km/h. Bin[12]: Number of speed measurements within ]240..260] km/h. Bin[13]: Number of speed measurements within ]260..280] km/h. Bin[14]: Number of speed measurements within ]280..300] km/h. Bin[15]: Number of speed measurements within ]300..] km/h..";
      type uint64;
      max-elements 16;
    }
    leaf pmMacPdcchBlockingPuschOccasions {
      description "Number of scheduling occasions when PDCCH limits number of sessions served by PUSCH. Scheduling occasion is when any number of requests are allocated PDCCH, PDSCH and PUSCH. Unit: N/A.";
      type ietfyang:mac-address;
      config false;
    }
    leaf pmMacRBSymUsedPdcchTypeBAggrLvl2 {
      description "Number of resource block symbols used by PDCCH with aggregation level 2 for scheduling of PDSCH or PUSCH using mapping type B. This includes DMRS and PTRS embedded in resources scheduling. Unit: N/A.";
      type ietfyang:mac-address;
      config false;
    }
    leaf pmRrcAccessFailMpLoad {
      description "Number of rejected RRC Connection procedures in NR SA because Baseband MP load control indicates OVERLOAD or VERY HIGH state. RRC Connection procedures can be one of the following options: - RRC Setup Request - RRC Resume Request - RRC Reestablishment Request.";
      type uint64;
      config false;
    }
    leaf pmMacVolUlOffloadSCell {
      description "MAC SDU volume successfully received through SCells when cell is used as PCell. Unit: bytes Deprecated: Since 23.Q4. Planned to be removed. Replaced by NRCellDU::pmMacOffloadVolUlSCell; MOM flags: noNotification.";
      type ietfyang:mac-address;
      config false;
      status deprecated;
    }
    leaf pmMacTimeDlCaConfigDrbActivity {
      description "Aggregated time for HARQ initial transmission scheduling activity of downlink DRB associated with carrier aggregation-configured UEs. Scheduling activity refers to time interval from first scheduling occasion of a burst until all data in DRB buffer is drained. Unit: 125 microseconds.";
      type ietfyang:mac-address;
      config false;
    }
    leaf-list pmMacTimeUlResDrbMaxQos {
      description "Maximum time in restricted uplink for each QoS. Unit: 125 microseconds Compressed: True.";
      type ietfyang:mac-address;
      max-elements 256;
    }
    leaf-list pmMacTimeDlDrbLastSlotSampQos {
      description "Aggregated number of samples for measuring time for last slot of burst scheduling of downlink DRB since last scheduled DRB (delta time between scheduling occasions). It is considered last slot if all data in DRB buffer is drained. It is considered part of a burst if there is at least one previous DL scheduling occasion that does not fully empty buffer. HARQ initial transmission is measured. HARQ retransmission is excluded. Samples from all DRBs with same QoS are accumulated. Unit: N/A Compressed: True.";
      type ietfyang:mac-address;
      max-elements 256;
    }
    leaf pmRadioMacTransUl2Layers {
      description "Total number of dual-layer uplink transmissions in each cell. Unit: N/A.";
      type ietfyang:mac-address;
      config false;
    }
    leaf-list pmMacVolPdschAdvMimoSinrThresUserDistr {
      description "Shows accumulated sum of data volume for first downlink transmission by a variable number of users that meet preset SINR thresholding conditions as a result of advanced beamforming. This PM counter can be used together with NRCellDU.pmMacRBSymUsedPdschAdvMimoSinrThresUserDistr PM counter to calculate SRS reciprocity resource block spectral efficiency. Unit: byte Ranges: Bin[0]: Accumulated sum of data volume for first downlink transmission for one user. Bin[1]: Accumulated sum of data volume for first downlink transmission for two users. Bin[2]: Accumulated sum of data volume for first downlink transmission for three users. Bin[3]: Accumulated sum of data volume for first downlink transmission for four users. Bin[4]: Accumulated sum of data volume for first downlink transmission for five users. Bin[5]: Accumulated sum of data volume for first downlink transmission for six users. Bin[6]: Accumulated sum of data volume for first downlink transmission for seven users. Bin[7]: Accumulated sum of data volume for first downlink transmission for eight users. Bin[8]: Reserved for future MU-MIMO. Bin[9]: Reserved for future MU-MIMO. Bin[10]: Reserved for future MU-MIMO. Bin[11]: Reserved for future MU-MIMO. Bin[12]: Reserved for future MU-MIMO. Bin[13]: Reserved for future MU-MIMO. Bin[14]: Reserved for future MU-MIMO. Bin[15]: Reserved for future MU-MIMO..";
      type ietfyang:mac-address;
      max-elements 16;
    }
    leaf pmMacHarqUlAck256QamInit {
      description "Total number of successful initial HARQ transmissions with 256-QAM uplink. Initial transmission is first transmission on HARQ process, where New Data Indicator (NDI) bit in DCI message is toggled. Unit: N/A.";
      type ietfyang:mac-address;
      config false;
    }
    leaf pmMacHarqUlAck16Qam {
      description "Total number of successful HARQ transmissions in uplink using 16-QAM modulation. Unit: N/A.";
      type ietfyang:mac-address;
      config false;
    }
    leaf-list pmRadioPuschPhrDistr {
      description "Distribution of UL Power Headroom reported by UE. Unit: N/A Ranges: Bin[0]: [0..3] PHR index Bin[1]: [4..7] PHR index Bin[2]: [8..11] PHR index Bin[3]: [12..15] PHR index Bin[4]: [16..19] PHR index Bin[5]: [20..23] PHR index Bin[6]: [24..27] PHR index Bin[7]: [28..31] PHR index Bin[8]: [32..35] PHR index Bin[9]: [36..39] PHR index Bin[10]: [40..43] PHR index Bin[11]: [44..47] PHR index Bin[12]: [48..51] PHR index Bin[13]: [52..55] PHR index Bin[14]: [56..59] PHR index Bin[15]: [60..63] PHR index.";
      type uint64;
      max-elements 16;
    }
    leaf-list pmMacSchedSlotDlTempAlarmSCellDistr {
      description "Aggregated number of scheduled downlink slots when SCells are active and UE temperature alarm is detected. Measured when this cell is used as PSCell. Unit: N/A Ranges: Bin[0]: Scheduled DL slots when UE temperature alarm is detected with 0 SCells activated. Bin[1]: Scheduled DL slots when UE temperature alarm is detected with 1 SCells activated. Bin[2]: Scheduled DL slots when UE temperature alarm is detected with 2 SCells activated. Bin[3]: Scheduled DL slots when UE temperature alarm is detected with 3 SCells activated. Bin[4]: Scheduled DL slots when UE temperature alarm is detected with 4 SCells activated. Bin[5]: Scheduled DL slots when UE temperature alarm is detected with 5 SCells activated. Bin[6]: Scheduled DL slots when UE temperature alarm is detected with 6 SCells activated. Bin[7]: Scheduled DL slots when UE temperature alarm is detected with 7 SCells activated..";
      type ietfyang:mac-address;
      max-elements 8;
    }
    leaf-list pmSessionTimeUeSssgSumDistr {
      description "Accumulated time sessions of UEs. PDF ranges: Bin[0]: Accumulated time sessions of UEs not configured with search space set group switching. Bin[1]: Accumulated time sessions of UEs configured with search space set group switching. Value of SssgSwitchUeCfg.sssgSwitchPmIdentity attribute must be 1 for UEs configured with a dense search space set group. Bin[2]: Accumulated time sessions of UEs configured with search space set group switching. Value of SssgSwitchUeCfg.sssgSwitchPmIdentity attribute must be 1 for UEs configured with a sparse search space set group. Bin[3]: Accumulated time sessions of UEs configured with search space set group switching. Value of SssgSwitchUeCfg.sssgSwitchPmIdentity attribute must be 2 for UEs configured with a dense search space set group. ... Bin[15]: Accumulated time sessions of UEs configured with search space set group switching. Value of SssgSwitchUeCfg.sssgSwitchPmIdentity attribute must be 8 for UEs configured with a dense search space set group. Bin[16]: Accumulated time sessions of UEs configured with search space set group switching. Value of SssgSwitchUeCfg.sssgSwitchPmIdentity attribute must be 8 for UEs configured with a sparse search space set group..";
      type uint64;
      max-elements 17;
    }
    leaf pmMacHarqDlNackQpsk {
      description "Total number of unsuccessful downlink HARQ transmissions using QPSK modulation. Unit: N/A.";
      type ietfyang:mac-address;
      config false;
    }
    leaf pmMacHarqUlAckQpskInit {
      description "Total number of successful initial HARQ transmissions in uplink using QPSK modulation. Initial transmission is first transmission on HARQ process, where NDI bit in DCI message is toggled. Unit: N/A.";
      type ietfyang:mac-address;
      config false;
    }
    leaf-list pmRadioSinrPuschDtxDistr {
      description "Total number of PUSCH DTX counts pegged at SINR values for each PUSCH transmission. Ranges: Bin[0]: [..-11] dB Bin[1]: ]-11..-8] dB Bin[2]: ]-8..-5] dB Bin[3]: ]-5..-2] dB Bin[4]: ]-2..1] dB Bin[5]: ]1..4] dB Bin[6]: ]4..7] dB Bin[7]: ]7..10] dB Bin[8]: ]10..13] dB Bin[9]: ]13..16] dB Bin[10]: ]16..] dB.";
      type uint64;
      max-elements 11;
    }
    leaf pmMacHarqUlNackQpskInit {
      description "Total number of unsuccessful initial HARQ transmissions in uplink using QPSK modulation. Initial transmission is first transmission on HARQ process, where NDI bit in DCI message is toggled. Unit: N/A.";
      type ietfyang:mac-address;
      config false;
    }
    leaf-list pmPdschSchedActivityBwp {
      description "Total duration of slots with downlink PDSCH scheduling activity in downlink BWP. For uplink BWP value is always zero. PDF ranges: Bin[0]: Total duration of slots with downlink PDSCH scheduling activity in the first BWP referenced in NRCellDU MO by BWPSet.allBWPRegularRef attribute Bin[1]: Total duration of slots with downlink PDSCH scheduling activity in the second BWP referenced in NRCellDU MO by BWPSet.allBWPRegularRef attribute Bin[2]: Total duration of slots with downlink PDSCH scheduling activity in the third BWP referenced in NRCellDU MO by BWPSet.allBWPRegularRef attribute ... Bin[15]: Total duration of slots with downlink PDSCH scheduling activity in the sixteenth BWP referenced in NRCellDU MO by BWPSet.allBWPRegularRef attribute Unit: 125 microseconds.";
      type uint64;
      max-elements 16;
    }
    leaf-list pmMacRBSymUsedPdcchOfdmSymDistr {
      description "Number of resource block symbols used for PDCCH for scheduling of PDSCH or PUSCH using mapping type A or Type B in OFDM-symbols. This includes DMRS and PTRS embedded in resources. Unit: N/A Ranges: Bin[0]: Accumulated downlink resource block symbols used by PDCCH in the 1st OFDM-symbol Bin[1]: Accumulated downlink resource block symbols used by PDCCH in the 2nd OFDM-symbol Bin[2]: Accumulated downlink resource block symbols used by PDCCH in the 3rd OFDM-symbol Bin[3]: Accumulated downlink resource block symbols used by PDCCH in the 4th OFDM-symbol Bin[4]: Accumulated downlink resource block symbols used by PDCCH in the 5th OFDM-symbol Bin[5]: Accumulated downlink resource block symbols used by PDCCH in the 6th OFDM-symbol Bin[6]: Accumulated downlink resource block symbols used by PDCCH in the 7th OFDM-symbol Bin[7]: Accumulated downlink resource block symbols used by PDCCH in the 8th OFDM-symbol Bin[8]: Accumulated downlink resource block symbols used by PDCCH in the 9th OFDM-symbol Bin[9]: Accumulated downlink resource block symbols used by PDCCH in the 10th OFDM-symbol Bin[10]: Accumulated downlink resource block symbols used by PDCCH in the 11th OFDM-symbol Bin[11]: Accumulated downlink resource block symbols used by PDCCH in the 12th OFDM-symbol Bin[12]: Accumulated downlink resource block symbols used by PDCCH in the 13th OFDM-symbol Bin[13]: Accumulated downlink resource block symbols used by PDCCH in the 14th OFDM-symbol.";
      type ietfyang:mac-address;
      max-elements 14;
    }
    leaf pmMacHarqUlDtx256QamInit {
      description "Number of DTX detections for initial HARQ transmissions with 256-QAM uplink. Initial transmission is first transmission on HARQ process, where NDI bit in DCI message is toggled. Unit: N/A.";
      type ietfyang:mac-address;
      config false;
    }
    leaf pmMacVolDlDrbOverlapLastSlot {
      description "Aggregated volume of downlink MAC SDUs transmitted for HARQ initial transmission in last slot of burst that overlaps with subsequent burst when buffer is emptied. HARQ retransmission is excluded. Unit: bytes.";
      type ietfyang:mac-address;
      config false;
    }
    leaf-list pmMacRBSymUsedPdschMimoLayerDistr {
      description "Distribution of aggregated number of resource block symbols used for PDSCH by different number of coscheduled layers as a result of SU-MIMO or MU-MIMO. DMRS and PTRS embedded in PDSCH resources are included. Unit: N/A Ranges: Bin[0]: Number of resource block symbols scheduled with 1 layer. Bin[1]: Number of resource block symbols scheduled with 2 layers. Bin[2]: Number of resource block symbols scheduled with 3 layers. Bin[3]: Number of resource block symbols scheduled with 4 layers. Bin[4]: Number of resource block symbols scheduled with 5 layers. Bin[5]: Number of resource block symbols scheduled with 6 layers. Bin[6]: Number of resource block symbols scheduled with 7 layers. Bin[7]: Number of resource block symbols scheduled with 8 layers. Bin[8]: Number of resource block symbols scheduled with 9 layers. Bin[9]: Number of resource block symbols scheduled with 10 layers. Bin[10]: Number of resource block symbols scheduled with 11 layers. Bin[11]: Number of resource block symbols scheduled with 12 layers. Bin[12]: Number of resource block symbols scheduled with 13 layers. Bin[13]: Number of resource block symbols scheduled with 14 layers. Bin[14]: Number of resource block symbols scheduled with 15 layers. Bin[15]: Number of resource block symbols scheduled with 16 layers..";
      type ietfyang:mac-address;
      max-elements 16;
    }
    leaf-list pmRadioRecInterferencePwrSpecialSlot1Distr {
      description "Absolute power value of SRS comb offsets in each uplink symbol of special slot 1. The absolute power value is expressed in units of 0.1 dBm. Bins correspond to SRS comb offsets in each uplink symbol. This ensures compatibility between the lengths of uplink symbols in a special slot. To extract average interference power for each bin across a ROP, divide by pmRadioRecInterferencePwrSlotSamp. Number of bins corresponds to maximum six uplink symbols in a special slot and four comb offsets in each uplink symbol. Bins support the following symbol number and comb offset combinations: Bin[0]: First comb offset in last uplink symbol of special slot Bin[1]: Second comb offset in last uplink symbol of special slot Bin[2]: Third comb offset in last uplink symbol of special slot Bin[3]: Fourth comb offset in last uplink symbol of special slot Bin[4]: First comb offset in second uplink symbol from last of special slot Bin[5]: Second comb offset in second uplink symbol from last of special slot .... Bin[22]: Third comb offset in sixth uplink symbol from last of special slot Bin[23]: Fourth comb offset in sixth uplink symbol from last of special slot Note: For TDD UL-DL pattern 'DDSSUUDDDD DDSSUUDDDD', there's no ul symbol in the first and the third S slot. Only the second and the fourth S slot will be pegged. So, only pmRadioRecInterferencePwrSpecialSlot1Distr and pmRadioRecInterferencePwrSpecialSlot2Distr will be used..";
      type uint64;
      max-elements 24;
    }
    leaf-list pmRadioPreambleSinrMsg3AckDistr {
      description "Total number of Msg3 ACKs for a preamble SINR range. Ranges: Bin[0]: [..-15] dB Bin[1]: ]-15..-12] dB Bin[2]: ]-12..-9] dB Bin[3]: ]-9..-6] dB Bin[4]: ]-6..-3] dB Bin[5]: ]-3..] dB.";
      type uint64;
      max-elements 6;
    }
    leaf-list pmPimAvoidPowerExcessDistr {
      description "Distribution of PIM power excess measured after PIM avoidance. Unit: N/A Ranges: Bin[0]: [..-10] dB Bin[1]: ]-10..-8] dB Bin[2]: ]-8..-6] dB Bin[3]: ]-6..-4] dB Bin[4]: ]-4..-2] dB Bin[5]: ]-2..0] dB Bin[6]: ]0..2] dB Bin[7]: ]2..4] dB Bin[8]: ]4..6] dB Bin[9]: ]6..8] dB Bin[10]: ]8..10] dB Bin[11]: ]10..12] dB Bin[12]: ]12..14] dB Bin[13]: ]14..16] dB Bin[14]: ]16..18] dB Bin[15]: ]18..20] dB Bin[16]: ]20..22] dB Bin[17]: ]22..24] dB Bin[18]: ]24..26] dB Bin[19]: ]26..28] dB Bin[20]: ]28..30] dB Bin[21]: ]30..] dB.";
      type uint64;
      max-elements 22;
    }
    leaf pmMacRBSymUsedPdcchCss {
      description "Aggregated number of resource block symbols used for common search space PDCCH allocation. Unit: N/A.";
      type ietfyang:mac-address;
      config false;
    }
    leaf-list pmMacTimeDlDrbQos {
      description "Aggregated time for HARQ initial transmission scheduling of downlink DRB, while there is data in buffer. Accumulates measured time from all DRBs with same QoS. Unit: 125 microseconds Compressed: True.";
      type ietfyang:mac-address;
      max-elements 256;
    }
    leaf-list pmMacRBSymUsedPdcchTypeAAggrLvl8Bwp {
      description "Number of resource block symbols used by PDCCH with aggregation level 8 for scheduling of PDSCH or PUSCH using mapping type A in BWP. This includes DMRS and PTRS embedded in resources. PDF ranges: Bin[0]: Accumulated downlink resource block symbols used by PDCCH with aggregation level 8 in the first BWP referenced in NRCellDU MO by BWPSet.allBWPRegularRef attribute Bin[1]: Accumulated downlink resource block symbols used by PDCCH with aggregation level 8 in the second BWP referenced in NRCellDU MO by BWPSet.allBWPRegularRef attribute Bin[2]: Accumulated downlink resource block symbols used by PDCCH with aggregation level 8 in the third BWP referenced in NRCellDU MO by BWPSet.allBWPRegularRef attribute ... Bin[15]: Accumulated downlink resource block symbols used by PDCCH with aggregation level 8 in the sixteenth BWP referenced in NRCellDU MO by BWPSet.allBWPRegularRef attribute Unit: N/A.";
      type ietfyang:mac-address;
      max-elements 16;
    }
    leaf pmRadioRaCfFailMsg2Disc {
      description "Number of CFRA preambles for which no random access Msg2 is sent due to expiry of random access response window. Unit: N/A.";
      type uint64;
      config false;
    }
    leaf-list pmMacRBSymUsedPdcchTypeAAggrLvl2Sssg {
      description "Number of resource block symbols used by PDCCH with aggregation level 2 for scheduling of PDSCH or PUSCH using mapping type A in search space set group. Includes DMRS and PTRS embedded in resources. PDF ranges: Bin[0]: Accumulated downlink resource block symbols that use PDCCH with aggregation level 2 for UEs that are not configured with search space set group switching. Bin[1]: Accumulated downlink resource block symbols that use PDCCH with aggregation level 2 for UEs configured with search space set group switching. Value of SssgSwitchUeCfg.sssgSwitchPmIdentity attribute must be 1 for UEs configured with a dense search space set group. Bin[2]: Accumulated downlink resource block symbols that use PDCCH with aggregation level 2 for UEs configured with search space set group switching. Value of SssgSwitchUeCfg.sssgSwitchPmIdentity attribute must be 1 for UEs configured with a sparse search space set group. Bin[3]: Accumulated downlink resource block symbols that use PDCCH with aggregation level 2 for UEs configured with search space set group switching. Value of SssgSwitchUeCfg.sssgSwitchPmIdentity attribute must be 2 for UEs configured with a dense search space set group. ... Bin[15]: Accumulated downlink resource block symbols that use PDCCH with aggregation level 2 for UEs configured with search space set group switching. Value of SssgSwitchUeCfg.sssgSwitchPmIdentity attribute must be 8 for UEs configured with a dense search space set group. Bin[16]: Accumulated downlink resource block symbols that use PDCCH with aggregation level 2 for UEs configured with search space set group switching. Value of SssgSwitchUeCfg.sssgSwitchPmIdentity attribute must be 8 for UEs configured with a sparse search space set group. Unit: N/A.";
      type ietfyang:mac-address;
      max-elements 17;
    }
    leaf pmMacVolDlRat {
      description "Aggregated volume of successfully transmitted downlink MAC PDUs for DRB or SRB using cell as PCell for RAT(Reciprocity assistant transmission) UE. Unit: bytes.";
      type ietfyang:mac-address;
      config false;
    }
    leaf pmDuCellDownLockAuto {
      description "Number of times cell is locked due to system-initiated action..";
      type uint64;
      config false;
    }
    leaf pmMacRBSymUsedPuschTypeA {
      description "Aggregated number of resource block symbols used for PUSCH mapping type A during complete ROP. DMRS and PTRS embedded in PUSCH resources are included. Unit: N/A.";
      type ietfyang:mac-address;
      config false;
    }
    leaf-list pmRadioUeRepPmiPrimaryCsiRsRank4Distr {
      description "Distribution of precoding weights reported by UE for rank 4 codebook associated with primary CSI-RS. Indicates spatial distribution of UEs using cell as PCell. Type 1 single-panel codebooks are defined in 3GPP TS 38.214. Represents distribution of requested departure angles from AAS-capable radio unit as estimated from UE CSI feedback, specifically main and diversity direction of PMI values. It is not recommended to use this PM counter for Remote radio units. For more information, see Massive MIMO Mid-Band and Manage Massive MIMO NR in CPI library. Unit: N/A Compressed: True.";
      type uint64;
      max-elements 256;
    }
    leaf pmMacRBSymAvailRach {
      description "Aggregated number of resource block symbols configured for RACH during complete ROP. Unit: N/A.";
      type ietfyang:mac-address;
      config false;
    }
    leaf pmMacHarqUlDtx16Qam {
      description "Total number of occasions when no HARQ is received in gNodeB uplink when the following conditions apply: - Uplink grant is meant for HARQ transmission of transport block that uses 16-QAM modulation. - DTX is considered the reason for no reception. Unit: N/A.";
      type ietfyang:mac-address;
      config false;
    }
    leaf pmMacRBSymUsedPuschTypeB {
      description "Aggregated number of resource block symbols used for PUSCH mapping type B during complete ROP. DMRS and PTRS that are embedded in PUSCH resources are included. Unit: N/A.";
      type ietfyang:mac-address;
      config false;
    }
    leaf pmMacHarqUlNack256QamInit {
      description "Total number of unsuccessful initial HARQ transmissions with 256-QAM UL. Initial transmission is first transmission on HARQ process, where New Data Indicator (NDI) bit in DCI message is toggled. Unit: N/A.";
      type ietfyang:mac-address;
      config false;
    }
    leaf pmActiveUeDlSamp {
      description "Number of times corresponding pmActiveUeDlSum counter is incremented. Unit: N/A.";
      type uint64;
      config false;
    }
    leaf-list pmDrbAdmissionPreemptQos {
      description "Number of DRBs required to be released by NR Service-Adaptive Preemption feature for each QoS value. Compressed: True.";
      type uint64;
      max-elements 256;
    }
    leaf pmMacHarqUlDtxQpskInit {
      description "Number of DTX detections for initial HARQ transmissions in uplink using QPSK modulation. Initial transmission is first transmission on HARQ process, where NDI bit in DCI message is toggled. Unit: N/A.";
      type ietfyang:mac-address;
      config false;
    }
    leaf-list pmRadioRecInterferencePwrUlSlot7Distr {
      description "Absolute power for each symbol in uplink slot 7 in one radio frame. Bins correspond to uplink symbol 2 and uplink symbol 11 respectively. To get average interference power for each bin across a Result Output Period (ROP), divide by NRCellDU.pmRadioRecInterferencePwrSlotSamp. Unit: 0.1 dBm/PRB.";
      type uint64;
      max-elements 2;
    }
    leaf-list pmRadioPreambleSinrMsg3HarqFailDistr {
      description "Total number of HARQ failures on Msg3 transmission counts due to DTX or NACK for a preamble SINR range. Ranges: Bin[0]: [..-15] dB Bin[1]: ]-15..-12] dB Bin[2]: ]-12..-9] dB Bin[3]: ]-9..-6] dB Bin[4]: ]-6..-3] dB Bin[5]: ]-3..] dB.";
      type uint64;
      max-elements 6;
    }
    leaf pmRadioSrsResAvailAntSwitching {
      description "Accumulates total number of SRS resources available for SRS antenna switching from every SRS slot. Each SRS resource is a combination of symbol, comb, and cyclic shift. Unit: N/A.";
      type uint64;
      config false;
    }
    leaf pmMacHarqDlAck64QamInit {
      description "Total number of successful initial downlink HARQ transmissions using 64-QAM modulation. Initial transmission is first transmission on HARQ process. Unit: N/A.";
      type ietfyang:mac-address;
      config false;
    }
    leaf pmSssgUeConfSamp {
      description "Number of times NRCellDU.pmSssgUeConfSumDistr PM counter accumulates new sample. Unit: N/A.";
      type uint64;
      config false;
    }
    leaf-list pmMacHarqDlAckQpskInitSlotDistr {
      description "For each downlink slot, bin that corresponds to number of successful initial HARQ PDSCH transmissions using QPSK modulation in slot is incremented. HARQ transmissions used for BWP DCI switch Scheduling Request (SR) are not pegged. Unit: N/A Ranges: Bin[0]: Total number of successful initial downlink HARQ transmissions using QPSK on slot 0. Bin[1]: Total number of successful initial downlink HARQ transmissions using QPSK on slot 1. Bin[2]: Total number of successful initial downlink HARQ transmissions using QPSK on slot 2. Bin[3]: Total number of successful initial downlink HARQ transmissions using QPSK on slot 3. Bin[4]: Total number of successful initial downlink HARQ transmissions using QPSK on slot 4. Bin[5]: Total number of successful initial downlink HARQ transmissions using QPSK on slot 5. Bin[6]: Total number of successful initial downlink HARQ transmissions using QPSK on slot 6. Bin[7]: Total number of successful initial downlink HARQ transmissions using QPSK on slot 7. Bin[8]: Total number of successful initial downlink HARQ transmissions using QPSK on slot 8. Bin[9]: Total number of successful initial downlink HARQ transmissions using QPSK on slot 9. Bin[10]: Total number of successful initial downlink HARQ transmissions using QPSK on slot 10. Bin[11]: Total number of successful initial downlink HARQ transmissions using QPSK on slot 11. Bin[12]: Total number of successful initial downlink HARQ transmissions using QPSK on slot 12. Bin[13]: Total number of successful initial downlink HARQ transmissions using QPSK on slot 13. Bin[14]: Total number of successful initial downlink HARQ transmissions using QPSK on slot 14. Bin[15]: Total number of successful initial downlink HARQ transmissions using QPSK on slot 15. Bin[16]: Total number of successful initial downlink HARQ transmissions using QPSK on slot 16. Bin[17]: Total number of successful initial downlink HARQ transmissions using QPSK on slot 17. Bin[18]: Total number of successful initial downlink HARQ transmissions using QPSK on slot 18. Bin[19]: Total number of successful initial downlink HARQ transmissions using QPSK on slot 19..";
      type ietfyang:mac-address;
      max-elements 20;
    }
    leaf-list pmRadioUeRepCqi64QamLowSeRank3Distr {
      description "Distribution of UE-reported CQI values with low Spectral Efficiency related to rank 3 transmissions when highest modulation order supported in downlink (DL) in NR cell is 64-QAM. CQI values and interpretations correspond to entries in Table 5.2.2.1-4 in 3GPP 38.214 for reporting CQI based on QPSK, 16-QAM, and 64-QAM. Unit: N/A Ranges: Bin[0]: CQI = 0 Bin[1]: CQI = 1 Bin[2]: CQI = 2 Bin[3]: CQI = 3 Bin[4]: CQI = 4 Bin[5]: CQI = 5 Bin[6]: CQI = 6 Bin[7]: CQI = 7 Bin[8]: CQI = 8 Bin[9]: CQI = 9 Bin[10]: CQI = 10 Bin[11]: CQI = 11 Bin[12]: CQI = 12 Bin[13]: CQI = 13 Bin[14]: CQI = 14 Bin[15]: CQI = 15.";
      type uint64;
      max-elements 16;
    }
    leaf-list pmPimAvoidPowerExcessReportMissDistr {
      description "Distribution of number of times when PIM power excess feedback is continuously missing. There is one system constant: pimMissingReportSamplesThreshold to limit the maximum times. The possible value for this SC is 5, 6, ..., 20. Once the threshold is reached, then stop PIM avoidance. Ranges: Bin[0]: one time Bin[1]: two times Bin[2]: three times Bin[3]: four times Bin[4]: five times Bin[5]: six times Bin[6]: seven times Bin[7]: eight times Bin[8]: nine times Bin[9]: ten times Bin[10]: eleven time Bin[11]: twelve time Bin[12]: thirteen times Bin[13]: fourteen times Bin[14]: fifteen times Bin[15]: sixteen times Bin[16]: seventeen times Bin[17]: eighteen times Bin[18]: nineteen times Bin[19]: twenty times.";
      type uint64;
      max-elements 20;
    }
    leaf pmSessionTimeUeSssgSamp {
      description "Number of times corresponding NRCellDU.pmSessionTimeUeSssgSumDistr PM counter is incremented. Unit: N/A.";
      type uint64;
      config false;
    }
    leaf-list pmPdschSchedEntityDistr {
      description "For each downlink slot, bin that corresponds to number of PDSCH-scheduled entities is incremented, including PDSCH-scheduling activities of Msg2 or Msg4, paging, or SI. Unit: N/A Ranges: Bin[0]: Number of PDSCH scheduled 0 SE is incremented. Bin[1]: Number of PDSCH scheduled 1 SE is incremented. Bin[2]: Number of PDSCH scheduled 2 SEs is incremented. Bin[3]: Number of PDSCH scheduled 3 SEs is incremented. Bin[4]: Number of PDSCH scheduled 4 SEs is incremented. Bin[5]: Number of PDSCH scheduled 5 SEs is incremented. Bin[6]: Number of PDSCH scheduled 6 SEs is incremented. Bin[7]: Number of PDSCH scheduled 7 SEs is incremented. Bin[8]: Number of PDSCH scheduled 8 SEs is incremented. Bin[9]: Number of PDSCH scheduled 9 SEs is incremented. Bin[10]: Number of PDSCH scheduled 10 SEs is incremented. Bin[11]: Number of PDSCH scheduled 11 SEs is incremented. Bin[12]: Number of PDSCH scheduled 12 SEs is incremented. Bin[13]: Number of PDSCH scheduled 13 SEs is incremented. Bin[14]: Number of PDSCH scheduled 14 SEs is incremented. Bin[15]: Number of PDSCH scheduled 15 SEs is incremented. Bin[16]: Number of PDSCH scheduled 16 SEs is incremented..";
      type uint64;
      max-elements 17;
    }
    leaf-list pmMacBsrLcg7Distr {
      description "Distribution of highest possible buffer size reported in BSRs in MAC Control Elements in UL LCG ID 7. Unit: N/A Ranges: Bin[0]: 0 bytes Bin[1]: [1..19] bytes Bin[2]: [20..36] bytes Bin[3]: [37..66] bytes Bin[4]: [67..124] bytes Bin[5]: [125..233] bytes Bin[6]: [234..436] bytes Bin[7]: [437..817] bytes Bin[8]: [818..1532] bytes Bin[9]: [1533..2873] bytes Bin[10]: [2874..5387] bytes Bin[11]: [5388..10104] bytes Bin[12]: [10105..18951] bytes Bin[13]: [18952..35543] bytes Bin[14]: [35544..66663] bytes Bin[15]: [66664..125030] bytes Bin[16]: [125031..] bytes.";
      type ietfyang:mac-address;
      max-elements 17;
    }
    leaf pmMacRBSymAvailDl {
      description "Aggregated number of resource block symbols available for downlink transmission during complete ROP. Unit: N/A.";
      type ietfyang:mac-address;
      config false;
    }
    leaf-list pmRadioRecInterferencePwrSpecialSlot2Distr {
      description "Absolute power value of SRS comb offsets in each uplink symbol of special slot 2. The absolute power value is expressed in units of 0.1 dBm. Bins correspond to SRS comb offsets in each uplink symbol. This ensures compatibility between the lengths of uplink symbols in a special slot. To extract average interference power for each bin across a ROP, divide by pmRadioRecInterferencePwrSlotSamp. Number of bins corresponds to maximum six uplink symbols in a special slot and four comb offsets in each uplink symbol. Bins support the following symbol number and comb offset combinations: Bin[0]: First comb offset in last uplink symbol of special slot Bin[1]: Second comb offset in last uplink symbol of special slot Bin[2]: Third comb offset in last uplink symbol of special slot Bin[3]: Fourth comb offset in last uplink symbol of special slot Bin[4]: First comb offset in second uplink symbol from last of special slot Bin[5]: Second comb offset in second uplink symbol from last of special slot .... Bin[22]: Third comb offset in sixth uplink symbol from last of special slot Bin[23]: Fourth comb offset in sixth uplink symbol from last of special slot Note: For TDD UL-DL pattern 'DDSSUUDDDD DDSSUUDDDD', there's no ul symbol in the first and the third S slot. Only the second and the fourth S slot will be pegged. So, only pmRadioRecInterferencePwrSpecialSlot1Distr and pmRadioRecInterferencePwrSpecialSlot2Distr will be used..";
      type uint64;
      max-elements 24;
    }
    leaf-list pmPuschSchedActivityBwp {
      description "Total duration of slots where at least one MAC SDU is received on PUSCH. PDF ranges: Bin[0]: Total duration of slots where at least one MAC SDU is received on PUSCH in the first BWP referenced in NRCellDU MO by BWPSet.allBWPRegularRef attribute Bin[1]: Total duration of slots where at least one MAC SDU is received on PUSCH in the second BWP referenced in NRCellDU MO by BWPSet.allBWPRegularRef attribute Bin[2]: Total duration of slots where at least one MAC SDU is received on PUSCH in the third BWP referenced in NRCellDU MO by BWPSet.allBWPRegularRef attribute ... Bin[15]: Total duration of slots where at least one MAC SDU is received on PUSCH in the sixteenth BWP referenced in NRCellDU MO by BWPSet.allBWPRegularRef attribute Unit: 125 microseconds.";
      type uint64;
      max-elements 16;
    }
    leaf-list pmRadioRecInterferencePwrUlSlot5Distr {
      description "Absolute power for each symbol in uplink slot 5 in one radio frame. Bins correspond to uplink symbol 2 and uplink symbol 11 respectively. To get average interference power for each bin across a Result Output Period (ROP), divide by NRCellDU.pmRadioRecInterferencePwrSlotSamp. Unit: 0.1 dBm/PRB.";
      type uint64;
      max-elements 2;
    }
    leaf-list pmRadioPreambleSinrMsg3DtxDistr {
      description "Total number of Msg3 DTX counts for a preamble SINR range. Ranges: Bin[0]: [..-15] dB Bin[1]: ]-15..-12] dB Bin[2]: ]-12..-9] dB Bin[3]: ]-9..-6] dB Bin[4]: ]-6..-3] dB Bin[5]: ]-3..] dB.";
      type uint64;
      max-elements 6;
    }
    leaf-list pmRadioPuschTable3McsDistr {
      description "Distribution of MCS used for PUSCH transmissions where MCS index table 3 is applied and UE instances are enabled. For more information, see 3GPP TS 38.214, Table 6.1.4.1-2 and Table 5.1.3.1-3 (depending on whether Transform Precoding is enabled/disabled). Each bin represents a specific MCS. Unit: N/A Ranges: Bin[0]: MCS = 0 Bin[1]: MCS = 1 Bin[2]: MCS = 2 Bin[3]: MCS = 3 Bin[4]: MCS = 4 Bin[5]: MCS = 5 Bin[6]: MCS = 6 Bin[7]: MCS = 7 Bin[8]: MCS = 8 Bin[9]: MCS = 9 Bin[10]: MCS = 10 Bin[11]: MCS = 11 Bin[12]: MCS = 12 Bin[13]: MCS = 13 Bin[14]: MCS = 14 Bin[15]: MCS = 15 Bin[16]: MCS = 16 Bin[17]: MCS = 17 Bin[18]: MCS = 18 Bin[19]: MCS = 19 Bin[20]: MCS = 20 Bin[21]: MCS = 21 Bin[22]: MCS = 22 Bin[23]: MCS = 23 Bin[24]: MCS = 24 Bin[25]: MCS = 25 Bin[26]: MCS = 26 Bin[27]: MCS = 27 Bin[28]: MCS = 28 Bin[29]: MCS = 29 Bin[30]: MCS = 30 Bin[31]: MCS = 31.";
      type uint64;
      max-elements 32;
    }
    leaf pmMacVolUlResUeLastSlot {
      description "Data volume in MAC SDUs successfully received in uplink while restricted by air interface. Received in last slot of burst. Unit: byte Deprecated: Since 24.Q1. Planned to be removed. Replaced by GNBDU::GNBDU_NRCellDU::pmMacVolUlUeLastSlot; MOM flags: noNotification.";
      type ietfyang:mac-address;
      config false;
      status deprecated;
    }
    leaf-list pmMacRBSymUsedPdschAdvEisMimoUserDistr {
      description "Distribution of aggregated number of resource block symbols used for PDSCH by different number of users as a result of advanced Ericsson Interference Sensing (EIS) beamforming. DMRS and PTRS embedded in PDSCH resources are included. Unit: N/A Ranges: Bin[0]: Distribution of aggregated number of resource block symbols for 1 user case. Bin[1]: Distribution of aggregated number of resource block symbols for 2 users case. Bin[2]: Distribution of aggregated number of resource block symbols for 3 users case. Bin[3]: Distribution of aggregated number of resource block symbols for 4 users case. Bin[4]: Distribution of aggregated number of resource block symbols for 5 users case. Bin[5]: Distribution of aggregated number of resource block symbols for 6 users case. Bin[6]: Distribution of aggregated number of resource block symbols for 7 users case. Bin[7]: Distribution of aggregated number of resource block symbols for 8 users case. Bin[8]: Reserved for future MU-MIMO. Bin[9]: Reserved for future MU-MIMO. Bin[10]: Reserved for future MU-MIMO. Bin[11]: Reserved for future MU-MIMO. Bin[12]: Reserved for future MU-MIMO. Bin[13]: Reserved for future MU-MIMO. Bin[14]: Reserved for future MU-MIMO. Bin[15]: Reserved for future MU-MIMO..";
      type ietfyang:mac-address;
      max-elements 16;
    }
    leaf pmMacRBSymUsedPdcchTypeBAggrLvl1 {
      description "Number of resource block symbols used by PDCCH with aggregation level 1 for scheduling of PDSCH or PUSCH using mapping type B. This includes DMRS and PTRS embedded in resources scheduling. Unit: N/A.";
      type ietfyang:mac-address;
      config false;
    }
    leaf pmRadioRaCbFailMsg1MaxMsg3Sched {
      description "Number of CBRA preambles (Msg1) that are discarded because maximum number of random access Msg3 scheduled is reached. Unit: messages.";
      type uint64;
      config false;
    }
    leaf-list pmRadioRecInterferencePwrUlSlot1Distr {
      description "Absolute power for each symbol in uplink slot 1 in one radio frame. Bins correspond to uplink symbol 2 and uplink symbol 11 respectively. To get average interference power for each bin across a Result Output Period (ROP), divide by NRCellDU.pmRadioRecInterferencePwrSlotSamp. Unit: 0.1 dBm/PRB.";
      type uint64;
      max-elements 2;
    }
    leaf-list pmRadioPathlossUlDistr {
      description "Distribution of uplink path loss values calculated for each UE scheduling on slot basis. Unit: N/A Ranges: Bin[0]: [..50] dB Bin[1]: ]50..55] dB Bin[2]: ]55..60] dB Bin[3]: ]60..65] dB Bin[4]: ]65..70] dB Bin[5]: ]70..75] dB Bin[6]: ]75..80] dB Bin[7]: ]80..85] dB Bin[8]: ]85..90] dB Bin[9]: ]90..95] dB Bin[10]: ]95..100] dB Bin[11]: ]100..105] dB Bin[12]: ]105..110] dB Bin[13]: ]110..115] dB Bin[14]: ]115..120] dB Bin[15]: ]120..125] dB Bin[16]: ]125..130] dB Bin[17]: ]130..135] dB Bin[18]: ]135..140] dB Bin[19]: ]140..145] dB Bin[20]: ]145..] dB.";
      type uint64;
      max-elements 21;
    }
    leaf pmUeCtxtAllocatedSum {
      description "Sum of the number of allocated UE contexts from periodic readings..";
      type uint64;
      config false;
    }
    leaf-list pmRadioUeRepCqi256QamRank2Distr {
      description "Distribution of UE-reported CQI values related to rank 2 transmissions when highest modulation order supported in downlink (DL) in NR cell is configured to be 256-QAM. CQI values and interpretations correspond to entries in Table 5.2.2.1-3 in 3GPP 38.214 for reporting CQI based on QPSK, 16-QAM, 64-QAM, and 256-QAM. Unit: N/A Ranges: Bin[0]: CQI = 0 Bin[1]: CQI = 1 Bin[2]: CQI = 2 Bin[3]: CQI = 3 Bin[4]: CQI = 4 Bin[5]: CQI = 5 Bin[6]: CQI = 6 Bin[7]: CQI = 7 Bin[8]: CQI = 8 Bin[9]: CQI = 9 Bin[10]: CQI = 10 Bin[11]: CQI = 11 Bin[12]: CQI = 12 Bin[13]: CQI = 13 Bin[14]: CQI = 14 Bin[15]: CQI = 15.";
      type uint64;
      max-elements 16;
    }
    leaf-list pmRadioSinrPuschDistr {
      description "Distribution of SINR values calculated for PUSCH transmissions. Unit: N/A Ranges: Bin[0]: [..-5] dB Bin[1]: ]-5..-2] dB Bin[2]: ]-2..1] dB Bin[3]: ]1..4] dB Bin[4]: ]4..7] dB Bin[5]: ]7..10] dB Bin[6]: ]10..13] dB Bin[7]: ]13..16] dB Bin[8]: ]16..19] dB Bin[9]: ]19..22] dB Bin[10]: ]22..25] dB Bin[11]: ]25..] dB.";
      type uint64;
      max-elements 12;
    }
    leaf-list pmRadioSinrPucchDistr {
      description "Distribution of SINR values calculated for PUCCH. Unit: N/A Ranges: Bin[0]: [..-15] dB Bin[1]: ]-15..-12] dB Bin[2]: ]-12..-9] dB Bin[3]: ]-9..-6] dB Bin[4]: ]-6..-3] dB Bin[5]: ]-3..0] dB Bin[6]: ]0..3] dB Bin[7]: ]3..] dB.";
      type uint64;
      max-elements 8;
    }
    leaf-list pmMacOverlapTimeDlDrbExtSCellQoS {
      description "Counter that records time overlap between carrier aggregation data bursts where original data burst time is overlapped with subsequent data burst times due to scheduling delay on external SCell. Accumulates measured time from all DRBs with same QoS. This time is subtracted from other counters intended for user throughput calculation. Unit: 125 microseconds Compressed: True.";
      type ietfyang:mac-address;
      max-elements 256;
    }
    leaf-list pmRadioSinrPuschAckDistr {
      description "Total number of PUSCH ACKs pegged at SINR values for each PUSCH transmission. Ranges: Bin[0]: [..-11] dB Bin[1]: ]-11..-8] dB Bin[2]: ]-8..-5] dB Bin[3]: ]-5..-2] dB Bin[4]: ]-2..1] dB Bin[5]: ]1..4] dB Bin[6]: ]4..7] dB Bin[7]: ]7..10] dB Bin[8]: ]10..13] dB Bin[9]: ]13..16] dB Bin[10]: ]16..] dB.";
      type uint64;
      max-elements 11;
    }
    leaf pmRadioRaCbFailMsg2Disc {
      description "Number of CBRA preambles for which no random access Msg2 is sent due to expiry of random access response window. Unit: messages.";
      type uint64;
      config false;
    }
  }
  grouping NRPimCancellationConfig-attributes {
    leaf createdBy {
      description "Whether NRPimCancellationConfig instance is created by operator or by the system..";
      type enumeration {
        enum SYSTEM;
        enum OPERATOR;
      }
      config false;
    }
    leaf dlPimCandidate {
      description "Whether DL carriers for PIM calculation are included.; Default value: false.";
      type boolean;
      default "false";
    }
    leaf nRPimCancellationConfigId {
      description "The value component of the RDN..";
      type string;
      mandatory true;
    }
    leaf pimCancellationFunctionRef {
      description "Reference to an instance of PimCancellationFunction MO. Reference specifies PIM cancellation function in which NRSectorCarrier instance participates. NRPimCancellationConfig instances belonging to same NRSectorCarrier instance cannot refer to same PimCancellationFunction instance..";
      type string;
      mandatory true;
    }
    leaf ulPimCancellationMode {
      description "PIM cancellation mode on uplink carriers. Cannot be set to value different than EXCLUDED for more than one NRPimCancellationConfig instance under an NRSectorCarrier instance..";
      type enumeration {
        enum EXCLUDED;
        enum DEACTIVATED;
        enum ACTIVATED;
      }
    }
  }
  grouping NRSectorCarrier-attributes {
    leaf administrativeState {
      description "The administrative state. If set to SHUTTINGDOWN, the state is immediately brought to LOCKED..";
      type enumeration {
        enum LOCKED;
        enum UNLOCKED;
        enum SHUTTINGDOWN;
      }
    }
    leaf altitude {
      description "Altitude of transmitter antenna position measured in meters. Positive value means height, negative value means depth. Altitude is in relation to WGS84 reference ellipsoid. WGS84 reference ellipsoid is based on theoretical mean sea level. If empty, value is not defined.; range -32768..32767.";
      type int32 {
        range "-32768..32767";
      }
      units "m";
    }
    leaf arfcnDL {
      description "NR Absolute Radio Frequency Channel Number (NR-ARFCN) for downlink. If value is less than 600000, value must be a multiple of 20, except for band n41 cells, where value must be multiple of 6. Only even values if between 600000 and 2016666. Only odd values supported if above 2016667.; range 0..3279165.";
      type eytypes:int32_range_0-3279165;
      mandatory true;
    }
    leaf arfcnUL {
      description "NR Absolute Radio Frequency Channel Number (NR-ARFCN) for uplink. If value is less than 600000, value must be a multiple of 20, except for band n41 cells, where value must be multiple of 6. Only even values if between 600000 and 2016666. Only odd values supported if above 2016667. If 0, uplink channel number for Low-Band cells is not applicable if txDirection is DL.; range 0..3279165.";
      type eytypes:int32_range_0-3279165;
      mandatory true;
    }
    leaf-list availabilityStatus {
      description "The availability status. It contains details about operationalState..";
      type AvailStatus;
      min-elements 0;
    }
    list azimuthNull {
      key "id";
      leaf id {
        type uint32;
        description "Synthetic key for struct sequence entry.";
      }
      min-elements 0;
      max-elements 7;
      uses AzimuthNull-struct;
    }
    leaf bbOnlyBackoffAllowed {
      description "Whether EVM-aware power backoff is allowed when Radio Unit cannot support reporting backoff data. Only applicable to Remote Radio Units. Only applicable to Low-Band and Mid-Band sector carriers.; Default value: false.";
      type boolean;
      default "false";
    }
    leaf bSChannelBwDL {
      description "BS Channel bandwidth in MHz for downlink..";
      type int32 {
        range "5 | 10 | 15 | 20 | 25 | 30 | 35 | 40 | 50 | 60 | 70 | 80 | 90 | 100 | 200";
      }
      mandatory true;
      units "MHz";
    }
    leaf bSChannelBwUL {
      description "BS Channel bandwidth in MHz for uplink. Not applicable to Low-Band cells if txDirection is DL..";
      type int32 {
        range "5 | 10 | 15 | 20 | 25 | 30 | 35 | 40 | 50 | 60 | 70 | 80 | 90 | 100 | 200";
      }
      mandatory true;
      units "MHz";
    }
    leaf cbrsEnabled {
      description "Whether sector carrier is externally supervised by authorized channel of Spectrum Access System. For CBRS sector carrier, set to true. Only applicable to Mid-Band sector carriers.; Default value: false.";
      type boolean;
      default "false";
    }
    leaf cbrsTxExpireTime {
      description "When to stop the transmission on assigned spectrum in UTC. Sector carrier becomes disabled when it expires or is empty. Updated by setCbrsTxExpireTime action. String format is YYYY-MM-DDThh:mm:ssZ. Only applicable when cbrsEnabled is true. Only applicable to Mid-Band sector carriers..";
      type string;
      config false;
    }
    leaf configuredMaxTxPower {
      description "Maximum output power to be used in an NRSectorCarrier instance. Output power is evenly distributed over antenna connectors used for TX transmission allocated for NRSectorCarrier instance. For High-Band and mmWave, EIRP value per cross-polarized beam pair must be used. Value 0 must not be used. Note: Value has an impact on maxTransmissionPower which displays the used output power.; range 0..10000000; Default value: 20000.";
      type eytypes:int32_range_0-10000000;
      default "20000";
      units "mW";
    }
    list coverage {
      key "id";
      leaf id {
        type uint32;
        description "Synthetic key for struct attribute.";
      }
      description "Transmission point coverage. Described by radius, bearing and opening angle..";
      uses NRCoverage-struct;
    }
    list dlCalibrationData {
      config false;
      description "Downlink antenna calibration information. Only applicable to Mid-Band sector carriers.; MOM flags: isNillable=true; Status info: Since 25.Q2. Planned to be removed..";
      uses DlCalibrationDataRO-struct;
    }
    leaf dlCalibrationEnabled {
      description "Whether downlink antenna calibration is enabled. If true, Antenna Calibration DL Failure alarm is raised on AAS-capable radios. Only applicable to Mid-Band sector carriers.; Default value: true; Takes effect: Next MO unlock; Status info: Since 25.Q2. Planned to be removed..";
      type boolean;
      status deprecated;
      default "true";
      reference "Takes effect: Next MO unlock.";
    }
    list elevationNull {
      key "id";
      leaf id {
        type uint32;
        description "Synthetic key for struct sequence entry.";
      }
      min-elements 0;
      max-elements 3;
      uses ElevationNull-struct;
    }
    leaf essScLocalId {
      description "The gNodeB internal ID attribute for SectorCarrier within Ericsson Shared Spectrum. Must be unique and non-zero in gNodeB for ESS NRSectorCarrier instances.; range 1..99999.";
      type int32 {
        range "1..99999";
      }
    }
    leaf essScPairId {
      description "ID attribute that pairs SectorCarriers from gNodeB and eNodeB in Ericsson Spectrum Sharing (ESS). Must be unique within gNodeB and eNodeB.; range 1..9223372036854775807.";
      type int64 {
        range "1..9223372036854775807";
      }
    }
    leaf frameStartOffset {
      description "Radio frame start offset of sector carrier at antenna reference point-relative GPS time. Tc = 1 / (480 * 10e3 * 4096) seconds.; range 0..19660799; Default value: 0.";
      type uint32 {
        range "0..19660799";
      }
      default "0";
      units "Tc";
    }
    leaf frequencyDL {
      description "RF Reference Frequency of downlink channel..";
      type int32;
      config false;
      units "kHz";
    }
    leaf frequencyUL {
      description "RF Reference Frequency of uplink channel..";
      type int32;
      config false;
      units "kHz";
    }
    leaf latitude {
      description "Latitude of transmitter antenna position. Positive value means north, negative value means south.; range -90000000..90000000.";
      type int32 {
        range "-90000000..90000000";
      }
      units "degree";
    }
    list lcsToGcsTranslation {
      key "id";
      leaf id {
        type uint32;
        description "Synthetic key for struct attribute.";
      }
      description "Local Coordinate System (LCS) to Global Coordinate System (GCS) translation information. If empty, this attribute is not used. Only applicable to Low-Band and Mid-Band cells..";
      uses LcsToGcsTranslation-struct;
    }
    leaf longitude {
      description "Longitude of transmitter antenna position. Positive value means east, negative value means west.; range -180000000..180000000.";
      type int32 {
        range "-180000000..180000000";
      }
      units "degree";
    }
    leaf massiveMimoSleepEnabled {
      description "Whether Massive MIMO Sleep Mode feature is enabled. Only applicable to Mid-Band sector carriers..";
      type enumeration {
        enum DISABLED;
        enum ENABLED;
        enum DETECTION;
      }
    }
    leaf massiveMimoSleepState {
      description "Status of feature Massive MIMO Sleep Mode. Only applicable to Mid-Band sector carriers..";
      type enumeration {
        enum DEACTIVATED;
        enum TXMUTE;
        enum ECO;
        enum ECO_PENDING;
      }
      config false;
    }
    leaf maxAllowedEirpPsd {
      description "Maximum EIRP density threshold per MHz required for EIRP restriction. If -1, no EIRP restriction. Only applicable to Mid-Band sector carriers.; Default value: -1.";
      type int32 {
        range "-1 | 1..10000";
      }
      default "-1";
      units "dBm/MHz";
    }
    leaf maxEirpPsdThresh {
      description "Maximum EIRP density threshold per MHz required for EIRP restriction. Only applicable for limiting EIRP within maximum EIRP stated by Ericsson product specifications. Only recommended for markets with restrictions on EIRP. If empty, EIRP restriction is not employed. If non-empty, attributes on CommonBeamforming MO cannot be updated while NRSectorCarrier::administrativeState is UNLOCKED.; range 1..1000.";
      type int32 {
        range "1..1000";
      }
      units "dBm/MHz";
    }
    leaf maxRegPowerLimit {
      description "Maximum downlink transmission power. If -1, configuredMaxTxPower is unrestricted.; range -1..10000000; Default value: -1.";
      type int32 {
        range "-1..10000000";
      }
      default "-1";
      units "mW";
    }
    leaf maxTransmissionPower {
      description "Maximum possible power at antenna reference point. Measured for all downlink channels in all TX branches used simultaneously in NRSectorCarrier instance..";
      type int32;
      config false;
      units "mW";
    }
    leaf mMimoSleepTimeGroupRef {
      description "Reference to an instance of MMimoSleepTimeGroup MO. If empty, no MMimoSleepTimeGroup instance is used in this sector carrier. Only applicable to Mid-Band sector carriers..";
      type string;
    }
    leaf muEirpPmiDistBasedThreshold {
      description "A PMI distance-based threshold used for adaptive power limitation in Advanced Downlink MU-MIMO. Used to determine if UEs must be of the same group. Only applicable to AAS radios. Only applicable to Mid-Band sector carriers.; range 0..31; Default value: 4.";
      type eytypes:int32_range_0-31-13;
      default "4";
    }
    leaf noOfRxAntennas {
      description "Number of antennas NRSectorCarrier MO uses for uplink transmission. Only used for NRSectorCarrier instances on sectors with non-AAS capable radios. If 0, NRSectorCarrier instance uses maximum number of RX antennas, else specified number is used. For Low-Band cells, value must be less than or equal to 8. For Mid-Band cells, value must be less than or equal to 8. For High-Band cells, value must be less than or equal to 2.; Default value: 0.";
      type int32 {
        range "0..2 | 4 | 8";
      }
      default "0";
    }
    leaf noOfTxAntennas {
      description "Number of antennas NRSectorCarrier MO uses for downlink transmission. Only used for NRSectorCarrier instances on sectors with non-AAS capable radios. If 0, NRSectorCarrier instance uses maximum number of TX antennas, else specified number is used. For Low-Band cells, value must be less than or equal to 4. For Mid-Band cells, value must be less than or equal to 8. For High-Band cells, value must be less than or equal to 2.; Default value: 0.";
      type int32 {
        range "0..2 | 4 | 8 | 16";
      }
      default "0";
    }
    leaf noOfUsedRxAntennas {
      description "Number of used RX antennas. Maximum number is determined by noOfRxAntennas. Empty means undefined..";
      type int32;
      config false;
    }
    leaf noOfUsedTxAntennas {
      description "Number of used TX antennas. Maximum number is determined by noOfTxAntennas. Empty means undefined..";
      type int32;
      config false;
    }
    leaf noTxPowerAction {
      description "Recovery action when no downlink TX power is detected. Controls which recovery action is performed when Advanced Cell Supervision feature detects no downlink TX power on sector carrier..";
      type enumeration {
        enum NO_ACTION;
        enum SC_AND_CELL_RESTART;
      }
    }
    leaf nRMicroSleepTxEnabled {
      description "Whether NR Micro Sleep TX feature is enabled. If false, feature is disabled. Not applicable to NRSectorCarrier instances that are on sectors with AAS capable radios nor RDS. Only applicable in radio equipment supporting Micro Sleep TX. For more information on hardware support, see NR Micro Sleep TX feature description.; Default value: true.";
      type boolean;
      default "true";
    }
    leaf nrppaCellPortionId {
      description "NRPPa Cell Portion ID. Only applicable to Low-Band and Mid-Band cells.; range 0..4095.";
      type eytypes:int32_range_0-4095;
      config false;
    }
    leaf nRSectorCarrierId {
      description "The value component of the RDN..";
      type string;
      mandatory true;
    }
    leaf nullSteeringMode {
      description "Spatial null-steering mode that determines impacted downlink channels. Only applicable to Mid-Band..";
      type enumeration {
        enum ALL;
        enum COMMON_BEAMFORMING;
        enum CSI_RS_MAPPING;
      }
    }
    leaf operationalState {
      description "The operational state..";
      type enumeration {
        enum DISABLED;
        enum ENABLED;
      }
      config false;
    }
    leaf pimAvoidDlMutingPeriod {
      description "Minimum slot interval between two blanked slots in downlink. Only applicable to Low-Band sector carriers.; range 1..15; Default value: 8.";
      type int32 {
        range "1..15";
      }
      default "8";
      units "slot";
    }
    leaf pimAvoidLevel {
      description "PIM Avoidance behavior level. Only applicable to Low-Band sector carriers..";
      type enumeration {
        enum DISABLED;
        enum LOW;
        enum MEDIUM;
        enum HIGH;
      }
    }
    leaf pimAvoidStatus {
      description "Whether PIM Avoidance is enabled on Baseband. True if both of following conditions apply: - Value of pimAvoidLevel is not DISABLED. - Value of pimDetected is true. Only applicable to Low-Band sector carriers..";
      type boolean;
      config false;
    }
    leaf pimDetected {
      description "Whether SectorCarrier is identified as a PIM victim. PIM Detection can identify a SectorCarrier as a PIM victim if SectorCarrier is affected by interference from passive intermodulation. Details on interference can be collected with PM events. If empty, PIM Detection is not active for this SectorCarrier instance. Only applicable to Low-Band NRSectorCarrier instances.; MOM flags: noNotification, isNillable=true; Status info: Since 24.Q1. Planned to be removed..";
      type boolean;
      config false;
      status deprecated;
    }
    leaf pimDetectionEnabled {
      description "Whether PIM Detection is activated for SectorCarrier.; Default value: false; Status info: Since 24.Q1. Planned to be removed..";
      type boolean;
      status deprecated;
      default "false";
    }
    list polygon {
      key "id";
      leaf id {
        type uint32;
        description "Synthetic key for struct sequence entry.";
      }
      min-elements 0;
      max-elements 15;
      uses NRPolygonCorner-struct;
    }
    leaf powerBackoffMode {
      description "Backoff mode for Modulation-Aware Power Control feature. Not applicable to radio equipment that supports AAS High-Band configuration..";
      type enumeration {
        enum AUTO;
        enum OFF;
        enum STATIC;
      }
    }
    leaf powerBackoffOffset {
      description "Backoff offset. Optional backoff offset for higher order modulation in addition to value calculated by Modulation-Aware Power Control feature. A negative offset reduces backoff but never boosts power over nominal output power. Not applicable to radio equipment that supports AAS High-Band configuration.; range -20..20; Default value: 0.";
      type int32 {
        range "-20..20";
      }
      default "0";
      units "dB";
    }
    leaf powerMeasAvgTime {
      description "Power averaging time for EMF exposure power measurements in Massive MIMO AAS Systems. Only applicable to High-Band cells. Must be empty for Low-Band and Mid-Band cells. If empty in High-Band cell, system uses value 360.; range 30..1800.";
      type uint32 {
        range "30..1800";
      }
      units "s";
    }
    leaf radioReportControlled {
      description "Whether radio report is evaluated for EVM-aware power backoff. Only applicable to Remote Radio Units. Only applicable to Low-Band and Mid-Band sector carriers.; Default value: true.";
      type boolean;
      default "true";
    }
    leaf radioTransmitPerfMode {
      description "Radio transmit operating mode. Better performance can be achieved in downlink according to cell traffic profile when radio is configured to maximum output level. Green modes are power saving modes, which can reduce energy consumption when radio transmits in low power modes..";
      type enumeration {
        enum COVERAGE;
        enum CAPACITY;
        enum COVERAGE_GREEN;
        enum CAPACITY_GREEN;
      }
    }
    leaf-list reservedBy {
      description "Contains a list of MO instances that reserve this MO instance..";
      type string;
      min-elements 0;
    }
    leaf-list rfBranchRxRef {
      description "References to instances of RfBranch or MulticastAntennaBranch MO. References are used for deterministic RX carrier allocation if noOfRxAntennas is greater than 0. If empty, carrier allocation is based on the RF Branch MOM list by default behavior..";
      type string;
      ordered-by user;
      min-elements 0;
      max-elements 8;
    }
    leaf-list rfBranchTxRef {
      description "References to instances of RfBranch or MulticastAntennaBranch MO. The references are used for deterministic TX carrier allocation if noOfTxAntennas is greater than 0. If empty, carrier allocation is based on the RF Branch MOM list by default behavior..";
      type string;
      ordered-by user;
      min-elements 0;
      max-elements 16;
    }
    leaf scaledTransmissionPower {
      description "Used power at antenna reference point. Covers all downlink channels in all TX branches used simultaneously in NRSectorCarrier instance. Represents the scaled power based on scaling factor, txPowerRatio, being applied to the allocated power at antenna reference point, maxTransmissionPower. Value is set every time txPowerState is set to STABLE..";
      type int32;
      config false;
      units "mW";
    }
    leaf sectorEquipmentFunctionRef {
      description "Reference to an instance of SectorEquipmentFunction MO..";
      type string;
      mandatory true;
    }
    leaf txDirection {
      description "Transmission direction. Value DL is only allowed in Low-Band and High-Band cells. For Low-Band cells, value DL is only applicable if license for NR Downlink-Only Cell Support for Carrier Aggregation feature is present and feature is active..";
      type enumeration {
        enum DL_AND_UL;
        enum DL;
      }
    }
    leaf txPowerChangeRate {
      description "Change rate for downlink output power to reach txPowerRatio. Example: If 5, a change of txPowerRatio from 100 to 80 will take 4 seconds.; range 1..10; Default value: 1.";
      type int32 {
        range "1..10";
      }
      default "1";
      units "%/s";
    }
    leaf txPowerPersistentLock {
      description "Whether configuredMaxTxPower is locked. If true, configuredMaxTxPower cannot be changed and MO cannot be deleted. Once set to true there is no possibility to change the value back to false unless a node re-integration is performed.; Default value: false.";
      type boolean;
      default "false";
    }
    leaf txPowerRatio {
      description "DL output power ratio. Default value is 100 %. At unlock of NRSectorCarrier the current value will be set directly. When the value is changed on an unlocked NRSectorCarrier instance, the TX power changes with rate txPowerChangeRate.; range 10..100; Default value: 100.";
      type eytypes:int32_range_10-100;
      default "100";
      units "percent";
    }
    leaf txPowerState {
      description "DL output power state..";
      type enumeration {
        enum INVALID;
        enum STABLE;
        enum CHANGING;
      }
      config false;
    }
    leaf ueAssistedPrecodingOptEnabled {
      description "Whether NR UE-Assisted Precoding Optimization feature is enabled. Only applicable to Low-Band and Mid-Band sector carriers.; Default value: false.";
      type boolean;
      default "false";
    }
    leaf ueAssistedPrecodingOptStatus {
      description "Status of NR UE Assisted Precoding Optimization feature. Only applicable to Low-Band and Mid-Band sector carriers..";
      type enumeration {
        enum INACTIVE;
        enum ACTIVE_NO_UPDATE;
        enum ACTIVE_FAILED;
        enum ACTIVE_CALIBRATED;
        enum ACTIVE_CALIBRATED_UPDATING;
      }
      config false;
    }
    leaf ueAssistedPrecodingOptTimeGap {
      description "Time gap between two NR UE Assisted Precoding Optimization events. Only applicable to Low-Band and Mid-Band sector carriers.; range 0..43198; Default value: 300.";
      type int32 {
        range "0..43198";
      }
      default "300";
      units "s";
    }
    list ulCalibrationData {
      config false;
      description "Uplink antenna calibration information. Only applicable to Mid-Band sector carriers.; MOM flags: isNillable=true; Status info: Since 25.Q2. Planned to be removed..";
      uses UlCalibrationDataRO-struct;
    }
    leaf-list pmEmfPwrBackoffPwrDir6Distr {
      description "Estimated average power distribution over time relative to maximum TX power for sectorcarrier for direction 6. Only backoff related to Directional EMF feature is reflected in this counter. Power Spectral Density limitation related to other features is not shown. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf-list pmEmfPwrBackoffPwrDir1Distr {
      description "Estimated average power distribution over time relative to maximum TX power for sectorcarrier for direction 1. Only backoff related to Directional EMF feature is reflected in this counter. Power Spectral Density limitation related to other features is not shown. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf pmSectorCarrierDowntimeMan {
      description "Length of time sector carrier is disabled due to being manually locked. Unit: seconds.";
      type uint64;
      config false;
    }
    leaf-list pmEmfPwrBackoffStepPwrDir4Distr {
      description "Estimated average power distribution over time relative to maximum TX power in each control step for SectorCarrier for direction 4. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf pmSectorCarrierDowntimeAutoCbrs {
      description "Length of time CBRS-enabled sector carrier is automatically disabled because grant period from Spectrum Access System is expired. Unit: seconds.";
      type uint64;
      config false;
    }
    leaf-list pmEmfPwrBackoffStepPwrDir3Distr {
      description "Estimated average power distribution over time relative to maximum TX power in each control step for SectorCarrier for direction 3. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf pmUeAssistedPrecodingOptCalibratedUpdating {
      description "Number of NR UE-Assisted Precoding Optimization calibrations with result ACTIVE-CALIBRATED-UPDATING. This counter is used for the feature NR UE-Assisted Precoding Optimization (applicable for 4Tx radio only). Calibration result ACTIVE-CALIBRATED-UPDATING means that the feature is active and calibrated, and the AC-event finished with estimated phase and/or time delay values outside preset limits. For more information, see Feature Description NR UE-Assisted Precoding Optimization in CPI library..";
      type uint64;
      config false;
    }
    leaf-list pmEmfPwrBackoffPwrDir8Distr {
      description "Estimated average power distribution over time relative to maximum TX power for sectorcarrier for direction 8. Only backoff related to Directional EMF feature is reflected in this counter. Power Spectral Density limitation related to other features is not shown. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf-list pmEmfPwrBackoffPwrDistr {
      description "Estimated average power distribution over time. Relative to maximum TX power for sectorcarrier when power backoff is ON. Unit: N/A Ranges: Bin[0]: [0..2.5] % Bin[1]: ]2.5..5] % Bin[2]: ]5..7.5] % Bin[3]: ]7.5..10] % Bin[4]: [10..12.5] % Bin[5]: ]12.5..15] % Bin[6]: ]15..17.5] % Bin[7]: ]17.5..20] % Bin[8]: [20..22.5] % Bin[9]: ]22.5..25] % Bin[10]: ]25..27.5] % Bin[11]: ]27.5..30] % Bin[12]: [30..32.5] % Bin[13]: ]32.5..35] % Bin[14]: ]35..37.5] % Bin[15]: ]37.5..40] % Bin[16]: [40..42.5] % Bin[17]: ]42.5..45] % Bin[18]: ]45..47.5] % Bin[19]: ]47.5..50] % Bin[20]: [50..52.5] % Bin[21]: ]52.5..55] % Bin[22]: ]55..57.5] % Bin[23]: ]57.5..60] % Bin[24]: [60..62.5] % Bin[25]: ]62.5..65] % Bin[26]: ]65..67.5] % Bin[27]: ]67.5..70] % Bin[28]: [70..72.5] % Bin[29]: ]72.5..75] % Bin[30]: ]75..77.5] % Bin[31]: ]77.5..80] % Bin[32]: [80..82.5] % Bin[33]: ]82.5..85] % Bin[34]: ]85..87.5] % Bin[35]: ]87.5..90] % Bin[36]: [90..92.5] % Bin[37]: ]92.5..95] % Bin[38]: ]95..97.5] % Bin[39]: ]97.5..100] %.";
      type uint32;
      max-elements 40;
    }
    leaf-list pmEmfPwrBackoffStepPwrDir6Distr {
      description "Estimated average power distribution over time relative to maximum TX power in each control step for SectorCarrier for direction 6. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf-list pmRadioBranchDeltaSinr0Distr {
      description "Value is SINR difference of PUSCH channel between antenna branch 1 and antenna branch 0 in antenna branch pair 0. Unit: N/A Ranges: Bin[0]: [..-29] dB Bin[1]: ]-29..-28] dB Bin[2]: ]-28..-27] dB Bin[3]: ]-27..-26] dB Bin[4]: ]-26..-25] dB Bin[5]: ]-25..-24] dB Bin[6]: ]-24..-23] dB Bin[7]: ]-23..-22] dB Bin[8]: ]-22..-21] dB Bin[9]: ]-21..-20] dB Bin[10]: ]-20..-19] dB Bin[11]: ]-19..-18] dB Bin[12]: ]-18..-17] dB Bin[13]: ]-17..-16] dB Bin[14]: ]-16..-15] dB Bin[15]: ]-15..-14] dB Bin[16]: ]-14..-13] dB Bin[17]: ]-13..-12] dB Bin[18]: ]-12..-11] dB Bin[19]: ]-11..-10] dB Bin[20]: ]-10..-9] dB Bin[21]: ]-9..-8] dB Bin[22]: ]-8..-7] dB Bin[23]: ]-7..-6] dB Bin[24]: ]-6..-5] dB Bin[25]: ]-5..-4] dB Bin[26]: ]-4..-3] dB Bin[27]: ]-3..-2] dB Bin[28]: ]-2..-1] dB Bin[29]: ]-1..0] dB Bin[30]: ]0..1] dB Bin[31]: ]1..2] dB Bin[32]: ]2..3] dB Bin[33]: ]3..4] dB Bin[34]: ]4..5] dB Bin[35]: ]5..6] dB Bin[36]: ]6..7] dB Bin[37]: ]7..8] dB Bin[38]: ]8..9] dB Bin[39]: ]9..10] dB Bin[40]: ]10..11] dB Bin[41]: ]11..12] dB Bin[42]: ]12..13] dB Bin[43]: ]13..14] dB Bin[44]: ]14..15] dB Bin[45]: ]15..16] dB Bin[46]: ]16..17] dB Bin[47]: ]17..18] dB Bin[48]: ]18..19] dB Bin[49]: ]19..20] dB Bin[50]: ]20..21] dB Bin[51]: ]21..22] dB Bin[52]: ]22..23] dB Bin[53]: ]23..24] dB Bin[54]: ]24..25] dB Bin[55]: ]25..26] dB Bin[56]: ]26..27] dB Bin[57]: ]27..28] dB Bin[58]: ]28..29] dB Bin[59]: ]29..] dB Compressed: True.";
      type uint64;
      max-elements 60;
    }
    leaf-list pmEmfPrbSclPowerDeboostPdschDirDistr {
      description "Distribution of PRB scale used to increase upper limit on PRB calculated by worst-case EMF controller with minimum number of allowed PRBs among all directions. Counter stepped on each power backoff control step. Unit: N/A Ranges: Bin[0]: 1 Bin[1]: 2 Bin[2]: 3 Bin[3]: 4.";
      type uint64;
      max-elements 4;
    }
    leaf-list pmEmfPwrBackoffPwrDir7Distr {
      description "Estimated average power distribution over time relative to maximum TX power for sectorcarrier for direction 7. Only backoff related to Directional EMF feature is reflected in this counter. Power Spectral Density limitation related to other features is not shown. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf pmEmfPwrBackoffHardLimit {
      description "Number of times when power is hard limited. Unit: N/A.";
      type uint32;
      config false;
    }
    leaf pmActiveUeUlSum {
      description "Number of UE instances considered active in uplink of sector carrier. UE is considered to have DRB or SRB data in its buffer. Unit: N/A.";
      type uint64;
      config false;
    }
    leaf-list pmEmfPwrBackoffStepPwrDir8Distr {
      description "Estimated average power distribution over time relative to maximum TX power in each control step for SectorCarrier for direction 8. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf-list pmEmfPwrBackoffDynResThrDir2Distr {
      description "Distribution of dynamic resource threshold conditioned on power backoff state set to ON for direction 2. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf-list pmEmfPwrBackoffDynResThrDistr {
      description "Distribution of dynamic resource threshold conditioned on power backoff state set to ON. Unit: N/A Ranges: Bin[0]: [0..2.5] % Bin[1]: ]2.5..5] % Bin[2]: ]5..7.5] % Bin[3]: ]7.5..10] % Bin[4]: [10..12.5] % Bin[5]: ]12.5..15] % Bin[6]: ]15..17.5] % Bin[7]: ]17.5..20] % Bin[8]: [20..22.5] % Bin[9]: ]22.5..25] % Bin[10]: ]25..27.5] % Bin[11]: ]27.5..30] % Bin[12]: [30..32.5] % Bin[13]: ]32.5..35] % Bin[14]: ]35..37.5] % Bin[15]: ]37.5..40] % Bin[16]: [40..42.5] % Bin[17]: ]42.5..45] % Bin[18]: ]45..47.5] % Bin[19]: ]47.5..50] % Bin[20]: [50..52.5] % Bin[21]: ]52.5..55] % Bin[22]: ]55..57.5] % Bin[23]: ]57.5..60] % Bin[24]: [60..62.5] % Bin[25]: ]62.5..65] % Bin[26]: ]65..67.5] % Bin[27]: ]67.5..70] % Bin[28]: [70..72.5] % Bin[29]: ]72.5..75] % Bin[30]: ]75..77.5] % Bin[31]: ]77.5..80] % Bin[32]: [80..82.5] % Bin[33]: ]82.5..85] % Bin[34]: ]85..87.5] % Bin[35]: ]87.5..90] % Bin[36]: [90..92.5] % Bin[37]: ]92.5..95] % Bin[38]: ]95..97.5] % Bin[39]: ]97.5..100] %.";
      type uint32;
      max-elements 40;
    }
    leaf-list pmRadioBranchDeltaSinr2Distr {
      description "Value is SINR difference of PUSCH channel between antenna branch 3 and antenna branch 2 in antenna branch pair 2. Unit: N/A Ranges: Bin[0]: [..-29] dB Bin[1]: ]-29..-28] dB Bin[2]: ]-28..-27] dB Bin[3]: ]-27..-26] dB Bin[4]: ]-26..-25] dB Bin[5]: ]-25..-24] dB Bin[6]: ]-24..-23] dB Bin[7]: ]-23..-22] dB Bin[8]: ]-22..-21] dB Bin[9]: ]-21..-20] dB Bin[10]: ]-20..-19] dB Bin[11]: ]-19..-18] dB Bin[12]: ]-18..-17] dB Bin[13]: ]-17..-16] dB Bin[14]: ]-16..-15] dB Bin[15]: ]-15..-14] dB Bin[16]: ]-14..-13] dB Bin[17]: ]-13..-12] dB Bin[18]: ]-12..-11] dB Bin[19]: ]-11..-10] dB Bin[20]: ]-10..-9] dB Bin[21]: ]-9..-8] dB Bin[22]: ]-8..-7] dB Bin[23]: ]-7..-6] dB Bin[24]: ]-6..-5] dB Bin[25]: ]-5..-4] dB Bin[26]: ]-4..-3] dB Bin[27]: ]-3..-2] dB Bin[28]: ]-2..-1] dB Bin[29]: ]-1..0] dB Bin[30]: ]0..1] dB Bin[31]: ]1..2] dB Bin[32]: ]2..3] dB Bin[33]: ]3..4] dB Bin[34]: ]4..5] dB Bin[35]: ]5..6] dB Bin[36]: ]6..7] dB Bin[37]: ]7..8] dB Bin[38]: ]8..9] dB Bin[39]: ]9..10] dB Bin[40]: ]10..11] dB Bin[41]: ]11..12] dB Bin[42]: ]12..13] dB Bin[43]: ]13..14] dB Bin[44]: ]14..15] dB Bin[45]: ]15..16] dB Bin[46]: ]16..17] dB Bin[47]: ]17..18] dB Bin[48]: ]18..19] dB Bin[49]: ]19..20] dB Bin[50]: ]20..21] dB Bin[51]: ]21..22] dB Bin[52]: ]22..23] dB Bin[53]: ]23..24] dB Bin[54]: ]24..25] dB Bin[55]: ]25..26] dB Bin[56]: ]26..27] dB Bin[57]: ]27..28] dB Bin[58]: ]28..29] dB Bin[59]: ]29..] dB Compressed: True.";
      type uint64;
      max-elements 60;
    }
    leaf pmSectorCarrierTimeSamp {
      description "Number of times corresponding sector carrier downtime and uptime counters accumulate new sample..";
      type uint64;
      config false;
    }
    leaf-list pmEmfPwrBackoffDynResThrDir7Distr {
      description "Distribution of dynamic resource threshold conditioned on power backoff state set to ON for direction 7. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf-list pmEmfPwrBackoffPwrDir3Distr {
      description "Estimated average power distribution over time relative to maximum TX power for sectorcarrier for direction 3. Only backoff related to Directional EMF feature is reflected in this counter. Power Spectral Density limitation related to other features is not shown. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf pmEmfPwrBackoffSamp {
      description "Number of times the power backoff algorithm is executed. Unit: N/A.";
      type uint32;
      config false;
    }
    leaf-list pmEmfPwrBackoffPwrDir2Distr {
      description "Estimated average power distribution over time relative to maximum TX power for sectorcarrier for direction 2. Only backoff related to Directional EMF feature is reflected in this counter. Power Spectral Density limitation related to other features is not shown. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf pmActiveUeUlSamp {
      description "Number of times corresponding NRSectorCarrier.pmActiveUeUlSum counter is incremented for each sector carrier. Unit: N/A.";
      type uint64;
      config false;
    }
    leaf-list pmEmfPwrBackoffPwrDir5Distr {
      description "Estimated average power distribution over time relative to maximum TX power for sectorcarrier for direction 5. Only backoff related to Directional EMF feature is reflected in this counter. Power Spectral Density limitation related to other features is not shown. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf-list pmRadioBranchDeltaSinr5Distr {
      description "Value is SINR difference of PUSCH channel between antenna branch 6 and antenna branch 5 in antenna branch pair 5. Unit: N/A Ranges: Bin[0]: [..-29] dB Bin[1]: ]-29..-28] dB Bin[2]: ]-28..-27] dB Bin[3]: ]-27..-26] dB Bin[4]: ]-26..-25] dB Bin[5]: ]-25..-24] dB Bin[6]: ]-24..-23] dB Bin[7]: ]-23..-22] dB Bin[8]: ]-22..-21] dB Bin[9]: ]-21..-20] dB Bin[10]: ]-20..-19] dB Bin[11]: ]-19..-18] dB Bin[12]: ]-18..-17] dB Bin[13]: ]-17..-16] dB Bin[14]: ]-16..-15] dB Bin[15]: ]-15..-14] dB Bin[16]: ]-14..-13] dB Bin[17]: ]-13..-12] dB Bin[18]: ]-12..-11] dB Bin[19]: ]-11..-10] dB Bin[20]: ]-10..-9] dB Bin[21]: ]-9..-8] dB Bin[22]: ]-8..-7] dB Bin[23]: ]-7..-6] dB Bin[24]: ]-6..-5] dB Bin[25]: ]-5..-4] dB Bin[26]: ]-4..-3] dB Bin[27]: ]-3..-2] dB Bin[28]: ]-2..-1] dB Bin[29]: ]-1..0] dB Bin[30]: ]0..1] dB Bin[31]: ]1..2] dB Bin[32]: ]2..3] dB Bin[33]: ]3..4] dB Bin[34]: ]4..5] dB Bin[35]: ]5..6] dB Bin[36]: ]6..7] dB Bin[37]: ]7..8] dB Bin[38]: ]8..9] dB Bin[39]: ]9..10] dB Bin[40]: ]10..11] dB Bin[41]: ]11..12] dB Bin[42]: ]12..13] dB Bin[43]: ]13..14] dB Bin[44]: ]14..15] dB Bin[45]: ]15..16] dB Bin[46]: ]16..17] dB Bin[47]: ]17..18] dB Bin[48]: ]18..19] dB Bin[49]: ]19..20] dB Bin[50]: ]20..21] dB Bin[51]: ]21..22] dB Bin[52]: ]22..23] dB Bin[53]: ]23..24] dB Bin[54]: ]24..25] dB Bin[55]: ]25..26] dB Bin[56]: ]26..27] dB Bin[57]: ]27..28] dB Bin[58]: ]28..29] dB Bin[59]: ]29..] dB Compressed: True.";
      type uint64;
      max-elements 60;
    }
    leaf pmEmfResourceAllowedDir {
      description "Number of allowed resources by Directional EMF solution considering power scale. Unit: N/A Deprecated: Since 24.Q2. Planned to be removed. Replaced by GNBDU::GNBDU_NRSectorCarrier::PmEmfResourceAllowedNormalizedDir; MOM flags: noNotification.";
      type uint64;
      config false;
      status deprecated;
    }
    leaf-list pmEmfPwrBackoffStepPwrDir1Distr {
      description "Estimated average power distribution over time relative to maximum TX power in each control step for SectorCarrier for direction 1. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf-list pmEmfPwrBackoffStepPwrDir2Distr {
      description "Estimated average power distribution over time relative to maximum TX power in each control step for SectorCarrier for direction 2. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf-list pmRadioPowerDlDistr {
      description "Measures sum of transmission power in downlink. Distributes time-averaged values of transmitted power relative to maximum transmission power for sectorCarrier. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf-list pmEmfPwrBackoffStepPwrDir7Distr {
      description "Estimated average power distribution over time relative to maximum TX power in each control step for SectorCarrier for direction 7. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf pmRadioScaledTxPowerMax {
      description "Maximum value of NRSectorCarrier.scaledTransmissionPower during ROP. Unit: mW.";
      type int64;
      config false;
    }
    leaf-list pmEmfPwrBackoffDynResThrDir6Distr {
      description "Distribution of dynamic resource threshold conditioned on power backoff state set to ON for direction 6. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf-list pmEmfPwrBackoffPwrDir4Distr {
      description "Estimated average power distribution over time relative to maximum TX power for sectorcarrier for direction 4. Only backoff related to Directional EMF feature is reflected in this counter. Power Spectral Density limitation related to other features is not shown. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf pmMicroTxSleepTime {
      description "Time of no radio power. Indicates total power saving time. Unit: 1 s. Applicable if the following conditions are met: - Micro Sleep Tx feature is activated. - Micro Sleep Tx-capable radios are used with only one carrier on the specific TX branch. If more than one carrier is configured on a specific TX branch, the radio only switches off the hardware related to those TX branches where no carriers are transmitting. RadioProcessing.pmTxOffTime, Rfport.pmTxOffTime or FreqBandData.pmTxOffTime can be used to observe total time transmission is switched off on hardware. Applicable to non-ESS cells and ESS FDD cells when partner LTE cell is locked..";
      type uint64;
      config false;
    }
    leaf-list pmRadioBranchDeltaSinr1Distr {
      description "Value is SINR difference of PUSCH channel between antenna branch 2 and antenna branch 1 in antenna branch pair 1. Unit: N/A Ranges: Bin[0]: [..-29] dB Bin[1]: ]-29..-28] dB Bin[2]: ]-28..-27] dB Bin[3]: ]-27..-26] dB Bin[4]: ]-26..-25] dB Bin[5]: ]-25..-24] dB Bin[6]: ]-24..-23] dB Bin[7]: ]-23..-22] dB Bin[8]: ]-22..-21] dB Bin[9]: ]-21..-20] dB Bin[10]: ]-20..-19] dB Bin[11]: ]-19..-18] dB Bin[12]: ]-18..-17] dB Bin[13]: ]-17..-16] dB Bin[14]: ]-16..-15] dB Bin[15]: ]-15..-14] dB Bin[16]: ]-14..-13] dB Bin[17]: ]-13..-12] dB Bin[18]: ]-12..-11] dB Bin[19]: ]-11..-10] dB Bin[20]: ]-10..-9] dB Bin[21]: ]-9..-8] dB Bin[22]: ]-8..-7] dB Bin[23]: ]-7..-6] dB Bin[24]: ]-6..-5] dB Bin[25]: ]-5..-4] dB Bin[26]: ]-4..-3] dB Bin[27]: ]-3..-2] dB Bin[28]: ]-2..-1] dB Bin[29]: ]-1..0] dB Bin[30]: ]0..1] dB Bin[31]: ]1..2] dB Bin[32]: ]2..3] dB Bin[33]: ]3..4] dB Bin[34]: ]4..5] dB Bin[35]: ]5..6] dB Bin[36]: ]6..7] dB Bin[37]: ]7..8] dB Bin[38]: ]8..9] dB Bin[39]: ]9..10] dB Bin[40]: ]10..11] dB Bin[41]: ]11..12] dB Bin[42]: ]12..13] dB Bin[43]: ]13..14] dB Bin[44]: ]14..15] dB Bin[45]: ]15..16] dB Bin[46]: ]16..17] dB Bin[47]: ]17..18] dB Bin[48]: ]18..19] dB Bin[49]: ]19..20] dB Bin[50]: ]20..21] dB Bin[51]: ]21..22] dB Bin[52]: ]22..23] dB Bin[53]: ]23..24] dB Bin[54]: ]24..25] dB Bin[55]: ]25..26] dB Bin[56]: ]26..27] dB Bin[57]: ]27..28] dB Bin[58]: ]28..29] dB Bin[59]: ]29..] dB Compressed: True.";
      type uint64;
      max-elements 60;
    }
    leaf-list pmEmfPwrBackoffDynResThrDir1Distr {
      description "Distribution of dynamic resource threshold conditioned on power backoff state set to ON for direction 1. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf pmSectorCarrierDowntime {
      description "Length of time sector carrier is disabled. Unit: seconds.";
      type uint64;
      config false;
    }
    leaf-list pmRadioBranchDeltaSinr4Distr {
      description "Value is SINR difference of PUSCH channel between antenna branch 5 and antenna branch 4 in antenna branch pair 4. Unit: N/A Ranges: Bin[0]: [..-29] dB Bin[1]: ]-29..-28] dB Bin[2]: ]-28..-27] dB Bin[3]: ]-27..-26] dB Bin[4]: ]-26..-25] dB Bin[5]: ]-25..-24] dB Bin[6]: ]-24..-23] dB Bin[7]: ]-23..-22] dB Bin[8]: ]-22..-21] dB Bin[9]: ]-21..-20] dB Bin[10]: ]-20..-19] dB Bin[11]: ]-19..-18] dB Bin[12]: ]-18..-17] dB Bin[13]: ]-17..-16] dB Bin[14]: ]-16..-15] dB Bin[15]: ]-15..-14] dB Bin[16]: ]-14..-13] dB Bin[17]: ]-13..-12] dB Bin[18]: ]-12..-11] dB Bin[19]: ]-11..-10] dB Bin[20]: ]-10..-9] dB Bin[21]: ]-9..-8] dB Bin[22]: ]-8..-7] dB Bin[23]: ]-7..-6] dB Bin[24]: ]-6..-5] dB Bin[25]: ]-5..-4] dB Bin[26]: ]-4..-3] dB Bin[27]: ]-3..-2] dB Bin[28]: ]-2..-1] dB Bin[29]: ]-1..0] dB Bin[30]: ]0..1] dB Bin[31]: ]1..2] dB Bin[32]: ]2..3] dB Bin[33]: ]3..4] dB Bin[34]: ]4..5] dB Bin[35]: ]5..6] dB Bin[36]: ]6..7] dB Bin[37]: ]7..8] dB Bin[38]: ]8..9] dB Bin[39]: ]9..10] dB Bin[40]: ]10..11] dB Bin[41]: ]11..12] dB Bin[42]: ]12..13] dB Bin[43]: ]13..14] dB Bin[44]: ]14..15] dB Bin[45]: ]15..16] dB Bin[46]: ]16..17] dB Bin[47]: ]17..18] dB Bin[48]: ]18..19] dB Bin[49]: ]19..20] dB Bin[50]: ]20..21] dB Bin[51]: ]21..22] dB Bin[52]: ]22..23] dB Bin[53]: ]23..24] dB Bin[54]: ]24..25] dB Bin[55]: ]25..26] dB Bin[56]: ]26..27] dB Bin[57]: ]27..28] dB Bin[58]: ]28..29] dB Bin[59]: ]29..] dB Compressed: True.";
      type uint64;
      max-elements 60;
    }
    leaf pmSectorCarrierDowntimeManCbrs {
      description "Length of time CBRS-enabled sector carrier is locked by Domain Coordinator due to reconfiguration. Unit: seconds.";
      type uint64;
      config false;
    }
    leaf-list pmEmfPwrBackoffDynResThrDir3Distr {
      description "Distribution of dynamic resource threshold conditioned on power backoff state set to ON for direction 3. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf-list pmRadioBranchDeltaSinr3Distr {
      description "Value is SINR difference of PUSCH channel between antenna branch 4 and antenna branch 3 in antenna branch pair 3. Unit: N/A Ranges: Bin[0]: [..-29] dB Bin[1]: ]-29..-28] dB Bin[2]: ]-28..-27] dB Bin[3]: ]-27..-26] dB Bin[4]: ]-26..-25] dB Bin[5]: ]-25..-24] dB Bin[6]: ]-24..-23] dB Bin[7]: ]-23..-22] dB Bin[8]: ]-22..-21] dB Bin[9]: ]-21..-20] dB Bin[10]: ]-20..-19] dB Bin[11]: ]-19..-18] dB Bin[12]: ]-18..-17] dB Bin[13]: ]-17..-16] dB Bin[14]: ]-16..-15] dB Bin[15]: ]-15..-14] dB Bin[16]: ]-14..-13] dB Bin[17]: ]-13..-12] dB Bin[18]: ]-12..-11] dB Bin[19]: ]-11..-10] dB Bin[20]: ]-10..-9] dB Bin[21]: ]-9..-8] dB Bin[22]: ]-8..-7] dB Bin[23]: ]-7..-6] dB Bin[24]: ]-6..-5] dB Bin[25]: ]-5..-4] dB Bin[26]: ]-4..-3] dB Bin[27]: ]-3..-2] dB Bin[28]: ]-2..-1] dB Bin[29]: ]-1..0] dB Bin[30]: ]0..1] dB Bin[31]: ]1..2] dB Bin[32]: ]2..3] dB Bin[33]: ]3..4] dB Bin[34]: ]4..5] dB Bin[35]: ]5..6] dB Bin[36]: ]6..7] dB Bin[37]: ]7..8] dB Bin[38]: ]8..9] dB Bin[39]: ]9..10] dB Bin[40]: ]10..11] dB Bin[41]: ]11..12] dB Bin[42]: ]12..13] dB Bin[43]: ]13..14] dB Bin[44]: ]14..15] dB Bin[45]: ]15..16] dB Bin[46]: ]16..17] dB Bin[47]: ]17..18] dB Bin[48]: ]18..19] dB Bin[49]: ]19..20] dB Bin[50]: ]20..21] dB Bin[51]: ]21..22] dB Bin[52]: ]22..23] dB Bin[53]: ]23..24] dB Bin[54]: ]24..25] dB Bin[55]: ]25..26] dB Bin[56]: ]26..27] dB Bin[57]: ]27..28] dB Bin[58]: ]28..29] dB Bin[59]: ]29..] dB Compressed: True.";
      type uint64;
      max-elements 60;
    }
    leaf-list pmEmfPwrBackoffDynResThrDir5Distr {
      description "Distribution of dynamic resource threshold conditioned on power backoff state set to ON for direction 5. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf-list pmRadioBranchDeltaSinr6Distr {
      description "Value is SINR difference of PUSCH channel between antenna branch 7 and antenna branch 6 in antenna branch pair 6. Unit: N/A Ranges: Bin[0]: [..-29] dB Bin[1]: ]-29..-28] dB Bin[2]: ]-28..-27] dB Bin[3]: ]-27..-26] dB Bin[4]: ]-26..-25] dB Bin[5]: ]-25..-24] dB Bin[6]: ]-24..-23] dB Bin[7]: ]-23..-22] dB Bin[8]: ]-22..-21] dB Bin[9]: ]-21..-20] dB Bin[10]: ]-20..-19] dB Bin[11]: ]-19..-18] dB Bin[12]: ]-18..-17] dB Bin[13]: ]-17..-16] dB Bin[14]: ]-16..-15] dB Bin[15]: ]-15..-14] dB Bin[16]: ]-14..-13] dB Bin[17]: ]-13..-12] dB Bin[18]: ]-12..-11] dB Bin[19]: ]-11..-10] dB Bin[20]: ]-10..-9] dB Bin[21]: ]-9..-8] dB Bin[22]: ]-8..-7] dB Bin[23]: ]-7..-6] dB Bin[24]: ]-6..-5] dB Bin[25]: ]-5..-4] dB Bin[26]: ]-4..-3] dB Bin[27]: ]-3..-2] dB Bin[28]: ]-2..-1] dB Bin[29]: ]-1..0] dB Bin[30]: ]0..1] dB Bin[31]: ]1..2] dB Bin[32]: ]2..3] dB Bin[33]: ]3..4] dB Bin[34]: ]4..5] dB Bin[35]: ]5..6] dB Bin[36]: ]6..7] dB Bin[37]: ]7..8] dB Bin[38]: ]8..9] dB Bin[39]: ]9..10] dB Bin[40]: ]10..11] dB Bin[41]: ]11..12] dB Bin[42]: ]12..13] dB Bin[43]: ]13..14] dB Bin[44]: ]14..15] dB Bin[45]: ]15..16] dB Bin[46]: ]16..17] dB Bin[47]: ]17..18] dB Bin[48]: ]18..19] dB Bin[49]: ]19..20] dB Bin[50]: ]20..21] dB Bin[51]: ]21..22] dB Bin[52]: ]22..23] dB Bin[53]: ]23..24] dB Bin[54]: ]24..25] dB Bin[55]: ]25..26] dB Bin[56]: ]26..27] dB Bin[57]: ]27..28] dB Bin[58]: ]28..29] dB Bin[59]: ]29..] dB Compressed: True.";
      type uint64;
      max-elements 60;
    }
    leaf pmSectorCarrierDowntimeAuto {
      description "Length of time sector carrier is automatically disabled. Unit: seconds.";
      type uint64;
      config false;
    }
    leaf-list pmEmfPwrBackoffStepPwrDirDistr {
      description "Estimated average power distribution over time relative to maximum TX power in each control step for SectorCarrier used with Directional EMF. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf-list pmEmfPwrBackoffDynResThrDir8Distr {
      description "Distribution of dynamic resource threshold conditioned on power backoff state set to ON for direction 8. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf pmEmfPwrBackoffSampDir {
      description "Number of times power backoff algorithm is executed. Unit: N/A.";
      type uint64;
      config false;
    }
    leaf-list pmEmfPwrBackoffPwrDirDistr {
      description "Distribution of estimated time-averaged power relative to maximum Tx power of the cell. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf pmUeAssistedPrecodingOptNoUpdate {
      description "Number of times MO attribute GNBDU NRSectorCarrier.ueAssistedPrecodingOptStatus is set to ACTIVE_NO_UPDATE. This counter is used for the feature NR UE-Assisted Precoding Optimization (applicable for 4Tx radio only). Status ACTIVE-NO-UPDATE means that the feature is active, but no AC-event with result ACTIVE-CALIBRATED or ACTIVE-CALIBRATED-UPDATING has occured within a preset time period. For more information, see Feature Description NR UE-Assisted Precoding Optimization in CPI library..";
      type uint64;
      config false;
    }
    leaf pmSectorCarrierUptime {
      description "Length of time sector carrier is enabled. Unit: seconds.";
      type uint64;
      config false;
    }
    leaf-list pmEmfPwrBackoffDynResThrDir4Distr {
      description "Distribution of dynamic resource threshold conditioned on power backoff state set to ON for direction 4. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf-list pmBwAssignedDistr {
      description "Distribution of assigned bandwidth (NRSectorCarrier.bsChannelBwDL) usage on sector carrier. Unit: N/A Ranges: Bin[0]: Sector carrier disabled Bin[1]: 5 MHz Bin[2]: 10 MHz Bin[3]: 15 MHz Bin[4]: 20 MHz Bin[5]: 25 MHz Bin[6]: 30 MHz Bin[7]: 40 MHz Bin[8]: 50 MHz Bin[9]: 60 MHz Bin[10]: 70 MHz Bin[11]: 80 MHz Bin[12]: 90 MHz Bin[13]: 100 MHz Bin[14]: 200 MHz.";
      type uint64;
      max-elements 15;
    }
    leaf-list pmEmfPwrBackoffStepPwrDir5Distr {
      description "Estimated average power distribution over time relative to maximum TX power in each control step for SectorCarrier for direction 5. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
    leaf pmActiveUeUlMax {
      description "Peak number of active UE instances that have DRB or SRB data in UE uplink buffer of sector carrier. Value is maximum of a set of samples, where following conditions apply: . In a throughout measurement period, each sample is an average of active UE instances on sector carrier. Rounding method can cause counter to show one less than real number of UE instances. . Sample is taken every second. Unit: N/A.";
      type int64;
      config false;
    }
    leaf pmEmfResourceAllowedNormalizedDir {
      description "Fraction of allowed resources by Directional EMF solution. A fraction of 1 means that there is no backoff needed by Directional EMF feature. Unit: N/A.";
      type uint64;
      config false;
    }
    leaf pmUeAssistedPrecodingOptCalibrated {
      description "Number of NR UE-Assisted Precoding Optimization calibrations with result ACTIVE-CALIBRATED. This counter is used for the feature NR UE-Assisted Precoding Optimization (applicable for 4Tx radio only). Calibration result ACTIVE-CALIBRATED means that the feature is active and calibrated, and the AC-event finished with estimated phase and time delay values within preset limits. For more information, see Feature Description NR UE-Assisted Precoding Optimization in CPI library..";
      type uint64;
      config false;
    }
    leaf-list pmEmfPwrBackoffScaledPwrDistr {
      description "Distribution of estimated effective isotropic radiated power for sector carrier-wide solution. Unit: N/A Ranges: Bin[0]: [0..2.5] % Bin[1]: ]2.5..5] % Bin[2]: ]5..7.5] % Bin[3]: ]7.5..10] % Bin[4]: ]10..12.5] % Bin[5]: ]12.5..15] % Bin[6]: ]15..17.5] % Bin[7]: ]17.5..20] % Bin[8]: ]20..22.5] % Bin[9]: ]22.5..25] % Bin[10]: ]25..27.5] % Bin[11]: ]27.5..30] % Bin[12]: ]30..32.5] % Bin[13]: ]32.5..35] % Bin[14]: ]35..37.5] % Bin[15]: ]37.5..40] % Bin[16]: ]40..42.5] % Bin[17]: ]42.5..45] % Bin[18]: ]45..47.5] % Bin[19]: ]47.5..50] % Bin[20]: ]50..52.5] % Bin[21]: ]52.5..55] % Bin[22]: ]55..57.5] % Bin[23]: ]57.5..60] % Bin[24]: ]60..62.5] % Bin[25]: ]62.5..65] % Bin[26]: ]65..67.5] % Bin[27]: ]67.5..70] % Bin[28]: ]70..72.5] % Bin[29]: ]72.5..75] % Bin[30]: ]75..77.5] % Bin[31]: ]77.5..80] % Bin[32]: ]80..82.5] % Bin[33]: ]82.5..85] % Bin[34]: ]85..87.5] % Bin[35]: ]87.5..90] % Bin[36]: ]90..92.5] % Bin[37]: ]92.5..95] % Bin[38]: ]95..97.5] % Bin[39]: ]97.5..100] %.";
      type uint64;
      max-elements 40;
    }
  }
  grouping NRSynchronization-attributes {
    leaf nRSynchronizationId {
      description "The value component of the RDN..";
      type string;
      mandatory true;
    }
  }
  grouping OutOfCov-attributes {
    leaf outOfCovId {
      description "The value component of the RDN..";
      type string;
      mandatory true;
    }
  }
  grouping OutOfCovUeCfg-attributes {
    leaf dlOutOfCovPCellReleaseThresh {
      description "Out of coverage (OOC) state threshold value, in DTX occurrence count, for downlink transmission. When threshold is reached for DTX occurrence count in PCell, RRC release is triggered. If -1, feature is disabled. Only applicable if license for RRC Release of Out-of-Coverage UEs for Dedicated RAN is present and feature is active. Only applicable to Low-Band and Mid-Band cells.; Default value: -1.";
      type int16 {
        range "-1 | 10 | 20 | 30 | 40 | 50 | 60 | 70 | 80 | 90 | 100 | 110 | 120 | 130 | 140 | 150 | 160 | 170 | 180 | 190 | 200";
      }
      default "-1";
    }
    leaf outOfCovUeCfgId {
      description "The value component of the RDN..";
      type string;
      mandatory true;
    }
    leaf-list reservedBy {
      description "Contains a list of MO instances that reserve this MO instance..";
      type string;
      min-elements 0;
    }
    leaf ulOutOfCovPCellReleaseThresh {
      description "Out of coverage (OOC) state threshold value, in DTX occurrence count, for uplink transmission. When threshold is reached for DTX occurrence count in PCell, RRC release is triggered. If -1, feature is disabled. Only applicable if license for RRC Release of Out-of-Coverage UEs for Dedicated RAN is present and feature is active. Only applicable to Low-Band and Mid-Band cells.; Default value: -1.";
      type int16 {
        range "-1 | 10 | 20 | 30 | 40 | 50 | 60 | 70 | 80 | 90 | 100 | 110 | 120 | 130 | 140 | 150 | 160 | 170 | 180 | 190 | 200";
      }
      default "-1";
    }
  }
  grouping Paging-attributes {
    leaf defaultPagingCycle {
      description "Paging cycle T. Used by the RBS and broadcasted in SIB1.; Default value: 128.";
      type int32 {
        range "32 | 64 | 128 | 256";
      }
      default "128";
    }
    leaf n {
      description "Number of PFs in the DRX cycle. For example, one T is every radio frame, half T is every second radio frame, quarter T is every fourth radio frame etc. For High-Band cells, value T is not supported, instead value T1_2, that is, half T is used. In following cases: - value is T and value of nS is 2 or 4 - value is T1_2 and value of nS is 4, it is recommended to set pagingDiscardTimerEdrx equal to or lower than pagingDiscardTimer. Reason is internal system performance..";
      type enumeration {
        enum T;
        enum T1_2;
        enum T1_4;
        enum T1_8;
        enum T1_16;
      }
    }
    leaf nS {
      description "Number of POs for one PF. For ESS cells, value 4 is not allowed. For High-Band cells, values 2 and 4 are not supported, instead value 1 is used. In following cases: - value is 2 and value of n is T - value is 4 and value of n is T or T1_2, it is recommended to set pagingDiscardTimerEdrx equal to or lower than pagingDiscardTimer. Reason is internal system performance.; Default value: 1.";
      type int32 {
        range "1..2 | 4";
      }
      default "1";
    }
    leaf pagingDiscardTimer {
      description "Time for which received paging is retained or queued in RBS before it is discarded. Recommended to set to same as or lower value than T3513 in AMF. Timer T3513 is defined in 3GPP 24.501. Timer T3513 starts when AMF sends Request paging and stops when it receives SERVICE REQUEST or REGISTRATION REQUEST.; range 1..15; Default value: 3.";
      type eytypes:int32_range_1-15;
      default "3";
      units "s";
    }
    leaf pagingDiscardTimerEdrx {
      description "Time for which received eDRX paging is retained or queued in RBS before it is discarded. Recommended to set to same as or lower value than paging resend timer in AMF, to prevent RBS from retaining or sending an old paging after re-sent copy is received from AMF. Only applicable to Low-Band and Mid-Band cells.; range 1..20; Default value: 10.";
      type eytypes:int32_range_1-20;
      default "10";
      units "s";
    }
    leaf pagingId {
      description "The value component of the RDN..";
      type string;
      mandatory true;
    }
  }
  grouping PartitionMapping-attributes {
    leaf caPartition {
      description "Whether partition mapping is used for a resource partition for CA SCell traffic.; Default value: false.";
      type boolean;
      default "false";
    }
    leaf-list listResourcePartitionRef {
      description "References to instances of ResourcePartition MO..";
      type string;
      ordered-by user;
      min-elements 0;
      max-elements 36;
    }
    leaf networkId {
      description "Policy group identity. If empty, partitions are not mapped to group.; range 1..6.";
      type int32 {
        range "1..6";
      }
    }
    leaf partitionId {
      description "Identity for observability of resource partition.; range 1..13.";
      type int32 {
        range "1..13";
      }
      mandatory true;
    }
    leaf partitionMappingId {
      description "The value component of the RDN..";
      type string;
      mandatory true;
    }
    leaf partitionMappingName {
      description "Name of a PartitionMapping.; length 1..255.";
      type string {
        length "1..255";
      }
    }
    leaf-list priorityPartition5qiList {
      description "List of 5QI values to be included in priority partition. To be appended to 5QI values configured in parent CellResourceMapping instance. If empty, no 5QI values shall be included in priority partition..";
      type eytypes:int32_range_1-255;
      ordered-by user;
      min-elements 0;
      max-elements 16;
    }
    leaf resourceAllocationPolicyRef {
      description "Reference to an instance of ResourceAllocationPolicy MO. If empty, residual partition is used..";
      type string;
    }
    leaf resourcePartitionRef {
      description "Reference to an instance of ResourcePartition MO.; Takes effect: New connection; MOM flags: isNillable=true; Status info: Since 23.Q2. Replaced by listResourcePartitionRef. Planned to be removed..";
      type string;
      status deprecated;
      reference "Takes effect: New connection.";
    }
    leaf userLabel {
      description "Label for free use..";
      type string;
    }
  }
  grouping PdcchLinkAdaptation-attributes {
    leaf pdcchLaSinrUeOffset {
      description "UE specific SINR offset added to estimated SINR.; range -10..10; Default value: 0.";
      type eytypes:int32_range_-10-10;
      default "0";
      units "dB";
    }
    leaf pdcchLinkAdaptationId {
      description "The value component of the RDN..";
      type string;
      mandatory true;
    }
  }
  grouping PdcchReuseForPdsch-attributes {
    leaf pdcchReuseForPdschId {
      description "The value component of the RDN..";
      type string;
      mandatory true;
    }
    leaf-list reservedBy {
      description "Contains a list of MO instances that reserve this MO instance..";
      type string;
      min-elements 0;
    }
    leaf ueConfGroupType {
      description "UE configuration group type. UE configuration group type that is applied in contained PdcchReuseForPdschUeCfg instances..";
      type enumeration {
        enum UE_MOBILITY_GROUP;
        enum UE_SERVICE_GROUP;
        enum UE_ADMISSION_GROUP;
      }
    }
    leaf userLabel {
      description "Label for free use..";
      type string;
    }
  }
  grouping PdcchReuseForPdschUeCfg-attributes {
    leaf pdcchReuseForPdschEnabled {
      description "Whether PDCCH and PDSCH Frequency Division Multiplexing in UE is enabled. Not applicable in High-Band cells.; Default value: false.";
      type boolean;
      default "false";
    }
    leaf pdcchReuseForPdschUeCfgId {
      description "The value component of the RDN..";
      type string;
      mandatory true;
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping PowerBackoff-attributes {
    leaf powerBackoffAvgTime {
      description "Power averaging time for EMF Exposure Power Back-off.; range 30..1800.";
      type eytypes:int32_range_30-1800;
      mandatory true;
      units "s";
    }
    leaf powerBackoffEnabled {
      description "Enables EMF Exposure Power Back-off. The feature reduces EMF safety distance in massive MIMO AAS systems. Creating this MO can result in throughput loss..";
      type boolean;
      mandatory true;
    }
    leaf powerBackoffEnhanced {
      description "Whether enhanced sector carrier-wide power backoff is used for 4Tx radios. If true, directionality of common beamformed traffic is taken into account. Only applicable to 4Tx radios. Only applicable if powerBackoffEnabled is true.; Default value: false.";
      type boolean;
      default "false";
    }
    leaf powerBackoffId {
      description "The value component of the RDN..";
      type string;
      mandatory true;
    }
    leaf powerBackoffThresh {
      description "Average transmitted power upper threshold for duration of powerBackoffAvgTime. In percentage of configuredMaxTxPower.; range 0..1000.";
      type eytypes:int32_range_0-1000-10;
      mandatory true;
    }
  }
  grouping PowerBackoffDir-attributes {
    leaf powerBackoffDirAvgTime {
      description "Power averaging time for EMF Exposure Power Back-off. Only used when powerBackoffDirEnabled is true.; range 30..1800.";
      type eytypes:int32_range_30-1800;
      mandatory true;
      units "s";
    }
    leaf powerBackoffDirEnabled {
      description "Whether EMF Exposure Power Back-off is enabled..";
      type boolean;
      mandatory true;
    }
    leaf powerBackoffDirId {
      description "The value component of the RDN..";
      type string;
      mandatory true;
    }
    list powerBackoffDirThresh {
      key "id";
      leaf id {
        type uint32;
        description "Synthetic key for struct attribute.";
      }
      min-elements 1;
      description "Average transmitted power upper threshold for duration of powerBackoffDirectAvgTime. In percentage of configuredMaxTxPower. Each struct member corresponds to one EMF direction. Only used when powerBackoffDirEnabled is true..";
      uses PowerBackoffDirThresh-struct;
    }
  }
  grouping PowerControl-attributes {
    leaf powerControlId {
      description "The value component of the RDN..";
      type string;
      mandatory true;
    }
  }
  grouping PowerControlUeCfg-attributes {
    leaf powerControlUeCfgId {
      description "The value component of the RDN..";
      type string;
      mandatory true;
    }
    leaf puschPowerControlModeFr1 {
      description "PUSCH power control mode for this UE. Not applicable to High-Band cells..";
      type enumeration {
        enum OLPC;
        enum POWER_BASED_CLPC;
      }
    }
    leaf puschPowerControlModeFr2 {
      description "PUSCH power control mode for this UE. Only applicable to High-Band cells..";
      type enumeration {
        enum OLPC;
        enum POWER_BASED_CLPC;
      }
    }
    leaf pZeroNomPuschOffset {
      description "P0 nominal offset for PUSCH power control.; range -16..15; Default value: 0.";
      type int32 {
        range "-16..15";
      }
      default "0";
      units "dB";
    }
    leaf-list reservedBy {
      description "Contains a list of MO instances that reserve this MO instance..";
      type string;
      min-elements 0;
    }
    leaf userLabel {
      description "Label for free use..";
      type string;
    }
  }
  grouping Prescheduling-attributes {
    leaf preschedulingId {
      description "The value component of the RDN..";
      type string;
      mandatory true;
    }
  }
  grouping PreschedulingUeCfg-attributes {
    leaf highPrioPreschedDuration {
      description "Prescheduling duration in high-priority mode. The gNodeB preschedules a UE with a high-priority uplink grant during this time. Only takes effect when preschedulingUeMode is HIGH_PRIORITY. Only applicable to High-Band cells.; range 10..1000; Default value: 100.";
      type uint32 {
        range "10..1000";
      }
      default "100";
      units "ms";
    }
    leaf highPrioPreschedPauseDuration {
      description "Prescheduling in high-priority mode is paused during this period. High-priority prescheduling is prohibited when timer is running (only basic prescheduling is allowed during that time). Only takes effect when preschedulingUeMode is HIGH_PRIORITY. Only applicable to High-Band cells.; range 1..100; Default value: 4.";
      type uint32 {
        range "1..100";
      }
      default "4";
      units "ms";
    }
    leaf highPrioPreschedSinrBackoff {
      description "SINR back off value applied to link adaptation for high-priority prescheduling grants. If 1000, only MCS0 is used for high-priority prescheduling grants. Only takes effect when preschedulingUeMode is HIGH_PRIORITY. Only applicable to High-Band cells.; Default value: 0.";
      type int32 {
        range "0..100 | 1000";
      }
      default "0";
      units "dB";
    }
    leaf preschedulingDataSize {
      description "Granted data size during prescheduling period. Only applicable to Low-Band and Mid-Band cells.; range 1..5000; Default value: 86.";
      type uint32 {
        range "1..5000";
      }
      default "86";
      units "byte";
    }
    leaf preschedulingDuration {
      description "Duration of prescheduling period. Prescheduling is stopped if there are no uplink transmissions during this time. Only applicable if prescheduling mode used for this UE is BASIC and Connected Mode DRX is activated in the UE. Only applicable to Low-Band and Mid-Band cells.; range 5..30000; Default value: 100.";
      type uint32 {
        range "5..30000";
      }
      default "100";
      units "ms";
    }
    leaf preschedulingUeCfgId {
      description "The value component of the RDN..";
      type string;
      mandatory true;
    }
    leaf preschedulingUeMode {
      description "Prescheduling mode used for this UE. If DEFAULT, value is DISABLE for FR1, and is BASIC for FR2. If DISABLE, UE never uses prescheduling and relies only on SR on PUCCH. If BASIC, prescheduling is performed in the lowest priority domain as long as timer preschedulingDuration has not expired. If HIGH_PRIORITY, for High-Band cells, HIGH_PRIORITY prescheduling is performed for duration configured by highPrioPreschedDuration. Basic prescheduling is also performed in the lowest priority..";
      type enumeration {
        enum DISABLE;
        enum BASIC;
        enum HIGH_PRIORITY;
        enum DEFAULT;
      }
    }
    leaf-list reservedBy {
      description "Contains a list of MO instances that reserve this MO instance..";
      type string;
      min-elements 0;
    }
    leaf userLabel {
      description "Label for free use..";
      type string;
    }
  }
  grouping PriorityDomainMapping-attributes {
    leaf priorityDomain {
      description "Internal representation of absolute priority differentiation. Connection using Priority Domain A always has higher priority than connection using Priority Domain B, if A is less than B. Multiple PriorityDomainMapping instances cannot have same value. Priority Domain less than 17 means absolute resource allocation priority over LTE best effort connections in an ESS cell. If SchedulingProfile::essResourceAllocationMode is DEMAND_WEIGHTED_RP, Priority Domain less than 17 means that absolute resource allocation priority is applied.; range 1..64; Default value: 48.";
      type eytypes:int32_range_1-64;
      default "48";
    }
    leaf priorityDomainMappingId {
      description "The value component of the RDN..";
      type string;
      mandatory true;
    }
    leaf-list priorityLevelsList {
      description "List of priority levels to realize using the specified Priority Domain. The same priority level value cannot be configured in multiple priorityLevelsLists..";
      type uint32 {
        range "1..127";
      }
      ordered-by user;
      min-elements 0;
      max-elements 127;
    }
  }
  grouping PuschRep-attributes {
    leaf puschRepId {
      description "The value component of the RDN..";
      type string;
      mandatory true;
    }
    leaf-list reservedBy {
      description "Contains a list of MO instances that reserve this MO instance..";
      type string;
      min-elements 0;
    }
    leaf ueConfGroupType {
      description "UE configuration group type. UE configuration group type that is applied in contained PuschRepUeCfg instances..";
      type enumeration {
        enum UE_MOBILITY_GROUP;
        enum UE_SERVICE_GROUP;
        enum UE_ADMISSION_GROUP;
      }
    }
  }
  grouping PuschRepRel16Drx-attributes {
    leaf puschRepDrxInactTimer {
      description "PUSCH Repetition specific DRX inactivity. If empty, DrxProfileUeCfg::drxInactivityTimer is used..";
      type enumeration {
        enum INACTIVITYTIMER_0MS;
        enum INACTIVITYTIMER_1MS;
        enum INACTIVITYTIMER_2MS;
        enum INACTIVITYTIMER_3MS;
        enum INACTIVITYTIMER_4MS;
        enum INACTIVITYTIMER_5MS;
        enum INACTIVITYTIMER_6MS;
        enum INACTIVITYTIMER_8MS;
        enum INACTIVITYTIMER_10MS;
        enum INACTIVITYTIMER_20MS;
        enum INACTIVITYTIMER_30MS;
        enum INACTIVITYTIMER_40MS;
        enum INACTIVITYTIMER_50MS;
        enum INACTIVITYTIMER_60MS;
        enum INACTIVITYTIMER_80MS;
        enum INACTIVITYTIMER_100MS;
        enum INACTIVITYTIMER_200MS;
        enum INACTIVITYTIMER_300MS;
        enum INACTIVITYTIMER_500MS;
        enum INACTIVITYTIMER_750MS;
        enum INACTIVITYTIMER_1280MS;
        enum INACTIVITYTIMER_1920MS;
        enum INACTIVITYTIMER_2560MS;
      }
    }
    leaf puschRepDrxMode {
      description "PUSCH Repetition specific DRX selection mode for UE..";
      type enumeration {
        enum ACTIVE;
        enum FORCED;
      }
    }
    leaf puschRepDrxRetxTimerUl {
      description "PUSCH Repetition specific DRX retransmission timer. PUSCH Repetition specific maximum number of consecutive PDCCH-subframes until uplink grant is received. If empty, DrxProfileUeCfg::drxRetransmissionTimerUl is used..";
      type int32 {
        range "6 | 8 | 16 | 24 | 33 | 40";
      }
      units "slot";
    }
    leaf puschRepRel16DrxId {
      description "The value component of the RDN..";
      type string;
      mandatory true;
    }
    leaf userLabel {
      description "Label for free use..";
      type string;
    }
  }
  grouping PuschRepUeCfg-attributes {
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf puschRepMode {
      description "PUSCH Repetition operational mode for UE. Only applicable if license for NR Dynamic Slot Aggregation for VoNR is present and feature is active..";
      type enumeration {
        enum NOT_ALLOWED;
        enum DYNAMIC;
      }
    }
    leaf puschRepUeCfgId {
      description "The value component of the RDN..";
      type string;
      mandatory true;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 16;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping QosPriorityMapping-attributes {
    leaf defaultDomain {
      description "Default Priority Domain. The default Priority Domain is used for all unmapped Priority Levels. If empty, value 48 is used.; range 48..48.";
      type uint32 {
        range "48";
      }
      config false;
    }
    leaf qosPriorityMappingId {
      description "The value component of the RDN..";
      type string;
      mandatory true;
    }
  }
  grouping QosPriorityShift-attributes {
    leaf qosPriorityShiftId {
      description "The value component of the RDN..";
      type string;
      mandatory true;
    }
  }
  grouping Rach-attributes {
    leaf rachId {
      description "The value component of the RDN..";
      type string;
      mandatory true;
    }
    leaf-list reservedBy {
      description "Contains a list of MO instances that reserve this MO instance..";
      type string;
      min-elements 0;
    }
    leaf ueConfGroupType {
      description "UE configuration group type. UE configuration group type that is applied in contained RachUeCfg instances..";
      type enumeration {
        enum UE_MOBILITY_GROUP;
        enum UE_SERVICE_GROUP;
        enum UE_ADMISSION_GROUP;
      }
    }
    leaf userLabel {
      description "Label for free use..";
      type string;
    }
  }
  grouping RachUeCfg-attributes {
    leaf cfraEnabled {
      description "Whether Contention Free Random Access (CFRA) is enabled. If true, system allocates a portion of random access preambles for CFRA, to be used for incoming NR SA HO. If allocation fails, CBRA is performed. Only applicable if NRCellDU::cfraEnabled is true. Only applicable to Low-Band and Mid-Band cells.; Default value: false.";
      type boolean;
      default "false";
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf rachUeCfgId {
      description "The value component of the RDN..";
      type string;
      mandatory true;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 16;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping RadioBearerTable-attributes {
    leaf radioBearerTableId {
      description "The value component of the RDN..";
      type string;
      mandatory true;
    }
  }
  grouping RadioLinkControl-attributes {
    leaf radioLinkControlId {
      description "The value component of the RDN..";
      type string;
      mandatory true;
    }
  }
  grouping ResourceAllocationPolicies-attributes {
    leaf resourceAllocationPoliciesId {
      description "The value component of the RDN..";
      type string;
      mandatory true;
    }
    leaf userLabel {
      description "Label for free use..";
      type string;
    }
  }
  grouping ResourceAllocationPolicy-attributes {
    leaf demotedRrpSchedulingPriority {
      description "Scheduling domain to be used by RRP when resource usage is above configured share..";
      type enumeration {
        enum DEMOTED_NORMAL;
        enum DEMOTED_LOW;
      }
    }
    leaf overAllocationAllowed {
      description "Whether over-allocation of partition shares is allowed.; Default value: true.";
      type boolean;
      default "true";
    }
    leaf-list reservedBy {
      description "Contains a list of MO instances that reserve this MO instance..";
      type string;
      min-elements 0;
    }
    leaf resourceAllocationPolicyId {
      description "The value component of the RDN..";
      type string;
      mandatory true;
    }
    leaf resourceShareLimitRef {
      description "Reference to an instance of ResourceShareLimit MO. If empty, none of following features is operable for partition: - Load-based Automated Radio Resource Partitioning. - Automated Radio Resource Partitioning..";
      type string;
    }
    leaf rrpControllerRef {
      description "Reference to an instance of RrpController MO. Automatically set to RrpController=NO_AUTO_CONTROL instance, unless manually set to refer to another MO instance..";
      type string;
    }
    leaf rrpOperationModeDl {
      description "Operation mode of RRP in downlink for a resource allocation policy. This can favor accuracy in share fulfillment over time or low impact on latency..";
      type enumeration {
        enum BALANCED;
        enum FAIRNESS_FAVORED;
      }
    }
    leaf rrpOperationModeUl {
      description "Operation mode of RRP in uplink for a resource allocation policy. This can favor accuracy in share fulfillment over time or low impact on latency..";
      type enumeration {
        enum BALANCED;
        enum FAIRNESS_FAVORED;
      }
    }
    leaf shareAdjustmentModeDl {
      description "Mode of RRP share adjustment. Applied when updating downlink usage share for partition..";
      type enumeration {
        enum ABSOLUTE;
        enum GENERAL_COMPENSATION;
      }
    }
    leaf shareAdjustmentModeUl {
      description "Mode of RRP share adjustment. Applied when updating uplink usage share for partition..";
      type enumeration {
        enum ABSOLUTE;
        enum GENERAL_COMPENSATION;
      }
    }
    leaf spectrumShareDl {
      description "Share of downlink spectrum resources for which resource partition has priority. Partitions can use more than their share if free resources remain in cell.; range 0..100.";
      type eytypes:int32_range_0-100;
      mandatory true;
      units "percent";
    }
    leaf spectrumShareUl {
      description "Share of uplink spectrum resources for which resource partition has priority. Partitions can use more than their share as long as free resources remain in cell.; range 0..100.";
      type eytypes:int32_range_0-100;
      mandatory true;
      units "percent";
    }
    leaf userLabel {
      description "Label for free use..";
      type string;
    }
  }
  grouping ResourceAllocTypeDl-attributes {
    leaf-list reservedBy {
      description "Contains a list of MO instances that reserve this MO instance..";
      type string;
      min-elements 0;
    }
    leaf resourceAllocTypeDlId {
      description "The value component of the RDN..";
      type string;
      mandatory true;
    }
    leaf ueConfGroupType {
      description "UE configuration group type. UE configuration group type that is applied in contained ResourceAllocTypeDlUeCfg instances..";
      type enumeration {
        enum UE_MOBILITY_GROUP;
        enum UE_SERVICE_GROUP;
        enum UE_ADMISSION_GROUP;
      }
    }
  }
  grouping ResourceAllocTypeDlUeCfg-attributes {
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf prefUeResourceAllocDlTypeFr1 {
      description "PDSCH resource allocation type in FR1. Only applicable to Low-Band and Mid-Band cells..";
      type enumeration {
        enum RESOURCE_ALLOCATION_TYPE_0;
        enum DYNAMIC_SWITCH_FB_TYPE_0;
        enum RESOURCE_ALLOCATION_TYPE_1;
        enum DYNAMIC_SWITCH_FB_TYPE_1;
      }
    }
    leaf resourceAllocTypeDlUeCfgId {
      description "The value component of the RDN..";
      type string;
      mandatory true;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 16;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping ResourcePartition-attributes {
    leaf related5qiTableRef {
      description "Reference to an instance of DU5qiTable MO..";
      type string;
    }
    leaf-list reservedBy {
      description "Contains a list of MO instances that reserve this MO instance..";
      type string;
      min-elements 0;
    }
    leaf resourcePartitionId {
      description "The value component of the RDN..";
      type string;
      mandatory true;
    }
    leaf resourcePartitionName {
      description "Name of a resource partition.; length 1..255.";
      type string {
        length "1..255";
      }
    }
  }
  grouping ResourcePartitionMember-attributes {
    leaf-list cellIdList {
      description "List of cell local IDs (NRCellDU::cellLocalId). If empty, all UEs are matched, regardless of cell ID..";
      type eytypes:int32_range_0-16383;
      ordered-by user;
      min-elements 0;
      max-elements 48;
    }
    leaf endpointResourceRef {
      description "Reference to an instance of EndpointResource MO. Defines transport network configuration for specific PLMN or NSSAI. If empty, GNBDUFunction::endpointResourceRef is used. Cannot refer to EndpointResource MO which has LocalSctpEndpoint::interfaceUsed set to F1. F1 SctpEndpoint can only be referenced from GNBDUFunction::endpointResourceRef..";
      type string;
    }
    list pLMNIdList {
      key "id";
      leaf id {
        type uint32;
        description "Synthetic key for struct sequence entry.";
      }
      min-elements 0;
      max-elements 12;
      uses PLMNId-struct;
    }
    leaf resourcePartitionMemberId {
      description "The value component of the RDN..";
      type string;
      mandatory true;
    }
    list sNSSAIList {
      key "id";
      leaf id {
        type uint32;
        description "Synthetic key for struct sequence entry.";
      }
      min-elements 0;
      max-elements 1024;
      uses SliceSelectionAssistInfo-struct;
    }
    leaf-list spidRfspList {
      description "List of SPID or RAT Frequency Selection Priority (RFSP), depending on trafficCategory. If empty, all UEs are matched, regardless of SPID or RFSP. If list has one value, only that SPID or RFSP is matched. If list has multiple values, at least one of them is matched. Value 0 matches all UEs without any assigned SPID or RFSP..";
      type eytypes:int32_range_0-256;
      ordered-by user;
      min-elements 0;
      max-elements 20;
    }
    leaf trafficCategory {
      description "Traffic category used by Slice QoS framework..";
      type enumeration {
        enum SA;
        enum ENDC;
      }
    }
  }
  grouping ResourcePartitions-attributes {
    leaf resourcePartitionsId {
      description "The value component of the RDN..";
      type string;
      mandatory true;
    }
  }
  grouping ResourceShareLimit-attributes {
    leaf-list reservedBy {
      description "Contains a list of MO instances that reserve this MO instance..";
      type string;
      min-elements 0;
    }
    leaf resourceShareLimitId {
      description "The value component of the RDN..";
      type string;
      mandatory true;
    }
    leaf spectrumShareDlLowerLimit {
      description "Lower limit for share of downlink spectrum resources for which resource partition has priority.; range 0..100; Default value: 10.";
      type eytypes:int32_range_0-100;
      default "10";
      units "percent";
    }
    leaf spectrumShareDlUpperLimit {
      description "Upper limit for share of downlink spectrum resources for which resource partition has priority.; range 1..100; Default value: 90.";
      type eytypes:int32_range_1-100;
      default "90";
      units "percent";
    }
    leaf spectrumShareUlLowerLimit {
      description "Lower limit for share of uplink spectrum resources for which resource partition has priority.; range 0..100; Default value: 10.";
      type eytypes:int32_range_0-100;
      default "10";
      units "percent";
    }
    leaf spectrumShareUlUpperLimit {
      description "Upper limit for share of uplink spectrum resources for which resource partition has priority.; range 1..100; Default value: 90.";
      type eytypes:int32_range_1-100;
      default "90";
      units "percent";
    }
    leaf userLabel {
      description "Label for free use..";
      type string;
    }
  }
  grouping RimOffload-attributes {
    leaf rimOffloadId {
      description "The value component of the RDN..";
      type string;
      mandatory true;
    }
  }
  grouping RimOffloadUeCfg-attributes {
    leaf-list reservedBy {
      description "Contains a list of MO instances that reserve this MO instance..";
      type string;
      min-elements 0;
    }
    leaf rimOffloadUeCfgId {
      description "The value component of the RDN..";
      type string;
      mandatory true;
    }
    leaf rimUlCriticalQualThresh {
      description "Critical uplink radio quality level threshold used for RIM triggered UE offload. Below this threshold, uplink quality is considered critical for UE under RIM conditions. Quality is represented by an estimate of the maximum SINR that could be achieved for maximum available power transmission on a single resource block. Applicable to NR SA. Only applicable to Low-Band and Mid-Band cells. Only applicable if NRCellDU::rimOffloadEnabled is true.; range -150..450; Default value: -50.";
      type eytypes:int32_range_-150-450;
      default "-50";
      units "dB";
    }
  }
  grouping RimRSGlobal-attributes {
    list frequencyDomainPara {
      key "id";
      leaf id {
        type uint32;
        description "Synthetic key for struct attribute.";
      }
      description "Frequency domain configuration parameters for RIM RS..";
      uses FrequencyDomainPara-struct;
    }
    leaf rimRSGlobalId {
      description "The value component of the RDN..";
      type string;
      mandatory true;
    }
    list sequenceDomainPara {
      key "id";
      leaf id {
        type uint32;
        description "Synthetic key for struct attribute.";
      }
      description "Sequence domain configuration parameters for RIM RS..";
      uses SequenceDomainPara-struct;
    }
    list timeDomainPara {
      key "id";
      leaf id {
        type uint32;
        description "Synthetic key for struct attribute.";
      }
      description "Time domain configuration parameters for RIM RS..";
      uses TimeDomainPara-struct;
    }
  }
  grouping RimRSSet-attributes {
    leaf-list reservedBy {
      description "Contains a list of MO instances that reserve this MO instance..";
      type string;
      min-elements 0;
    }
    leaf rimRSSetId {
      description "The value component of the RDN..";
      type string;
      mandatory true;
    }
    leaf setId {
      description "RIM set ID.; range 0..4194303.";
      type int32 {
        range "0..4194303";
      }
      mandatory true;
    }
    leaf setType {
      description "RIM RS type..";
      type enumeration {
        enum RS_1;
        enum RS_2;
      }
    }
  }
  grouping Rrc-attributes {
    leaf n310 {
      description "Maximum number of consecutive out of sync indications received from lower layers. Provided to UE by SIB1 or RRCReconfiguration. For EN-DC, provided to UE by SCG radio configuration.; Default value: 20.";
      type int32 {
        range "1..4 | 6 | 8 | 10 | 20";
      }
      default "20";
    }
    leaf n311 {
      description "Maximum number of consecutive in-sync indications received from lower layers. Provided to UE by SIB1 or RRCReconfiguration. For EN-DC, provided to UE by SCG radio configuration.; Default value: 1.";
      type int32 {
        range "1..6 | 8 | 10";
      }
      default "1";
    }
    leaf rrcId {
      description "The value component of the RDN..";
      type string;
      mandatory true;
    }
    leaf t300 {
      description "UE timer to supervise response to RRC Connection Request. Provided to UE by SIB1.; Default value: 1000.";
      type int32 {
        range "100 | 200 | 300 | 400 | 600 | 1000 | 1500 | 2000";
      }
      default "1000";
      units "ms";
    }
    leaf t301 {
      description "Timer t301. UE timer to supervise response to RRC Connection Reestablishment Request during radio connection re-establishment procedure. UE returns to idle mode and optionally starts to reconnect over NAS when timer expires. Provided to UE by SIB1.; Default value: 400.";
      type int32 {
        range "100 | 200 | 300 | 400 | 600 | 1000 | 1500 | 2000";
      }
      default "400";
      units "ms";
    }
    leaf t304 {
      description "Timer t304. Waiting time for successful completion of random access. For EN-DC, provided to UE by SCG radio configuration.; Default value: 1000.";
      type int32 {
        range "50 | 100 | 150 | 200 | 500 | 1000 | 2000 | 10000";
      }
      default "1000";
      units "ms";
    }
    leaf t310 {
      description "Timer t310. Waiting time for radio link failure. Provided to UE by SIB1 or RRCReconfiguration. Values 4000 and 6000 are not supported in SIB1. For standalone, if values 4000 or 6000 are configured, 2000 is used in SIB1. For EN-DC, provided to UE by SCG radio configuration. All values are relevant for EN-DC.; Default value: 2000.";
      type int32 {
        range "0 | 50 | 100 | 200 | 500 | 1000 | 2000 | 4000 | 6000";
      }
      default "2000";
      units "ms";
    }
    leaf t311 {
      description "Timer t311. UE timer triggered at radio link failure. UE tries to re-establish radio connection with one of following options: - Performing RRC Connection Reestablishment. - Finding a suitable cell on another RAT. UE returns to idle mode and optionally starts to reconnect over NAS when timer expires. Provided to UE by SIB1 or RRCReconfiguration.; Default value: 3000.";
      type int32 {
        range "1000 | 3000 | 5000 | 10000 | 15000 | 20000 | 30000";
      }
      default "3000";
      units "ms";
    }
    leaf t319 {
      description "UE timer to supervise response to RRC Connection Resume Request. Provided to UE by SIB1.; Default value: 400.";
      type int32 {
        range "100 | 200 | 300 | 400 | 600 | 1000 | 1500 | 2000";
      }
      default "400";
      units "ms";
    }
  }
  grouping RrpController-attributes {
    leaf-list reservedBy {
      description "Contains a list of MO instances that reserve this MO instance..";
      type string;
      min-elements 0;
    }
    leaf rrpControllerId {
      description "The value component of the RDN..";
      type string;
      mandatory true;
    }
    leaf rrpControllerMode {
      description "RRP controller mode. RrpController instances referenced by rrpControllerRef under ResourceAllocationPolicy and its child ServicePolicy instances must not have a pair of rrpControllerMode set to AUTO_CONTROL_1 and AUTO_CONTROL_2..";
      type enumeration {
        enum NO_AUTO_CONTROL;
        enum AUTO_CONTROL_1;
        enum AUTO_CONTROL_2;
      }
    }
    list slopeInfoDl {
      key "id";
      leaf id {
        type uint32;
        description "Synthetic key for struct sequence entry.";
      }
      min-elements 0;
      max-elements 8;
      uses SlopeInfo-struct;
    }
    list slopeInfoUl {
      key "id";
      leaf id {
        type uint32;
        description "Synthetic key for struct sequence entry.";
      }
      min-elements 0;
      max-elements 8;
      uses SlopeInfo-struct;
    }
    leaf spectrumShareDlDownStepLimit {
      description "Downstep size limit for share of downlink spectrum resources.; range 1..100; Default value: 5.";
      type eytypes:int32_range_1-100;
      default "5";
      units "percent";
    }
    leaf spectrumShareDlUpStepLimit {
      description "Upstep size limit for share of downlink spectrum resources.; range 1..100; Default value: 5.";
      type eytypes:int32_range_1-100;
      default "5";
      units "percent";
    }
    leaf spectrumShareUlDownStepLimit {
      description "Downstep size limit for share of uplink spectrum resources.; range 1..100; Default value: 5.";
      type eytypes:int32_range_1-100;
      default "5";
      units "percent";
    }
    leaf spectrumShareUlUpStepLimit {
      description "Upstep size limit for share of uplink spectrum resources.; range 1..100; Default value: 5.";
      type eytypes:int32_range_1-100;
      default "5";
      units "percent";
    }
    leaf targetThpDl {
      description "Target throughput for downlink. If 0, value is ignored. No automated RRP.; range 0..1000000; Default value: 0.";
      type eytypes:int32_range_0-1000000;
      default "0";
      units "kbps";
    }
    leaf targetThpUl {
      description "Target throughput for uplink. If 0, value is ignored. No automated RRP.; range 0..1000000; Default value: 0.";
      type eytypes:int32_range_0-1000000;
      default "0";
      units "kbps";
    }
    leaf userLabel {
      description "Label for free use..";
      type string;
    }
  }
  grouping SchedulingProfile-attributes {
    leaf dlCaSchedulingMode {
      description "Scheduling mode controlling the type of Downlink CA for each DRB. Not applicable in High-Band cells..";
      type enumeration {
        enum UNLIMITED;
        enum PCELL_ONLY;
      }
    }
    leaf essResourceAllocationMode {
      description "Operation mode for resource allocation between RATs in ESS. If SCHED_POLICY, SharingGroup::schedPolicy in LTE partner is used for prioritization of RAT resource needs in ESS resource allocation. If DEMAND_WEIGHTED_RP, relativePriority and resource demand are used for prioritization of RAT resource needs in ESS resource allocation. The corresponding 5QI is prioritized over SCHED_POLICY configured 5QIs. relativePriorityMode is handled as having RP_ONLY set, regardless of configured value. Only relevant for ESS cells. Only applicable if licenses for NR Relative Priority Scheduling and LTE-NR FDD Spectrum Sharing with QoS-Aware Relative Resource Allocation are present and features are active..";
      type enumeration {
        enum SCHED_POLICY;
        enum DEMAND_WEIGHTED_RP;
      }
    }
    leaf relativePriority {
      description "Relative priority associated with scheduling profile.; range 1..256; Default value: 1.";
      type eytypes:int32_range_1-256;
      default "1";
    }
    leaf relativePriorityMode {
      description "Input parameter for scheduling weight calculation. System uses RP_ONLY in ESS cell for SchedulingProfile instance configured with essResourceAllocationMode set to DEMAND_WEIGHTED_RP..";
      type enumeration {
        enum RP_ONLY;
        enum PDB_ONLY;
        enum RP_AND_PDB;
      }
    }
    leaf-list reservedBy {
      description "Contains a list of MO instances that reserve this MO instance..";
      type string;
      min-elements 0;
    }
    leaf schedulingAlgorithm {
      description "Scheduling algorithm to use for scheduling profile. For High-Band cells, only value RESOURCE_FAIR is applicable, other values are handled as RESOURCE_FAIR. Used for both uplink and downlink if ulSchedulingAlgorithm is empty, else only for downlink. SchedulingAlgorithm RESOURCE_FAIR is applied to UE by default if configured mode is invalid, for example when feature license in gNodeB is missing..";
      type enumeration {
        enum RESOURCE_FAIR;
        enum PRIORITIZED_RATE;
        enum SOFT_RATE_THROTTLING;
        enum ELEVATION_TIME;
        enum LATENCY_PRIORITIZED;
        enum LATENCY_PRIORITIZED_TCC;
      }
    }
    leaf schedulingProfileId {
      description "The value component of the RDN..";
      type string;
      mandatory true;
    }
    leaf ulRelativePriority {
      description "UL-relative priority associated with this scheduling profile. If empty, the value from relativePriority is used.; range 1..256.";
      type eytypes:int32_range_1-256;
    }
    leaf ulSchedulingAlgorithm {
      description "Scheduling algorithm to use for scheduling profile in uplink. For High-Band cells, only value RESOURCE_FAIR is applicable, other values are handled as RESOURCE_FAIR. If empty, value from schedulingAlgorithm is used..";
      type enumeration {
        enum RESOURCE_FAIR;
        enum PRIORITIZED_RATE;
        enum SOFT_RATE_THROTTLING;
        enum ELEVATION_TIME;
        enum LATENCY_PRIORITIZED;
        enum LATENCY_PRIORITIZED_TCC;
      }
    }
    leaf userLabel {
      description "Label for free use..";
      type string;
    }
  }
  grouping ServicePolicy-attributes {
    leaf demotedRrpSchedulingPriority {
      description "Scheduling domain to be used by RRP when resource usage is above configured share..";
      type enumeration {
        enum DEMOTED_NORMAL;
        enum DEMOTED_LOW;
      }
    }
    leaf resourceShareLimitRef {
      description "Reference to an instance of ResourceShareLimit MO. If empty, none of following features is operable for partition: - Load-based Automated Radio Resource Partitioning. - Automated Radio Resource Partitioning..";
      type string;
    }
    leaf rrpControllerRef {
      description "Reference to an instance of RrpController MO. Automatically set to RrpController=NO_AUTO_CONTROL instance, unless manually set to refer to another MO instance..";
      type string;
    }
    leaf rrpOperationModeDl {
      description "Operation mode of RRP in downlink for a service policy. This can favor accuracy in share fulfillment over time or low impact on latency..";
      type enumeration {
        enum BALANCED;
        enum FAIRNESS_FAVORED;
      }
    }
    leaf rrpOperationModeUl {
      description "Operation mode of RRP in uplink for a service policy. This can favor accuracy in share fulfillment over time or low impact on latency..";
      type enumeration {
        enum BALANCED;
        enum FAIRNESS_FAVORED;
      }
    }
    leaf serviceId {
      description "Identity for observability of service within a resource partition.; range 1..2.";
      type eytypes:int32_range_1-2;
      mandatory true;
    }
    leaf-list servicePolicy5qiList {
      description "5QI values used to identify services of ServicePolicy..";
      type eytypes:int32_range_1-255;
      ordered-by user;
      min-elements 0;
      max-elements 8;
    }
    leaf servicePolicyId {
      description "The value component of the RDN..";
      type string;
      mandatory true;
    }
    leaf servicePolicyName {
      description "Name of a ServicePolicy.; length 1..255.";
      type string {
        length "1..255";
      }
    }
    leaf spectrumShareDl {
      description "Share of downlink spectrum resources for which services defined by ServicePolicy MO has priority. A ServicePolicy MO spectrum share refers to a fraction of parent ResourceAllocationPolicy instance spectrum share. Partitions can use more than their share if free resources remain in cell.; range 0..100.";
      type eytypes:int32_range_0-100;
      mandatory true;
      units "percent";
    }
    leaf spectrumShareUl {
      description "Share of uplink spectrum resources for which services defined by ServicePolicy MO has priority. A ServicePolicy MO spectrum share refers to a fraction of parent ResourceAllocationPolicy instance spectrum share. Partitions can use more than their share if free resources remain in cell.; range 0..100.";
      type eytypes:int32_range_0-100;
      mandatory true;
      units "percent";
    }
    leaf userLabel {
      description "Label for free use..";
      type string;
    }
  }
  grouping SessionLimit-attributes {
    leaf maxNoOfSessions {
      description "Maximum number of sessions. If empty, number of sessions is not limited. Not applicable if referenced from TrafficGroupMember instance with trafficCategory value ENDC. Only applicable if license for at least one of following features is present and feature is active: - NR Service Admission Control - Service Adaptive Admission and Preemption; range 0..2147483647.";
      type eytypes:int32_range_0-2147483647;
    }
    leaf-list reservedBy {
      description "Contains a list of MO instances that reserve this MO instance..";
      type string;
      min-elements 0;
    }
    leaf sessionLimitId {
      description "The value component of the RDN..";
      type string;
      mandatory true;
    }
  }
  grouping SignalingRadioBearer-attributes {
    leaf dlMaxRetxThreshold {
      description "Maximum number of AM RLC downlink retransmissions. When this value is reached, AM RLC downlink retransmission is stopped and RRC is notified.; Default value: 8.";
      type int32 {
        range "1..4 | 6 | 8 | 16 | 32";
      }
      default "8";
    }
    leaf rlcAckPduDelayMode {
      description "Delay mode of RLC Ack STATUS PDU. Only applicable if license for Energy-Optimized Slot Allocation is present and feature is active. Otherwise handled as default. Only applicable to Low-Band and Mid-Band cells..";
      type enumeration {
        enum NO_DELAY;
        enum VERY_LOW;
        enum LOW;
        enum BALANCED;
        enum HIGH;
      }
    }
    leaf signalingRadioBearerId {
      description "The value component of the RDN..";
      type string;
      mandatory true;
    }
    leaf tPollRetransmitDl {
      description "Timer supervising the poll for STATUS PDU. AM RLC DL transmitter to wait for RLC STATUS feedback after sending a poll for STATUS before retransmitting the poll.; Default value: 45.";
      type int32 {
        range "5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 2000 | 4000";
      }
      default "45";
      units "ms";
    }
    leaf tPollRetransmitUl {
      description "Timer for UE to supervise the poll for STATUS PDU. AM RLC UL transmitter waits for RLC STATUS feedback after sending a poll for STATUS before retransmitting the poll.; Default value: 45.";
      type int32 {
        range "5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 2000 | 4000";
      }
      default "45";
      units "ms";
    }
    leaf tReassemblyDl {
      description "Timer for UE used by the receiving side of AM RLC and receiving UM RLC. Detects loss of RLC PDUs at lower layers.; Default value: 35.";
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200";
      }
      default "35";
      units "ms";
    }
    leaf tReassemblyUl {
      description "Timer for receiving side of AM RLC and receiving UM RLC. Detects loss of RLC PDUs at lower layers.; Default value: 35.";
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200";
      }
      default "35";
      units "ms";
    }
    leaf ulMaxRetxThreshold {
      description "Maximum number of AM RLC uplink retransmissions. When this value is reached, AM RLC uplink retransmission is stopped and RRC is notified.; Default value: 8.";
      type int32 {
        range "1..4 | 6 | 8 | 16 | 32";
      }
      default "8";
    }
  }
  grouping SoftAcAssist-attributes {
    leaf softAcAssistId {
      description "The value component of the RDN..";
      type string;
      mandatory true;
    }
    leaf ueConfGroupType {
      description "UE configuration group type. UE configuration group type that is applied in contained SoftAcAssistUeCfg instances..";
      type enumeration {
        enum UE_MOBILITY_GROUP;
        enum UE_SERVICE_GROUP;
        enum UE_ADMISSION_GROUP;
      }
    }
  }
  grouping SoftAcAssistUeCfg-attributes {
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf-list reservedBy {
      description "Contains a list of MO instances that reserve this MO instance..";
      type string;
      min-elements 0;
    }
    leaf softAcAssistEnabled {
      description "Whether Soft Antenna Calibration is assisted by UE.; Default value: true.";
      type boolean;
      default "true";
    }
    leaf softAcAssistUeCfgId {
      description "The value component of the RDN..";
      type string;
      mandatory true;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
  }
  grouping SrbPriority-attributes {
    leaf-list reservedBy {
      description "Contains a list of MO instances that reserve this MO instance..";
      type string;
      min-elements 0;
    }
    leaf srbPriorityId {
      description "The value component of the RDN..";
      type string;
      mandatory true;
    }
    leaf ueConfGroupType {
      description "UE configuration group type. UE configuration group type that is applied in contained SrbPriorityUeCfg instances..";
      type enumeration {
        enum UE_MOBILITY_GROUP;
        enum UE_SERVICE_GROUP;
        enum UE_ADMISSION_GROUP;
      }
    }
  }
  grouping SrbPriorityUeCfg-attributes {
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf srbPriority {
      description "SRB priority. Value 1 indicates lowest priority. Only applicable if license for Adaptive SRB Priority is present and feature is active.; range 1..16; Default value: 1.";
      type eytypes:int32_range_1-16;
      default "1";
    }
    leaf srbPriorityUeCfgId {
      description "The value component of the RDN..";
      type string;
      mandatory true;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
  }
  grouping SrHandling-attributes {
    leaf-list reservedBy {
      description "Contains a list of MO instances that reserve this MO instance..";
      type string;
      min-elements 0;
    }
    leaf srHandlingId {
      description "The value component of the RDN..";
      type string;
      mandatory true;
    }
    leaf ueConfGroupType {
      description "UE configuration group type. UE configuration group type that is applied in contained SrHandlingUeCfg instances..";
      type enumeration {
        enum UE_MOBILITY_GROUP;
        enum UE_SERVICE_GROUP;
        enum UE_ADMISSION_GROUP;
      }
    }
    leaf userLabel {
      description "Label for free use..";
      type string;
    }
  }
  grouping SrHandlingUeCfg-attributes {
    leaf-list conditional5qi {
      description "Conditional 5QI to be established for priority to be used. Empty list or value 0 indicates no condition applies..";
      type eytypes:int32_range_0-255;
      ordered-by user;
      min-elements 0;
      max-elements 4;
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf srHandlingMode {
      description "The initial scheduling request priority algorithm used. Conditionally dependent on value of conditional5qi..";
      type enumeration {
        enum DISABLED;
        enum SR_PRIO_5QI;
      }
    }
    leaf srHandlingUeCfgId {
      description "The value component of the RDN..";
      type string;
      mandatory true;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
  }
  grouping SrPeriodicity-attributes {
    leaf-list reservedBy {
      description "Contains a list of MO instances that reserve this MO instance..";
      type string;
      min-elements 0;
    }
    leaf srPeriodicityId {
      description "The value component of the RDN..";
      type string;
      mandatory true;
    }
    leaf ueConfGroupType {
      description "UE configuration group type. UE configuration group type that is applied in contained SrPeriodicityUeCfg instances..";
      type enumeration {
        enum UE_MOBILITY_GROUP;
        enum UE_SERVICE_GROUP;
        enum UE_ADMISSION_GROUP;
      }
    }
  }
  grouping SrPeriodicityCovAdaptUeCfg-attributes {
    leaf covAdaptSrPEnabled {
      description "Whether coverage adaptive scheduling request periodicity is enabled. Only applicable to High-Band cells.; Default value: false.";
      type boolean;
      default "false";
    }
    leaf covAdaptSrPNrLowQualThresh {
      description "NR radio quality threshold. Used for configuring SR periodicity on PUCCH. Below this threshold, uplink channel quality is assumed limited hence SR Periodicity on PUCCH is configured to longer duration. Uplink SINR is used for estimating uplink coverage. Recommended to be set to a value 3 dB higher than endcUlNrLowQualThresh. Only applicable if covAdaptSrPEnabled is True. Only applicable to High-Band cells.; range -40..145; Default value: 20.";
      type int32 {
        range "-40..145";
      }
      default "20";
      units "dB";
    }
    leaf covAdaptSrPNrQualHyst {
      description "NR radio quality hysteresis. Used for configuring SR periodicity on PUCCH. Quality needs to be hysteresis better than covAdaptSrPNrLowQualThresh to configure SR periodicity on PUCCH back to shorter duration. Uplink SINR is used for estimating uplink coverage. Only applicable if covAdaptSrPEnabled is True. Only applicable to High-Band cells.; range 0..60; Default value: 5.";
      type eytypes:int32_range_0-60;
      default "5";
      units "dB";
    }
    leaf covAdaptSrPStartRsrpThresh {
      description "RSRP threshold. SR periodicity is configured to longer duration if reported RSRP value is below RSRP threshold. RSRP is reported in 3GPP TS 38.331 CG-ConfigInfo. Applicable at PSCell setup and PSCell change in the Secondary Node (for NR-DC and EN-DC). Recommended to be set to a value 3 dB lower than dftSOfdmPuschStartRsrpThresh. Only applicable if covAdaptSrPEnabled is True. Only applicable to High-Band cells.; range -156..-29; Default value: -107.";
      type eytypes:int32_range_-156--29;
      default "-107";
      units "dBm";
    }
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf srPeriodicityCovAdaptUeCfgId {
      description "The value component of the RDN..";
      type string;
      mandatory true;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
  }
  grouping SrPeriodicityPoolSet-attributes {
    leaf fddTddUlDlPattern {
      description "FDD or TDD uplink-downlink pattern configuration..";
      type enumeration {
        enum TDD_ULDL_PATTERN_00;
        enum TDD_ULDL_PATTERN_01;
        enum TDD_ULDL_PATTERN_02;
        enum TDD_ULDL_PATTERN_03;
        enum TDD_ULDL_PATTERN_04;
        enum TDD_ULDL_PATTERN_05;
        enum TDD_ULDL_PATTERN_06;
        enum TDD_ULDL_PATTERN_07;
        enum TDD_ULDL_PATTERN_08;
        enum FDD;
      }
      mandatory true;
    }
    leaf noOfSrResourcesHsPool1 {
      description "Number of PUCCH PF0 and PF1 resources reserved for SR in pool 1. Applicable if referring Low-Band or Mid-Band cells support High Speed UEs. Not applicable to High-Band cells.; range 0..32; Default value: 32.";
      type eytypes:int32_range_0-32;
      default "32";
    }
    leaf noOfSrResourcesHsPool2 {
      description "Number of PUCCH PF0 and PF1 resources reserved for SR in pool 2. Applicable if referring Low-Band or Mid-Band cells support High Speed UEs. Not applicable to High-Band cells.; range 0..32; Default value: 0.";
      type eytypes:int32_range_0-32;
      default "0";
    }
    leaf noOfSrResourcesHsPool3 {
      description "Number of PUCCH PF0 and PF1 resources reserved for SR in pool 3. Applicable if referring Low-Band or Mid-Band cells support High Speed UEs. Not applicable to High-Band cells.; range 0..32; Default value: 0.";
      type eytypes:int32_range_0-32;
      default "0";
    }
    leaf noOfSrResourcesHsPool4 {
      description "Number of PUCCH PF0 and PF1 resources reserved for SR in pool 4. Applicable if referring Low-Band or Mid-Band cells support High Speed UEs. Not applicable to High-Band cells.; range 0..32; Default value: 0.";
      type eytypes:int32_range_0-32;
      default "0";
    }
    leaf noOfSrResourcesHsPool5 {
      description "Number of PUCCH PF0 and PF1 resources reserved for SR in pool 5. Applicable if referring Low-Band or Mid-Band cells support High Speed UEs. Not applicable to High-Band cells.; range 0..32; Default value: 0.";
      type eytypes:int32_range_0-32;
      default "0";
    }
    leaf noOfSrResourcesPool1 {
      description "Number of PUCCH PF0 and PF1 resources reserved for SR in pool 1. Applicable if referring Low-Band or Mid-Band cells do not support High Speed UEs. Applicable to referring High-Band cells.; range 0..240; Default value: 56.";
      type eytypes:int32_range_0-240;
      default "56";
    }
    leaf noOfSrResourcesPool2 {
      description "Number of PUCCH PF0 and PF1 resources reserved for SR in pool 2. Applicable if referring Low-Band or Mid-Band cells do not support High Speed UEs. Applicable to referring High-Band cells.; range 0..240; Default value: 0.";
      type eytypes:int32_range_0-240;
      default "0";
    }
    leaf noOfSrResourcesPool3 {
      description "Number of PUCCH PF0 and PF1 resources reserved for SR in pool 3. Applicable if referring Low-Band or Mid-Band cells do not support High Speed UEs. Applicable to referring High-Band cells.; range 0..240; Default value: 0.";
      type eytypes:int32_range_0-240;
      default "0";
    }
    leaf noOfSrResourcesPool4 {
      description "Number of PUCCH PF0 and PF1 resources reserved for SR in pool 4. Applicable if referring Low-Band or Mid-Band cells do not support High Speed UEs. Applicable to referring High-Band cells.; range 0..240; Default value: 0.";
      type eytypes:int32_range_0-240;
      default "0";
    }
    leaf noOfSrResourcesPool5 {
      description "Number of PUCCH PF0 and PF1 resources reserved for SR in pool 5. Applicable if referring Low-Band or Mid-Band cells do not support High Speed UEs. Applicable to referring High-Band cells.; range 0..240; Default value: 0.";
      type eytypes:int32_range_0-240;
      default "0";
    }
    leaf-list reservedBy {
      description "Contains a list of MO instances that reserve this MO instance..";
      type string;
      min-elements 0;
    }
    leaf srPeriodicityPool1 {
      description "SR Periodicity value for pool 1..";
      type enumeration {
        enum SR_PERIODICITY_SYM2;
        enum SR_PERIODICITY_SYM6_OR_7;
        enum SR_PERIODICITY_SL1;
        enum SR_PERIODICITY_SL2;
        enum SR_PERIODICITY_SL4;
        enum SR_PERIODICITY_SL5;
        enum SR_PERIODICITY_SL8;
        enum SR_PERIODICITY_SL10;
        enum SR_PERIODICITY_SL16;
        enum SR_PERIODICITY_SL20;
        enum SR_PERIODICITY_SL40;
        enum SR_PERIODICITY_SL80;
        enum SR_PERIODICITY_SL160;
        enum SR_PERIODICITY_SL320;
        enum SR_PERIODICITY_SL640;
      }
    }
    leaf srPeriodicityPool2 {
      description "SR Periodicity value for pool 2..";
      type enumeration {
        enum SR_PERIODICITY_SYM2;
        enum SR_PERIODICITY_SYM6_OR_7;
        enum SR_PERIODICITY_SL1;
        enum SR_PERIODICITY_SL2;
        enum SR_PERIODICITY_SL4;
        enum SR_PERIODICITY_SL5;
        enum SR_PERIODICITY_SL8;
        enum SR_PERIODICITY_SL10;
        enum SR_PERIODICITY_SL16;
        enum SR_PERIODICITY_SL20;
        enum SR_PERIODICITY_SL40;
        enum SR_PERIODICITY_SL80;
        enum SR_PERIODICITY_SL160;
        enum SR_PERIODICITY_SL320;
        enum SR_PERIODICITY_SL640;
      }
    }
    leaf srPeriodicityPool3 {
      description "SR Periodicity value for pool 3..";
      type enumeration {
        enum SR_PERIODICITY_SYM2;
        enum SR_PERIODICITY_SYM6_OR_7;
        enum SR_PERIODICITY_SL1;
        enum SR_PERIODICITY_SL2;
        enum SR_PERIODICITY_SL4;
        enum SR_PERIODICITY_SL5;
        enum SR_PERIODICITY_SL8;
        enum SR_PERIODICITY_SL10;
        enum SR_PERIODICITY_SL16;
        enum SR_PERIODICITY_SL20;
        enum SR_PERIODICITY_SL40;
        enum SR_PERIODICITY_SL80;
        enum SR_PERIODICITY_SL160;
        enum SR_PERIODICITY_SL320;
        enum SR_PERIODICITY_SL640;
      }
    }
    leaf srPeriodicityPool4 {
      description "SR Periodicity value for pool 4..";
      type enumeration {
        enum SR_PERIODICITY_SYM2;
        enum SR_PERIODICITY_SYM6_OR_7;
        enum SR_PERIODICITY_SL1;
        enum SR_PERIODICITY_SL2;
        enum SR_PERIODICITY_SL4;
        enum SR_PERIODICITY_SL5;
        enum SR_PERIODICITY_SL8;
        enum SR_PERIODICITY_SL10;
        enum SR_PERIODICITY_SL16;
        enum SR_PERIODICITY_SL20;
        enum SR_PERIODICITY_SL40;
        enum SR_PERIODICITY_SL80;
        enum SR_PERIODICITY_SL160;
        enum SR_PERIODICITY_SL320;
        enum SR_PERIODICITY_SL640;
      }
    }
    leaf srPeriodicityPool5 {
      description "SR Periodicity value for pool 5..";
      type enumeration {
        enum SR_PERIODICITY_SYM2;
        enum SR_PERIODICITY_SYM6_OR_7;
        enum SR_PERIODICITY_SL1;
        enum SR_PERIODICITY_SL2;
        enum SR_PERIODICITY_SL4;
        enum SR_PERIODICITY_SL5;
        enum SR_PERIODICITY_SL8;
        enum SR_PERIODICITY_SL10;
        enum SR_PERIODICITY_SL16;
        enum SR_PERIODICITY_SL20;
        enum SR_PERIODICITY_SL40;
        enum SR_PERIODICITY_SL80;
        enum SR_PERIODICITY_SL160;
        enum SR_PERIODICITY_SL320;
        enum SR_PERIODICITY_SL640;
      }
    }
    leaf srPeriodicityPoolSetId {
      description "The value component of the RDN..";
      type string;
      mandatory true;
    }
    leaf subCarrierSpacing {
      description "Sub-carrier spacing for common elements at cell level.; Default value: 120.";
      type int32 {
        range "15 | 30 | 120";
      }
      default "120";
      units "kHz";
    }
  }
  grouping SrPeriodicityUeCfg-attributes {
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf prefUeSrPeriodicityPool {
      description "Preferred SR periodicity pool for corresponding UE. Applicable to Low-Band and Mid-Band cells if license NR Service-Adaptive SR Periodicity is present and feature is active. Not applicable to High-Band cells..";
      type enumeration {
        enum SR_PERIODICITY_POOL_1;
        enum SR_PERIODICITY_POOL_2;
        enum SR_PERIODICITY_POOL_3;
        enum SR_PERIODICITY_POOL_4;
        enum SR_PERIODICITY_POOL_5;
      }
    }
    leaf prefUeSrPeriodicityPoolFr2 {
      description "Preferred SR periodicity pool for corresponding UE. Applicable to High-Band cells if license Service-Adaptive SR Periodicity High-Band for Dedicated RAN or license Service-Adaptive SR Periodicity High-Band for Public RAN is present and feature is active. Not applicable to Low-Band and Mid-Band cells..";
      type enumeration {
        enum SR_PERIODICITY_POOL_1;
        enum SR_PERIODICITY_POOL_2;
        enum SR_PERIODICITY_POOL_3;
        enum SR_PERIODICITY_POOL_4;
        enum SR_PERIODICITY_POOL_5;
      }
    }
    leaf srPeriodicityUeCfgId {
      description "The value component of the RDN..";
      type string;
      mandatory true;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping SssgSwitch-attributes {
    leaf-list reservedBy {
      description "Contains a list of MO instances that reserve this MO instance..";
      type string;
      min-elements 0;
    }
    leaf sssgSwitchId {
      description "The value component of the RDN..";
      type string;
      mandatory true;
    }
    leaf ueConfGroupType {
      description "UE configuration group type. UE configuration group type that is applied in contained SssgSwitchUeCfg instances..";
      type enumeration {
        enum UE_MOBILITY_GROUP;
        enum UE_SERVICE_GROUP;
        enum UE_ADMISSION_GROUP;
      }
    }
    leaf userLabel {
      description "Label for free use..";
      type string;
    }
  }
  grouping SssgSwitchPwrOpt-attributes {
    leaf downDlThreshold {
      description "Threshold used for SSSG switch from dense to sparse SSSG in downlink. If 0, switch timer lowDlActivityTimer starts directly after downlink buffer is empty.; range 0..2000; Default value: 10.";
      type eytypes:int32_range_0-2000;
      default "10";
      units "slot";
    }
    leaf downUlThreshold {
      description "Threshold used for SSSG switch from dense to sparse SSSG in uplink. If 0, switch timer lowUlActivityTimer starts directly after uplink buffer is empty.; range 0..2000; Default value: 10.";
      type eytypes:int32_range_0-2000;
      default "10";
      units "slot";
    }
    leaf lowDlActivityTimer {
      description "Timer used for SSSG switch from dense to sparse SSSG in downlink. If 0, switch can be triggered as soon as amount of data in downlink buffer is not bigger than switch threshold calculated from downDlThreshold.; range 0..5000; Default value: 200.";
      type eytypes:int32_range_0-5000-4;
      default "200";
      units "ms";
    }
    leaf lowUlActivityTimer {
      description "Timer used for SSSG switch from dense to sparse SSSG in uplink. If 0, switch can be triggered as soon as amount of data in uplink buffer is not bigger than switch threshold calculated from downUlThreshold.; range 0..5000; Default value: 200.";
      type eytypes:int32_range_0-5000-4;
      default "200";
      units "ms";
    }
    leaf-list reservedBy {
      description "Contains a list of MO instances that reserve this MO instance..";
      type string;
      min-elements 0;
    }
    leaf sssgSwitchPwrOptId {
      description "The value component of the RDN..";
      type string;
      mandatory true;
    }
    leaf upDlThreshold {
      description "Threshold used for SSSG switch from sparse to dense SSSG in downlink. If 0, switch is triggered as soon as downlink buffer is non-empty.; range 0..2000; Default value: 100.";
      type eytypes:int32_range_0-2000;
      default "100";
      units "slot";
    }
    leaf upUlThreshold {
      description "Threshold used for SSSG switch from sparse to dense SSSG in uplink. If 0, switch is triggered as soon as uplink buffer is non-empty.; range 0..2000; Default value: 100.";
      type eytypes:int32_range_0-2000;
      default "100";
      units "slot";
    }
    leaf userLabel {
      description "Label for free use..";
      type string;
    }
  }
  grouping SssgSwitchUeCfg-attributes {
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf sssgSwitchPmIdentity {
      description "Identity of bins of SSSG switch-related PM counters. Used to match given configuration profile for SSSG switch with PM counter bins in which measured metrics are available.; range 1..8.";
      type eytypes:int32_range_1-8;
      config false;
    }
    leaf sssgSwitchPwrOptRef {
      description "Reference to an instance of SssgSwitchPwrOpt MO. If empty, SSSG switching is not enabled in given SSSG switch configuration profile..";
      type string;
    }
    leaf sssgSwitchUeCfgId {
      description "The value component of the RDN..";
      type string;
      mandatory true;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf userLabel {
      description "Label for free use..";
      type string;
    }
  }
  grouping TermPointToGNBCUCP-attributes {
    leaf administrativeState {
      description "The administrative state. Can be set to LOCKED only if there is no NRCellDU instance with administrativeState UNLOCKED in GNBDUFunction instance. If set to SHUTTINGDOWN, the state is immediately brought to LOCKED..";
      type enumeration {
        enum LOCKED;
        enum UNLOCKED;
        enum SHUTTINGDOWN;
      }
    }
    leaf-list availabilityStatus {
      description "The availability status. It contains details about operational state..";
      type AvailStatus;
      min-elements 0;
    }
    leaf gNBCUName {
      description "Central Unit (CU) name.; length 1..150.";
      type string {
        length "1..150";
      }
      config false;
    }
    leaf ipv4Address {
      description "IPv4 address of the gNodeB-CU-CP. The input format is four fields of digits, separated by dots. Each field may consist of three digits. The value of each field is in the range 0..255.; length 7..15; Default value: 0.0.0.0.";
      type ietfinet:ipv4-address;
      default "0.0.0.0";
    }
    leaf ipv6Address {
      description "IPv6 address of gNodeB-CU-CP. Format is eight fields, separated by colons. Each field consists of four hexadecimal characters. Value of each field is in range 0..FFFF. Leading zeroes can be omitted in a field, and multiple groups of 16 bits of zeroes can be compressed to ::. The :: can appear only once in an address.; length 2..39; Default value: ::.";
      type ietfinet:ipv6-address;
      default "::";
    }
    leaf operationalState {
      description "The operational state..";
      type enumeration {
        enum DISABLED;
        enum ENABLED;
      }
      config false;
    }
    leaf termPointToGNBCUCPId {
      description "The value component of the RDN..";
      type string;
      mandatory true;
    }
    leaf usedIpAddress {
      description "Destination address used for initialization of underlying SCTP association. Contains address of latest successful F1-C setup. IP address can be an IPv4 or an IPv6 address..";
      type string;
      config false;
    }
  }
  grouping TrafficDefinition-attributes {
    leaf-list reservedBy {
      description "Contains a list of MO instances that reserve this MO instance..";
      type string;
      min-elements 0;
    }
    leaf trafficDefinitionId {
      description "The value component of the RDN..";
      type string;
      mandatory true;
    }
  }
  grouping TrafficDefinitions-attributes {
    leaf trafficDefinitionsId {
      description "The value component of the RDN..";
      type string;
      mandatory true;
    }
  }
  grouping TrafficGroup-attributes {
    leaf-list reservedBy {
      description "Contains a list of MO instances that reserve this MO instance.; Status info: Since 25.Q2. Planned to be removed..";
      type string;
      min-elements 0;
    }
    leaf trafficGroupId {
      description "The value component of the RDN.; MOM flags: restricted, noNotification; Status info: Since 25.Q2. Planned to be removed..";
      type string;
      mandatory true;
      status deprecated;
    }
  }
  grouping TrafficGroupMember-attributes {
    list pLMNIdList {
      key "id";
      leaf id {
        type uint32;
        description "Synthetic key for struct sequence entry.";
      }
      min-elements 0;
      max-elements 12;
      uses PLMNId-struct;
    }
    leaf sessionLimitRef {
      description "Reference to an instance of SessionLimit MO. Automatically set to SessionLimit=Default instance, unless manually set to refer to another MO instance. Only applicable if license for at least one of following features is present and feature is active: - NR Service Admission Control - Service Adaptive Admission and Preemption; MOM flags: isNillable=true; Status info: Since 25.Q2. Replaced by TrafficSet::sessionLimitRef. Planned to be removed..";
      type string;
      status deprecated;
    }
    list sNSSAIList {
      key "id";
      leaf id {
        type uint32;
        description "Synthetic key for struct sequence entry.";
      }
      min-elements 0;
      max-elements 1024;
      uses SliceSelectionAssistInfo-struct;
    }
    leaf-list spidRfspList {
      description "List of SPID or RAT Frequency Selection Priority (RFSP), depending on trafficCategory. If list has one value, only that SPID or RFSP is matched. If list has multiple values, at least one of them is matched. Value 0 matches all UEs without any assigned SPID or RFSP.; Status info: Since 25.Q2. Replaced by TrafficSetMember::spidRfspList. Planned to be removed..";
      type eytypes:int32_range_0-256;
      ordered-by user;
      min-elements 0;
      max-elements 20;
    }
    leaf trafficCategory {
      description "Traffic category of configured traffic group member. Set to ENDC in TrafficGroupMember=Default_ENDC instance.; Default value: SA; Status info: Since 25.Q2. Replaced by TrafficSetMember::trafficCategory. Planned to be removed..";
      type enumeration {
        enum SA;
        enum ENDC;
      }
      status deprecated;
      default "SA";
    }
    leaf trafficGroupMemberId {
      description "The value component of the RDN.; MOM flags: restricted, noNotification; Status info: Since 25.Q2. Planned to be removed..";
      type string;
      mandatory true;
      status deprecated;
    }
  }
  grouping TrafficGroups-attributes {
    leaf trafficGroupsId {
      description "The value component of the RDN.; MOM flags: restricted, noNotification; Status info: Since 25.Q2. Planned to be removed..";
      type string;
      mandatory true;
      status deprecated;
    }
  }
  grouping TrafficSet-attributes {
    leaf sessionLimitRef {
      description "Reference to an instance of SessionLimit MO. Automatically set to SessionLimit=Default instance, unless manually set to refer to another MO instance..";
      type string;
    }
    leaf trafficSetId {
      description "The value component of the RDN..";
      type string;
      mandatory true;
    }
  }
  grouping TrafficSetMember-attributes {
    list pLMNIdList {
      key "id";
      leaf id {
        type uint32;
        description "Synthetic key for struct sequence entry.";
      }
      min-elements 0;
      max-elements 12;
      uses PLMNId-struct;
    }
    list sNSSAIList {
      key "id";
      leaf id {
        type uint32;
        description "Synthetic key for struct sequence entry.";
      }
      min-elements 0;
      max-elements 1024;
      uses SliceSelectionAssistInfo-struct;
    }
    leaf-list spidRfspList {
      description "List of SPIDs or RFSPs, depending on trafficCategory. If list has one value, only that SPID or RFSP is matched. If list has multiple values, at least one of them is matched. Value 0 matches all UEs without any assigned SPID or RFSP..";
      type eytypes:int32_range_0-256;
      ordered-by user;
      min-elements 0;
      max-elements 20;
    }
    leaf trafficCategory {
      description "Traffic category of configured traffic set member. Set to ENDC in TrafficSetMember=Default_ENDC instance. Set to SA in TrafficSetMember=Default_SA instance..";
      type enumeration {
        enum SA;
        enum ENDC;
      }
    }
    leaf trafficSetMemberId {
      description "The value component of the RDN..";
      type string;
      mandatory true;
    }
  }
  grouping UeAdaptiveRlc-attributes {
    leaf ueAdaptiveRlcId {
      description "The value component of the RDN..";
      type string;
      mandatory true;
    }
    leaf ueConfGroupType {
      description "UE configuration group type. UE configuration group type that is applied in contained UeAdaptiveRlcUeCfg instances..";
      type enumeration {
        enum UE_MOBILITY_GROUP;
        enum UE_SERVICE_GROUP;
        enum UE_ADMISSION_GROUP;
      }
    }
  }
  grouping UeAdaptiveRlcUeCfg-attributes {
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf ueAdaptiveRlcRetxMode {
      description "Operation mode for feature NR Service-Adaptive RLC Poll Retransmission. Only applicable if license for NR Service-Adaptive RLC Poll Retransmission feature is present and feature is active..";
      type enumeration {
        enum ENABLED;
        enum DISABLED;
      }
    }
    leaf ueAdaptiveRlcUeCfgId {
      description "The value component of the RDN..";
      type string;
      mandatory true;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
  }
  grouping UeBb-attributes {
    leaf ueBbId {
      description "The value component of the RDN..";
      type string;
      mandatory true;
    }
  }
  grouping UeBbProfile-attributes {
    leaf-list reservedBy {
      description "Contains a list of MO instances that reserve this MO instance..";
      type string;
      min-elements 0;
    }
    leaf ueBbProfileId {
      description "The value component of the RDN..";
      type string;
      mandatory true;
    }
    leaf ueConfGroupType {
      description "UE configuration group type. UE configuration group type that is applied in contained UeBbProfileUeCfg instances..";
      type enumeration {
        enum UE_MOBILITY_GROUP;
        enum UE_SERVICE_GROUP;
        enum UE_ADMISSION_GROUP;
      }
    }
    leaf userLabel {
      description "Label for free use..";
      type string;
    }
  }
  grouping UeBbProfileUeCfg-attributes {
    leaf bsrUeCfgRef {
      description "Reference to an instance of BsrUeCfg MO. Automatically set to BsrUeCfg=Base instance, unless manually set to refer to another MO instance..";
      type string;
    }
    leaf configuredGrantUeCfgRef {
      description "Reference to an instance of ConfiguredGrantUeCfg MO. Automatically set to ConfiguredGrantUeCfg=Base instance, unless manually set to refer to another MO instance..";
      type string;
    }
    leaf csiProfileUeCfgRef {
      description "Reference to an instance of CsiProfileUeCfg MO. Automatically set to CsiProfileUeCfg=Base instance, unless manually set to refer to another MO instance..";
      type string;
    }
    leaf dlBeamOptProfileUeCfgRef {
      description "Reference to an instance of DlBeamOptProfileUeCfg MO. Automatically set to DlBeamOptProfileUeCfg=Base instance, unless manually set to refer to another MO instance..";
      type string;
    }
    leaf dlMimoUeCfgRef {
      description "Reference to an instance of DlMimoUeCfg MO. Automatically set to DlMimoUeCfg=Base instance, unless manually set to refer to another MO instance..";
      type string;
    }
    leaf harqUeCfgRef {
      description "Reference to an instance of HarqUeCfg MO. Automatically set to HarqUeCfg=Base instance, unless manually set to refer to another MO instance..";
      type string;
    }
    leaf linkAdaptationUeCfgRef {
      description "Reference to an instance of LinkAdaptationUeCfg MO. Automatically set to LinkAdaptationUeCfg=Base instance, unless manually set to refer to another MO instance..";
      type string;
    }
    leaf outOfCovUeCfgRef {
      description "Reference to an instance of OutOfCovUeCfg MO. Automatically set to OutOfCovUeCfg=Base instance, unless manually set to refer to another MO instance..";
      type string;
    }
    leaf powerControlUeCfgRef {
      description "Reference to an instance of PowerControlUeCfg MO. Automatically set to PowerControlUeCfg=Base instance, unless manually set to refer to another MO instance..";
      type string;
    }
    leaf-list prefUeGroupList {
      description "Preference UE group list. List of preference UE group identifiers. If empty, MO instance matches preference UE group identifiers not defined in prefUeGroupList of any other MO instances under parent MO instance. Value 0 is no longer allowed and is planned to be removed from valid range..";
      type eytypes:int32_range_0-255;
      ordered-by user;
      min-elements 0;
      max-elements 8;
    }
    leaf preschedulingUeCfgRef {
      description "Reference to an instance of PreschedulingUeCfg MO. Automatically set to PreschedulingUeCfg=Base instance, unless manually set to refer to another MO instance..";
      type string;
    }
    leaf rimOffloadUeCfgRef {
      description "Reference to an instance of RimOffloadUeCfg MO. Automatically set to RimOffloadUeCfg=Base instance, unless manually set to refer to another MO instance..";
      type string;
    }
    leaf ueBbProfileUeCfgId {
      description "The value component of the RDN..";
      type string;
      mandatory true;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers. Value 0 is no longer allowed and is planned to be removed from valid range..";
      type eytypes:int32_range_0-255;
      ordered-by user;
      min-elements 0;
      max-elements 16;
    }
    leaf ulServiceDefinitionUeCfgRef {
      description "Reference to an instance of UlServiceDefinitionUeCfg MO. Automatically set to UlServiceDefinitionUeCfg=Base instance, unless manually set to refer to another MO instance..";
      type string;
    }
    leaf ulWfPortSwitchUeCfgRef {
      description "Reference to an instance of UlWfPortSwitchUeCfg MO. Automatically set to UlWfPortSwitchUeCfg=Base instance, unless manually set to refer to another MO instance..";
      type string;
    }
    leaf userLabel {
      description "Label for free use..";
      type string;
    }
  }
  grouping UeCA-attributes {
    leaf ueCAId {
      description "The value component of the RDN..";
      type string;
      mandatory true;
    }
  }
  grouping UeCC-attributes {
    leaf ueCCId {
      description "The value component of the RDN..";
      type string;
      mandatory true;
    }
  }
  grouping UlCgSwitch-attributes {
    leaf-list reservedBy {
      description "Contains a list of MO instances that reserve this MO instance..";
      type string;
      min-elements 0;
    }
    leaf ueConfGroupType {
      description "UE configuration group type. UE configuration group type that is applied in contained UlCgSwitchUeCfg instances..";
      type enumeration {
        enum UE_MOBILITY_GROUP;
        enum UE_SERVICE_GROUP;
        enum UE_ADMISSION_GROUP;
      }
    }
    leaf ulCgSwitchId {
      description "The value component of the RDN..";
      type string;
      mandatory true;
    }
    leaf userLabel {
      description "Label for free use..";
      type string;
    }
  }
  grouping UlCgSwitchCfg-attributes {
    leaf-list reservedBy {
      description "Contains a list of MO instances that reserve this MO instance..";
      type string;
      min-elements 0;
    }
    leaf ulCgSwitchCfgId {
      description "The value component of the RDN..";
      type string;
      mandatory true;
    }
    leaf ulCgSwitchMode {
      description "Uplink cell group switching mode. Used for SN terminated split bearer. Applicable to EN-DC and NR-DC..";
      type enumeration {
        enum DISABLED;
        enum ENABLED;
      }
    }
    leaf ulScgLowQualHyst {
      description "Low SCG uplink radio quality hysteresis. Above ulScgLowQualThresh value plus this hysteresis, SCG uplink quality changes from low to good for UE. SINR is used to represent quality. Used for SN terminated split bearer. Applicable to EN-DC and NR-DC.; range 5..600; Default value: 60.";
      type eytypes:int32_range_5-600;
      default "60";
      units "dB";
    }
    leaf ulScgLowQualThresh {
      description "Low SCG uplink radio quality level threshold. Below this threshold, SCG uplink quality is considered low for UE. SINR is used to represent quality. Used for SN terminated split bearer. Applicable to EN-DC and NR-DC.; range -400..1450; Default value: 170.";
      type eytypes:int32_range_-400-1450;
      default "170";
      units "dB";
    }
    leaf userLabel {
      description "Label for free use..";
      type string;
    }
  }
  grouping UlCgSwitchUeCfg-attributes {
    leaf-list prefUeGroupList {
      description "Preference UE group list. List of preference UE group identifiers. If empty, MO instance matches preference UE group identifiers not defined in prefUeGroupList of any other MO instances under parent MO instance..";
      type eytypes:int32_range_1-255;
      ordered-by user;
      min-elements 0;
      max-elements 8;
    }
    leaf-list ueConfGroupList {
      description "UE configuration group list. List of UE configuration group identifiers. If empty, MO instance matches all UE configuration group identifiers. UE configuration group type is defined by ueConfGroupType in parent MO instance..";
      type eytypes:int32_range_1-255;
      ordered-by user;
      min-elements 0;
      max-elements 32;
    }
    leaf-list ueGroupList {
      description "UE group list. List of UE group identifiers. If empty, MO instance matches all UE group identifiers..";
      type eytypes:int32_range_1-255;
      ordered-by user;
      min-elements 0;
      max-elements 16;
    }
    leaf ulCgSwitchCfgRef {
      description "Reference to an instance of UlCgSwitchCfg MO. Automatically set to UlCgSwitchCfg=Default instance, unless manually set to refer to another MO instance..";
      type string;
    }
    leaf ulCgSwitchUeCfgId {
      description "The value component of the RDN..";
      type string;
      mandatory true;
    }
    leaf userLabel {
      description "Label for free use..";
      type string;
    }
  }
  grouping UlDelayBasedPriority-attributes {
    leaf ulDelayBasedPriorityId {
      description "The value component of the RDN..";
      type string;
      mandatory true;
    }
    leaf ulDemotedPriority {
      description "Priority used before CellPriorityShift::cellUlElevationTime is reached..";
      type enumeration {
        enum LOW;
        enum HIGH;
      }
    }
  }
  grouping UlLatencyBasedPriority-attributes {
    leaf ulDemotedPriority {
      description "Uplink demoted priority for latency prioritized scheduling..";
      type enumeration {
        enum LOW;
        enum HIGH;
      }
    }
    leaf ulLatencyBasedPriorityId {
      description "The value component of the RDN..";
      type string;
      mandatory true;
    }
    leaf ulPriorityScaler {
      description "Priority scaler that scales uplink weight slope for latency prioritized scheduling.; range 1..8; Default value: 1.";
      type eytypes:int32_range_1-8;
      default "1";
    }
    leaf ulPriorityShiftMargin {
      description "Time margin to determine uplink delay threshold for priority shift. The margin is relative to RAN packet delay budget (PDB) used for uplink. If time margin is greater than the RAN PDB used for uplink, it is set to RAN PDB used for uplink.; range -231..280; Default value: 0.";
      type int32 {
        range "-231..280";
      }
      default "0";
      units "ms";
    }
    leaf ulResourceControlLevel {
      description "Resource control level used by LPS in uplink..";
      type enumeration {
        enum LEVEL_0;
        enum LEVEL_1;
        enum LEVEL_2;
        enum LEVEL_3;
        enum LEVEL_4;
        enum LEVEL_5;
      }
    }
    leaf ulWeightOffset {
      description "Uplink weight offset for latency prioritized scheduling..";
      type enumeration {
        enum ZERO;
        enum LOW;
        enum MEDIUM;
        enum HIGH;
      }
    }
  }
  grouping UlLinkAdaptation-attributes {
    leaf ulBlerTarget {
      description "Target BLER for uplink after initial HARQ transmission. If license for Link Adaptation for Low Target BLER for Dedicated RAN is present and feature is active, following applies: - Applicable if ulBlerTargetExtended is -1. - For Low-Band and Mid-Band cells, this attribute is overridden by ulBlerTargetExtended, if ulBlerTargetExtended is not -1. Also applicable if license for Link Adaptation for Low Target BLER for Dedicated RAN is not active. Low range value, less than 1 %, can only be utilized if at least one of following licenses is present and feature is active: - Link Adaptation for Low Target BLER for Public RAN - Link Adaptation for Low Target BLER for Dedicated RAN Otherwise, handled as 1 %.; range 1..3000; Default value: 1000.";
      type int32 {
        range "1..3000";
      }
      default "1000";
      units "percent";
    }
    leaf ulBlerTargetExtended {
      description "Extended target BLER for uplink after initial HARQ transmission. Very low range value between 0.0001 % and 0.01 % can only be utilized if license for Link Adaptation for Low Target BLER for Dedicated RAN is present and feature is active. Otherwise, this attribute is not applicable. If -1, extended target BLER is disabled and ulBlerTarget is applicable. Only applicable to Low-Band and Mid-Band cells.; Default value: -1.";
      type int32 {
        range "-1 | 1..100";
      }
      default "-1";
      units "percent";
    }
    leaf ulDownStep {
      description "Uplink down step size. Used for outer loop. If 0, uplink link adaptation applies general mode outer loop adjustment steps. Only applicable if license for at least one of following features is present and feature is active: - Link Adaptation for Low Target BLER for Public RAN - Link Adaptation for Low Target BLER for Dedicated RAN Otherwise handled as 0 for Low-Band and Mid-Band cells and 1 for High-Band cells.; range 0..100; Default value: 0.";
      type eytypes:int32_range_0-100-5;
      default "0";
      units "dB";
    }
    leaf ulLinkAdaptationId {
      description "The value component of the RDN..";
      type string;
      mandatory true;
    }
    leaf ulMaxMcsIndex {
      description "Maximum allowed MCS index for uplink. Maximum MCS index for QAM256 is 27.; range 0..28; Default value: 27.";
      type eytypes:int32_range_0-28;
      default "27";
    }
    leaf ulMinTbs {
      description "Minimum allowed TBS to allocate for UE in DCI grant. If -1, UlService::ulServicePacketSize and UlService::ulServicePacketInterval are used instead. If -1 and both UlService::ulServicePacketSize and UlService::ulServicePacketInterval are -1, default value according to MO class definition is used.; Default value: 96.";
      type int32 {
        range "-1 | 96..1023";
      }
      default "96";
      units "bit";
    }
    leaf ulServicePacketInterval {
      description "Interval during packets are sent.; Default value: -1; Takes effect: New connection; Status info: Since 24.Q3. Replaced by UlService::ulServicePacketInterval. Planned to be removed..";
      type int32 {
        range "-1 | 10..100";
      }
      status deprecated;
      default "-1";
      units "ms";
      reference "Takes effect: New connection.";
    }
    leaf ulServicePacketSize {
      description "Packet size of service limiting TBS. Used by system for calculating size of DCI grant triggered by Scheduling Request. If not -1, BsrUeCfg::srGrantSize, BsrUeCfg::srGrantSizeMode and BsrUeCfg::srGrantSizeOpt have no effect.; Default value: -1; Takes effect: New connection; Status info: Since 24.Q3. Replaced by UlService::ulServicePacketSize. Planned to be removed..";
      type int32 {
        range "-1 | 30..120";
      }
      status deprecated;
      default "-1";
      units "byte";
      reference "Takes effect: New connection.";
    }
    leaf ulSinrBackoff {
      description "Uplink SINR backoff. Only applicable if license for at least one of following features is present and feature is active: - Link Adaptation for Low Target BLER for Public RAN - Link Adaptation for Low Target BLER for Dedicated RAN Otherwise handled as default.; range 0..100; Default value: 0.";
      type eytypes:int32_range_0-100-5;
      default "0";
      units "dB";
    }
  }
  grouping UlRateBasedPriority-attributes {
    leaf ulDemotedPriority {
      description "Priority to use after priority downshift fulfills at rate..";
      type enumeration {
        enum LOW;
        enum HIGH;
      }
    }
    leaf ulDemotedRelativePriority {
      description "Whether relative priority for uplink is used in demoted state. If false, value of relative priority is 1. Otherwise, value of relative priority is SchedulingProfile::relativePriority.; Default value: false.";
      type boolean;
      default "false";
    }
    leaf ulDrbOverloadHandling {
      description "Determines what happens when UE is overloaded with rate-based priority shift algorithm. Overload means a DRB with rate tracking is attempted to be set up while UE already has two DRBs with rate tracking. Rate tracking is activated when SchedulingProfile::ulSchedulingAlgorithm or SchedulingProfile::schedulingAlgorithm is PRIORITIZED_RATE or SOFT_RATE_THROTTLING..";
      type enumeration {
        enum BASIC;
        enum REJECT;
      }
    }
    leaf ulPrioritizedRate {
      description "Rate to be prioritized.; Default value: 1.";
      type int32 {
        range "1..10 | 20 | 30 | 40 | 50 | 60 | 70 | 80 | 90 | 100 | 200 | 300 | 400 | 500 | 600 | 700 | 800 | 900 | 1000 | 2000 | 3000 | 4000 | 5000 | 6000 | 7000 | 8000 | 9000 | 10000 | 20000 | 30000 | 40000 | 50000 | 60000 | 70000 | 80000 | 90000 | 100000 | 200000 | 300000 | 400000 | 500000 | 600000 | 700000 | 800000 | 900000 | 1000000";
      }
      default "1";
      units "kbps";
    }
    leaf ulRateBasedPriorityId {
      description "The value component of the RDN..";
      type string;
      mandatory true;
    }
  }
  grouping UlResourceBasedPriority-attributes {
    leaf ulDrbPriorityLimit {
      description "Limit of uplink spectrum resources. Used with elevated priority by a single DRB configured with a rate. The lower the value, the less spectrum resources can be utilized with elevated priority by rate-controlled scheduling.; range 1..100; Default value: 100.";
      type eytypes:int32_range_1-100-3;
      default "100";
    }
    leaf ulResourceBasedPriorityId {
      description "The value component of the RDN..";
      type string;
      mandatory true;
    }
    leaf ulResourceLimitMode {
      description "Controls operation of resource limit for uplink..";
      type enumeration {
        enum NO_LIMIT;
        enum LIMITED;
        enum LIMITED_TO_CELL_LIMIT;
      }
    }
  }
  grouping UlService-attributes {
    leaf ulPacketPredictionMode {
      description "Packet prediction mode used for uplink service. If BASIC, ulService5qi must be other than empty and both ulServicePacketSize and ulServicePacketInterval must be other than -1..";
      type enumeration {
        enum DEACTIVATED;
        enum BASIC;
      }
    }
    leaf ulService5qi {
      description "Uplink service 5QI. 5QI toward which uplink service is mapped. If empty, uplink service is not mapped to 5QI.; range 1..255.";
      type eytypes:int32_range_1-255;
    }
    leaf ulServiceId {
      description "The value component of the RDN..";
      type string;
      mandatory true;
    }
    leaf ulServicePacketInterval {
      description "Interval during which packets are sent. Used by system for: - Calculating minimum allowed TBS. - Uplink buffer prediction on ulService5qi. In combination with ulServicePacketSize, overrides UlLinkAdaptation::ulMinTbs when its value is -1. If -1, this attribute has no effect.; Default value: -1.";
      type int32 {
        range "-1 | 10..160";
      }
      default "-1";
      units "ms";
    }
    leaf ulServicePacketSize {
      description "Size of packets used by service in uplink. Used by system for: - Calculating minimum allowed TBS. - Uplink buffer prediction on ulService5qi. - Calculating size of DCI grant triggered by scheduling request. Overrides BsrUeCfg::srGrantSize. In combination with ulServicePacketInterval, overrides UlLinkAdaptation::ulMinTbs when its value is -1. If -1, this attribute has no effect. If not -1, BsrUeCfg::srGrantSizeMode and BsrUeCfg::srGrantSizeOpt have no effect.; Default value: -1.";
      type int32 {
        range "-1 | 30..200";
      }
      default "-1";
      units "byte";
    }
  }
  grouping UlServiceDefinition-attributes {
    leaf ulServiceDefinitionId {
      description "The value component of the RDN..";
      type string;
      mandatory true;
    }
  }
  grouping UlServiceDefinitionUeCfg-attributes {
    leaf-list reservedBy {
      description "Contains a list of MO instances that reserve this MO instance..";
      type string;
      min-elements 0;
    }
    leaf ulServiceDefinitionUeCfgId {
      description "The value component of the RDN..";
      type string;
      mandatory true;
    }
  }
  grouping UlWfPortSwitch-attributes {
    leaf ulWfPortSwitchId {
      description "The value component of the RDN..";
      type string;
      mandatory true;
    }
  }
  grouping UlWfPortSwitchUeCfg-attributes {
    leaf-list reservedBy {
      description "Contains a list of MO instances that reserve this MO instance..";
      type string;
      min-elements 0;
    }
    leaf ulLayerSwitchMetric {
      description "Uplink quality metric for FR1 layer switching function. Used for UEs that support two uplink TX ports. Only applicable if license for Uplink Single-User MIMO is present and feature is active. Only applicable to Low-Band and Mid-Band cells..";
      type enumeration {
        enum UL_WB_SINR;
        enum UL_SINR_MAX;
        enum UL_SINR_MIN;
      }
    }
    leaf ulLayerSwitchQualHyst {
      description "Quality hysteresis for NR radio quality level for layer switching in FR1. Used for UEs that support two uplink TX ports. Only applicable if license for Uplink Single-User MIMO is present and feature is active. Only applicable to Low-Band and Mid-Band cells.; range 0..100; Default value: 50.";
      type eytypes:int32_range_0-100-5;
      default "50";
      units "dB";
    }
    leaf ulLayerSwitchQualThresh {
      description "NR radio quality level threshold for layer switching in FR1. Used for UEs that support two uplink TX ports. Fixed values are used for layer selection. If -10000, two layers under two ports are selected. if 10000, one layer is selected. Only applicable if license for Uplink Single-User MIMO is present and feature is active. Only applicable to Low-Band and Mid-Band cells.; Default value: 50.";
      type int32 {
        range "-10000 | -400..1150 | 10000";
      }
      default "50";
      units "dB";
    }
    leaf ulPortSwitchFr1Mode {
      description "Port switching mode in FR1. Used for UEs supporting two uplink TX ports. Only applicable when Uplink Single-User MIMO feature is active. Only applicable to Low-Band and Mid-Band cells..";
      type enumeration {
        enum PORT_FIXED_PC_DIFF;
        enum PORT_SWITCHED;
        enum PORT_SWITCHED_ONLY_PC1_5;
        enum PORT_SWITCHED_INIT_2_PORT;
      }
    }
    leaf ulPortSwitchMetric {
      description "Uplink quality metric for FR1 port switching function. Used for UEs that support two uplink TX ports. Only applicable if license for Uplink Single-User MIMO is present and feature is active. Only applicable to Low-Band and Mid-Band cells..";
      type enumeration {
        enum UL_WB_SINR;
        enum UL_SINR_MAX;
        enum UL_SINR_MIN;
      }
    }
    leaf ulPortSwitchQualHyst {
      description "Quality hysteresis for NR radio quality level for port switching in FR1. Used for UEs that support two uplink TX ports. Only applicable if license for Uplink Single-User MIMO is present and feature is active. Only applicable to Low-Band and Mid-Band cells.; range 0..100; Default value: 50.";
      type ietfinet:port-number;
      default "50";
      units "dB";
    }
    leaf ulPortSwitchQualThresh {
      description "NR radio quality level threshold for port switching in FR1. Used for UEs that support two uplink TX ports. Fixed values are used for port selection. If -10000, two ports are selected. if 10000, one port is selected. Only applicable if license for Uplink Single-User MIMO is present and feature is active. Only applicable to Low-Band and Mid-Band cells.; Default value: 50.";
      type ietfinet:port-number;
      default "50";
      units "dB";
    }
    leaf ulPortSwitchTimeToTrigger {
      description "Time to trigger TX port switching between two ports and one port. Timer is started when conditions for port switching are met. Used for UEs that support two uplink TX ports. Only applicable if license for Uplink Single-User MIMO is present and feature is active. Only applicable to Low-Band and Mid-Band cells.; range 0..4000; Default value: 4000.";
      type ietfinet:port-number;
      default "4000";
      units "ms";
    }
    leaf ulWfPortSwitchUeCfgId {
      description "The value component of the RDN..";
      type string;
      mandatory true;
    }
    leaf ulWfPuschStartFr1RsrpThresh {
      description "UE starts on DFT-s-OFDM when reported RSRP is below threshold in this attribute value in FR1. RSRP is defined in 3GPP TS 38.331 CG-ConfigInfo. Applicable at secondary cell group addition. Used for UEs supporting only one uplink TX port when Uplink Single-User MIMO feature is active. Used for all UEs when Uplink Single-User MIMO feature is not active. Only applicable to Low-Band and Mid-Band cells.; range -156..-29; Default value: -104.";
      type eytypes:int32_range_-156--29;
      default "-104";
      units "dBm";
    }
    leaf ulWfSwitchFr1CpRetProhibTimer {
      description "Time-to-trigger for waveform switching from DFT-s-OFDM to CP-OFDM. Timer is started when conditions for waveform switching are met. Used for UEs supporting only one uplink TX port when Uplink Single-User MIMO feature is active. Used for all UEs when Uplink Single-User MIMO feature is not active. Only applicable to Low-Band and Mid-Band cells.; range 0..10000; Default value: 1000.";
      type eytypes:int32_range_0-10000;
      default "1000";
      units "ms";
    }
    leaf ulWfSwitchFr1Mode {
      description "Uplink waveform switching mode in FR1. Used for UEs supporting only one uplink TX port when Uplink Single-User MIMO feature is active. Used for all UEs when Uplink Single-User MIMO is not active. Values DFTS_OFDM_NOSWITCH and WAVEFORM_SWITCH are only applicable to NRCellDU instances in which NRCellDU::dftSOfdmPuschEnabled is true. Otherwise handled as CP_OFDM_NOSWITCH. Only applicable to Low-Band and Mid-Band cells..";
      type enumeration {
        enum CP_OFDM_NOSWITCH;
        enum DFTS_OFDM_NOSWITCH;
        enum WAVEFORM_SWITCH;
      }
    }
    leaf ulWfSwitchFr1QualHyst {
      description "Quality hysteresis for waveform switching between DFT-s-OFDM and CP-OFDM in FR1. Used for UEs supporting only one uplink TX port when Uplink Single-User MIMO feature is active. Used for all UEs when Uplink Single-User MIMO feature is not active. Only applicable to Low-Band and Mid-Band cells.; range 1..300; Default value: 100.";
      type int32 {
        range "1..300";
      }
      default "100";
      units "dB";
    }
    leaf ulWfSwitchFr1QualThresh {
      description "NR radio quality level threshold used for waveform switching in FR1. Used for UEs supporting only one uplink TX port when Uplink Single-User MIMO feature is active. Used for all UEs when Uplink Single-User MIMO feature is not active. Only applicable to Low-Band and Mid-Band cells.; range -400..1150; Default value: -400.";
      type int32 {
        range "-400..1150";
      }
      default "-400";
      units "dB";
    }
    leaf userLabel {
      description "Label for free use..";
      type string;
    }
  }
}
