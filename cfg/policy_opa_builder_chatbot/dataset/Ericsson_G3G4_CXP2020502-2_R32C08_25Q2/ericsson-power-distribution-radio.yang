module ericsson-power-distribution-radio {
  yang-version 1.1;
  namespace "urn:com:ericsson:ecim:ResPowerDistribution";
  prefix pwdistrdo;
  import ericsson-equipment-support-function-radio {
    prefix eqsupfnrdo;
  }
  import ericsson-managed-element {
    prefix emael;
  }
  description "Auto-generated from Ericsson CPI MOM XML 15554-lza7016014_33-v1uenfk.xml\n.";
  revision "2026-03-29" {
    description "Ericsson G3G4, version: CXP2020502/2-R32C08";
  }

  augment "/emael:ManagedElement/eqsupfnrdo:EquipmentSupportFunction" {
    list PowerDistribution {
      description "Additional definitions from MOM:min/max-elements:0/unbounded;root; MO represents logical resource providing configuration and supervision support for cabinet power distribution capabilities. Examples include configuration of alarm levels and supervision of input voltage. Dependencies: Can only exist in the node when the attribute supportSystemControl is set to true on a parent MO EquipmentSupportFunction.";
      key "powerDistributionId";
      leaf powerDistributionId {
        type leafref {
          path "../attributes/powerDistributionId";
        }
      }
      container attributes {
      uses PowerDistribution-attributes;
      }
    }
  }
  typedef AvailStatus {
    description "The availability status is used to qualify the operational state. It indicates why the operational state has changed its value.";
    type enumeration {
      enum IN_TEST {
        description "The resource is undergoing a test procedure. If the administrative state is locked or shutting down, normal users are prevented from using the resource.";
      }
      enum FAILED {
        description "The resource has an internal fault that prevents it from operating.";
      }
      enum POWER_OFF {
        description "The resource requires power to be applied and is not powered on.";
      }
      enum OFF_LINE {
        description "The resource requires a routine operation to be performed. This routine operation is to place the resource online and make it available for use. The operation may be manual or automatic, or both. The operational state is disabled.";
      }
      enum OFF_DUTY {
        description "The resource has been made inactive by an internal control process.";
      }
      enum DEPENDENCY {
        description "The resource cannot operate because some other resource on which it depends is unavailable.";
      }
      enum DEGRADED {
        description "The service available from the resource is degraded in some respect.";
      }
      enum NOT_INSTALLED {
        description "The resource represented by the managed object is not present, or is incomplete.";
      }
      enum LOG_FULL {
        description "Indicates a log full condition. The semantics are defined in CCITT Rec. X.735 | ISO/IEC 10164-6.";
      }
      enum DEPENDENCY_LOCKED {
        description "The administrative state of a resource that this resource depends on is locked. Alternatively, the availability status of the other resource is dependency locked.";
      }
      enum DEPENDENCY_FAILED {
        description "The availability status of a resource that this resource depends on is failed or dependency failed.";
      }
      enum DEPENDENCY_SHUTTINGDOWN {
        description "The administrative state of a resource that this resource depends on is shutting down. Alternatively, the availability status of the other resource is dependency shutting down.";
      }
      enum DEPENDENCY_RECOVERY {
        description "Resource that this resource depends on is undergoing a recovery procedure.";
      }
      enum DEPENDENCY_HOLDING {
        description "Resource cannot operate because some other resource on which it depends is currently unavailable. The situation is expected to be resolved. Actions to facilitate dependency resolution may be ongoing.";
      }
    }
  }
  typedef OperState {
    description "Operational states of a resource.";
    type enumeration {
      enum DISABLED {
        description "The resource is totally inoperable.";
      }
      enum ENABLED {
        description "The resource is partially or fully operable.";
      }
    }
  }
  grouping PowerDistribution-attributes {
    leaf powerDistributionId {
      description "The value component of the RDN..";
      type string;
      mandatory true;
    }
    leaf mainLoadUndervoltageDisconnect {
      description "Voltage at which BFU must disconnect main load. Main load is disconnected when value of systemVoltage is below mainLoadUndervoltageDisconnect. For example, default value -460 = -46.0 V means that main load is disconnected if systemVoltage is -45.9 V. During deprecation period, setting of mainLoadUndervoltageDisconnect is converted and mirrored to BatteryBackup.mainLoadDisconnectLevel.; range -480..-400; Default value: -460; Status info: Since 18A. Replaced by mainLoadDisconnectLevel on MO BatteryBackup. Planned to be removed..";
      type int32 {
        range "-480..-400";
      }
      status deprecated;
      default "-460";
      units "V";
    }
    leaf priorityLoadUndervoltageDisconnect {
      description "The voltage at which the Battery Fuse Unit (BFU) must disconnect the Priority Load. The primary load is disconnected when systemVoltage is below priorityLoadUndervoltageDisconnect. Example: The default value -450 = -45.0 V, gives that the priority load is disconnected if systemVoltage is e.g. -44.9 V. During deprecation period, a setting of the priorityLoadUndervoltageDisconnect is converted and mirrored to attribute batteryDisconnectLevel of MO BatteryBackup.; range -480..-400; Default value: -450; Status info: Since 18A. Replaced by batteryDisconnectLevel on MO BatteryBackup. Planned to be removed..";
      type int32 {
        range "-480..-400";
      }
      status deprecated;
      default "-450";
      units "V";
    }
    leaf undervoltageDisconnectCeaseOffset {
      description "The offset for the disconnected voltage above which the Battery Fuse Unit (BFU) reconnects the load. Applies to both main and priority load. The main load is reconnected when system voltage is above (mainLoadUndervoltageDisconect - undervoltageDisconnectCeaseOffset). systemVoltage = batteryVoltage when the system is running on battery supply. Example: The default values gives a main load undervoltage reconnection at -460 – 70 = -530 (-53.0 V DC), the load is reconnected if systemVoltage is e.g. -53.1 V. Note: the batteries are reconnected when systemVoltage is above (mainLoadUndervoltageDisconnected -underVoltageDisconnectCeaseOffset) and batteryVoltage is above -39.0V. systemVoltage is an attribute in MO PowerSupply. batteryVoltage is an attribute in MO BatteryBackup.; range 10..100; Default value: 70; Status info: Since 18A. Planned to be removed..";
      type int32 {
        range "10..100";
      }
      status deprecated;
      default "70";
      units "V";
    }
    leaf userLabel {
      description "Label for free use.; length 1..128.";
      type string {
        length "1..128";
      }
    }
    leaf-list availabilityStatus {
      description "The availability status. It contains details about operationalState..";
      type AvailStatus;
      min-elements 0;
    }
    leaf operationalState {
      description "Defines the operational state..";
      type enumeration {
        enum DISABLED;
        enum ENABLED;
      }
      config false;
    }
    leaf controlDomainRef {
      description "The cabinet or hwGroup where functions represented by this MO are deployed..";
      type string;
    }
    leaf systemOvervoltageAlarmLevel {
      description "Alarm level for system over voltage. The alarm active condition is true when systemVoltage is above SystemOvervoltageAlarmLevel.; range -600..-530; Default value: -575.";
      type int32 {
        range "-600..-530";
      }
      default "-575";
      units "V";
    }
    leaf systemUndervoltageAlarmLevel {
      description "Alarm level for system undervoltage. The alarm is raised when systemVoltage is lower than SystemUndervoltageAlarmLevel.; range -480..-380; Default value: -475.";
      type int32 {
        range "-480..-380";
      }
      default "-475";
      units "V";
    }
    leaf systemVoltage {
      description "The measured system voltage. Undefined value -1 indicates that no value has been retrieved..";
      type int32 {
        range "-600..-380 | -1";
      }
      config false;
      units "V";
    }
    leaf-list pmSystemVoltage {
      description "Average values of DC system voltage measured in 60 second periods. As DC system voltage is reported with negative values, this counter uses absolute values. Unit: 0.1 V.";
      type int32;
      max-elements 15;
    }
  }
}
