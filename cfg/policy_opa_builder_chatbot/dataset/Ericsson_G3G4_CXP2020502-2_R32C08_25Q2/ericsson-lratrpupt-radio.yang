module ericsson-lratrpupt-radio {
  yang-version 1.1;
  namespace "urn:com:ericsson:ecim:LratRpUpt";
  prefix lratrpup;
  import ericsson-lrat-radio {
    prefix lrat;
  }
  import ericsson-managed-element {
    prefix emael;
  }
  description "Auto-generated from Ericsson CPI MOM XML 15554-lza7016014_33-v1uenfk.xml\nIt contains the RpUserPlaneTermination.";
  revision "2026-03-29" {
    description "Ericsson G3G4, version: CXP2020502/2-R32C08";
  }

  augment "/emael:ManagedElement/lrat:ENodeBFunction" {
    list RpUserPlaneTermination {
      description "Additional definitions from MOM:min/max-elements:0/1;root;systemCreated; Local termination point of the radio processing user plane interface. System created when the first radio processing user plane link is established. System deleted when the last radio processing user plane link is released. The RDN of this MO is RpUserPlaneTermination=1.";
      key "rpUserPlaneTerminationId";
      leaf rpUserPlaneTerminationId {
        type leafref {
          path "../attributes/rpUserPlaneTerminationId";
        }
      }
      container attributes {
      uses RpUserPlaneTermination-attributes;
      }
    }
  }

  augment "/emael:ManagedElement/lrat:ENodeBFunction/lratrpup:RpUserPlaneTermination" {
    list RpUserPlaneLink {
      description "Additional definitions from MOM:min/max-elements:0/unbounded;systemCreated; User plane link for the radio processing interface. System created when a radio processing user plane link is established. System deleted when a radio processing user plane link is released. The RDN of this MO is RpUserPlaneLink=[Remote Managed Element Identity].";
      key "rpUserPlaneLinkId";
      leaf rpUserPlaneLinkId {
        type leafref {
          path "../attributes/rpUserPlaneLinkId";
        }
      }
      container attributes {
      uses RpUserPlaneLink-attributes;
      }
    }
  }
  grouping RpUserPlaneLink-attributes {
    leaf rpUserPlaneLinkId {
      description "The value component of the RDN..";
      type string;
      mandatory true;
    }
    leaf remoteEndPoint {
      description "Remote GTP transport address. IP address can be an IPv4 or an IPv6 address.; length 2..39.";
      type string {
        length "2..39";
      }
      config false;
    }
    leaf localEndPoint {
      description "Local GTP transport address. IP address can be an IPv4 or an IPv6 address.; length 2..39.";
      type string {
        length "2..39";
      }
      config false;
    }
  }
  grouping RpUserPlaneTermination-attributes {
    leaf rpUserPlaneTerminationId {
      description "The value component of the RDN..";
      type string;
      mandatory true;
    }
  }
}
