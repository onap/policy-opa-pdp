module ericsson-o-hybrid-radio {
  yang-version 1.1;
  namespace "urn:com:ericsson:ecim:RmeOHybrid";
  prefix ohybrdo;
  import ericsson-rmesupport-radio {
    prefix rmesuppo;
  }
  import ericsson-managed-element {
    prefix emael;
  }
  description "Auto-generated from Ericsson CPI MOM XML 15554-lza7016014_33-v1uenfk.xml\nConfiguration of hybrid M-plane architecture model for all ORadio instances.";
  revision "2026-03-29" {
    description "Ericsson G3G4, version: CXP2020502/2-R32C08";
  }

  augment "/emael:ManagedElement/rmesuppo:NodeSupport" {
    list OHybrid {
      description "Additional definitions from MOM:min/max-elements:0/1;root; Configuration of hybrid M-plane architecture model for all ORadio instances. Configuration is applied for all ORadio instances in Hybrid mode configured with ORiPort MO. The RDN of this MO must be OHybrid=1.";
      key "oHybridId";
      leaf oHybridId {
        type leafref {
          path "../attributes/oHybridId";
        }
      }
      container attributes {
      uses OHybrid-attributes;
      }
    }
  }
  grouping OHybrid-attributes {
    leaf oHybridId {
      description "The value component of the RDN..";
      type string;
      mandatory true;
    }
    leaf smoAddress {
      description "IP address of external Service Management and Orchestrator (SMO)..";
      type string;
      mandatory true;
    }
    leaf smoUserName {
      description "Username for Service Management and Orchestrator (SMO)..";
      type string;
      mandatory true;
    }
    leaf nodeCredentialRef {
      description "Reference to NodeCredential MO..";
      type string;
      mandatory true;
    }
  }
}
