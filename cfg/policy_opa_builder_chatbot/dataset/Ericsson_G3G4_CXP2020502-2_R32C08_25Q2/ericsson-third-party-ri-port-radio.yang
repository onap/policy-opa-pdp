module ericsson-third-party-ri-port-radio {
  yang-version 1.1;
  namespace "urn:com:ericsson:ecim:ReqThirdPartyRiPort";
  prefix tpriptrdo;
  import ericsson-equip-radio {
    prefix equiprdo;
  }
  import ericsson-field-replaceable-unit-radio {
    prefix frurdo;
  }
  import ericsson-managed-element {
    prefix emael;
  }
  description "Auto-generated from Ericsson CPI MOM XML 15554-lza7016014_33-v1uenfk.xml\nReqThirdPartyRiPort";
  revision "2026-03-29" {
    description "Ericsson G3G4, version: CXP2020502/2-R32C08";
  }

  augment "/emael:ManagedElement/equiprdo:Equipment/frurdo:FieldReplaceableUnit" {
    list ThirdPartyRiPort {
      description "Additional definitions from MOM:min/max-elements:0/unbounded;root; Third-party Radio Interface Port.";
      key "thirdPartyRiPortId";
      leaf thirdPartyRiPortId {
        type leafref {
          path "../attributes/thirdPartyRiPortId";
        }
      }
      container attributes {
      uses ThirdPartyRiPort-attributes;
      }
    }
  }
  typedef AdmState {
    description "Administrative state of a resource.";
    type enumeration {
      enum LOCKED {
        description "The resource is administratively prohibited from performing services for its users.";
      }
      enum UNLOCKED {
        description "The resource is administratively permitted to perform services for its users. This is independent of its inherent operability.";
      }
      enum SHUTTINGDOWN {
        description "Use of the resource is administratively permitted to existing instances of use only. While the system remains in the shutting down state the manager may at any time cause the managed object to revert to the locked state.";
      }
    }
  }
  typedef AvailStatus {
    description "The availability status is used to qualify the operational state. It indicates why the operational state has changed its value.";
    type enumeration {
      enum IN_TEST {
        description "The resource is undergoing a test procedure. If the administrative state is locked or shutting down, normal users are prevented from using the resource.";
      }
      enum FAILED {
        description "The resource has an internal fault that prevents it from operating.";
      }
      enum POWER_OFF {
        description "The resource requires power to be applied and is not powered on.";
      }
      enum OFF_LINE {
        description "The resource requires a routine operation to be performed. This routine operation is to place the resource online and make it available for use. The operation may be manual or automatic, or both. The operational state is disabled.";
      }
      enum OFF_DUTY {
        description "The resource has been made inactive by an internal control process.";
      }
      enum DEPENDENCY {
        description "The resource cannot operate because some other resource on which it depends is unavailable.";
      }
      enum DEGRADED {
        description "The service available from the resource is degraded in some respect.";
      }
      enum NOT_INSTALLED {
        description "The resource represented by the managed object is not present, or is incomplete.";
      }
      enum LOG_FULL {
        description "Indicates a log full condition. The semantics are defined in CCITT Rec. X.735 | ISO/IEC 10164-6.";
      }
      enum DEPENDENCY_LOCKED {
        description "The administrative state of a resource that this resource depends on is locked. Alternatively, the availability status of the other resource is dependency locked.";
      }
      enum DEPENDENCY_FAILED {
        description "The availability status of a resource that this resource depends on is failed or dependency failed.";
      }
      enum DEPENDENCY_SHUTTINGDOWN {
        description "The administrative state of a resource that this resource depends on is shutting down. Alternatively, the availability status of the other resource is dependency shutting down.";
      }
      enum DEPENDENCY_RECOVERY {
        description "Resource that this resource depends on is undergoing a recovery procedure.";
      }
      enum DEPENDENCY_HOLDING {
        description "Resource cannot operate because some other resource on which it depends is currently unavailable. The situation is expected to be resolved. Actions to facilitate dependency resolution may be ongoing.";
      }
    }
  }
  typedef OperState {
    description "Operational states of a resource.";
    type enumeration {
      enum DISABLED {
        description "The resource is totally inoperable.";
      }
      enum ENABLED {
        description "The resource is partially or fully operable.";
      }
    }
  }
  typedef TransmissionStandard {
    description "Transmission standard for communication between DU and RU.";
    type enumeration {
      enum CPRI {
        description "CPRI.";
      }
      enum ETHERNET {
        description "Ethernet.";
      }
    }
  }
  grouping ThirdPartyRiPort-attributes {
    leaf thirdPartyRiPortId {
      description "The value component of the RDN..";
      type string;
      mandatory true;
    }
    leaf administrativeState {
      description "The administrative state. If set to SHUTTINGDOWN, the state is immediately brought to LOCKED..";
      type enumeration {
        enum LOCKED;
        enum UNLOCKED;
        enum SHUTTINGDOWN;
      }
    }
    leaf-list availabilityStatus {
      description "The availabilityStatus. It contains details about operationalState..";
      type AvailStatus;
      min-elements 0;
    }
    leaf operationalState {
      description "The operational state..";
      type enumeration {
        enum DISABLED;
        enum ENABLED;
      }
      config false;
    }
    leaf-list reservedBy {
      description "Contains a list of MO instances that reserve this MO instance..";
      type string;
      min-elements 0;
    }
    leaf-list channelRef {
      description "Reference to SfpChannel MO instance connected to this port..";
      type string;
      min-elements 0;
    }
    leaf preferredSfpProductNumber {
      description "Ericsson product number of preferred SFP module for ThirdPartyRiPort. If SFP with different product number is detected, \"SFP Product Number Mismatch\" alarm is raised. Default value nil means SFP validation function is disabled.; length 1..13.";
      type string {
        length "1..13";
      }
    }
    leaf sfpModuleRef {
      description "Refers to one SfpModule on this unit to which the port is connected..";
      type string;
      config false;
    }
    leaf transmissionStandard {
      description "Shows if Third Party RiPort has come up as CPRI or Ethernet..";
      type enumeration {
        enum CPRI;
        enum ETHERNET;
      }
      config false;
    }
    leaf externalTrustCategoryRef {
      description "Reference to ExternalTrustCategory MO instance associated with this port..";
      type string;
    }
  }
}
