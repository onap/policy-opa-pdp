module ericsson-sync-eth-input-sync-radio {
  yang-version 1.1;
  namespace "urn:com:ericsson:ecim:RsyncSyncEthInput";
  prefix syncethinrdo;
  import ericsson-synchronization-sync-radio {
    prefix syncrdo;
  }
  import ericsson-managed-element {
    prefix emael;
  }
  description "Auto-generated from Ericsson CPI MOM XML 15554-lza7016014_33-v1uenfk.xml\nSynchronization Ethernet Input Model";
  revision "2026-03-29" {
    description "Ericsson G3G4, version: CXP2020502/2-R32C08";
  }

  augment "/emael:ManagedElement/emael:Transport/syncrdo:Synchronization" {
    list SyncEthInput {
      description "Additional definitions from MOM:min/max-elements:0/8;root; Represents synchronous Ethernet properties of Ethernet interface configured for synchronization.";
      key "syncEthInputId";
      leaf syncEthInputId {
        type leafref {
          path "../attributes/syncEthInputId";
        }
      }
      container attributes {
      uses SyncEthInput-attributes;
      }
    }
  }
  typedef AvailStatus {
    description "The availability status is used to qualify the operational state. It indicates why the operational state has changed its value.";
    type enumeration {
      enum IN_TEST {
        description "The resource is undergoing a test procedure. If the administrative state is locked or shutting down then normal users are precluded from using the resource.";
      }
      enum FAILED {
        description "The resource has an internal fault that prevents it from operating.";
      }
      enum POWER_OFF {
        description "The resource requires power to be applied and is not powered on.";
      }
      enum OFF_LINE {
        description "The resource requires a routine operation to be performed. This routine operation is to place the resource online and make it available for use. The operation may be manual or automatic, or both. The operational state is disabled.";
      }
      enum OFF_DUTY {
        description "The resource has been made inactive by an internal control process.";
      }
      enum DEPENDENCY {
        description "The resource cannot operate because some other resource on which it depends is unavailable.";
      }
      enum DEGRADED {
        description "The service available from the resource is degraded in some respect.";
      }
      enum NOT_INSTALLED {
        description "The resource represented by the managed object is not present, or is incomplete.";
      }
      enum LOG_FULL {
        description "This indicates a log full condition.";
      }
      enum DEPENDENCY_LOCKED {
        description "The administrative state of a resource that this resource depends on is locked. or the availability status of the other resource is dependency locked.";
      }
      enum DEPENDENCY_FAILED {
        description "The availability status of a resource that this resource depends on is failed or dependency failed.";
      }
      enum DEPENDENCY_SHUTTINGDOWN {
        description "The administrative state of a resource that this resource depends on is shutting down. or the availability status of the other resource is dependency shutting down.";
      }
    }
  }
  typedef EecFrom {
    description "Number of cascaded EECs or eEECs from nearest SSU, PRC, ePRC, PRTC, or ePRTC is received from network, or administrator EEC or eEEC numbers are used.";
    type enumeration {
      enum RECEIVED_TLV {
        description "Quality Level Type Length Value containing number of cascaded EEC or eEECs received from SyncE network.";
      }
      enum ADMIN_TLV1 {
        description "Quality Level Type Length Value containing number of cascaded EEC or eEECs remapped from received QL TLV to user defined QL TLV with adminCascadedEec and adminCascadedEnhancedEec.";
      }
    }
  }
  typedef OperState {
    description "The operational states of a resource.";
    type enumeration {
      enum DISABLED {
        description "The resource is totally inoperable.";
      }
      enum ENABLED {
        description "The resource is partially or fully operable.";
      }
    }
  }
  typedef SyncEthPhysical {
    description "Type of connected physical cable.";
    type enumeration {
      enum SFP_UNKNOWN {
      }
      enum SFP_DAC {
      }
      enum SFP_OPTICAL {
      }
      enum SFP_CAT_X_CABLE {
        description "SFP-RJ45 electrical cable.";
      }
      enum CAT_X_CABLE {
      }
    }
  }
  typedef SyncEthStatus {
    description "Synchronous Ethernet status for used Ethernet port.";
    type enumeration {
      enum UNKNOWN {
        description "No status information available.";
      }
      enum NO_FAULT {
        description "No fault detected.";
      }
      enum NO_SUPPORT_SFP_CAT_X_CABLE {
        description "SFP-RJ45 electrical cable not supported.";
      }
      enum LOSS_OF_SIGNAL {
        description "Signal not received.";
      }
      enum LOSS_OF_ESMC {
        description "No valid ESMC-PDU detected within five seconds.";
      }
      enum RJ45_1000_BASE_T_NOT_SLAVE {
        description "Ethernet port configured as sync reference is not in slave state.";
      }
    }
  }
  grouping SyncEthInput-attributes {
    leaf adminCascadedEec {
      description "Number of cascaded EECs from nearest SSU, PRC, ePRC, PRTC, or ePRTC.; range 0..100; Default value: 0.";
      type uint8 {
        range "0..100";
      }
      default "0";
    }
    leaf adminCascadedEnhancedEec {
      description "Number of cascaded eEECs from nearest SSU, PRC, ePRC, PRTC, or ePRTC.; range 0..100; Default value: 0.";
      type uint8 {
        range "0..100";
      }
      default "0";
    }
    leaf-list availabilityStatus {
      description "The availability status. It contains details about operationalState..";
      type AvailStatus;
      min-elements 0;
    }
    leaf encapsulation {
      description "Reference to underlying encapsulation. Must be EthernetPort MO..";
      type string;
      mandatory true;
    }
    leaf mixedEecEnhancedEec {
      description "Specifies whether chain is mixed EEC or eEEC..";
      type boolean;
      config false;
    }
    leaf numberCascadedEec {
      description "Number of cascaded EECs from nearest SSU, PRC, ePRC, PRTC, or ePRTC..";
      type uint8;
      config false;
    }
    leaf numberCascadedEnhancedEec {
      description "Number of cascaded eEECs from nearest SSU, PRC, ePRC, PRTC, or ePRTC..";
      type uint8;
      config false;
    }
    leaf operationalState {
      description "The operational state..";
      type enumeration {
        enum DISABLED;
        enum ENABLED;
      }
      config false;
    }
    leaf partialChain {
      description "Whether chain is incomplete..";
      type boolean;
      config false;
    }
    leaf receivedSsmCode {
      description "Synchronization Status Messages code..";
      type string;
      config false;
    }
    leaf-list reservedBy {
      description "Contains a list of MO instances that reserve this MO instance..";
      type string;
      min-elements 0;
    }
    leaf syncEMasterId {
      description "SyncE Master ID..";
      type string;
      config false;
    }
    leaf syncEthInputId {
      description "The value component of the RDN..";
      type string;
      mandatory true;
    }
    leaf syncEthPhysical {
      description "Type of connected physical cable..";
      type enumeration {
        enum SFP_UNKNOWN;
        enum SFP_DAC;
        enum SFP_OPTICAL;
        enum SFP_CAT_X_CABLE;
        enum CAT_X_CABLE;
      }
      config false;
    }
    leaf syncEthStatus {
      description "Status of port..";
      type enumeration {
        enum UNKNOWN;
        enum NO_FAULT;
        enum NO_SUPPORT_SFP_CAT_X_CABLE;
        enum LOSS_OF_SIGNAL;
        enum LOSS_OF_ESMC;
        enum RJ45_1000_BASE_T_NOT_SLAVE;
      }
      config false;
    }
    leaf useNumberEecFrom {
      description "Number of cascaded EECs or eEECs from nearest SSU, PRC, ePRC, PRTC, or ePRTC is received from network, or administrator EEC or eEEC numbers are used..";
      type enumeration {
        enum RECEIVED_TLV;
        enum ADMIN_TLV1;
      }
    }
  }
}
