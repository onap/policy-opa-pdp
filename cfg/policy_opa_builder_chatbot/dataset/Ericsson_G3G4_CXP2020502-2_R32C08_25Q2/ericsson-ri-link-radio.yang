module ericsson-ri-link-radio {
  yang-version 1.1;
  namespace "urn:com:ericsson:ecim:ReqRiLink";
  prefix rilinkrdo;
  import ericsson-yang-types {
    prefix eytypes;
  }
  import ericsson-equip-radio {
    prefix equiprdo;
  }
  import ericsson-managed-element {
    prefix emael;
  }
  description "Auto-generated from Ericsson CPI MOM XML 15554-lza7016014_33-v1uenfk.xml\nThis Managed Object (MO) is used to configure and monitor a Radio Interface (RI) link. It contains references to the two Radio Interface Ports (RiPort) comprising the link. On a link to an ORadio, following apply: - the link end on the Baseband refers to an RiPort MO. - and the link end on the ORadio refers to an ORiPort MO. On a link to a third-party radio, following apply: - the link end on the Baseband refers to an RiPort MO. - and the link end on the third-party radio refers to a ThirdPartyRiPort MO. The two port references must be provided to make configuration of the radio interface connection complete.";
  revision "2026-03-29" {
    description "Ericsson G3G4, version: CXP2020502/2-R32C08";
  }

  augment "/emael:ManagedElement/equiprdo:Equipment" {
    list RiLink {
      description "Additional definitions from MOM:min/max-elements:0/unbounded;root; This Managed Object (MO) is used to configure and monitor a Radio Interface (RI) link. It contains references to the two Radio Interface Ports (RiPort) comprising the link. On a link to an ORadio, following apply: - the link end on the Baseband refers to an RiPort MO. - and the link end on the ORadio refers to an ORiPort MO. On a link to a third-party radio, following apply: - the link end on the Baseband refers to an RiPort MO. - and the link end on the third-party radio refers to a ThirdPartyRiPort MO. The two port references must be provided to make the configuration of the radio interface connection complete.";
      key "riLinkId";
      leaf riLinkId {
        type leafref {
          path "../attributes/riLinkId";
        }
      }
      container attributes {
      uses RiLink-attributes;
      }
    }
  }
  typedef AvailStatus {
    description "The availability status is used to qualify the operational state. It indicates why the operational state has changed its value.";
    type enumeration {
      enum IN_TEST {
        description "The resource is undergoing a test procedure. If the administrative state is locked or shutting down, normal users are prevented from using the resource.";
      }
      enum FAILED {
        description "The resource has an internal fault that prevents it from operating.";
      }
      enum POWER_OFF {
        description "The resource requires power to be applied and is not powered on.";
      }
      enum OFF_LINE {
        description "The resource requires a routine operation to be performed. This routine operation is to place the resource online and make it available for use. The operation may be manual or automatic, or both. The operational state is disabled.";
      }
      enum OFF_DUTY {
        description "The resource has been made inactive by an internal control process.";
      }
      enum DEPENDENCY {
        description "The resource cannot operate because some other resource on which it depends is unavailable.";
      }
      enum DEGRADED {
        description "The service available from the resource is degraded in some respect.";
      }
      enum NOT_INSTALLED {
        description "The resource represented by the managed object is not present, or is incomplete.";
      }
      enum LOG_FULL {
        description "Indicates a log full condition. The semantics are defined in CCITT Rec. X.735 | ISO/IEC 10164-6.";
      }
      enum DEPENDENCY_LOCKED {
        description "The administrative state of a resource that this resource depends on is locked. Alternatively, the availability status of the other resource is dependency locked.";
      }
      enum DEPENDENCY_FAILED {
        description "The availability status of a resource that this resource depends on is failed or dependency failed.";
      }
      enum DEPENDENCY_SHUTTINGDOWN {
        description "The administrative state of a resource that this resource depends on is shutting down. Alternatively, the availability status of the other resource is dependency shutting down.";
      }
      enum DEPENDENCY_RECOVERY {
        description "Resource that this resource depends on is undergoing a recovery procedure.";
      }
      enum DEPENDENCY_HOLDING {
        description "Resource cannot operate because some other resource on which it depends is currently unavailable. The situation is expected to be resolved. Actions to facilitate dependency resolution may be ongoing.";
      }
    }
  }
  typedef FronthaulDeviceLineRate {
    description "Line rate of Radio Interface link. Used if fronthaul device is adopted.";
    type enumeration {
      enum NOT_SET {
        description "Line rate not set by operator. System determines optimal or highest possible rate with installed equipment.";
      }
      enum CPRI_LINE_RATE_2 {
        description "CPRI line rate is limited to 1.2288 Gbps.";
      }
      enum CPRI_LINE_RATE_3 {
        description "CPRI line rate is limited to 2.4575 Gbps.";
      }
      enum CPRI_LINE_RATE_5 {
        description "CPRI line rate is limited to 4.9152 Gbps.";
      }
      enum CPRI_LINE_RATE_7 {
        description "CPRI line rate is limited to 9.8304 Gbps.";
      }
      enum CPRI_LINE_RATE_8 {
        description "CPRI line rate is limited to 10.1376 Gbps.";
      }
      enum ECPRI_LINE_RATE_25G_RS_FEC {
        description "Line rate is 25 Gbps with Reed-Solomon (RS) FEC enabled. Specification: IEEE 802.3 Clause 108";
      }
    }
  }
  typedef OperState {
    description "Operational states of a resource.";
    type enumeration {
      enum DISABLED {
        description "The resource is totally inoperable.";
      }
      enum ENABLED {
        description "The resource is partially or fully operable.";
      }
    }
  }
  typedef RbsTransportType {
    description "The transport type and protocol of the Radio Interface(RI) link. Change of this parameter during network runtime can trigger restart of CPRI link.";
    type enumeration {
      enum CPRI_OVER_DWDM_LINEAR {
        description "CPRI over DWDM in linear configuration.";
      }
      enum CPRI_OVER_DWDM_RING {
        description "CPRI over DWDM in ring configuration.";
      }
      enum CPRI_OVER_CWDM_LINEAR {
        description "CPRI over coarse wavelength-division multiplexing in linear configuration.";
      }
      enum CPRI_OVER_CWDM_RING {
        description "CPRI over coarse wavelength-division multiplexing in ring configuration.";
      }
      enum CPRI_OVER_MICROWAVE_PTOP {
        description "CPRI over microwave in point-to-point configuration.";
      }
      enum CPRI_OVER_MICROWAVE_PTOM {
        description "CPRI over microwave in point-to-multipoint configuration.";
      }
      enum CPRI_OVER_GIGABIT_ETHERNET {
        description "CPRI over gigabit Ethernet configuration.";
      }
      enum NOT_SET {
        description "Transport type not set.";
      }
      enum CPRI_OVER_DIRECT_CABLE {
        description "CPRI over direct cable configuration.";
      }
      enum ETHERNET_OVER_E_LINE {
        description "Ethernet over point-to-point connection that is tunneled through arbitrary switched network.";
      }
    }
  }
  grouping RiLink-attributes {
    leaf riLinkId {
      description "The value component of the RDN..";
      type string;
      mandatory true;
    }
    leaf operationalState {
      description "The operational state..";
      type enumeration {
        enum DISABLED;
        enum ENABLED;
      }
      config false;
    }
    leaf riPortRef1 {
      description "Refers to one RiPort on the unit to which the link is connected. When the link is to an ORadio, the link end on the ORadio is an ORiPort MO instead of an RiPort MO. When the link is to a third-party device, the link end on the third-party device is a ThirdPartyRiPort MO instead of an RiPort MO..";
      type string;
      mandatory true;
    }
    leaf riPortRef2 {
      description "Refers to the other RiPort on the unit to which the link is connected. When the link is to an ORadio, the link end on the ORadio is an ORiPort MO instead of an RiPort MO. When the link is to a third party device, the link end on the third party device is a ThirdPartyRiPort MO instead of an RiPort MO..";
      type string;
      mandatory true;
    }
    leaf linkRate {
      description "The negotiated link rate for a CPRI or Ethernet link.; range 0..25700.";
      type int32 {
        range "0..25700";
      }
      config false;
      units "Mbps";
    }
    leaf-list availabilityStatus {
      description "The availability status. It contains details about operationalState..";
      type AvailStatus;
      min-elements 0;
    }
    leaf transportType {
      description "The transport type and protocol of the Radio Interface(RI) link..";
      type enumeration {
        enum CPRI_OVER_DWDM_LINEAR;
        enum CPRI_OVER_DWDM_RING;
        enum CPRI_OVER_CWDM_LINEAR;
        enum CPRI_OVER_CWDM_RING;
        enum CPRI_OVER_MICROWAVE_PTOP;
        enum CPRI_OVER_MICROWAVE_PTOM;
        enum CPRI_OVER_GIGABIT_ETHERNET;
        enum NOT_SET;
        enum CPRI_OVER_DIRECT_CABLE;
        enum ETHERNET_OVER_E_LINE;
      }
    }
    leaf linkTag {
      description "CPRI link tag (32 bits). The linkTag contains two parts - Node identity part (24 bits) followed by Link identity part (8 bits). The node identity part is from the nodeTag attribute of CpriLinkTagging MO. If 0, there is no linkTag set for this CPRI link.; range 0..4294967295.";
      type eytypes:int64_range_0-4294967295;
      config false;
    }
    leaf fronthaulDeviceLineRate {
      description "Line rate of CPRI link. Used if fronthaul device is adopted. NOT_SET is recommended value. Use other value only if explicitly needed..";
      type enumeration {
        enum NOT_SET;
        enum CPRI_LINE_RATE_2;
        enum CPRI_LINE_RATE_3;
        enum CPRI_LINE_RATE_5;
        enum CPRI_LINE_RATE_7;
        enum CPRI_LINE_RATE_8;
        enum ECPRI_LINE_RATE_25G_RS_FEC;
      }
    }
    leaf-list reservedBy {
      description "Contains a list of MO instances that reserve this MO instance..";
      type string;
      min-elements 0;
    }
    leaf operationalStateChangeTime {
      description "Timestamp of last change of operationalState..";
      type string;
      config false;
    }
    leaf pmLinkRestart {
      description "Total number of L1 reset requests on link. Only valid for CPRI link..";
      type uint32;
      config false;
    }
    leaf pmCableDelayHigh {
      description "Highest one-way delay for cable connecting units. Unit: 1 ns..";
      type int32;
      config false;
    }
    leaf pmLinkDelayHigh {
      description "Highest one-way delay for link between units. Unit: 1 ns. Only valid for CPRI link..";
      type int32;
      config false;
    }
    leaf pmCableDelayLow {
      description "Lowest one-way delay for cable connecting units. Unit: 1 ns..";
      type int32;
      config false;
    }
    leaf pmLinkStabilityError {
      description "Number of L1 disruptions on link represented by the owning MO RiLink (value corresponds to associated RiPort::pmLossOfSignal).";
      type uint32;
      config false;
    }
    leaf pmLinkDelayLow {
      description "Lowest one-way delay for link between units. Unit: 1 ns. Only valid for CPRI link..";
      type int32;
      config false;
    }
  }
}
