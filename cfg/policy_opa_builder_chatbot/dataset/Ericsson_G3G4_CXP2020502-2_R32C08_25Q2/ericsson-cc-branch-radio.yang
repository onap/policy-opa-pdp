module ericsson-cc-branch-radio {
  yang-version 1.1;
  namespace "urn:com:ericsson:ecim:ReqCcBranch";
  prefix ccbrnchrdo;
  import ericsson-antenna-radio {
    prefix antrdo;
  }
  import ericsson-equip-radio {
    prefix equiprdo;
  }
  import ericsson-managed-element {
    prefix emael;
  }
  description "Auto-generated from Ericsson CPI MOM XML 15554-lza7016014_33-v1uenfk.xml\nThis MO represents the functional \"long antenna branch\" between the Antenna Reference Point and the cross connected receiving radio unit. It conceptually includes an RfBranch and a CcLink.";
  revision "2026-03-29" {
    description "Ericsson G3G4, version: CXP2020502/2-R32C08";
  }

  augment "/emael:ManagedElement/equiprdo:Equipment/antrdo:AntennaUnitGroup" {
    list CcBranch {
      description "Additional definitions from MOM:min/max-elements:0/24;root; This MO represents the functional \"long antenna branch\" between the Antenna Reference Point and the cross connected receiving radio unit. It conceptually includes an RfBranch and a CcLink.";
      key "ccBranchId";
      leaf ccBranchId {
        type leafref {
          path "../attributes/ccBranchId";
        }
      }
      container attributes {
      uses CcBranch-attributes;
      }
    }
  }
  grouping CcBranch-attributes {
    leaf ccBranchId {
      description "The value component of the RDN..";
      type string;
      mandatory true;
    }
    leaf ccLinkRef {
      description "Contains reference to the CcLink included in the CcBranch. The CcLink represents cross connect cable part of the CcBranch..";
      type string;
      mandatory true;
    }
    leaf-list reservedBy {
      description "Contains a list of MO instances that reserve this MO instance..";
      type string;
      min-elements 0;
    }
    leaf rfBranchRef {
      description "Contains reference to the RfBranch included in the CcBranch. The RfBranch represents the RF feeder part of the CcBranch..";
      type string;
      mandatory true;
    }
  }
}
