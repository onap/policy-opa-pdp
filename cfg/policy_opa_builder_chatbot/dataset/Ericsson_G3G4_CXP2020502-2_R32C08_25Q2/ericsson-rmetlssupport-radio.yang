module ericsson-rmetlssupport-radio {
  yang-version 1.1;
  namespace "urn:com:ericsson:ecim:RmeTlsSupport";
  prefix rmetlssu;
  import ericsson-rmesupport-radio {
    prefix rmesuppo;
  }
  import ericsson-managed-element {
    prefix emael;
  }
  description "Auto-generated from Ericsson CPI MOM XML 15554-lza7016014_33-v1uenfk.xml\nRCS Tls support.";
  revision "2026-03-29" {
    description "Ericsson G3G4, version: CXP2020502/2-R32C08";
  }

  augment "/emael:ManagedElement/rmesuppo:NodeSupport" {
    list TlsSupport {
      description "Additional definitions from MOM:min/max-elements:0/1;root; Proprietary parameters for TLS.";
      key "tlsSupportId";
      leaf tlsSupportId {
        type leafref {
          path "../attributes/tlsSupportId";
        }
      }
      container attributes {
      uses TlsSupport-attributes;
      }
    }
  }
  grouping TlsSupport-attributes {
    leaf tlsSupportId {
      description "The value component of the RDN..";
      type string;
      mandatory true;
    }
    leaf maxTlsSessions {
      description "Maximum number of simultaneous TLS sessions allowed on the OAM TLS servers..";
      type string;
    }
  }
}
