module ericsson-power-supply-radio {
  yang-version 1.1;
  namespace "urn:com:ericsson:ecim:ResPowerSupply";
  prefix pwsuplrdo;
  import ericsson-equipment-support-function-radio {
    prefix eqsupfnrdo;
  }
  import ericsson-yang-types {
    prefix eytypes;
  }
  import ericsson-managed-element {
    prefix emael;
  }
  description "Auto-generated from Ericsson CPI MOM XML 15554-lza7016014_33-v1uenfk.xml\n.";
  revision "2026-03-29" {
    description "Ericsson G3G4, version: CXP2020502/2-R32C08";
  }

  augment "/emael:ManagedElement/eqsupfnrdo:EquipmentSupportFunction" {
    list PowerSupply {
      description "Additional definitions from MOM:min/max-elements:0/unbounded;root; This MO represents the logical resource providing configuration and supervision support for the cabinet power supply. Examples include configuration of charging algorithms and supervision levels and switching functions on/off etc. Dependencies: Can only exist in the node when the attribute supportSystemControl is set to true on a parent MO EquipmentSupportFunction.";
      key "powerSupplyId";
      leaf powerSupplyId {
        type leafref {
          path "../attributes/powerSupplyId";
        }
      }
      container attributes {
      uses PowerSupply-attributes;
      }
    }
  }
  typedef AvailStatus {
    description "The availability status is used to qualify the operational state. It indicates why the operational state has changed its value.";
    type enumeration {
      enum IN_TEST {
        description "The resource is undergoing a test procedure. If the administrative state is locked or shutting down, normal users are prevented from using the resource.";
      }
      enum FAILED {
        description "The resource has an internal fault that prevents it from operating.";
      }
      enum POWER_OFF {
        description "The resource requires power to be applied and is not powered on.";
      }
      enum OFF_LINE {
        description "The resource requires a routine operation to be performed. This routine operation is to place the resource online and make it available for use. The operation may be manual or automatic, or both. The operational state is disabled.";
      }
      enum OFF_DUTY {
        description "The resource has been made inactive by an internal control process.";
      }
      enum DEPENDENCY {
        description "The resource cannot operate because some other resource on which it depends is unavailable.";
      }
      enum DEGRADED {
        description "The service available from the resource is degraded in some respect.";
      }
      enum NOT_INSTALLED {
        description "The resource represented by the managed object is not present, or is incomplete.";
      }
      enum LOG_FULL {
        description "Indicates a log full condition. The semantics are defined in CCITT Rec. X.735 | ISO/IEC 10164-6.";
      }
      enum DEPENDENCY_LOCKED {
        description "The administrative state of a resource that this resource depends on is locked. Alternatively, the availability status of the other resource is dependency locked.";
      }
      enum DEPENDENCY_FAILED {
        description "The availability status of a resource that this resource depends on is failed or dependency failed.";
      }
      enum DEPENDENCY_SHUTTINGDOWN {
        description "The administrative state of a resource that this resource depends on is shutting down. Alternatively, the availability status of the other resource is dependency shutting down.";
      }
      enum DEPENDENCY_RECOVERY {
        description "Resource that this resource depends on is undergoing a recovery procedure.";
      }
      enum DEPENDENCY_HOLDING {
        description "Resource cannot operate because some other resource on which it depends is currently unavailable. The situation is expected to be resolved. Actions to facilitate dependency resolution may be ongoing.";
      }
    }
  }
  typedef OperState {
    description "Operational states of a resource.";
    type enumeration {
      enum DISABLED {
        description "The resource is totally inoperable.";
      }
      enum ENABLED {
        description "The resource is partially or fully operable.";
      }
    }
  }
  grouping SmartLoadSharingConfig-struct {
    description "Configuration structure defining PSU Loads which trigger switching.";
    leaf lowLoadLevelTreshold {
      description "range 10..40; Default value: 30.";
      type int32 {
        range "10..40";
      }
      default "30";
      units "percent";
    }
    leaf highLoadLevelTreshold {
      description "range 55..85; Default value: 70.";
      type int32 {
        range "55..85";
      }
      default "70";
      units "percent";
    }
    leaf highLoadLevelThreshold {
      description "range 55..85; Default value: 70.";
      type int32 {
        range "55..85";
      }
      default "70";
      units "percent";
    }
    leaf lowLoadLevelThreshold {
      description "range 10..40; Default value: 30.";
      type int32 {
        range "10..40";
      }
      default "30";
      units "percent";
    }
  }
  grouping PowerSupply-attributes {
    leaf powerSupplyId {
      description "The value component of the RDN..";
      type string;
      mandatory true;
    }
    leaf nominalVoltage {
      description "The desired system voltage.; range -570..-480; Default value: -545.";
      type eytypes:int32_range_-570--480;
      default "-545";
      units "V";
    }
    leaf systemOvervoltageAlarmCeaseOffset {
      description "The offset for the system over voltage level below which the system over voltage alarm is ceased. The alarm cease condition is true when systemVoltage is below SystemOvervoltageAlarmLevel + SystemOvervoltageAlarmCeaseOffset. Example: The default values -575 + 5 = -570 (-57.0 V) gives an alarm cease if systemVoltage is e.g. -56.9 V.; range 0..50; Default value: 5; Status info: Since 18A. Planned to be removed..";
      type int32 {
        range "0..50";
      }
      status deprecated;
      default "5";
      units "V";
    }
    leaf systemUndervoltageAlarmLevel {
      description "Alarm level for system undervoltage. The alarm is raised when systemVoltage is lower than SystemUndervoltageAlarmLevel. Example: The default value -475 (-47.5 V) gives an alarm if systemVoltage is e.g. -47.4 V.; range -480..-380; Default value: -475; Status info: Since 18A. Replaced by systemUndervoltageAlarmLevel on MO PowerDistribution. Planned to be removed..";
      type int32 {
        range "-480..-380";
      }
      status deprecated;
      default "-475";
      units "V";
    }
    leaf systemVoltage {
      description "The measured system voltage. It is equal to the attribute batteryVoltage, MO BatteryBackup, when the battery is connected. Undefined value: indicates no connection with neither PDU, BFU nor PSU.; range -600..-380; MOM flags: noNotification, isNillable=true; Status info: Since 18A. Replaced by systemVoltage on MO PowerDistribution. Planned to be removed..";
      type int32 {
        range "-600..-380";
      }
      config false;
      status deprecated;
      units "V";
    }
    leaf userLabel {
      description "Label for free use.; length 1..128.";
      type string {
        length "1..128";
      }
    }
    leaf systemUndervoltageAlarmCeaseOffset {
      description "The offset for the system under voltage level above which the system undervoltage alarm ceases. The alarm cease condition is true when systemVoltage is above SystemUndervoltageAlarmLevel - SystemUndervoltageAlarmCeaseOffset. Example: The default values -440 - 30 = -470 (-47.0 V) gives an alarm cease if systemVoltage is e.g. -47.1 V; range 0..50; Default value: 30; Status info: Since 18A. Planned to be removed..";
      type int32 {
        range "0..50";
      }
      status deprecated;
      default "30";
      units "V";
    }
    leaf systemOvervoltageAlarmLevel {
      description "Alarm level for system over voltage. The alarm active condition is true when systemVoltage is above SystemOvervoltageAlarmLevel. Example: The default value -575 (-57.5 V) gives an alarm if systemVoltage is e.g. -57.6 V.; range -600..-530; Default value: -575; Status info: Since 18A. Replaced by systemOvervoltageAlarmLevel on MO PowerDistribution. Planned to be removed..";
      type int32 {
        range "-600..-530";
      }
      status deprecated;
      default "-575";
      units "V";
    }
    leaf-list availabilityStatus {
      description "The availability status. It contains details about operationalState..";
      type AvailStatus;
      min-elements 0;
    }
    leaf operationalState {
      description "Defines the operational state..";
      type enumeration {
        enum DISABLED;
        enum ENABLED;
      }
      config false;
    }
    leaf multiplePowerSystem {
      description "Indicates if all power supplies in the power domain provide the same load. true: Several power systems provide separate loads within same cabinet. Multiple sub-racks operate individually and form one power system each. false: All loads within same cabinet are powered from one power system. Multiple sub-racks are internally connected by a cabinet bus bar.; Default value: true.";
      type boolean;
      default "true";
    }
    leaf controlDomainRef {
      description "The cabinet or hwGroup where functions represented by this MO are deployed..";
      type string;
    }
    list smartLoadSharingConfig {
      key "id";
      leaf id {
        type uint32;
        description "Synthetic key for struct attribute.";
      }
      description "Configuration structure defining PSU Loads which trigger switching..";
      uses SmartLoadSharingConfig-struct;
    }
    leaf smartLoadSharing {
      description "Parameter responsible for activating/deactivation Smart PSU load sharing; Default value: false.";
      type boolean;
      default "false";
    }
    leaf-list pmPsuAcInputVoltageInterruption {
      description "Distribution of AC power supply interruptions due to loss of mains. PDF ranges: [0]: Number of AC interruptions caused by loss of mains with duration less than 20 seconds. [1]: Number of AC interruptions caused by loss of mains with duration in range [20.. 60] seconds. [2]: Number of AC interruptions caused by loss of mains with duration in range ]1.. 3] minutes. [3]: Number of AC interruptions caused by loss of mains with duration in range ]3.. 10] minutes. [4]: Number of AC interruptions caused by loss of mains with duration in range ]10.. 30] minutes. [5]: Number of AC interruptions caused by loss of mains with duration in range ]30.. 60] minutes. [6]: Number of AC interruptions caused by loss of mains with duration in range ]1.. 2] hours. [7]: Number of AC interruptions caused by loss of mains with duration in range ]2.. 5] hours. [8]: Number of AC interruptions caused by loss of mains with duration in range ]5.. 10] hours. [9]: Number of AC interruptions caused by loss of mains with duration greater than 10 hours..";
      type uint32;
      max-elements 10;
    }
    leaf-list pmPsuPowerLoad {
      description "Average of power loads measured for every PSU in 60 second periods. Unit: %.";
      type int32;
      max-elements 15;
    }
  }
}
