module ericsson-fwslot-radio {
  yang-version 1.1;
  namespace "urn:com:ericsson:ecim:ReqFwSlot";
  prefix fwslotrdo;
  import ericsson-support-unit-radio {
    prefix supurdo;
  }
  import ericsson-equip-radio {
    prefix equiprdo;
  }
  import ericsson-managed-element {
    prefix emael;
  }
  description "Auto-generated from Ericsson CPI MOM XML 15554-lza7016014_33-v1uenfk.xml\nThis MO represents Firmware (FW) slots available for a unit. When the unit has capability of FW download support this MO serves as container for downloaded FW revisions.";
  revision "2026-03-29" {
    description "Ericsson G3G4, version: CXP2020502/2-R32C08";
  }

  augment "/emael:ManagedElement/equiprdo:Equipment/supurdo:SupportUnit" {
    list FwSlot {
      description "Additional definitions from MOM:min/max-elements:0/2;root;systemCreated; Firmware slots available for a unit. When unit has capability of firmware download support, this MO serves as container for downloaded firmware revisions. The RDNs of these MOs are FwSlot=1, 2, 3, and so on.";
      key "fwSlotId";
      leaf fwSlotId {
        type leafref {
          path "../attributes/fwSlotId";
        }
      }
      container attributes {
      uses FwSlot-attributes;
      }
    }
  }
  typedef FwSlotStatus {
    description "Current load status of firmware slot.";
    type enumeration {
      enum EMPTY {
        description "Firmware slot is empty. No software is loaded.";
      }
      enum CHECKING {
        description "Firmware check is initiated and ongoing.";
      }
      enum FAILED {
        description "Firmware load fails.";
      }
      enum LOADED {
        description "Firmware is loaded into slot.";
      }
      enum LOADING {
        description "Firmware is downloaded to slot.";
      }
      enum ERROR {
        description "Firmware slot PID cannot be fetched from unit.";
      }
    }
  }
  grouping FwSlot-attributes {
    leaf fwSlotId {
      description "The value component of the RDN..";
      type string;
      mandatory true;
    }
    leaf slotStatus {
      description "Current load status of firmware slot..";
      type enumeration {
        enum EMPTY;
        enum CHECKING;
        enum FAILED;
        enum LOADED;
        enum LOADING;
        enum ERROR;
      }
      config false;
    }
    leaf name {
      description "Name of firmware present in slot or empty value when firmware is not loaded..";
      type string;
      config false;
    }
    leaf activated {
      description "Set to true when firmware in this slot is currently activated on unit..";
      type boolean;
      config false;
    }
    leaf prioritized {
      description "Set to true when slot is set as prioritized..";
      type boolean;
      config false;
    }
    leaf revision {
      description "Firmware revision present in slot or empty value when firmware is not loaded..";
      type string;
      config false;
    }
  }
}
