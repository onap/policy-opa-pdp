module ericsson-authentication-server-rtn-radio {
  yang-version 1.1;
  namespace "urn:com:ericsson:ecim:RtnAuthenticationServer";
  prefix authsrvrdo;
  import ericsson-l3-router-rtn-radio {
    prefix l3rtrdo;
  }
  import ericsson-managed-element {
    prefix emael;
  }
  description "Auto-generated from Ericsson CPI MOM XML 15554-lza7016014_33-v1uenfk.xml\nAuthenticationServer MO.";
  revision "2026-03-29" {
    description "Ericsson G3G4, version: CXP2020502/2-R32C08";
  }

  augment "/emael:ManagedElement/emael:Transport/l3rtrdo:Router" {
    list AuthenticationServer {
      description "Additional definitions from MOM:min/max-elements:0/unbounded;root; Provides access to redundant remote authentication servers.";
      key "authenticationServerId";
      leaf authenticationServerId {
        type leafref {
          path "../attributes/authenticationServerId";
        }
      }
      container attributes {
      uses AuthenticationServer-attributes;
      }
    }
  }
  grouping AuthenticationServer-attributes {
    leaf authenticationServerId {
      description "The value component of the RDN..";
      type string;
      mandatory true;
    }
    leaf-list reservedBy {
      description "Contains a list of MO instances that reserve this MO instance..";
      type string;
      min-elements 0;
    }
    leaf-list serverAddress {
      description "List of configured remote authentication server addresses. For each configured remote authentication server address, pre-shared key must be installed with action installPreSharedKey..";
      type string;
      min-elements 1;
      max-elements 8;
    }
    leaf-list usedServerAddress {
      description "List of used authentication server addresses. IPv4 address is specified in dotted quad notation, for example 130.100.92.154. RFC 791 describes syntax details. IPv6 address is specified by 8 groups of 16 bit hexadecimal values separated by colons, for example 2001:0db8:85a3:0000:0000:8a2e:0370:7334. RFC 4291 describes syntax details..";
      type string;
      min-elements 1;
      max-elements 8;
    }
    leaf userLabel {
      description "Label for free use.; length 1..128.";
      type string {
        length "1..128";
      }
    }
  }
}
