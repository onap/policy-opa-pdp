module ericsson-cpri-link-iq-data-radio {
  yang-version 1.1;
  namespace "urn:com:ericsson:ecim:ReqCpriLinkIqData";
  prefix cpriiqdatardo;
  import ericsson-rmesupport-radio {
    prefix rmesuppo;
  }
  import ericsson-managed-element {
    prefix emael;
  }
  description "Auto-generated from Ericsson CPI MOM XML 15554-lza7016014_33-v1uenfk.xml\nThis MO handles specific settings for IQ user data. Only valid for CPRI links.";
  revision "2026-03-29" {
    description "Ericsson G3G4, version: CXP2020502/2-R32C08";
  }

  augment "/emael:ManagedElement/rmesuppo:NodeSupport" {
    list CpriLinkIqData {
      description "Additional definitions from MOM:min/max-elements:0/unbounded;root; This MO handles specific settings for IQ user data. Only valid for CPRI links.";
      key "cpriLinkIqDataId";
      leaf cpriLinkIqDataId {
        type leafref {
          path "../attributes/cpriLinkIqDataId";
        }
      }
      container attributes {
      uses CpriLinkIqData-attributes;
      }
    }
  }
  typedef CpriCompressionState {
    description "CPRI Compression setting for referred RiLinks. Only valid for CPRI links.";
    type enumeration {
      enum DEFAULT {
        description "Default setting of CPRI Compression feature. CPRI Compression is enabled for referred RiLink MOs.";
      }
      enum DISABLED {
        description "CPRI Compression feature is disabled for referred RiLink MOs.";
      }
      enum RESERVED {
      }
    }
  }
  grouping CpriLinkIqData-attributes {
    leaf cpriLinkIqDataId {
      description "The value component of the RDN..";
      type string;
      mandatory true;
    }
    leaf-list riLinkRef {
      description "References to RiLink MOs..";
      type string;
      min-elements 0;
    }
    leaf cpriCompression {
      description "CPRI Compression setting for referred RiLinks. Only valid for CPRI links..";
      type enumeration {
        enum DEFAULT;
        enum DISABLED;
        enum RESERVED;
      }
    }
  }
}
