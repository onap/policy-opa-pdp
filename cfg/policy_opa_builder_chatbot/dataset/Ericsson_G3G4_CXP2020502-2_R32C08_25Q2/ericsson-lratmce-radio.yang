module ericsson-lratmce-radio {
  yang-version 1.1;
  namespace "urn:com:ericsson:ecim:LratMce";
  prefix lratmce;
  import ericsson-managed-element {
    prefix emael;
  }
  description "Auto-generated from Ericsson CPI MOM XML 15554-lza7016014_33-v1uenfk.xml\nIt contains the M3 connection classes.";
  revision "2026-03-29" {
    description "Ericsson G3G4, version: CXP2020502/2-R32C08";
  }

  augment "/emael:ManagedElement" {
    list MceFunction {
      description "Additional definitions from MOM:min/max-elements:0/1;root; This MO is the top level MO for MCE functions. It contains the M3 connection classes.";
      key "mceFunctionId";
      leaf mceFunctionId {
        type leafref {
          path "../attributes/mceFunctionId";
        }
      }
      container attributes {
      uses MceFunction-attributes;
      }
    }
  }

  augment "/emael:ManagedElement/lratmce:MceFunction" {
    list TermPointToMmeM3 {
      description "Additional definitions from MOM:min/max-elements:0/64; Models the MME termination point of an M3 link between the RBS and the MME node.";
      key "termPointToMmeM3Id";
      leaf termPointToMmeM3Id {
        type leafref {
          path "../attributes/termPointToMmeM3Id";
        }
      }
      container attributes {
      uses TermPointToMmeM3-attributes;
      }
    }
  }
  typedef AdmState {
    description "Administrative state of a resource.";
    type enumeration {
      enum LOCKED {
        description "The resource is administratively prohibited from performing services for its users.";
      }
      enum UNLOCKED {
        description "The resource is administratively permitted to perform services for its users. This is independent of its inherent operability.";
      }
      enum SHUTTINGDOWN {
        description "Use of the resource is administratively permitted to existing instances of use only. While the system remains in the shutting down state the manager may at any time cause the managed object to revert to the locked state.";
      }
    }
  }
  typedef AvailStatus {
    description "The availability status is used to qualify the operational state. It indicates why the operational state has changed its value.";
    type enumeration {
      enum IN_TEST {
        description "The resource is undergoing a test procedure. If the administrative state is locked or shutting down, normal users are prevented from using the resource.";
      }
      enum FAILED {
        description "The resource has an internal fault that prevents it from operating.";
      }
      enum POWER_OFF {
        description "The resource requires power to be applied and is not powered on.";
      }
      enum OFF_LINE {
        description "The resource requires a routine operation to be performed. This routine operation is to place the resource online and make it available for use. The operation may be manual or automatic, or both. The operational state is disabled.";
      }
      enum OFF_DUTY {
        description "The resource has been made inactive by an internal control process.";
      }
      enum DEPENDENCY {
        description "The resource cannot operate because some other resource on which it depends is unavailable.";
      }
      enum DEGRADED {
        description "The service available from the resource is degraded in some respect.";
      }
      enum NOT_INSTALLED {
        description "The resource represented by the managed object is not present, or is incomplete.";
      }
      enum LOG_FULL {
        description "Indicates a log full condition. The semantics are defined in CCITT Rec. X.735 | ISO/IEC 10164-6.";
      }
      enum DEPENDENCY_LOCKED {
        description "The administrative state of a resource that this resource depends on is locked. Alternatively, the availability status of the other resource is dependency locked.";
      }
      enum DEPENDENCY_FAILED {
        description "The availability status of a resource that this resource depends on is failed or dependency failed.";
      }
      enum DEPENDENCY_SHUTTINGDOWN {
        description "The administrative state of a resource that this resource depends on is shutting down. Alternatively, the availability status of the other resource is dependency shutting down.";
      }
      enum DEPENDENCY_RECOVERY {
        description "Resource that this resource depends on is undergoing a recovery procedure.";
      }
      enum DEPENDENCY_HOLDING {
        description "Resource cannot operate because some other resource on which it depends is currently unavailable. The situation is expected to be resolved. Actions to facilitate dependency resolution may be ongoing.";
      }
    }
  }
  typedef OperState {
    description "Operational states of a resource.";
    type enumeration {
      enum DISABLED {
        description "The resource is totally inoperable.";
      }
      enum ENABLED {
        description "The resource is partially or fully operable.";
      }
    }
  }
  typedef OrderCode {
    type enumeration {
      enum RETAIN_EXISTING {
      }
      enum RENEW_ALL_EXISTING {
      }
    }
  }
  grouping MceFunction-attributes {
    leaf mceFunctionId {
      description "The value component of the RDN..";
      type string;
      mandatory true;
    }
    leaf useM3dnsFormat {
      description "This parameter specifies if the DNS lookup shall use the M3 or S1 format for the TAI domain name: m3mme.tac-lb<tac-lb>.tac-hb<tac-hb>.tac.epc.mnc<mnc>.mcc<mcc>.3gppnetwork.org (true) s1mme.tac-lb<tac-lb>.tac-hb<tac-hb>.tac.epc.mnc<mnc>.mcc<mcc>.3gppnetwork.org (false); Default value: false.";
      type boolean;
      default "false";
    }
    leaf release {
      description "The product release of the ManagedFunction. It commonly contains the Managed Function release, for example L12.0, 13A, R1A.";
      type string;
      config false;
    }
    leaf userLabel {
      description "Used for product free-text description..";
      type string;
    }
    leaf pmMbmsSessionEnd {
      description "The total number of times an MBMS session is stopped by MBMS session duration timeout. Scanner: Not included in any predefined scanner.";
      type uint32;
      config false;
    }
    leaf pmMbmsSessionStopMmeNoSession {
      description "The total number of times the eNodeB receives the MBMS SESSION STOP REQUEST message for an MBMS session that is already stopped. Scanner: Not included in any predefined scanner.";
      type uint32;
      config false;
    }
    leaf pmMbmsSessionEstabSucc {
      description "The total number of times an MBMS session is successfully established in the eNodeB. It is incremented each time the MBMS SESSION START RESPONSE is sent. Scanner: Not included in any predefined scanner.";
      type uint32;
      config false;
    }
    leaf pmMbmsSessionEstabFailUpdate {
      description "The total number of times an MBMS session start fails due to unsupported MBMS session parameter update. It is incremented each time the MBMS SESSION START FAILURE is sent for an already started session. Scanner: Not included in any predefined scanner.";
      type uint32;
      config false;
    }
    leaf pmMbmsSessionUpdateFailParam {
      description "Total failures of MBMS session update caused by unsupported MBMS session update parameter. Scanner: Not included in any predefined scanner.";
      type uint32;
      config false;
    }
    leaf pmMbmsSessionUpdateAtt {
      description "The total number of MBMS session update attempts. It is incremented each time the MBMS SESSION UPDATE REQUEST is received. Scanner: Not included in any predefined scanner.";
      type uint32;
      config false;
    }
    leaf pmMbmsSessionUpdateFailNotSupp {
      description "Total failures of MBMS session update caused by unsupported eNodeB configuration. Scanner: Not included in any predefined scanner.";
      type uint32;
      config false;
    }
    leaf pmMbmsSessionEstabFailNotSupp {
      description "The total number of MBMS sessions that have failed to be established due to unsupported configuration in eNodeB. It is incremented each time the MBMS SESSION START FAILURE is sent. Scanner: Not included in any predefined scanner.";
      type uint32;
      config false;
    }
    leaf pmMbmsSessionStopAuditTimer {
      description "The total number of times an MBMS session is stopped by the MBMS audit timer. Scanner: Not included in any predefined scanner.";
      type uint32;
      config false;
    }
    leaf pmMbmsSessionEstabAtt {
      description "The total number of MBMS session establishment attempts. It is incremented each time the MBMS SESSION START REQUEST is received. Scanner: Not included in any predefined scanner.";
      type uint32;
      config false;
    }
    leaf pmMbmsSessionUpdateSucc {
      description "The total number of times an MBMS session update is successfully handled in the eNodeB. It is incremented each time the MBMS SESSION UPDATE RESPONSE is sent. Scanner: Not included in any predefined scanner.";
      type uint32;
      config false;
    }
    leaf pmZtemporary102 {
      description "Normally this counter is not used, it can however sometimes be temporarily used for very late additions in a release. If so, for description see Network Impact Report in the CPI. Scanner: Not included in any predefined scanner.";
      type uint32;
      config false;
    }
    leaf pmZtemporary103 {
      description "Normally this counter is not used, it can however sometimes be temporarily used for very late additions in a release. If so, for description see Network Impact Report in the CPI. Scanner: Not included in any predefined scanner.";
      type uint32;
      config false;
    }
    leaf pmMbmsSessionStopMme {
      description "The total number of times an MBMS session is stopped by a received MBMS SESSION STOP REQUEST message. Scanner: Not included in any predefined scanner.";
      type uint32;
      config false;
    }
  }
  grouping TermPointToMmeM3-attributes {
    leaf termPointToMmeM3Id {
      description "The value component of the RDN..";
      type string;
      mandatory true;
    }
    leaf-list availabilityStatus {
      description "The availability status. It contains details about operationalState. This attribute is set by the application in the RBS..";
      type AvailStatus;
      min-elements 0;
    }
    leaf administrativeState {
      description "The administrative state. Note: If this attribute is set to SHUTTING_DOWN, it will immediately go into the state LOCKED..";
      type enumeration {
        enum LOCKED;
        enum UNLOCKED;
        enum SHUTTINGDOWN;
      }
    }
    leaf domainName {
      description "The fully-qualified domain name of the MME. A valid domain name consists of 1 or more labels separated by dots (.). Valid characters for a label are limited to letters a - z, A - Z, digits 0 - 9, and the character - (dash). Character case is preserved. Length of a label may not exceed 255 characters. NOTE: The first and last character in the domain name must be one of the following alphanumeric characters a - z, A - Z or digits 0 - 9. For more information refer to RFC 952, 1101 and 1123. To set this attribute, administrativeState must be LOCKED.; length 0..255.";
      type string {
        length "0..255";
      }
    }
    leaf ipAddress1 {
      description "The primary IP address of the MME. A unique IP address is required for each MME. The input format is four fields of digits, separated by dots. Each field consists of three digits. The value of each field must be in the range 0-255. To set this attribute, administrativeState must be LOCKED.; length 7..15; Default value: 0.0.0.0.";
      type string {
        length "7..15";
      }
      default "0.0.0.0";
    }
    leaf ipAddress2 {
      description "The secondary IP address of the MME. A unique IP address is required for each MME. The input format is four fields of digits, separated by dots. Each field consists of three digits. The value of each field must be in the range 0-255. To set this attribute, administrativeState must be LOCKED.; length 7..15; Default value: 0.0.0.0.";
      type string {
        length "7..15";
      }
      default "0.0.0.0";
    }
    leaf ipv6Address1 {
      description "The primary IPv6 address of the MME. The input format is eight fields, separated by colons. Each field consists of four hexadecimal characters. The value of each field must be in the range 0-FFFF. Leading zeroes can be omitted in a field, and multiple groups of 16 bits of zeroes can be compressed to ::. The :: can be used only once in an address. To set this attribute, administrativeState must be LOCKED.; length 2..39; Default value: ::.";
      type string {
        length "2..39";
      }
      default "::";
    }
    leaf ipv6Address2 {
      description "The secondary IPv6 address of the MME. The input format is eight fields, separated by colons. Each field consists of four hexadecimal characters. The value of each field must be in the range 0-FFFF. Leading zeroes can be omitted in a field, and multiple groups of 16 bits of zeroes can be compressed to ::. The :: can be used only once in an address. To set this attribute, administrativeState must be LOCKED.; length 2..39; Default value: ::.";
      type string {
        length "2..39";
      }
      default "::";
    }
    leaf operationalState {
      description "The operational state. This attribute is set by the application in the RBS..";
      type enumeration {
        enum DISABLED;
        enum ENABLED;
      }
      config false;
    }
    leaf usedIpAddress {
      description "The destination address used for initialization of the underlying SCTP association of the latest successful M3-Setup. The IP address can be an IPv4 or an IPv6 address. Note: usedIpAddress never changes during the lifetime of the SCTP association.; length 2..39.";
      type string {
        length "2..39";
      }
      config false;
    }
  }
}
