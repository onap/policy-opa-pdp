module ericsson-rtndhcprelayipv6-radio {
  yang-version 1.1;
  namespace "urn:com:ericsson:ecim:RtnDhcpRelayIPv6";
  prefix rtndhcpr;
  import ericsson-l3-router-rtn-radio {
    prefix l3rtrdo;
  }
  import ericsson-managed-element {
    prefix emael;
  }
  description "Auto-generated from Ericsson CPI MOM XML 15554-lza7016014_33-v1uenfk.xml\nDhcpRelay MOM";
  revision "2026-03-29" {
    description "Ericsson G3G4, version: CXP2020502/2-R32C08";
  }

  augment "/emael:ManagedElement/emael:Transport/l3rtrdo:Router" {
    list DhcpRelayIPv6 {
      description "Additional definitions from MOM:min/max-elements:0/unbounded;root; Represents DHCP relay agent, that can relay IPv6 DHCP messages between DHCP clients and servers, which are not attached to same link.";
      key "dhcpRelayIPv6Id";
      leaf dhcpRelayIPv6Id {
        type leafref {
          path "../attributes/dhcpRelayIPv6Id";
        }
      }
      container attributes {
      uses DhcpRelayIPv6-attributes;
      }
    }
  }
  grouping DhcpRelayIPv6-attributes {
    leaf dhcpRelayIPv6Id {
      description "The value component of the RDN..";
      type string;
      mandatory true;
    }
    leaf-list linkAddress {
      description "Reference to AddressIPv6 MO, used by DHCPv6 server to determine link from which client should be assigned address and other configuration information..";
      type string;
      min-elements 1;
    }
    leaf-list server {
      description "Reference to PeerIPv6 MO that DHCP packets will be relayed to..";
      type string;
      min-elements 1;
      max-elements 10;
    }
    leaf dhcpv6InClientMsgsHC {
      description "Number of DHCPv6 messages received from DHCPv6 clients. Note that this counter includes all those counted by dhcpv6InClientErrorsHC..";
      type uint64;
      config false;
    }
    leaf dhcpv6OutClientMsgsHC {
      description "Number of DHCPv6 messages attempted to send to DHCPv6 clients..";
      type uint64;
      config false;
    }
    leaf dhcpv6InServerErrorsHC {
      description "Number of DHCPv6 messages received from DHCPv6 servers that are discarded because of DHCPv6-specific errors..";
      type uint64;
      config false;
    }
    leaf dhcpv6InClientErrorsHC {
      description "Number of DHCPv6 messages received from DHCPv6 clients that are discarded because of DHCPv6-specific errors..";
      type uint64;
      config false;
    }
    leaf dhcpv6OutServerMsgsHC {
      description "Number of DHCPv6 messages attempted to send to DHCPv6 servers..";
      type uint64;
      config false;
    }
    leaf dhcpv6InServerMsgsHC {
      description "Number of DHCPv6 messages received from DHCPv6 servers. Note that this counter includes all those counted by dhcpv6InServerErrorsHC..";
      type uint64;
      config false;
    }
  }
}
