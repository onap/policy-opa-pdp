module ericsson-macsec-ca-rtn-radio {
  yang-version 1.1;
  namespace "urn:com:ericsson:ecim:RtnMacSecCa";
  prefix macseccardo;
  import ietf-yang-types {
    prefix ietfyang;
  }
  import ericsson-managed-element {
    prefix emael;
  }
  description "Auto-generated from Ericsson CPI MOM XML 15554-lza7016014_33-v1uenfk.xml\nRtnMacSecCa fragment contains Media Access Control Security (MACsec) MO.";
  revision "2026-03-29" {
    description "Ericsson G3G4, version: CXP2020502/2-R32C08";
  }

  augment "/emael:ManagedElement/emael:Transport" {
    list MacSecCa {
      description "Additional definitions from MOM:min/max-elements:0/unbounded;root;systemCreated; Represents Connectivity Association, as seen by MKA Key server. Only created when RiLink MO is created with following conditions: - When one MacSecProfile MO is associated with RiLink MO. - When Ethernet is detected on link.";
      key "macSecCaId";
      leaf macSecCaId {
        type leafref {
          path "../attributes/macSecCaId";
        }
      }
      container attributes {
      uses MacSecCa-attributes;
      }
    }
  }
  typedef AvailStatus {
    description "The availability status is used to qualify the operational state. It indicates why the operational state has changed its value.";
    type enumeration {
      enum IN_TEST {
        description "The resource is undergoing a test procedure. If the administrative state is locked or shutting down then normal users are precluded from using the resource.";
      }
      enum FAILED {
        description "The resource has an internal fault that prevents it from operating.";
      }
      enum POWER_OFF {
        description "The resource requires power to be applied and is not powered on.";
      }
      enum OFF_LINE {
        description "The resource requires a routine operation to be performed. This routine operation is to place the resource online and make it available for use. The operation may be manual or automatic, or both. The operational state is disabled.";
      }
      enum OFF_DUTY {
        description "The resource has been made inactive by an internal control process.";
      }
      enum DEPENDENCY {
        description "The resource cannot operate because some other resource on which it depends is unavailable.";
      }
      enum DEGRADED {
        description "The service available from the resource is degraded in some respect.";
      }
      enum NOT_INSTALLED {
        description "The resource represented by the managed object is not present, or is incomplete.";
      }
      enum LOG_FULL {
        description "This indicates a log full condition.";
      }
      enum DEPENDENCY_LOCKED {
        description "The administrative state of a resource that this resource depends on is locked. or the availability status of the other resource is dependency locked.";
      }
      enum DEPENDENCY_FAILED {
        description "The availability status of a resource that this resource depends on is failed or dependency failed.";
      }
      enum DEPENDENCY_SHUTTINGDOWN {
        description "The administrative state of a resource that this resource depends on is shutting down. or the availability status of the other resource is dependency shutting down.";
      }
    }
  }
  typedef MacSecCipher {
    description "MACsec cipher suites.";
    type enumeration {
      enum GCM_AES_128 {
        description "Specification: IEEE 802.1AE 2018";
      }
      enum GCM_AES_256 {
        description "Specification: IEEE 802.1AE 2018";
      }
    }
  }
  typedef MacSecSecurityLevel {
    description "Security level provided by MACsec.";
    type enumeration {
      enum NONE {
        description "Best-effort security using MACsec based on hardware capabilities.";
      }
      enum INTEGRITY_AND_CONFIDENTIALITY {
        description "Maximum security using MACsec that includes both integrity and confidentiality.";
      }
    }
  }
  typedef OperState {
    description "The operational states of a resource.";
    type enumeration {
      enum DISABLED {
        description "The resource is totally inoperable.";
      }
      enum ENABLED {
        description "The resource is partially or fully operable.";
      }
    }
  }
  grouping MacSecCa-attributes {
    leaf-list availabilityStatus {
      description "The availability status. It contains details about operationalState..";
      type AvailStatus;
      min-elements 0;
    }
    leaf macSecCaId {
      description "The value component of the RDN..";
      type ietfyang:mac-address;
      mandatory true;
    }
    leaf-list macSecCiphers {
      description "Currently used cipher. Empty value indicates that this attribute is invalid..";
      type ietfyang:mac-address;
      min-elements 0;
    }
    leaf operationalState {
      description "The operational state..";
      type enumeration {
        enum DISABLED;
        enum ENABLED;
      }
      config false;
    }
    leaf-list reservedBy {
      description "Contains a list of MO instances that reserve this MO instance..";
      type string;
      min-elements 0;
    }
    leaf-list securityLevel {
      description "Currently provided security level. Empty value indicates that this attribute is invalid..";
      type MacSecSecurityLevel;
      min-elements 0;
    }
  }
}
