module ericsson-frequency-sync-io-sync-radio {
  yang-version 1.1;
  namespace "urn:com:ericsson:ecim:RsyncFrequencySyncIO";
  prefix fsynciordo;
  import ericsson-synchronization-sync-radio {
    prefix syncrdo;
  }
  import ericsson-managed-element {
    prefix emael;
  }
  description "Auto-generated from Ericsson CPI MOM XML 15554-lza7016014_33-v1uenfk.xml\nECIM Transport frequency SyncIO Model.";
  revision "2026-03-29" {
    description "Ericsson G3G4, version: CXP2020502/2-R32C08";
  }

  augment "/emael:ManagedElement/emael:Transport/syncrdo:Synchronization" {
    list FrequencySyncIO {
      description "Additional definitions from MOM:min/max-elements:0/8;root; The MO class specifies that a physical synchronization port is used for frequency synchronization.";
      key "frequencySyncIOId";
      leaf frequencySyncIOId {
        type leafref {
          path "../attributes/frequencySyncIOId";
        }
      }
      container attributes {
      uses FrequencySyncIO-attributes;
      }
    }
  }
  typedef AvailStatus {
    description "The availability status is used to qualify the operational state. It indicates why the operational state has changed its value.";
    type enumeration {
      enum IN_TEST {
        description "The resource is undergoing a test procedure. If the administrative state is locked or shutting down then normal users are precluded from using the resource.";
      }
      enum FAILED {
        description "The resource has an internal fault that prevents it from operating.";
      }
      enum POWER_OFF {
        description "The resource requires power to be applied and is not powered on.";
      }
      enum OFF_LINE {
        description "The resource requires a routine operation to be performed. This routine operation is to place the resource online and make it available for use. The operation may be manual or automatic, or both. The operational state is disabled.";
      }
      enum OFF_DUTY {
        description "The resource has been made inactive by an internal control process.";
      }
      enum DEPENDENCY {
        description "The resource cannot operate because some other resource on which it depends is unavailable.";
      }
      enum DEGRADED {
        description "The service available from the resource is degraded in some respect.";
      }
      enum NOT_INSTALLED {
        description "The resource represented by the managed object is not present, or is incomplete.";
      }
      enum LOG_FULL {
        description "This indicates a log full condition.";
      }
      enum DEPENDENCY_LOCKED {
        description "The administrative state of a resource that this resource depends on is locked. or the availability status of the other resource is dependency locked.";
      }
      enum DEPENDENCY_FAILED {
        description "The availability status of a resource that this resource depends on is failed or dependency failed.";
      }
      enum DEPENDENCY_SHUTTINGDOWN {
        description "The administrative state of a resource that this resource depends on is shutting down. or the availability status of the other resource is dependency shutting down.";
      }
    }
  }
  typedef OperState {
    description "The operational states of a resource.";
    type enumeration {
      enum DISABLED {
        description "The resource is totally inoperable.";
      }
      enum ENABLED {
        description "The resource is partially or fully operable.";
      }
    }
  }
  typedef PortDirection {
    description "The direction of the synchronization interface.";
    type enumeration {
      enum INPUT_ONLY {
        description "The port can only input signals. It cannot output any signals.";
      }
      enum OUTPUT_ONLY {
        description "The port can only output signals. It cannot input any signals.";
      }
    }
  }
  typedef SyncIOMode {
    description "Frequency mode of the synchronization IO port.";
    type enumeration {
      enum UNKNOWN_MODE {
        description "Unknown mode.";
      }
      enum FREQUENCY_1PPS {
        description "Frequency synchronization IO works in 1PPS mode.";
      }
      enum FREQUENCY_2_MHZ {
        description "Frequency synchronization IO works in 2 MHz mode.";
      }
      enum FREQUENCY_10_MHZ {
        description "Frequency synchronization IO works in 10 MHz mode.";
      }
    }
  }
  grouping FrequencySyncIO-attributes {
    leaf adminPortDirection {
      description "Specifies the port direction of the frequency synchronization IO port.; Default value: INPUT_ONLY.";
      type enumeration {
        enum INPUT_ONLY;
        enum OUTPUT_ONLY;
      }
      status deprecated;
      default "INPUT_ONLY";
    }
    leaf-list availabilityStatus {
      description "The availability status. It contains details about operationalState..";
      type AvailStatus;
      min-elements 0;
    }
    leaf encapsulation {
      description "Reference to the underlying encapsulation, which must be a SyncPort MO..";
      type string;
      mandatory true;
    }
    leaf frequencySyncIOId {
      description "The value component of the RDN..";
      type string;
      mandatory true;
    }
    leaf operationalState {
      description "The operational state..";
      type enumeration {
        enum DISABLED;
        enum ENABLED;
      }
      config false;
    }
    leaf operPortMode {
      description "Indicates the frequency mode of the frequency synchronization IO..";
      type enumeration {
        enum UNKNOWN_MODE;
        enum FREQUENCY_1PPS;
        enum FREQUENCY_2_MHZ;
        enum FREQUENCY_10_MHZ;
      }
      config false;
    }
    leaf-list reservedBy {
      description "Contains a list of MO instances that reserve this MO instance..";
      type string;
      min-elements 0;
    }
  }
}
