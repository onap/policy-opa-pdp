module ericsson-fan-group-radio {
  yang-version 1.1;
  namespace "urn:com:ericsson:ecim:ReqFanGroup";
  prefix fangrrdo;
  import ietf-inet-types {
    prefix ietfinet;
  }
  import ericsson-equip-radio {
    prefix equiprdo;
  }
  import ericsson-cabinet-radio {
    prefix cabrdo;
  }
  import ericsson-managed-element {
    prefix emael;
  }
  description "Auto-generated from Ericsson CPI MOM XML 15554-lza7016014_33-v1uenfk.xml\n.";
  revision "2026-03-29" {
    description "Ericsson G3G4, version: CXP2020502/2-R32C08";
  }

  augment "/emael:ManagedElement/equiprdo:Equipment/cabrdo:Cabinet" {
    list FanGroup {
      description "Additional definitions from MOM:min/max-elements:0/unbounded;root;systemCreated; This MO models a fan group. A fan group is one or more fans which are supervised and controlled as a group. The MO ID will match the physical fan group ID. Number of MOs created depends on cabinet type and climate system. The RDNs of these MOs are FanGroup=1, FanGroup=2, and so on. Dependencies: Can only exist in the node when the attribute supportSystemControl on MO EquipmentSupportFunction is set to true.";
      key "fanGroupId";
      leaf fanGroupId {
        type leafref {
          path "../attributes/fanGroupId";
        }
      }
      container attributes {
      uses FanGroup-attributes;
      }
    }
  }
  typedef ApcIndicatorStatus {
    description "Possible states for green, yellow and red indicators. Since the semantics of the different indicator states depend on the color of the indicator, the semantics is described as part of the corresponding indicator status attribute description.";
    type enumeration {
      enum NOT_APPLICABLE {
        description "The indicator is not supported.";
      }
      enum NOT_AVAILABLE {
        description "The indicator state is currently not available.";
      }
      enum OFF {
        description "The indicator is off.";
      }
      enum STEADY_ON {
        description "The indicator is on continuously.";
      }
      enum SLOW_BLINK {
        description "The indicator blinks slowly.";
      }
      enum FAST_BLINK {
        description "The indicator blinks quickly.";
      }
      enum DOUBLE_FLASH_AND_STEADY_ON {
        description "The indicator blinks twice and is then on for a short time. This cycle is then repeated.";
      }
      enum DOUBLE_FLASH_AND_OFF {
        description "The indicator blinks twice and is then off for a short time. This cycle is then repeated.";
      }
    }
  }
  grouping FanGroup-attributes {
    leaf fanGroupFaultIndicator {
      description "The current fault indicator status of the fan group shown by the optical fan group fault indicator on the Support Control Unit (SCU). Possible values: • NOT_APPLICABLE = This indicator is not supported. • NOT_AVAILABLE = The indicator state is currently not available. • OFF = Fans connected and no fault exists in this unit. • STEADY_ON = A fan fault exists in this unit. • SLOW_BLINK = A fan in this unit is disconnected..";
      type enumeration {
        enum NOT_APPLICABLE;
        enum NOT_AVAILABLE;
        enum OFF;
        enum STEADY_ON;
        enum SLOW_BLINK;
        enum FAST_BLINK;
        enum DOUBLE_FLASH_AND_STEADY_ON;
        enum DOUBLE_FLASH_AND_OFF;
      }
      config false;
    }
    leaf fanPort {
      description "The physical port where the fan is connected.; range 1..10.";
      type ietfinet:port-number;
      config false;
    }
    leaf fanGroupId {
      description "The value component of the RDN..";
      type string;
      mandatory true;
    }
  }
}
