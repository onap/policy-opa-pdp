module ericsson-qos-system-rtn-radio {
  yang-version 1.1;
  namespace "urn:com:ericsson:ecim:RtnQoSSystem";
  prefix qossysrdo;
  import ericsson-l2-eth-port-rtn-radio {
    prefix l2ethptrdo;
  }
  import ericsson-yang-types {
    prefix eytypes;
  }
  import ericsson-managed-element {
    prefix emael;
  }
  description "Auto-generated from Ericsson CPI MOM XML 15554-lza7016014_33-v1uenfk.xml\nQoS system providing (hierarchical) scheduling, queue management, policing, and shaping.";
  revision "2026-03-29" {
    description "Ericsson G3G4, version: CXP2020502/2-R32C08";
  }

  augment "/emael:ManagedElement/emael:Transport/l2ethptrdo:EthernetPort" {
    list QueueSystem {
      description "Additional definitions from MOM:min/max-elements:0/1;root; Quality of Service (QoS) queue system. Bandwidth and sizes (burst sizes, queue sizes) include the complete Ethernet frame. Dependencies: Must have one child element.";
      key "queueSystemId";
      leaf queueSystemId {
        type leafref {
          path "../attributes/queueSystemId";
        }
      }
      container attributes {
      uses QueueSystem-attributes;
      }
    }
  }

  augment "/emael:ManagedElement/emael:Transport/l2ethptrdo:EthernetPort/qossysrdo:QueueSystem/qossysrdo:QoSClassifier/qossysrdo:DscpToPCPMap" {
    list DscpSetToPCP {
      description "Additional definitions from MOM:min/max-elements:0/unbounded; Mapping of a set of DSCP values to a PCP.";
      key "dscpSetToPCPId";
      leaf dscpSetToPCPId {
        type leafref {
          path "../attributes/dscpSetToPCPId";
        }
      }
      container attributes {
      uses DscpSetToPCP-attributes;
      }
    }
  }

  augment "/emael:ManagedElement/emael:Transport/l2ethptrdo:EthernetPort/qossysrdo:QueueSystem/qossysrdo:QoSClassifier/qossysrdo:PcpToQueueMap" {
    list PcpSetToQueue {
      description "Additional definitions from MOM:min/max-elements:0/unbounded; Mapping of a set of PCP values to a queue.";
      key "pcpSetToQueueId";
      leaf pcpSetToQueueId {
        type leafref {
          path "../attributes/pcpSetToQueueId";
        }
      }
      container attributes {
      uses PcpSetToQueue-attributes;
      }
    }
  }

  augment "/emael:ManagedElement/emael:Transport/l2ethptrdo:EthernetPort/qossysrdo:QueueSystem/qossysrdo:QoSClassifier" {
    list DscpToPCPMap {
      description "Additional definitions from MOM:min/max-elements:0/1; A DSCP to PCP map.";
      key "dscpToPCPMapId";
      leaf dscpToPCPMapId {
        type leafref {
          path "../attributes/dscpToPCPMapId";
        }
      }
      container attributes {
      uses DscpToPCPMap-attributes;
      }
    }
  }

  augment "/emael:ManagedElement/emael:Transport/l2ethptrdo:EthernetPort/qossysrdo:QueueSystem/qossysrdo:QoSClassifier" {
    list PcpToQueueMap {
      description "Additional definitions from MOM:min/max-elements:1/unbounded; PCP to queue map.";
      key "pcpToQueueMapId";
      leaf pcpToQueueMapId {
        type leafref {
          path "../attributes/pcpToQueueMapId";
        }
      }
      container attributes {
      uses PcpToQueueMap-attributes;
      }
    }
  }

  augment "/emael:ManagedElement/emael:Transport/l2ethptrdo:EthernetPort/qossysrdo:QueueSystem" {
    list QoSClassifier {
      description "Additional definitions from MOM:min/max-elements:1/1; Container of QoS Classifier schemes.";
      key "qosClassifierId";
      leaf qosClassifierId {
        type leafref {
          path "../attributes/qosClassifierId";
        }
      }
      container attributes {
      uses QoSClassifier-attributes;
      }
    }
  }

  augment "/emael:ManagedElement/emael:Transport/l2ethptrdo:EthernetPort/qossysrdo:QueueSystem" {
    list QueueRed {
      description "Additional definitions from MOM:min/max-elements:0/1; Represents queue using Random Early Detection (RED) packet-dropping strategy.";
      key "queueRedId";
      leaf queueRedId {
        type leafref {
          path "../attributes/queueRedId";
        }
      }
      container attributes {
      uses QueueRed-attributes;
      }
    }
  }

  augment "/emael:ManagedElement/emael:Transport/l2ethptrdo:EthernetPort/qossysrdo:QueueSystem" {
    list QueueTailDrop {
      description "Additional definitions from MOM:min/max-elements:0/1; Represents queue using tail-drop packet-dropping strategy.";
      key "queueTailDropId";
      leaf queueTailDropId {
        type leafref {
          path "../attributes/queueTailDropId";
        }
      }
      container attributes {
      uses QueueTailDrop-attributes;
      }
    }
  }

  augment "/emael:ManagedElement/emael:Transport/l2ethptrdo:EthernetPort/qossysrdo:QueueSystem" {
    list SchedulerDwrr {
      description "Additional definitions from MOM:min/max-elements:0/1; Represents Deficit Weighted Round Robin (DWRR) scheduler. In hierarchical QoS context, SchedulerDwrr MO can contain multiple MO types as SchedulerDwrr, SchedulerSp, Shaper, QueueRed and QueueTailDrop as its children to construct hierarchical tree. Dependencies: SchedulerDwrr MO can have maximum 8 children.";
      key "schedulerDwrrId";
      leaf schedulerDwrrId {
        type leafref {
          path "../attributes/schedulerDwrrId";
        }
      }
      container attributes {
      uses SchedulerDwrr-attributes;
      }
    }
  }

  augment "/emael:ManagedElement/emael:Transport/l2ethptrdo:EthernetPort/qossysrdo:QueueSystem" {
    list SchedulerSp {
      description "Additional definitions from MOM:min/max-elements:0/1; Represents Strict Priority (SP) scheduler. In hierarchical QoS context, scheduler can contain multiple queues, and/or schedulers, and/or shapers as its children to construct hierarchical tree.";
      key "schedulerSpId";
      leaf schedulerSpId {
        type leafref {
          path "../attributes/schedulerSpId";
        }
      }
      container attributes {
      uses SchedulerSp-attributes;
      }
    }
  }

  augment "/emael:ManagedElement/emael:Transport/l2ethptrdo:EthernetPort/qossysrdo:QueueSystem" {
    list Shaper {
      description "Additional definitions from MOM:min/max-elements:0/1; Represents traffic shaping entity supporting: 1B1R.";
      key "shaperId";
      leaf shaperId {
        type leafref {
          path "../attributes/shaperId";
        }
      }
      container attributes {
      uses Shaper-attributes;
      }
    }
  }

  augment "/emael:ManagedElement/emael:Transport/l2ethptrdo:EthernetPort/qossysrdo:QueueSystem/qossysrdo:SchedulerDwrr" {
    list QueueRed {
      description "Additional definitions from MOM:min/max-elements:0/8; Represents queue using Random Early Detection (RED) packet-dropping strategy.";
      key "queueRedId";
      leaf queueRedId {
        type leafref {
          path "../attributes/queueRedId";
        }
      }
      container attributes {
      uses QueueRed-attributes;
      }
    }
  }

  augment "/emael:ManagedElement/emael:Transport/l2ethptrdo:EthernetPort/qossysrdo:QueueSystem/qossysrdo:SchedulerDwrr" {
    list QueueTailDrop {
      description "Additional definitions from MOM:min/max-elements:0/8; Represents queue using tail-drop packet-dropping strategy.";
      key "queueTailDropId";
      leaf queueTailDropId {
        type leafref {
          path "../attributes/queueTailDropId";
        }
      }
      container attributes {
      uses QueueTailDrop-attributes;
      }
    }
  }

  augment "/emael:ManagedElement/emael:Transport/l2ethptrdo:EthernetPort/qossysrdo:QueueSystem/qossysrdo:SchedulerDwrr" {
    list SchedulerDwrr {
      description "Additional definitions from MOM:min/max-elements:0/8; Represents Deficit Weighted Round Robin (DWRR) scheduler. In hierarchical QoS context, SchedulerDwrr MO can contain multiple MO types as SchedulerDwrr, SchedulerSp, Shaper, QueueRed and QueueTailDrop as its children to construct hierarchical tree. Dependencies: SchedulerDwrr MO can have maximum 8 children.";
      key "schedulerDwrrId";
      leaf schedulerDwrrId {
        type leafref {
          path "../attributes/schedulerDwrrId";
        }
      }
      container attributes {
      uses SchedulerDwrr-attributes;
      }
    }
  }

  augment "/emael:ManagedElement/emael:Transport/l2ethptrdo:EthernetPort/qossysrdo:QueueSystem/qossysrdo:SchedulerDwrr" {
    list SchedulerSp {
      description "Additional definitions from MOM:min/max-elements:0/8; Represents Strict Priority (SP) scheduler. In hierarchical QoS context, scheduler can contain multiple queues, and/or schedulers, and/or shapers as its children to construct hierarchical tree.";
      key "schedulerSpId";
      leaf schedulerSpId {
        type leafref {
          path "../attributes/schedulerSpId";
        }
      }
      container attributes {
      uses SchedulerSp-attributes;
      }
    }
  }

  augment "/emael:ManagedElement/emael:Transport/l2ethptrdo:EthernetPort/qossysrdo:QueueSystem/qossysrdo:SchedulerDwrr" {
    list Shaper {
      description "Additional definitions from MOM:min/max-elements:0/8; Represents traffic shaping entity supporting: 1B1R.";
      key "shaperId";
      leaf shaperId {
        type leafref {
          path "../attributes/shaperId";
        }
      }
      container attributes {
      uses Shaper-attributes;
      }
    }
  }

  augment "/emael:ManagedElement/emael:Transport/l2ethptrdo:EthernetPort/qossysrdo:QueueSystem/qossysrdo:SchedulerSp" {
    list QueueRed {
      description "Additional definitions from MOM:min/max-elements:0/4; Represents queue using Random Early Detection (RED) packet-dropping strategy.";
      key "queueRedId";
      leaf queueRedId {
        type leafref {
          path "../attributes/queueRedId";
        }
      }
      container attributes {
      uses QueueRed-attributes;
      }
    }
  }

  augment "/emael:ManagedElement/emael:Transport/l2ethptrdo:EthernetPort/qossysrdo:QueueSystem/qossysrdo:SchedulerSp" {
    list QueueTailDrop {
      description "Additional definitions from MOM:min/max-elements:0/4; Represents queue using tail-drop packet-dropping strategy.";
      key "queueTailDropId";
      leaf queueTailDropId {
        type leafref {
          path "../attributes/queueTailDropId";
        }
      }
      container attributes {
      uses QueueTailDrop-attributes;
      }
    }
  }

  augment "/emael:ManagedElement/emael:Transport/l2ethptrdo:EthernetPort/qossysrdo:QueueSystem/qossysrdo:SchedulerSp" {
    list SchedulerDwrr {
      description "Additional definitions from MOM:min/max-elements:0/4; Represents Deficit Weighted Round Robin (DWRR) scheduler. In hierarchical QoS context, SchedulerDwrr MO can contain multiple MO types as SchedulerDwrr, SchedulerSp, Shaper, QueueRed and QueueTailDrop as its children to construct hierarchical tree. Dependencies: SchedulerDwrr MO can have maximum 8 children.";
      key "schedulerDwrrId";
      leaf schedulerDwrrId {
        type leafref {
          path "../attributes/schedulerDwrrId";
        }
      }
      container attributes {
      uses SchedulerDwrr-attributes;
      }
    }
  }

  augment "/emael:ManagedElement/emael:Transport/l2ethptrdo:EthernetPort/qossysrdo:QueueSystem/qossysrdo:SchedulerSp" {
    list SchedulerSp {
      description "Additional definitions from MOM:min/max-elements:0/4; Represents Strict Priority (SP) scheduler. In hierarchical QoS context, scheduler can contain multiple queues, and/or schedulers, and/or shapers as its children to construct hierarchical tree.";
      key "schedulerSpId";
      leaf schedulerSpId {
        type leafref {
          path "../attributes/schedulerSpId";
        }
      }
      container attributes {
      uses SchedulerSp-attributes;
      }
    }
  }

  augment "/emael:ManagedElement/emael:Transport/l2ethptrdo:EthernetPort/qossysrdo:QueueSystem/qossysrdo:SchedulerSp" {
    list Shaper {
      description "Additional definitions from MOM:min/max-elements:0/4; Represents traffic shaping entity supporting: 1B1R.";
      key "shaperId";
      leaf shaperId {
        type leafref {
          path "../attributes/shaperId";
        }
      }
      container attributes {
      uses Shaper-attributes;
      }
    }
  }

  augment "/emael:ManagedElement/emael:Transport/l2ethptrdo:EthernetPort/qossysrdo:QueueSystem/qossysrdo:Shaper" {
    list QueueRed {
      description "Additional definitions from MOM:min/max-elements:0/1; Represents queue using Random Early Detection (RED) packet-dropping strategy.";
      key "queueRedId";
      leaf queueRedId {
        type leafref {
          path "../attributes/queueRedId";
        }
      }
      container attributes {
      uses QueueRed-attributes;
      }
    }
  }

  augment "/emael:ManagedElement/emael:Transport/l2ethptrdo:EthernetPort/qossysrdo:QueueSystem/qossysrdo:Shaper" {
    list QueueTailDrop {
      description "Additional definitions from MOM:min/max-elements:0/1; Represents queue using tail-drop packet-dropping strategy.";
      key "queueTailDropId";
      leaf queueTailDropId {
        type leafref {
          path "../attributes/queueTailDropId";
        }
      }
      container attributes {
      uses QueueTailDrop-attributes;
      }
    }
  }

  augment "/emael:ManagedElement/emael:Transport/l2ethptrdo:EthernetPort/qossysrdo:QueueSystem/qossysrdo:Shaper" {
    list SchedulerDwrr {
      description "Additional definitions from MOM:min/max-elements:0/1; Represents Deficit Weighted Round Robin (DWRR) scheduler. In hierarchical QoS context, SchedulerDwrr MO can contain multiple MO types as SchedulerDwrr, SchedulerSp, Shaper, QueueRed and QueueTailDrop as its children to construct hierarchical tree. Dependencies: SchedulerDwrr MO can have maximum 8 children.";
      key "schedulerDwrrId";
      leaf schedulerDwrrId {
        type leafref {
          path "../attributes/schedulerDwrrId";
        }
      }
      container attributes {
      uses SchedulerDwrr-attributes;
      }
    }
  }

  augment "/emael:ManagedElement/emael:Transport/l2ethptrdo:EthernetPort/qossysrdo:QueueSystem/qossysrdo:Shaper" {
    list SchedulerSp {
      description "Additional definitions from MOM:min/max-elements:0/1; Represents Strict Priority (SP) scheduler. In hierarchical QoS context, scheduler can contain multiple queues, and/or schedulers, and/or shapers as its children to construct hierarchical tree.";
      key "schedulerSpId";
      leaf schedulerSpId {
        type leafref {
          path "../attributes/schedulerSpId";
        }
      }
      container attributes {
      uses SchedulerSp-attributes;
      }
    }
  }
  grouping CbsInShaper-struct {
    description "Union to wrap different unit forms for attribute committedBurstSize in Shaper.";
    leaf bytes {
      type string;
    }
  }
  grouping CirInShaper-struct {
    description "Union to wrap different unit forms for attribute committedInformationRate in Shaper.";
    leaf kbps {
      type string;
    }
  }
  grouping MaxThresholdForRed-struct {
    description "The maximum threshold for RED.";
    leaf percent {
      type string;
    }
  }
  grouping MinThresholdForRed-struct {
    description "The minimum threshold for RED.";
    leaf percent {
      type string;
    }
  }
  grouping QueueSizeForRed-struct {
    description "The queue size for RED.";
    leaf bytes {
      type string;
    }
  }
  grouping QueueSizeForTailDrop-struct {
    description "The queue size for TailDrop.";
    leaf bytes {
      type string;
    }
  }
  grouping DscpSetToPCP-attributes {
    leaf dscpSet {
      description "A set of DSCP values..";
      type string {
        pattern "(([0-9]|[0-5][0-9]|6[0-3])(, ([0-9]|[0-5][0-9]|6[0-3]))*)";
      }
      mandatory true;
    }
    leaf dscpSetToPCPId {
      description "The value component of the RDN..";
      type string;
      mandatory true;
    }
    leaf pcp {
      description "The PCP value.; range 0..7.";
      type eytypes:uint8_range_0-7;
      mandatory true;
    }
    leaf userLabel {
      description "Label for free use.; length 1..128.";
      type string {
        length "1..128";
      }
    }
  }
  grouping DscpToPCPMap-attributes {
    leaf defaultPCP {
      description "The default PCP is chosen if no match on DSCP value can be found.; range 0..7.";
      type eytypes:uint8_range_0-7;
      mandatory true;
    }
    leaf dscpToPCPMapId {
      description "The value component of the RDN..";
      type string;
      mandatory true;
    }
    leaf userLabel {
      description "Label for free use.; length 1..128.";
      type string {
        length "1..128";
      }
    }
  }
  grouping PcpSetToQueue-attributes {
    leaf pcpSet {
      description "A set of PCP values..";
      type string {
        pattern "([0-7](, [0-7])*)";
      }
      mandatory true;
    }
    leaf pcpSetToQueueId {
      description "The value component of the RDN..";
      type string;
      mandatory true;
    }
    leaf queue {
      description "A reference to the queue..";
      type string;
      mandatory true;
    }
  }
  grouping PcpToQueueMap-attributes {
    leaf defaultQueue {
      description "The default queue is chosen if no match on PCP value can be found..";
      type string;
      mandatory true;
    }
    leaf pcpToQueueMapId {
      description "The value component of the RDN..";
      type string;
      mandatory true;
    }
    leaf-list reservedBy {
      description "Contains a list of MO instances that reserve this MO instance..";
      type string;
      min-elements 0;
    }
    leaf userLabel {
      description "Label for free use.; length 1..128.";
      type string {
        length "1..128";
      }
    }
  }
  grouping QoSClassifier-attributes {
    leaf qosClassifierId {
      description "The value component of the RDN..";
      type string;
      mandatory true;
    }
  }
  grouping QueueRed-attributes {
    leaf exponentWeight {
      description "The averaging weight factor used by the RED drop mechanism. The weight factor is used when calculating the average queue length and it is represented as the parameter n in the following formula: average_queue_length = old_average_queue_length * (1 - 2^-n) + current_queue_length * 2^-n, where 2^-n means: 2 raised to the power of –n. The averaging weight factor controls the sensitivity to bursts and rapid changes in the current queue length. Setting the averaging weight factor too high causes the average queue length to respond too slowly to changes in the current queue size, thus not reacting to congestion. Setting the averaging weight factor too low causes the average queue length to respond too fast to changes in the actual queue size, thus overreacting to bursts and dropping packets unnecessarily. Guideline: The egress bandwidth and the average packet size should influence the choice of this attribute value..";
      type string;
    }
    list maxThreshold {
      key "id";
      leaf id {
        type uint32;
        description "Synthetic key for struct attribute.";
      }
      min-elements 1;
      description "The maximum threshold for RED. When the average queue length is above the minimum threshold, RED starts dropping packets. The rate of packet drop increases linearly as the average queue length increases until the average queue length reaches the maximum threshold. When the average queue length is above the maximum threshold, all packets are dropped..";
      uses MaxThresholdForRed-struct;
    }
    list minThreshold {
      key "id";
      leaf id {
        type uint32;
        description "Synthetic key for struct attribute.";
      }
      min-elements 1;
      description "The minimum threshold for RED. When the average queue length is above the minimum threshold, RED starts dropping packets. The rate of packet drop increases linearly as the average queue length increases until the average queue length reaches the maximum threshold. When the average queue length is above the maximum threshold, all packets are dropped..";
      uses MinThresholdForRed-struct;
    }
    leaf order {
      description "If parent is SchedulerDwrr MO or SchedulerSP MO, this attribute indicates unique index amongst its children. If parent is SchedulerSP MO, this index denotes scheduling priority.; Default value: 0.";
      type uint16;
      default "0";
    }
    leaf queueRedId {
      description "The value component of the RDN..";
      type string;
      mandatory true;
    }
    list queueSize {
      key "id";
      leaf id {
        type uint32;
        description "Synthetic key for struct attribute.";
      }
      min-elements 1;
      description "Maximum queue length..";
      uses QueueSizeForRed-struct;
    }
    leaf-list reservedBy {
      description "Contains a list of MO instances that reserve this MO instance..";
      type string;
      min-elements 0;
    }
    leaf userLabel {
      description "Label for free use.; length 1..128.";
      type string {
        length "1..128";
      }
    }
    leaf queueHCInPkts {
      description "The number (64-bit) of packets transmitted into the queue. Unit: Packets.";
      type uint64;
      config false;
    }
    leaf filledUpperThreshold {
      description "The number (64-bit) of samples, taken a 1000 times per ROP, when a queue is filled more than 80% of its size..";
      type uint64;
      config false;
    }
    leaf queueHCDroppedOctets {
      description "The number (64-bit) of octets discarded by the queue. Ethernet header, payload and FCS are counted. Unit: Octets.";
      type uint64;
      config false;
    }
    leaf queueHCOutPkts {
      description "The number (64-bit) of packets transmitted by the queue. Ethernet header, payload and FCS are counted. Unit: Octets.";
      type uint64;
      config false;
    }
    leaf filledLowerThreshold {
      description "The number (64-bit) of samples, taken a 1000 times per ROP, when a queue is filled more than 20% of its size..";
      type uint64;
      config false;
    }
    leaf queueHCDroppedPkts {
      description "The number (64-bit) of packets discarded by the queue. Unit: Packets; MOM flags: noNotification.";
      type uint64;
      config false;
      status deprecated;
    }
    leaf queueHCOutOctets {
      description "The number (64-bit) of octets transmitted by the queue. Ethernet header, payload and FCS are counted. Unit: Octets.";
      type uint64;
      config false;
    }
    leaf queueHCInOctets {
      description "The number (64-bit) of octets transmitted into the queue. Ethernet header, payload and FCS are counted. Unit: Octets.";
      type uint64;
      config false;
    }
  }
  grouping QueueSystem-attributes {
    leaf queueSystemId {
      description "The value component of the RDN..";
      type string;
      mandatory true;
    }
  }
  grouping QueueTailDrop-attributes {
    leaf order {
      description "If parent is SchedulerDwrr MO or SchedulerSP MO, this attribute indicates unique index amongst its children. If parent is SchedulerSP MO, this index denotes scheduling priority.; Default value: 0.";
      type uint16;
      default "0";
    }
    list queueSize {
      key "id";
      leaf id {
        type uint32;
        description "Synthetic key for struct attribute.";
      }
      min-elements 1;
      description "Maximum queue length..";
      uses QueueSizeForTailDrop-struct;
    }
    leaf queueTailDropId {
      description "The value component of the RDN..";
      type string;
      mandatory true;
    }
    leaf-list reservedBy {
      description "Contains a list of MO instances that reserve this MO instance..";
      type string;
      min-elements 0;
    }
    leaf userLabel {
      description "Label for free use.; length 1..128.";
      type string {
        length "1..128";
      }
    }
    leaf queueHCOutOctets {
      description "The number (64-bit) of octets transmitted by the queue. Ethernet header, payload and FCS are counted. Unit: Octets.";
      type uint64;
      config false;
    }
    leaf filledLowerThreshold {
      description "The number (64-bit) of samples, taken a 1000 times per ROP, when a queue is filled more than 20% of its size..";
      type uint64;
      config false;
    }
    leaf filledUpperThreshold {
      description "The number (64-bit) of samples, taken a 1000 times per ROP, when a queue is filled more than 80% of its size..";
      type uint64;
      config false;
    }
    leaf queueHCDroppedPkts {
      description "The number (64-bit) of packets discarded by the queue. Unit: Packets; MOM flags: noNotification.";
      type uint64;
      config false;
      status deprecated;
    }
    leaf queueHCDroppedOctets {
      description "The number (64-bit) of octets discarded by the queue. Ethernet header, payload and FCS are counted. Unit: Octets.";
      type uint64;
      config false;
    }
    leaf queueHCInOctets {
      description "The number (64-bit) of octets transmitted into the queue. Ethernet header, payload and FCS are counted. Unit: Octets.";
      type uint64;
      config false;
    }
    leaf queueHCOutPkts {
      description "The number (64-bit) of packets transmitted by the queue. Ethernet header, payload and FCS are counted. Unit: Octets.";
      type uint64;
      config false;
    }
    leaf queueHCInPkts {
      description "The number (64-bit) of packets transmitted into the queue. Unit: Packets.";
      type uint64;
      config false;
    }
  }
  grouping SchedulerDwrr-attributes {
    leaf order {
      description "If parent is SchedulerDwrr MO or SchedulerSP MO, this attribute indicates unique index amongst its children. If parent is SchedulerSP MO, this index denotes scheduling priority.; Default value: 0.";
      type uint16;
      default "0";
    }
    leaf schedulerDwrrId {
      description "The value component of the RDN..";
      type string;
      mandatory true;
    }
    leaf-list schedulingWeight {
      description "Scheduling weight..";
      type uint32;
      ordered-by user;
      min-elements 0;
    }
    leaf userLabel {
      description "Label for free use.; length 1..128.";
      type string {
        length "1..128";
      }
    }
  }
  grouping SchedulerSp-attributes {
    leaf order {
      description "If parent is SchedulerDwrr MO or SchedulerSP MO, this attribute indicates unique index amongst its children. If parent is SchedulerSP MO, this index denotes scheduling priority.; Default value: 0.";
      type uint16;
      default "0";
    }
    leaf schedulerSpId {
      description "The value component of the RDN..";
      type string;
      mandatory true;
    }
    leaf userLabel {
      description "Label for free use.; length 1..128.";
      type string {
        length "1..128";
      }
    }
  }
  grouping Shaper-attributes {
    list committedBurstSize {
      key "id";
      leaf id {
        type uint32;
        description "Synthetic key for struct attribute.";
      }
      min-elements 1;
      description "Committed burst size. If set to less than 4000 bytes, shaper still allows 4000 bytes bursting. If set to more than 64000 bytes, shaper still allows maximum 64000 bytes bursting. Unit: 1 bytes.";
      uses CbsInShaper-struct;
    }
    list committedInformationRate {
      key "id";
      leaf id {
        type uint32;
        description "Synthetic key for struct attribute.";
      }
      min-elements 1;
      description "Committed information rate. If set to less than 1000 kbps, shaper still allows 1000 kbps sending. Only applicable to RAN Compute Group 4 and higher. Unit: 1 kbps.";
      uses CirInShaper-struct;
    }
    leaf order {
      description "If parent is SchedulerDwrr MO or SchedulerSP MO, this attribute indicates unique index amongst its children. If parent is SchedulerSP MO, this index denotes scheduling priority.; Default value: 0.";
      type uint16;
      default "0";
    }
    leaf shaperId {
      description "The value component of the RDN..";
      type string;
      mandatory true;
    }
    leaf userLabel {
      description "Label for free use.; length 1..128.";
      type string {
        length "1..128";
      }
    }
  }
}
