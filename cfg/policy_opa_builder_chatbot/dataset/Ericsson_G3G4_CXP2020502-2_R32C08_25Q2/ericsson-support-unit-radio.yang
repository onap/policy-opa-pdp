module ericsson-support-unit-radio {
  yang-version 1.1;
  namespace "urn:com:ericsson:ecim:ReqSupportUnit";
  prefix supurdo;
  import ericsson-yang-types {
    prefix eytypes;
  }
  import ericsson-equip-radio {
    prefix equiprdo;
  }
  import ericsson-managed-element {
    prefix emael;
  }
  description "Auto-generated from Ericsson CPI MOM XML 15554-lza7016014_33-v1uenfk.xml\n.";
  revision "2026-03-29" {
    description "Ericsson G3G4, version: CXP2020502/2-R32C08";
  }

  augment "/emael:ManagedElement/equiprdo:Equipment" {
    list SupportUnit {
      description "Additional definitions from MOM:min/max-elements:0/unbounded;root;systemCreated; A unit that provides support to adjacent units, in terms of power, climate and/or external alarms. RDNs of these MOs are SupportUnit=1, SupportUnit=2 and so on. Autocreated when the support unit is detected by the system.";
      key "supportUnitId";
      leaf supportUnitId {
        type leafref {
          path "../attributes/supportUnitId";
        }
      }
      container attributes {
      uses SupportUnit-attributes;
      }
    }
  }
  typedef AdmState {
    description "Administrative state of a resource.";
    type enumeration {
      enum LOCKED {
        description "The resource is administratively prohibited from performing services for its users.";
      }
      enum UNLOCKED {
        description "The resource is administratively permitted to perform services for its users. This is independent of its inherent operability.";
      }
      enum SHUTTINGDOWN {
        description "Use of the resource is administratively permitted to existing instances of use only. While the system remains in the shutting down state the manager may at any time cause the managed object to revert to the locked state.";
      }
    }
  }
  typedef AvailStatus {
    description "The availability status is used to qualify the operational state. It indicates why the operational state has changed its value.";
    type enumeration {
      enum IN_TEST {
        description "The resource is undergoing a test procedure. If the administrative state is locked or shutting down, normal users are prevented from using the resource.";
      }
      enum FAILED {
        description "The resource has an internal fault that prevents it from operating.";
      }
      enum POWER_OFF {
        description "The resource requires power to be applied and is not powered on.";
      }
      enum OFF_LINE {
        description "The resource requires a routine operation to be performed. This routine operation is to place the resource online and make it available for use. The operation may be manual or automatic, or both. The operational state is disabled.";
      }
      enum OFF_DUTY {
        description "The resource has been made inactive by an internal control process.";
      }
      enum DEPENDENCY {
        description "The resource cannot operate because some other resource on which it depends is unavailable.";
      }
      enum DEGRADED {
        description "The service available from the resource is degraded in some respect.";
      }
      enum NOT_INSTALLED {
        description "The resource represented by the managed object is not present, or is incomplete.";
      }
      enum LOG_FULL {
        description "Indicates a log full condition. The semantics are defined in CCITT Rec. X.735 | ISO/IEC 10164-6.";
      }
      enum DEPENDENCY_LOCKED {
        description "The administrative state of a resource that this resource depends on is locked. Alternatively, the availability status of the other resource is dependency locked.";
      }
      enum DEPENDENCY_FAILED {
        description "The availability status of a resource that this resource depends on is failed or dependency failed.";
      }
      enum DEPENDENCY_SHUTTINGDOWN {
        description "The administrative state of a resource that this resource depends on is shutting down. Alternatively, the availability status of the other resource is dependency shutting down.";
      }
      enum DEPENDENCY_RECOVERY {
        description "Resource that this resource depends on is undergoing a recovery procedure.";
      }
      enum DEPENDENCY_HOLDING {
        description "Resource cannot operate because some other resource on which it depends is currently unavailable. The situation is expected to be resolved. Actions to facilitate dependency resolution may be ongoing.";
      }
    }
  }
  typedef IndicatorStatus {
    description "IndicatorStatus.";
    type enumeration {
      enum NOT_APPLICABLE {
        description "Indicator is not supported.";
      }
      enum NOT_AVAILABLE {
        description "Indicator state is not available.";
      }
      enum OFF {
        description "Indicator is off.";
      }
      enum STEADY_ON {
        description "Indicator is continuously on.";
      }
      enum SLOW_BLINK {
        description "Indicator blinks slowly.";
      }
      enum FAST_BLINK {
        description "Indicator blinks fast.";
      }
      enum DOUBLE_FLASH_AND_STEADY_ON {
        description "Indicator flashes twice and is then on for a short time. Cycle is repeated.";
      }
      enum DOUBLE_FLASH_AND_OFF {
        description "Indicator flashes twice and is then off for a short time. Cycle is repeated.";
      }
    }
  }
  typedef OperState {
    description "Operational states of a resource.";
    type enumeration {
      enum DISABLED {
        description "The resource is totally inoperable.";
      }
      enum ENABLED {
        description "The resource is partially or fully operable.";
      }
    }
  }
  typedef ProvidedServices {
    description "Services provided by the support unit.";
    type enumeration {
      enum POWER_SUPPLY {
        description "Supplies power.";
      }
      enum POWER_DISTRIBUTION {
        description "Distributes power.";
      }
      enum FAN {
        description "Provides air flow, typically for cooling purposes.";
      }
      enum EXTERNAL_ALARM_PORTS {
        description "Provides external alarm ports.";
      }
      enum BATTERY_BACKUP {
        description "Provides battery backup.";
      }
      enum GENERIC_DEVICE {
        description "Provides generic device.";
      }
    }
  }
  typedef TempMeasType {
    description "Type of temperature measurement supported by support unit.";
    type enumeration {
      enum NOT_SUPPORTED {
        description "Temperature measurement not supported.";
      }
      enum AIR_INLET_TEMP {
        description "Temperature sensor measures air temperature where air flows into enclosure.";
      }
      enum AIR_OUTLET_TEMP {
        description "Temperature sensor measures air temperature where air flows out from enclosure.";
      }
    }
  }
  grouping ApcProductData-struct {
    description ".";
    leaf productionDate {
      description "length 5..8.";
      type string {
        length "5..8";
      }
    }
    leaf productName {
      description "length 1..32.";
      type string {
        length "1..32";
      }
    }
    leaf productNumber {
      description "length 1..24.";
      type string {
        length "1..24";
      }
    }
    leaf productRevision {
      description "length 1..7.";
      type string {
        length "1..7";
      }
    }
    leaf serialNumber {
      description "length 1..13.";
      type string {
        length "1..13";
      }
    }
  }
  grouping SpecialIndicator-struct {
    description "Special indicator data.";
    leaf indicatorStatus {
      type enumeration {
        enum NOT_APPLICABLE;
        enum NOT_AVAILABLE;
        enum OFF;
        enum STEADY_ON;
        enum SLOW_BLINK;
        enum FAST_BLINK;
        enum DOUBLE_FLASH_AND_STEADY_ON;
        enum DOUBLE_FLASH_AND_OFF;
      }
    }
    leaf indicatorName {
      description "length 0..128.";
      type string {
        length "0..128";
      }
    }
  }
  grouping SuAddressInfo-struct {
    description "The address elements of the support unit, one set per host the support unit is connected to. Note that a support unit can be directly connected to one or several hosts by one support unit bus for each host. Alternatively, it can be connected indirectly by another support unit, which in turn is connected to the hosts. If indirectly connected, the support unit is referred to as a \"hosted support unit\".";
    leaf hostObjectReference {
      type string;
    }
    leaf hostPortNumber {
      type string;
    }
    leaf supportUnitBusAddress {
      type string;
    }
    leaf supportUnitHostPortNumber {
      type string;
    }
    leaf hostedSupportUnitReference {
      description "range 0..8.";
      type eytypes:int32_range_0-8;
    }
  }
  grouping SupportUnit-attributes {
    leaf supportUnitId {
      description "The value component of the RDN..";
      type string;
      mandatory true;
    }
    leaf administrativeState {
      description "Defines the administrative state..";
      type enumeration {
        enum LOCKED;
        enum UNLOCKED;
        enum SHUTTINGDOWN;
      }
    }
    leaf-list availabilityStatus {
      description "The availability status. It contains details about operationalState..";
      type AvailStatus;
      min-elements 0;
    }
    leaf operationalState {
      description "Defines the operational state..";
      type enumeration {
        enum DISABLED;
        enum ENABLED;
      }
      config false;
    }
    leaf faultIndicator {
      description "Fault status of support unit as shown by fault indicator of unit..";
      type enumeration {
        enum NOT_APPLICABLE;
        enum NOT_AVAILABLE;
        enum OFF;
        enum STEADY_ON;
        enum SLOW_BLINK;
        enum FAST_BLINK;
        enum DOUBLE_FLASH_AND_STEADY_ON;
        enum DOUBLE_FLASH_AND_OFF;
      }
      config false;
    }
    leaf operationalIndicator {
      description "Operational status of support unit as shown by operational indicator of the unit..";
      type enumeration {
        enum NOT_APPLICABLE;
        enum NOT_AVAILABLE;
        enum OFF;
        enum STEADY_ON;
        enum SLOW_BLINK;
        enum FAST_BLINK;
        enum DOUBLE_FLASH_AND_STEADY_ON;
        enum DOUBLE_FLASH_AND_OFF;
      }
      config false;
    }
    list productData {
      config false;
      description "Product data of the support unit..";
      uses ApcProductData-struct;
    }
    leaf-list providedServices {
      description "Services provided by the support unit..";
      type ProvidedServices;
      min-elements 0;
    }
    leaf-list reservedBy {
      description "Contains a list of MO instances that reserve this MO instance..";
      type string;
      min-elements 0;
    }
    list specialIndicator {
      config false;
      min-elements 0;
      uses SpecialIndicator-struct;
    }
    list suAddressInfo {
      config false;
      min-elements 0;
      uses SuAddressInfo-struct;
    }
    leaf commandResult {
      description "Result of sendCommand action, not interpreted by the system.; length 1..64.";
      type string {
        length "1..64";
      }
      config false;
    }
    leaf fanTrayTemperatureMeasurementType {
      description "Type of fan tray temperature measurement supported by support unit. Only applicable to SupportUnit instance with providedServices = FAN..";
      type enumeration {
        enum NOT_SUPPORTED;
        enum AIR_INLET_TEMP;
        enum AIR_OUTLET_TEMP;
      }
      config false;
    }
    leaf-list pmFanSpeed {
      description "Average fan tray unit fan speed. [0]: Average fan speed from 0 to 299 seconds of ROP, % of maximum fan speed. [1]: Average fan speed from 300 to 599 seconds of ROP, % of maximum fan speed. [2]: Average fan speed from 600 to 899 seconds of ROP, % of maximum fan speed..";
      type int32;
      max-elements 3;
    }
    leaf-list pmFanOperatingTemperature {
      description "Average fan operating temperature. The temperature is calculated as average air inlet temperature, or average air outlet temperature depending on fan tray type. Measured air temperature from fan tray is reported with offset of +1000. To convert it to degree Celsius, use following formula: T = (value_reported - 1000)/10. [0]: Average unit temperature 0 to 299 seconds of ROP. [1]: Average unit temperature 300 to 599 seconds of ROP. [2]: Average unit temperature 600 to 899 seconds of ROP..";
      type int32;
      max-elements 3;
    }
  }
}
