module ericsson-consumed-energy-measurement-radio {
  yang-version 1.1;
  namespace "urn:com:ericsson:ecim:ReqConsumedEnergyMeasurement";
  prefix cenmrntrdo;
  import ericsson-rmesupport-radio {
    prefix rmesuppo;
  }
  import ericsson-managed-element {
    prefix emael;
  }
  description "Auto-generated from Ericsson CPI MOM XML 15554-lza7016014_33-v1uenfk.xml\nEcimMOM for ConsumedEnergyMeasurement MO";
  revision "2026-03-29" {
    description "Ericsson G3G4, version: CXP2020502/2-R32C08";
  }

  augment "/emael:ManagedElement/rmesuppo:NodeSupport" {
    list ConsumedEnergyMeasurement {
      description "Additional definitions from MOM:min/max-elements:1/1;root;systemCreated; This MO displays the energy consumption by Radio and Baseband units in the node. The RDN of this MO is ConsumedEnergyMeasurement=1.";
      key "consumedEnergyMeasurementId";
      leaf consumedEnergyMeasurementId {
        type leafref {
          path "../attributes/consumedEnergyMeasurementId";
        }
      }
      container attributes {
      uses ConsumedEnergyMeasurement-attributes;
      }
    }
  }
  grouping ConsumedEnergyMeasurement-attributes {
    leaf consumedEnergyMeasurementId {
      description "The value component of the RDN..";
      type string;
      mandatory true;
    }
    leaf-list reservedBy {
      description "Managed object instances that reserves this managed object instance. References to energy meters included in the PM counters..";
      type string;
      ordered-by user;
      min-elements 0;
    }
    leaf noOfContributingUnits {
      description "Number of energy meters of Radio units and Baseband units. Divide noOfContributingUnits with totalNumberOfUnits to get the ratio of contributing Radio and Baseband units..";
      type int16;
      config false;
    }
    leaf totalNumberOfUnits {
      description "Total number of Radio units and Baseband units in the node..";
      type int16;
      config false;
    }
    leaf-list pmPowerConsumption {
      description "Average power consumption in 6 second periods. Sums up power consumption of all consumer units having an EnergyMeter. Unit: 1 W.";
      type int32;
      max-elements 150;
    }
    leaf-list pmVoltage {
      description "Average voltage in 6 second periods. Sums up voltage of all consumer units having an EnergyMeter. Deprecated: Since 17.Q3. Has no functional behaviour. Planned to be removed..";
      type int32;
      max-elements 150;
    }
    leaf pmConsumedEnergyAccumulated {
      description "Sum of accumulated energy consumption from start for all consumer units with an EnergyMeter. Unit: 1 Wh.";
      type uint64;
      config false;
    }
    leaf pmConsumedEnergy {
      description "Energy consumed during each ROP. Sums up energy consumption of all consumer units having an EnergyMeter. Unit: 1 Wh.";
      type uint32;
      config false;
    }
  }
}
