module ericsson-alarm-port-radio {
  yang-version 1.1;
  namespace "urn:com:ericsson:ecim:ReqAlarmPort";
  prefix alprtrdo;
  import ericsson-yang-types {
    prefix eytypes;
  }
  import ericsson-equip-radio {
    prefix equiprdo;
  }
  import ericsson-field-replaceable-unit-radio {
    prefix frurdo;
  }
  import ericsson-managed-element {
    prefix emael;
  }
  description "Auto-generated from Ericsson CPI MOM XML 15554-lza7016014_33-v1uenfk.xml\n.";
  revision "2026-03-29" {
    description "Ericsson G3G4, version: CXP2020502/2-R32C08";
  }

  augment "/emael:ManagedElement/equiprdo:Equipment/frurdo:FieldReplaceableUnit" {
    list AlarmPort {
      description "Additional definitions from MOM:min/max-elements:0/unbounded;root; This MO models an Alarm Port. It is used to detect a fault indication from external equipment and report it as external alarm to the Network Management System.";
      key "alarmPortId";
      leaf alarmPortId {
        type leafref {
          path "../attributes/alarmPortId";
        }
      }
      container attributes {
      uses AlarmPort-attributes;
      }
    }
  }
  typedef AdmState {
    description "Administrative state of a resource.";
    type enumeration {
      enum LOCKED {
        description "The resource is administratively prohibited from performing services for its users.";
      }
      enum UNLOCKED {
        description "The resource is administratively permitted to perform services for its users. This is independent of its inherent operability.";
      }
      enum SHUTTINGDOWN {
        description "Use of the resource is administratively permitted to existing instances of use only. While the system remains in the shutting down state the manager may at any time cause the managed object to revert to the locked state.";
      }
    }
  }
  typedef ApcFilterAlgorithm {
    type enumeration {
      enum NONE {
      }
      enum FIXED {
      }
      enum AUTO {
      }
    }
  }
  typedef ApcPerceivedSeverity {
    description "This parameter provides an indication of how it is perceived that the capability of the managed object has been affected.";
    type enumeration {
      enum CRITICAL {
        description "The Critical severity level indicates that a service affecting condition has occurred and an immediate corrective action is required. Such a severity can be reported, for example, when a managed object becomes totally out of service and its capability must be restored.";
      }
      enum MAJOR {
        description "The Major severity level indicates that a service affecting condition has developed and an urgent corrective action is required. Such a severity can be reported, for example, when there is a severe degradation in the capability of the managed object and its full capability must be restored.";
      }
      enum MINOR {
        description "The Minor severity level indicates the existence of a non-service affecting fault condition and that corrective action should be taken in order to prevent a more serious (for example, service affecting) fault. Such a severity can be reported, for example, when the detected alarm condition is not currently degrading the capacity of the managed object.";
      }
      enum WARNING {
        description "The Warning severity level indicates the detection of a potential or impending service affecting fault, before any significant effects have been felt. Action should be taken to further diagnose (if necessary) and correct the problem in order to prevent it from becoming a more serious service affecting fault.";
      }
    }
  }
  typedef AvailStatus {
    description "The availability status is used to qualify the operational state. It indicates why the operational state has changed its value.";
    type enumeration {
      enum IN_TEST {
        description "The resource is undergoing a test procedure. If the administrative state is locked or shutting down, normal users are prevented from using the resource.";
      }
      enum FAILED {
        description "The resource has an internal fault that prevents it from operating.";
      }
      enum POWER_OFF {
        description "The resource requires power to be applied and is not powered on.";
      }
      enum OFF_LINE {
        description "The resource requires a routine operation to be performed. This routine operation is to place the resource online and make it available for use. The operation may be manual or automatic, or both. The operational state is disabled.";
      }
      enum OFF_DUTY {
        description "The resource has been made inactive by an internal control process.";
      }
      enum DEPENDENCY {
        description "The resource cannot operate because some other resource on which it depends is unavailable.";
      }
      enum DEGRADED {
        description "The service available from the resource is degraded in some respect.";
      }
      enum NOT_INSTALLED {
        description "The resource represented by the managed object is not present, or is incomplete.";
      }
      enum LOG_FULL {
        description "Indicates a log full condition. The semantics are defined in CCITT Rec. X.735 | ISO/IEC 10164-6.";
      }
      enum DEPENDENCY_LOCKED {
        description "The administrative state of a resource that this resource depends on is locked. Alternatively, the availability status of the other resource is dependency locked.";
      }
      enum DEPENDENCY_FAILED {
        description "The availability status of a resource that this resource depends on is failed or dependency failed.";
      }
      enum DEPENDENCY_SHUTTINGDOWN {
        description "The administrative state of a resource that this resource depends on is shutting down. Alternatively, the availability status of the other resource is dependency shutting down.";
      }
      enum DEPENDENCY_RECOVERY {
        description "Resource that this resource depends on is undergoing a recovery procedure.";
      }
      enum DEPENDENCY_HOLDING {
        description "Resource cannot operate because some other resource on which it depends is currently unavailable. The situation is expected to be resolved. Actions to facilitate dependency resolution may be ongoing.";
      }
    }
  }
  typedef OperState {
    description "Operational states of a resource.";
    type enumeration {
      enum DISABLED {
        description "The resource is totally inoperable.";
      }
      enum ENABLED {
        description "The resource is partially or fully operable.";
      }
    }
  }
  grouping AlarmPort-attributes {
    leaf alarmPortId {
      description "The value component of the RDN. The value shall match the the number on the physical port..";
      type string;
      mandatory true;
    }
    leaf filterDelay {
      description "Reduces toggling alarm notifications by configuring delay before an alarm is cleared. Subsequent alarm port state changes to active state occurring during this time are reported as one alarm event. Exact time of clearing the alarm is chosen by the system, but not lower than value set.; range 60..28800; Default value: 60.";
      type int32 {
        range "60..28800";
      }
      default "60";
      units "s";
    }
    leaf activeExternalAlarm {
      description "Indicates that an active alarm was sent and an external alarm exists on the port..";
      type boolean;
      config false;
    }
    leaf alarmSlogan {
      description "Specifies the alarm. Used in additional text in the alarm ExternalAlarm.; length 1..63.";
      type string {
        length "1..63";
      }
    }
    leaf userLabel {
      description "Label for free use.; length 1..128.";
      type string {
        length "1..128";
      }
    }
    leaf normallyOpen {
      description "The active state of the alarm port: true = Closing the circuit generates an alarm. false = Opening the circuit generates an alarm.; Default value: true.";
      type boolean;
      default "true";
    }
    leaf administrativeState {
      description "Defines the administrative state. Note: State \"SHUTTING_DOWN\" will immediately be switched to \"LOCKED\"..";
      type enumeration {
        enum LOCKED;
        enum UNLOCKED;
        enum SHUTTINGDOWN;
      }
    }
    leaf-list availabilityStatus {
      description "The availability status. It contains details about operationalState..";
      type AvailStatus;
      min-elements 0;
    }
    leaf operationalState {
      description "Defines the operational state..";
      type enumeration {
        enum DISABLED;
        enum ENABLED;
      }
      config false;
    }
    leaf perceivedSeverity {
      description "The severity level of the alarm ExternalAlarm..";
      type enumeration {
        enum CRITICAL;
        enum MAJOR;
        enum MINOR;
        enum WARNING;
      }
    }
    leaf alarmInExternalMe {
      description "In primary node: whether to distribute alarm status to a secondary node sharing the external equipment or not.; Default value: false.";
      type boolean;
      default "false";
    }
    leaf filterTime {
      description "Alarms shorter than the value set are not reported. An alarm is raised when the alarm port is active for at least the time set. The alarm is cleared when the alarm port is inactive for at least the time set.; range 0..3600; Default value: 0.";
      type eytypes:int32_range_0-3600;
      default "0";
      units "s";
    }
    leaf filterAlgorithm {
      description "Filter algorithm can be used to decrease the number of alarm notifications generated by alarm port based on the value set..";
      type enumeration {
        enum NONE;
        enum FIXED;
        enum AUTO;
      }
    }
  }
}
