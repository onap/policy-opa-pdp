module ericsson-pbr-ipv6-rtn-radio {
  yang-version 1.1;
  namespace "urn:com:ericsson:ecim:RtnPBRIPv6";
  prefix pbrv6rdo;
  import ericsson-l3-router-rtn-radio {
    prefix l3rtrdo;
  }
  import ericsson-managed-element {
    prefix emael;
  }
  description "Auto-generated from Ericsson CPI MOM XML 15554-lza7016014_33-v1uenfk.xml\nECIM T Policy Based Routing.";
  revision "2026-03-29" {
    description "Ericsson G3G4, version: CXP2020502/2-R32C08";
  }

  augment "/emael:ManagedElement/emael:Transport/l3rtrdo:Router" {
    list RoutingPolicyIpv6 {
      description "Additional definitions from MOM:min/max-elements:0/64;root; Represents IPv6 routing-policy used for PBR. Referring to routing-policy from IP interface, incoming packets on that IP interface are routed according to classification configured in routing-policy. Referring to routing-policy from Router MO, packets generated by Router MO are routed according to classification configured in routing-policy. Routing policy comprises list of each policy rules, which contains set of criterions and forwarding action. Dependencies: Maximum total number of RoutingPolicyIpv4 and RoutingPolicyIpv6 MOs in node is limited to 64.";
      key "routingPolicyIpv6Id";
      leaf routingPolicyIpv6Id {
        type leafref {
          path "../attributes/routingPolicyIpv6Id";
        }
      }
      container attributes {
      uses RoutingPolicyIpv6-attributes;
      }
    }
  }

  augment "/emael:ManagedElement/emael:Transport/l3rtrdo:Router/pbrv6rdo:RoutingPolicyIpv6" {
    list RoutingRuleIpv6 {
      description "Additional definitions from MOM:min/max-elements:0/16; IPv6 routing rule, which contains criterions and forwarding action attributes.";
      key "routingRuleIpv6Id";
      leaf routingRuleIpv6Id {
        type leafref {
          path "../attributes/routingRuleIpv6Id";
        }
      }
      container attributes {
      uses RoutingRuleIpv6-attributes;
      }
    }
  }

  augment "/emael:ManagedElement/emael:Transport/l3rtrdo:Router/pbrv6rdo:RoutingPolicyIpv6/pbrv6rdo:RoutingRuleIpv6" {
    list NextHop {
      description "Additional definitions from MOM:min/max-elements:1/2; Route information defined by this NextHop MO and its parent RoutingRuleIpv6 MO.";
      key "nextHopId";
      leaf nextHopId {
        type leafref {
          path "../attributes/nextHopId";
        }
      }
      container attributes {
      uses NextHop-attributes;
      }
    }
  }
  typedef PBRNextHopState {
    description "Reachability of next hop and whether NextHop MO is currently active for routing rule.";
    type enumeration {
      enum UNREACHABLE {
        description "NextHop is unreachable.";
      }
      enum AVAILABLE {
        description "NextHop is reachable. Route is not active.";
      }
      enum ACTIVE {
        description "NextHop is reachable. Route is active.";
      }
    }
  }
  grouping NextHop-attributes {
    leaf address {
      description "IP address of next hop gateway of this route..";
      type string;
    }
    leaf adminDistance {
      description "Priority of this NextHop MO relative to other NextHop MOs under same RoutingRuleIpv6 MO. Two NextHop MOs under same RoutingRuleIpv6 MO cannot have same adminDistance value..";
      type string;
    }
    leaf bfdMonitoring {
      description "Whether availability of this route depends on BFD session that monitors next hop gateway. If true, availability of this route depends on session state if BFD session monitors next hop gateway. If false, availability of this route does not depend on session state, even when BFD session monitors next hop gateway. For details on how to enable BFD monitoring of next hop gateway, see InterfaceIPv6::bfdStaticRoutes.; Default value: true.";
      type boolean;
      default "true";
    }
    leaf nextHopId {
      description "Value component of the RDN..";
      type string;
      mandatory true;
    }
    leaf nextHopState {
      description "Reachability of next hop and whether NextHop MO is currently active for routing rule..";
      type enumeration {
        enum UNREACHABLE;
        enum AVAILABLE;
        enum ACTIVE;
      }
      config false;
    }
    leaf reference {
      description "Route traffic from inner network through IPsec VPN connection..";
      type string;
    }
  }
  grouping RoutingPolicyIpv6-attributes {
    leaf-list reservedBy {
      description "Contains a list of MO instances that reserve this MO instance..";
      type string;
      min-elements 0;
    }
    leaf routingPolicyIpv6Id {
      description "Value component of the RDN..";
      type string;
      mandatory true;
    }
    leaf userLabel {
      description "Label for free use.; length 1..128.";
      type string {
        length "1..128";
      }
    }
  }
  grouping RoutingRuleIpv6-attributes {
    leaf addrDst {
      description "IPv6 destination address criterion. This criterion matches IPv6 destination address field against configured subnet address. If value list is empty, any IP address matches this rule..";
      type string;
    }
    leaf addrSrc {
      description "IPv6 source address criterion. This criterion matches IPv6 source address field against configured subnet address. If value list is empty, any IP address matches this rule..";
      type string;
    }
    leaf priority {
      description "Rule priority. Rule priority orders rules within RoutingPolicyIpv6 MO. Ordering is from lesser numerical value towards greater numerical value. Priorities must be unique among rules in given RoutingPolicyIpv6 MO..";
      type string;
      mandatory true;
    }
    leaf routingRuleIpv6Id {
      description "Value component of the RDN..";
      type string;
      mandatory true;
    }
    leaf userLabel {
      description "Label for free use.; length 1..128.";
      type string {
        length "1..128";
      }
    }
  }
}
