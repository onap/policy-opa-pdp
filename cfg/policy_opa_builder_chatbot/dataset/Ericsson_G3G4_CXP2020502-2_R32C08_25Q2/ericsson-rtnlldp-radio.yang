module ericsson-rtnlldp-radio {
  yang-version 1.1;
  namespace "urn:com:ericsson:ecim:RtnLldp";
  prefix rtnlldp;
  import ericsson-managed-element {
    prefix emael;
  }
  description "Auto-generated from Ericsson CPI MOM XML 15554-lza7016014_33-v1uenfk.xml\nLLDP functionality MIM.";
  revision "2026-03-29" {
    description "Ericsson G3G4, version: CXP2020502/2-R32C08";
  }

  augment "/emael:ManagedElement/emael:Transport" {
    list Lldp {
      description "Additional definitions from MOM:min/max-elements:0/1;root; Represents Link Layer Discovery Protocol (LLDP) operation in Baseband. When MO is created, LLDP Rx functionality is enabled on all EthernetPorts. Lldp MO must be created before LLDP Tx functionality can be enabled. LLPD Tx is enabled separately per EthernetPort MO.";
      key "lldpId";
      leaf lldpId {
        type leafref {
          path "../attributes/lldpId";
        }
      }
      container attributes {
      uses Lldp-attributes;
      }
    }
  }
  grouping Lldp-attributes {
    leaf lldpId {
      description "The value component of the RDN..";
      type string;
      mandatory true;
    }
    leaf userLabel {
      description "Label for free use.; length 1..128.";
      type string {
        length "1..128";
      }
    }
  }
}
