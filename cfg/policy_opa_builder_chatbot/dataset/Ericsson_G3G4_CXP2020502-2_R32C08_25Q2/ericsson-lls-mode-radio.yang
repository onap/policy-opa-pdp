module ericsson-lls-mode-radio {
  yang-version 1.1;
  namespace "urn:com:ericsson:ecim:RmeLlsMode";
  prefix llsmrdo;
  import ericsson-rmesupport-radio {
    prefix rmesuppo;
  }
  import ericsson-managed-element {
    prefix emael;
  }
  description "Auto-generated from Ericsson CPI MOM XML 15554-lza7016014_33-v1uenfk.xml\nRepresents preferred fronthaul Lower Layer Split setting.";
  revision "2026-03-29" {
    description "Ericsson G3G4, version: CXP2020502/2-R32C08";
  }

  augment "/emael:ManagedElement/rmesuppo:NodeSupport" {
    list LlsMode {
      description "Additional definitions from MOM:min/max-elements:0/1;root; Represents preferred fronthaul Lower Layer Split setting. The RDN of this MO must be LlsMode=1.";
      key "llsModeId";
      leaf llsModeId {
        type leafref {
          path "../attributes/llsModeId";
        }
      }
      container attributes {
      uses LlsMode-attributes;
      }
    }
  }
  typedef llsModePreferenceType {
    description "Lower Layer Split preference type.";
    type enumeration {
      enum DEFAULT {
        description "Open LLS preference is not set, so default communication is preferred.";
      }
      enum OPEN_LLS {
        description "Open LLS preference is set, so Open LLS communication is preferred.";
      }
    }
  }
  grouping LlsMode-attributes {
    leaf llsModeId {
      description "The value component of the RDN..";
      type string;
      mandatory true;
    }
    leaf llsModePreference {
      description "Open Lower Layer Split type. Used to select Lower Layer Split preference type..";
      type enumeration {
        enum DEFAULT;
        enum OPEN_LLS;
      }
    }
    leaf-list fieldReplaceableUnitRef {
      description "Reference to instances of FieldReplaceableUnit MO. Only applicable if llsModePreference is OPEN_LLS..";
      type string;
      min-elements 0;
    }
  }
}
