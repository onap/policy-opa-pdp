module ericsson-rcslogm-radio {
  yang-version 1.1;
  namespace "urn:com:ericsson:ecim:RcsLogM";
  prefix rcslogm;
  import ericsson-managed-element {
    prefix emael;
  }
  description "Auto-generated from Ericsson CPI MOM XML 15554-lza7016014_33-v1uenfk.xml\nThis is the model for the log management fragment.";
  revision "2026-03-29" {
    description "Ericsson G3G4, version: CXP2020502/2-R32C08";
  }

  augment "/emael:ManagedElement/emael:SystemFunctions" {
    list LogM {
      description "Additional definitions from MOM:min/max-elements:1/1;root;systemCreated; Enables configuration of the LogM general properties. This is the root MO for the log management fragment. It contains various parameters concerning the log management service.";
      key "logMId";
      leaf logMId {
        type leafref {
          path "../attributes/logMId";
        }
      }
      container attributes {
      uses LogM-attributes;
      }
    }
  }

  augment "/emael:ManagedElement/emael:SystemFunctions/rcslogm:LogM/rcslogm:Log" {
    list LogPushTransfer {
      description "Additional definitions from MOM:min/max-elements:0/5; Enables configuration of the connection parameters for both LogM and LogM. An MO shall be created to cause the system to transfer a specific log whenever it reaches a maximum level or as a continuous stream. A rotating log will transfer a file whenever a new file is rotated in. If there is no instance of this class for a specific log, the log service will simply stop writing to a non-wrapping log when it has reached its maximum size. A wrap log will wrap as usual when reaching its maximum size. Log data transfer for wrap files occurs before the log is wrapped.";
      key "logPushTransferId";
      leaf logPushTransferId {
        type leafref {
          path "../attributes/logPushTransferId";
        }
      }
      container attributes {
      uses LogPushTransfer-attributes;
      }
    }
  }

  augment "/emael:ManagedElement/emael:SystemFunctions/rcslogm:LogM" {
    list Log {
      description "Additional definitions from MOM:min/max-elements:0/unbounded;systemCreated; Enables configuration of the Log general properties. The Log MO contains parameters for a specific log file/stream in the system.";
      key "logId";
      leaf logId {
        type leafref {
          path "../attributes/logId";
        }
      }
      container attributes {
      uses Log-attributes;
      }
    }
  }
  typedef ActionResultType {
    description "Lists the different results of an action.";
    type enumeration {
      enum SUCCESS {
        description "The asynchronous action ended with success.";
      }
      enum FAILURE {
        description "The asynchronous action ended with failure.";
      }
      enum NOT_AVAILABLE {
        description "No result is available yet.";
      }
    }
  }
  typedef ActionStateType {
    description "Lists the action states.";
    type enumeration {
      enum CANCELLING {
        description "Cancellation is in progress.";
      }
      enum RUNNING {
        description "The execution of the action is currently in progress.";
      }
      enum FINISHED {
        description "The action is finished.";
      }
      enum CANCELLED {
        description "The action has been cancelled and cancellation has been done.";
      }
    }
  }
  typedef AvailStatus {
    description "The availability status is used to qualify the operational state. It indicates why the operational state has changed its value.";
    type enumeration {
      enum IN_TEST {
        description "The resource is undergoing a test procedure. If the administrative state is locked or shutting down, normal users are prevented from using the resource.";
      }
      enum FAILED {
        description "The resource has an internal fault that prevents it from operating.";
      }
      enum POWER_OFF {
        description "The resource requires power to be applied and is not powered on.";
      }
      enum OFF_LINE {
        description "The resource requires a routine operation to be performed. This routine operation is to place the resource online and make it available for use. The operation may be manual or automatic, or both. The operational state is disabled.";
      }
      enum OFF_DUTY {
        description "The resource has been made inactive by an internal control process.";
      }
      enum DEPENDENCY {
        description "The resource cannot operate because some other resource on which it depends is unavailable.";
      }
      enum DEGRADED {
        description "The service available from the resource is degraded in some respect.";
      }
      enum NOT_INSTALLED {
        description "The resource represented by the managed object is not present, or is incomplete.";
      }
      enum LOG_FULL {
        description "Indicates a log full condition. The semantics are defined in CCITT Rec. X.735 | ISO/IEC 10164-6.";
      }
      enum DEPENDENCY_LOCKED {
        description "The administrative state of a resource that this resource depends on is locked. Alternatively, the availability status of the other resource is dependency locked.";
      }
      enum DEPENDENCY_FAILED {
        description "The availability status of a resource that this resource depends on is failed or dependency failed.";
      }
      enum DEPENDENCY_SHUTTINGDOWN {
        description "The administrative state of a resource that this resource depends on is shutting down. Alternatively, the availability status of the other resource is dependency shutting down.";
      }
    }
  }
  typedef LogSeverity {
    description "Each log entry is assigned a severity. Attribute used to filter log so that only events of a certain severity get logged. Add any number of log severites to filter to exclude events of specified severities from the log.";
    type enumeration {
      enum EMERGENCY {
        description "Add this to the severity filter to exclude EMERGENCY events from the log.";
      }
      enum ALERT {
        description "Add this to the severity filter to exclude ALERT type events from the log.";
      }
      enum CRITICAL {
        description "Add this to the severity filter to exclude CRITICAL events from the log.";
      }
      enum ERROR {
        description "Add this to the severity filter to exclude ERROR events from the log.";
      }
      enum WARNING {
        description "add this to the severity filter to exclude WARNING events from the log.";
      }
      enum NOTICE {
        description "Add this to the severity filter to exclude NOTICE events from the log.";
      }
      enum INFO {
        description "Add this to the severity filter to exclude INFO events from the log.";
      }
    }
  }
  typedef OperState {
    description "Operational states of a resource.";
    type enumeration {
      enum DISABLED {
        description "The resource is totally inoperable.";
      }
      enum ENABLED {
        description "The resource is partially or fully operable.";
      }
    }
  }
  typedef TransferType {
    description "The transfer type makes it possible to instruct the system to transfer log content. It can be as a continous stream or as individual files.";
    type enumeration {
      enum STREAM {
        description "Instructs the system to transfer log data in a continuous stream.";
      }
      enum BULK {
        description "Instructs the system to transfer log data in bulk mode.";
      }
    }
  }
  grouping AsyncActionProgress-struct {
    description "Records the progress of an asynchronous action.";
    leaf actionName {
      type string;
    }
    leaf-list additionalInfo {
      type string;
      min-elements 0;
    }
    leaf progressInfo {
      type string;
    }
    leaf progressPercentage {
      type string;
    }
    leaf result {
      type enumeration {
        enum SUCCESS;
        enum FAILURE;
        enum NOT_AVAILABLE;
      }
    }
    leaf resultInfo {
      type string;
    }
    leaf state {
      type enumeration {
        enum CANCELLING;
        enum RUNNING;
        enum FINISHED;
        enum CANCELLED;
      }
    }
    leaf actionId {
      type string;
    }
    leaf timeActionStarted {
      type string;
    }
    leaf timeActionCompleted {
      type string;
    }
    leaf timeOfLastStatusUpdate {
      type string;
    }
  }
  grouping EcimPassword-struct {
    description "Stores the password.";
    leaf cleartext {
      type boolean;
    }
    leaf password {
      type string;
    }
  }
  grouping Log-attributes {
    leaf logId {
      description "Holds the name used when identifying the MO. It has no effect on the transfer function..";
      type string;
      mandatory true;
    }
    leaf-list severityFilter {
      description "Attribute used to filter log so that only events of a certain severity get logged. Add any number of log severites to filter to exclude events of specified severities from the log. If no value is set, all entries will be kept..";
      type LogSeverity;
      min-elements 0;
      max-elements 7;
    }
    list reportProgress {
      config false;
      min-elements 0;
      uses AsyncActionProgress-struct;
    }
    list progressReport {
      config false;
      description "Reports the progress of a exportEsi or exportAvailabilityLog action..";
      uses AsyncActionProgress-struct;
    }
  }
  grouping LogM-attributes {
    leaf logMId {
      description "This is the identity for the LogM, it does not affect the file transfer and default value is 1..";
      type string;
      mandatory true;
    }
    leaf nodeCredential {
      description "NodeCredential associated with CertM (optional)..";
      type string;
    }
    leaf trustCategory {
      description "trustCategory associated with CertM (optional)..";
      type string;
    }
    list reportProgress {
      config false;
      min-elements 0;
      uses AsyncActionProgress-struct;
    }
    list progressReport {
      config false;
      description "Reports the progress of a exportEsi or exportAvailabilityLog action..";
      uses AsyncActionProgress-struct;
    }
  }
  grouping LogPushTransfer-attributes {
    leaf logPushTransferId {
      description "This is the logPushTransfer MOC id attribute. It has no affect on the transfer function..";
      type string;
      mandatory true;
    }
    leaf uri {
      description "A uniform resource locator describing the file transfer for log streams. This attribute holds the uniform resource indicator which specifies the file transfer protocol, server and destination directory to which the log file should be exported. E.g. sftp://myserver.mydomain.com/logs The name of the file being exported is determined by the system..";
      type string;
      mandatory true;
    }
    leaf transferType {
      description "The transfer type makes it possible to instruct the system to transfer log content. This attribute indicates whether automatic transfer log data should be sent continously in a stream or in bulk whenever a file is filled..";
      type enumeration {
        enum STREAM;
        enum BULK;
      }
    }
    list password {
      key "id";
      leaf id {
        type uint32;
        description "Synthetic key for struct attribute.";
      }
      description "Password field for the remote server..";
      uses EcimPassword-struct;
    }
    leaf-list availStatus {
      description "Available status for this log push transfer object..";
      type AvailStatus;
      min-elements 0;
    }
    leaf operationalState {
      description "Operational state of this log Push Transfer object..";
      type enumeration {
        enum DISABLED;
        enum ENABLED;
      }
      config false;
    }
    leaf-list availabilityStatus {
      description "Available status for this log push transfer object..";
      type AvailStatus;
      min-elements 0;
    }
  }
}
