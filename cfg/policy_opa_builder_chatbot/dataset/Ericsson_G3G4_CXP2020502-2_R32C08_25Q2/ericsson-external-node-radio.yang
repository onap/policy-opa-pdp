module ericsson-external-node-radio {
  yang-version 1.1;
  namespace "urn:com:ericsson:ecim:ReqExternalNode";
  prefix exndrdo;
  import ericsson-equip-radio {
    prefix equiprdo;
  }
  import ericsson-managed-element {
    prefix emael;
  }
  description "Auto-generated from Ericsson CPI MOM XML 15554-lza7016014_33-v1uenfk.xml\n.";
  revision "2026-03-29" {
    description "Ericsson G3G4, version: CXP2020502/2-R32C08";
  }

  augment "/emael:ManagedElement/equiprdo:Equipment" {
    list ExternalNode {
      description "Additional definitions from MOM:min/max-elements:0/unbounded;root; MO ExternalNode in a node represents an external node sharing resources (climate, power and external alarm hardware) with it and possibly other external nodes. A node here is understood as node with ManagedElement as top MO. Where the node acts in a primary role: - ExternalNode MO instances represent every external secondary role node. - Number of ExternalNode MOs must match number of external nodes. - Child MO EcPort is used to configure the termination point for inter-node communication. (Has no function for non-EcBus inter-node communication) - Attribute inciConnectorRef points to termination point for the inter-node communication. - Attribute equipmentSupportFunctionRef points to an EquipmentSupportFunction MO instance that correlates the ExternalNode to belong to a primary role node. Where the node acts in a secondary role: - ExternalNode MO instances represent external neighbouring primary and secondary role node(s). - MO ExternalNode is optional in case of inter-node communication over the EC-bus. - Child MO EcPort has no function. - Attribute inciConnectorRef points to termination point for the inter-node communication. - Attribute equipmentSupportFunctionRef points to an EquipmentSupportFunction MO instance that correlate the ExternalNode MO to belong to a secondary role node.";
      key "externalNodeId";
      leaf externalNodeId {
        type leafref {
          path "../attributes/externalNodeId";
        }
      }
      container attributes {
      uses ExternalNode-attributes;
      }
    }
  }
  typedef ApcRadioAccessTechnology {
    type enumeration {
      enum NOT_AVAILABLE {
      }
      enum GSM {
      }
      enum WCDMA {
      }
      enum LTE {
      }
      enum MULTI_STANDARD {
      }
      enum TRANSMISSION {
      }
    }
  }
  typedef ApcSupportSystemControl {
    type enumeration {
      enum FALSE {
      }
      enum TRUE {
      }
      enum NOT_AVAILABLE {
      }
    }
  }
  grouping ExternalNode-attributes {
    leaf externalNodeId {
      description "The value component of the RDN..";
      type string;
      mandatory true;
    }
    leaf radioAccessTechnology {
      description "Radio access technology that external node can support. NOT_AVAILABLE used if no information is available from the external node. When external node can run more than one standard, set to MULTI_STANDARD..";
      type enumeration {
        enum NOT_AVAILABLE;
        enum GSM;
        enum WCDMA;
        enum LTE;
        enum MULTI_STANDARD;
        enum TRANSMISSION;
      }
      config false;
    }
    leaf supportSystemControl {
      description "Support system control on MO EquipmentSupportFunction in external node. NOT_AVAILABLE is used when no information is available from the external node..";
      type enumeration {
        enum FALSE;
        enum TRUE;
        enum NOT_AVAILABLE;
      }
      config false;
    }
    leaf logicalName {
      description "Logical name on MO ManagedElement in external node. Undefined value, an empty string, is used for node that has no configured logicalName. NOT AVAILABLE is used when no information is available from external node. NOT_AVAILABLE is also used for MULTI_STANDARD node which doesn't have a logical name on MO ManagedElement.; length 1..255.";
      type string {
        length "1..255";
      }
      config false;
    }
    leaf informationOnly {
      description "Indicates if the MO data is only for informational purposes or for configuration purposes. When set to true, the MO contains read-only data about the external nodes. The number of MO ExternalNode does not have to match the actual number of external nodes. The MO attributes are populated with data if a corresponding external node exists. When set to false, the MO contains configuration data such as MO EcPort. The MO ExternalNode number must match the actual number of external nodes.; Default value: false.";
      type boolean;
      default "false";
    }
    leaf fullDistinguishedName {
      description "Full Distinguished Name (FDN) on MO ManagedElement in external node. Undefined value, an empty string, is used for node that has no configured fullDistinguishedName, such as a GSM node. NOT AVAILABLE is used when no information is available from external node. For MULTI_STANDARD node the FDN is derived from attributes dnPrefix and managedElementId.; length 1..255.";
      type string {
        length "1..255";
      }
      config false;
    }
    leaf equipmentSupportFunctionRef {
      description "Reference to the EquipmentSupportFunction MO where the MO ExternalNode belongs..";
      type string;
    }
    leaf-list reservedBy {
      description "Contains a list of MO instances that reserve this MO instance..";
      type string;
      min-elements 0;
    }
    leaf inciConnectorRef {
      description "Reference to the MOC that provides the inter node communication towards the external node. The MOC is an instance of MOC FieldReplaceableUnit or EcBus. For an ExternalNode MO representing another secondary role node in a secondary role node, the attribute points to the ExternalNode MO instance that represents the primary role..";
      type string;
    }
  }
}
