module ericsson-ec-port-radio {
  yang-version 1.1;
  namespace "urn:com:ericsson:ecim:ReqEcPort";
  prefix eprtrdo;
  import ericsson-external-node-radio {
    prefix exndrdo;
  }
  import ericsson-equip-radio {
    prefix equiprdo;
  }
  import ericsson-field-replaceable-unit-radio {
    prefix frurdo;
  }
  import ericsson-yang-types {
    prefix eytypes;
  }
  import ericsson-managed-element {
    prefix emael;
  }
  description "Auto-generated from Ericsson CPI MOM XML 15554-lza7016014_33-v1uenfk.xml\n.";
  revision "2026-03-29" {
    description "Ericsson G3G4, version: CXP2020502/2-R32C08";
  }

  augment "/emael:ManagedElement/equiprdo:Equipment/exndrdo:ExternalNode" {
    list EcPort {
      description "Additional definitions from MOM:min/max-elements:0/unbounded;root; This MO represents one port in a FieldReplaceableUnit MO.";
      key "ecPortId";
      leaf ecPortId {
        type leafref {
          path "../attributes/ecPortId";
        }
      }
      container attributes {
      uses EcPort-attributes;
      }
    }
  }

  augment "/emael:ManagedElement/equiprdo:Equipment/frurdo:FieldReplaceableUnit" {
    list EcPort {
      description "Additional definitions from MOM:min/max-elements:0/1;root; This MO represents one port in a FieldReplaceableUnit MO.";
      key "ecPortId";
      leaf ecPortId {
        type leafref {
          path "../attributes/ecPortId";
        }
      }
      container attributes {
      uses EcPort-attributes;
      }
    }
  }
  typedef AvailStatus {
    description "The availability status is used to qualify the operational state. It indicates why the operational state has changed its value.";
    type enumeration {
      enum IN_TEST {
        description "The resource is undergoing a test procedure. If the administrative state is locked or shutting down, normal users are prevented from using the resource.";
      }
      enum FAILED {
        description "The resource has an internal fault that prevents it from operating.";
      }
      enum POWER_OFF {
        description "The resource requires power to be applied and is not powered on.";
      }
      enum OFF_LINE {
        description "The resource requires a routine operation to be performed. This routine operation is to place the resource online and make it available for use. The operation may be manual or automatic, or both. The operational state is disabled.";
      }
      enum OFF_DUTY {
        description "The resource has been made inactive by an internal control process.";
      }
      enum DEPENDENCY {
        description "The resource cannot operate because some other resource on which it depends is unavailable.";
      }
      enum DEGRADED {
        description "The service available from the resource is degraded in some respect.";
      }
      enum NOT_INSTALLED {
        description "The resource represented by the managed object is not present, or is incomplete.";
      }
      enum LOG_FULL {
        description "Indicates a log full condition. The semantics are defined in CCITT Rec. X.735 | ISO/IEC 10164-6.";
      }
      enum DEPENDENCY_LOCKED {
        description "The administrative state of a resource that this resource depends on is locked. Alternatively, the availability status of the other resource is dependency locked.";
      }
      enum DEPENDENCY_FAILED {
        description "The availability status of a resource that this resource depends on is failed or dependency failed.";
      }
      enum DEPENDENCY_SHUTTINGDOWN {
        description "The administrative state of a resource that this resource depends on is shutting down. Alternatively, the availability status of the other resource is dependency shutting down.";
      }
      enum DEPENDENCY_RECOVERY {
        description "Resource that this resource depends on is undergoing a recovery procedure.";
      }
      enum DEPENDENCY_HOLDING {
        description "Resource cannot operate because some other resource on which it depends is currently unavailable. The situation is expected to be resolved. Actions to facilitate dependency resolution may be ongoing.";
      }
    }
  }
  typedef OperState {
    description "Operational states of a resource.";
    type enumeration {
      enum DISABLED {
        description "The resource is totally inoperable.";
      }
      enum ENABLED {
        description "The resource is partially or fully operable.";
      }
    }
  }
  grouping EcPort-attributes {
    leaf ecPortId {
      description "The value component of the RDN..";
      type string;
      mandatory true;
    }
    leaf cascadingOrder {
      description "The cascading order when there are multiple hubs or units connected in a cascade chain. The first unit in a cascade chain has value 1. If the EC-bus isn’t connected in cascade then the value shall be set to 0 (not applicable).; range 0..7; Default value: 0.";
      type eytypes:int32_range_0-7;
      default "0";
    }
    leaf hubPosition {
      description "The hub port that the external node or FRU is connected to. Must be set for FieldReplaceableUnit MOs of type DU or Baseband, TCU or Baseband T, BFU, PSU, PDU, EMU, SCU, SAU, CLU, SUP and BPA. Must be set for ExternalNode MOs on the primary node. System-updated attribute to reflect actual port. In case attribute is updated by system, the system cannot detect what kind of hub is used. The system will reflect hub position as if the hub is an SHU. See actual hub-specific lookup table to get label found on SCU or SUP. Value: Based on label for used port on hw. Valid values: Ain, A0, A1, A2, A3, A4, A5, A6, A7, A8, Bin, B0, B1, B2, B3, B4, B5, B6, B7, B8, A, B, C, D, E, X, Y, SAU, NA, CLU, BPA NA: Might be used in existing configurations for SCU and SUP..";
      type string;
    }
    leaf ecBusRef {
      description "The EcBus to which the EcPort is connected..";
      type string;
    }
    leaf-list availabilityStatus {
      description "The availability status. It contains details about operationalState..";
      type AvailStatus;
      min-elements 0;
    }
    leaf operationalState {
      description "The operational state..";
      type enumeration {
        enum DISABLED;
        enum ENABLED;
      }
      config false;
    }
  }
}
