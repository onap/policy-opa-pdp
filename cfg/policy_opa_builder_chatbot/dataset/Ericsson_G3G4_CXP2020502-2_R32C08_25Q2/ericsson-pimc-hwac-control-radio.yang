module ericsson-pimc-hwac-control-radio {
  yang-version 1.1;
  namespace "urn:com:ericsson:ecim:ReqPimcHwacControl";
  prefix phctrlrdo;
  import ericsson-equip-radio {
    prefix equiprdo;
  }
  import ericsson-field-replaceable-unit-radio {
    prefix frurdo;
  }
  import ericsson-managed-element {
    prefix emael;
  }
  description "Auto-generated from Ericsson CPI MOM XML 15554-lza7016014_33-v1uenfk.xml\ncreate mom ReqPimcHwacControl";
  revision "2026-03-29" {
    description "Ericsson G3G4, version: CXP2020502/2-R32C08";
  }

  augment "/emael:ManagedElement/equiprdo:Equipment/frurdo:FieldReplaceableUnit" {
    list PimcHwacControl {
      description "Additional definitions from MOM:min/max-elements:0/1;root; Represents Passive Inter-Modulation Cancellation (PIMC) function configured on a radio unit. Created manually for enabling PIMC on current radio unit.";
      key "pimcHwacControlId";
      leaf pimcHwacControlId {
        type leafref {
          path "../attributes/pimcHwacControlId";
        }
      }
      container attributes {
      uses PimcHwacControl-attributes;
      }
    }
  }
  grouping PimcHwacControl-attributes {
    leaf pimcHwacControlId {
      description "The value component of the RDN..";
      type string;
      mandatory true;
    }
    leaf pimcEnabled {
      description "Whether PIMC is enabled on radio unit. Triggers PIMC HWAC allocation and release on radio unit. true: PIMC is enabled. Setting value to true allocates PIMC HWAC for PIMC capable radio unit. false: PIMC is disabled.; Default value: false.";
      type boolean;
      default "false";
    }
    leaf pimcHwacAllocated {
      description "Whether PIMC HWAC is allocated for current radio unit. Default value is false..";
      type boolean;
      config false;
    }
  }
}
