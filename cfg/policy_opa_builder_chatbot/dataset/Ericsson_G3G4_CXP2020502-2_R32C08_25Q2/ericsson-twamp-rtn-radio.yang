module ericsson-twamp-rtn-radio {
  yang-version 1.1;
  namespace "urn:com:ericsson:ecim:RtnTwamp";
  prefix twrdo;
  import ietf-inet-types {
    prefix ietfinet;
  }
  import ericsson-l3-router-rtn-radio {
    prefix l3rtrdo;
  }
  import ericsson-managed-element {
    prefix emael;
  }
  description "Auto-generated from Ericsson CPI MOM XML 15554-lza7016014_33-v1uenfk.xml\nECIM Transport TWAMP Responder MOM.";
  revision "2026-03-29" {
    description "Ericsson G3G4, version: CXP2020502/2-R32C08";
  }

  augment "/emael:ManagedElement/emael:Transport/l3rtrdo:Router" {
    list TwampLightResponder {
      description "Additional definitions from MOM:min/max-elements:0/8;root; Two Way Active Measurement Protocol Responder. This MO represents the session responder functionality (according to RFC 5357) in a TWAMP light architecture. When created, the node reflects TWAMP packets received on the specified UDP port.";
      key "twampLightResponderId";
      leaf twampLightResponderId {
        type leafref {
          path "../attributes/twampLightResponderId";
        }
      }
      container attributes {
      uses TwampLightResponder-attributes;
      }
    }
  }
  typedef ResponderType {
    description "Responder type.";
    type enumeration {
      enum LIGHT {
        description "TWAMP light stateful. Light (stateful): sequence number in reflected packet is generated by responder, which enables measurement of packet loss in forward and reverse direction.";
      }
      enum LIGHT_SL {
        description "TWAMP light stateless. Light-SL (stateless): sequence number is copied from sender test packet to reflected packet, thus it is only possible to measure round trip packet loss.";
      }
    }
  }
  grouping TwampLightResponder-attributes {
    leaf ipAddress {
      description "Responder assigned IP address. Valid reference is an AddressIpv4 or an AddressIpv6 MO in the L3 infra fragment..";
      type string;
      mandatory true;
    }
    leaf responderType {
      description "Type of the responder..";
      type enumeration {
        enum LIGHT;
        enum LIGHT_SL;
      }
      config false;
    }
    leaf twampLightResponderId {
      description "Value component of the RDN..";
      type string;
      mandatory true;
    }
    leaf udpPort {
      description "Specify a UDP port to send and receive TWAMP test packets..";
      type ietfinet:port-number;
      mandatory true;
    }
    leaf userLabel {
      description "Label for free use.; length 1..128.";
      type string {
        length "1..128";
      }
    }
  }
}
