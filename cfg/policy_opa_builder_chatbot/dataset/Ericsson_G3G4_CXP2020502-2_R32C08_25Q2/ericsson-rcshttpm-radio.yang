module ericsson-rcshttpm-radio {
  yang-version 1.1;
  namespace "urn:com:ericsson:ecim:RcsHttpM";
  prefix rcshttpm;
  import ericsson-rcssysm-radio {
    prefix rcssysm;
  }
  import ericsson-managed-element {
    prefix emael;
  }
  description "Auto-generated from Ericsson CPI MOM XML 15554-lza7016014_33-v1uenfk.xml\nGeneral HTTP service.";
  revision "2026-03-29" {
    description "Ericsson G3G4, version: CXP2020502/2-R32C08";
  }

  augment "/emael:ManagedElement/emael:SystemFunctions/rcssysm:SysM/rcshttpm:HttpM" {
    list Https {
      description "Additional definitions from MOM:min/max-elements:0/1;systemCreated; Configuration for HTTP secure service. The HTTPS service allows secure communication over TLS with the web applications of the system. Basic web-service (port 443) is only using certificates for secure transport. Extended web-service (port 8443) is using certificates for secure transport and login validation.";
      key "httpsId";
      leaf httpsId {
        type leafref {
          path "../attributes/httpsId";
        }
      }
      container attributes {
      uses Https-attributes;
      }
    }
  }

  augment "/emael:ManagedElement/emael:SystemFunctions/rcssysm:SysM" {
    list HttpM {
      description "Additional definitions from MOM:min/max-elements:1/1;root;systemCreated; HTTP management.";
      key "httpMId";
      leaf httpMId {
        type leafref {
          path "../attributes/httpMId";
        }
      }
      container attributes {
      uses HttpM-attributes;
      }
    }
  }
  grouping HttpM-attributes {
    leaf httpMId {
      description "The value part of the RDN..";
      type string;
      mandatory true;
    }
  }
  grouping Https-attributes {
    leaf httpsId {
      description "The value part of the RDN..";
      type string;
      mandatory true;
    }
    leaf nodeCredential {
      description "Node credential to be used when accessing the service..";
      type string;
    }
    leaf trustCategory {
      description "Trust category to be used when accessing the service..";
      type string;
    }
  }
}
