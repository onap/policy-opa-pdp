module ericsson-rmesupport-radio {
  yang-version 1.1;
  namespace "urn:com:ericsson:ecim:RmeSupport";
  prefix rmesuppo;
  import ericsson-managed-element {
    prefix emael;
  }
  description "Auto-generated from Ericsson CPI MOM XML 15554-lza7016014_33-v1uenfk.xml\nTop of the NodeSupport branch";
  revision "2026-03-29" {
    description "Ericsson G3G4, version: CXP2020502/2-R32C08";
  }

  augment "/emael:ManagedElement" {
    list NodeSupport {
      description "Additional definitions from MOM:min/max-elements:1/1;root;systemCreated; Top MO for the NodeSupport branch";
      key "nodeSupportId";
      leaf nodeSupportId {
        type leafref {
          path "../attributes/nodeSupportId";
        }
      }
      container attributes {
      uses NodeSupport-attributes;
      }
    }
  }
  grouping NodeSupport-attributes {
    leaf nodeSupportId {
      description "Holds the name used when identifying this MO..";
      type string;
      mandatory true;
    }
    leaf supportFunction {
      description "A read-only attribute boolean supportFunction, default true, always set to true. For use by management systems to distinguish supportFunction implementations.; Default value: true.";
      type boolean;
      config false;
      default "true";
    }
    leaf userLabel {
      description "Used for product free-text description..";
      type string;
    }
    leaf release {
      description "The product release of the SupportFunction..";
      type string;
      config false;
    }
  }
}
