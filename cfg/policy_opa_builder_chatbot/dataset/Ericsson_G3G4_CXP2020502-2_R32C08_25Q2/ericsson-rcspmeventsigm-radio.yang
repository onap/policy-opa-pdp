module ericsson-rcspmeventsigm-radio {
  yang-version 1.1;
  namespace "urn:com:ericsson:ecim:RcsPMEventSigM";
  prefix rcspmeve;
  import ietf-inet-types {
    prefix ietfinet;
  }
  import ericsson-managed-element {
    prefix emael;
  }
  description "Auto-generated from Ericsson CPI MOM XML 15554-lza7016014_33-v1uenfk.xml\nThis fragment is used to manage UE trace event TCP streaming port used by NR and custom filtering of PM Events from UE trace jobs for both NR and LTE.";
  revision "2026-03-29" {
    description "Ericsson G3G4, version: CXP2020502/2-R32C08";
  }

  augment "/emael:ManagedElement/emael:SystemFunctions" {
    list PmEventSigM {
      description "Additional definitions from MOM:min/max-elements:1/1;root;systemCreated; Performance management (PM) event fragment for signalling based event jobs. It is used to provide event producer specific provisioning of event jobs controlled by signalling based activation from the core network.";
      key "pmEventSigMId";
      leaf pmEventSigMId {
        type leafref {
          path "../attributes/pmEventSigMId";
        }
      }
      container attributes {
      uses PmEventSigM-attributes;
      }
    }
  }

  augment "/emael:ManagedElement/emael:SystemFunctions/rcspmeve:PmEventSigM/rcspmeve:EventProducerS/rcspmeve:EventGroupS" {
    list EventTypeS {
      description "Additional definitions from MOM:min/max-elements:0/unbounded;systemCreated; Event type generated by ME. The RDN of this MO is EventTypeS=<ID>.";
      key "eventTypeSId";
      leaf eventTypeSId {
        type leafref {
          path "../attributes/eventTypeSId";
        }
      }
      container attributes {
      uses EventTypeS-attributes;
      }
    }
  }

  augment "/emael:ManagedElement/emael:SystemFunctions/rcspmeve:PmEventSigM/rcspmeve:EventProducerS" {
    list EventGroupS {
      description "Additional definitions from MOM:min/max-elements:0/unbounded;systemCreated; A group of related event types. The RDN of this MO is EventGroupS=<ID>.";
      key "eventGroupSId";
      leaf eventGroupSId {
        type leafref {
          path "../attributes/eventGroupSId";
        }
      }
      container attributes {
      uses EventGroupS-attributes;
      }
    }
  }

  augment "/emael:ManagedElement/emael:SystemFunctions/rcspmeve:PmEventSigM" {
    list EventProducerS {
      description "Additional definitions from MOM:min/max-elements:0/unbounded;systemCreated; Event producer. Allows for multiple types of event producer within an application describing distinct event functions. The RDN of this MO is EventProducerS=<ID>.";
      key "eventProducerSId";
      leaf eventProducerSId {
        type leafref {
          path "../attributes/eventProducerSId";
        }
      }
      container attributes {
      uses EventProducerS-attributes;
      }
    }
  }
  typedef EventStatus {
    description "Identifies the status of the Event Type";
    type enumeration {
      enum PRELIMINARY {
        description "The event is available and stepped in this version of the Managed Element, but is not yet approved.";
      }
      enum USED {
        description "The event is approved, available and stepped in this version of the Managed Element.";
      }
      enum DEPRECATED {
        description "The event is available in this version of the Managed Element, but as it is planned for removal it is not recommended for use.";
      }
      enum OBSOLETE {
      }
    }
  }
  grouping EventGroupS-attributes {
    leaf eventGroupSId {
      description "Holds the name used when identifying the MO..";
      type string;
      mandatory true;
    }
    leaf description {
      description "Describes the content and purpose of the event group..";
      type string;
      config false;
    }
    leaf eventGroupVersion {
      description "Event Group version identifier. Unique version identifier associated with a change to the contents of the Event Group, where new Event Types have been added..";
      type string;
      config false;
    }
    leaf-list ueTraceEventBlacklist {
      description "Indicates the eventTypeSId of events to be filtered from UE trace jobs.; Status info: Since 23.Q1. Replaced by ueTraceEventFilterlist. Planned to be removed..";
      type string;
      min-elements 0;
    }
    leaf-list ueTraceEventFilterlist {
      description "Indicates the eventTypeSId of events to be filtered from UE trace jobs..";
      type string;
      min-elements 0;
    }
  }
  grouping EventProducerS-attributes {
    leaf eventProducerSId {
      description "Holds the name used when identifying the MO..";
      type string;
      mandatory true;
    }
    leaf name {
      description "Name of event producer..";
      type string;
      config false;
    }
    leaf generation {
      description "Determines if event producer concerns GSM, UMTS, EPS, combined GSM+UMTS+EPS, IMS or 5GS measurements..";
      type string;
      config false;
    }
    leaf streamDestinationPort {
      description "Port on target for UE trace streaming over TCP.; Default value: 51544.";
      type ietfinet:port-number;
      default "51544";
    }
  }
  grouping EventTypeS-attributes {
    leaf eventTypeSId {
      description "Holds the name used when identifying the MO..";
      type string;
      mandatory true;
    }
    leaf eventStatus {
      description "Status of event type..";
      type enumeration {
        enum PRELIMINARY;
        enum USED;
        enum DEPRECATED;
        enum OBSOLETE;
      }
      config false;
    }
  }
  grouping PmEventSigM-attributes {
    leaf pmEventSigMId {
      description "Holds the name used when identifying the MO..";
      type string;
      mandatory true;
    }
    leaf userLabel {
      description "Label for free use..";
      type string;
    }
  }
}
