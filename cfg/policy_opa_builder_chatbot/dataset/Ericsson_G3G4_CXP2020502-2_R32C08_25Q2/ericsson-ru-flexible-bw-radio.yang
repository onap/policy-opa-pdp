module ericsson-ru-flexible-bw-radio {
  yang-version 1.1;
  namespace "urn:com:ericsson:ecim:RmeRuFlexibleBw";
  prefix flxbwrdo;
  import ericsson-rmesupport-radio {
    prefix rmesuppo;
  }
  import ericsson-managed-element {
    prefix emael;
  }
  description "Auto-generated from Ericsson CPI MOM XML 15554-lza7016014_33-v1uenfk.xml\nRmeRuFlexibleBw";
  revision "2026-03-29" {
    description "Ericsson G3G4, version: CXP2020502/2-R32C08";
  }

  augment "/emael:ManagedElement/rmesuppo:NodeSupport" {
    list RuFlexibleBw {
      description "Additional definitions from MOM:min/max-elements:0/unbounded;root; Configuration of flexible frequency ranges for IRU. One instance defines frequency ranges for one or several IRUs. Same FieldReplaceableUnit instance can only be referenced by one RuFlexibleBw instance. Frequency ranges must not overlap.";
      key "ruFlexibleBwId";
      leaf ruFlexibleBwId {
        type leafref {
          path "../attributes/ruFlexibleBwId";
        }
      }
      container attributes {
      uses RuFlexibleBw-attributes;
      }
    }
  }
  grouping FlexBwLimit-struct {
    description "Flexible bandwidth for IRU.";
    leaf ulLowerEdgeFrequency {
      description "Default value: 0.";
      type int32;
      default "0";
      units "kHz";
    }
    leaf ulInstantaneousBandwidth {
      description "Default value: 0.";
      type int32 {
        range "0 | 5..200";
      }
      default "0";
      units "MHz";
    }
    leaf dlLowerEdgeFrequency {
      description "Default value: 0.";
      type int32;
      default "0";
      units "kHz";
    }
    leaf dlInstantaneousBandwidth {
      description "Default value: 0.";
      type int32 {
        range "0 | 5..200";
      }
      default "0";
      units "MHz";
    }
  }
  grouping RuFlexibleBw-attributes {
    leaf ruFlexibleBwId {
      description "The value component of the RDN..";
      type string;
      mandatory true;
    }
    list flexibleBwLimit {
      key "id";
      leaf id {
        type uint32;
        description "Synthetic key for struct sequence entry.";
      }
      min-elements 0;
      max-elements 8;
      uses FlexBwLimit-struct;
    }
    leaf-list fieldReplaceableUnitRef {
      description "References to FieldReplaceableUnit instances with flexible bandwidth..";
      type string;
      min-elements 1;
    }
  }
}
