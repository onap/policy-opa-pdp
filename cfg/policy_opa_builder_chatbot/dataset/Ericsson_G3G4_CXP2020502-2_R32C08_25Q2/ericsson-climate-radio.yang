module ericsson-climate-radio {
  yang-version 1.1;
  namespace "urn:com:ericsson:ecim:ResClimate";
  prefix climrdo;
  import ericsson-equipment-support-function-radio {
    prefix eqsupfnrdo;
  }
  import ericsson-managed-element {
    prefix emael;
  }
  description "Auto-generated from Ericsson CPI MOM XML 15554-lza7016014_33-v1uenfk.xml\nThis MO represents the logical resource providing configuration and supervision support for the climate control function.";
  revision "2026-03-29" {
    description "Ericsson G3G4, version: CXP2020502/2-R32C08";
  }

  augment "/emael:ManagedElement/eqsupfnrdo:EquipmentSupportFunction" {
    list Climate {
      description "Additional definitions from MOM:min/max-elements:0/unbounded;root; This MO represents the logical resource providing configuration and supervision support for the climate control function.";
      key "climateId";
      leaf climateId {
        type leafref {
          path "../attributes/climateId";
        }
      }
      container attributes {
      uses Climate-attributes;
      }
    }
  }
  typedef ApcClimateControlMode {
    type enumeration {
      enum NORMAL {
      }
      enum BATTERY_LIFE_EXTENSION {
      }
      enum BOOST {
      }
      enum ECO {
      }
      enum ENHANCED {
      }
    }
  }
  typedef AvailStatus {
    description "The availability status is used to qualify the operational state. It indicates why the operational state has changed its value.";
    type enumeration {
      enum IN_TEST {
        description "The resource is undergoing a test procedure. If the administrative state is locked or shutting down, normal users are prevented from using the resource.";
      }
      enum FAILED {
        description "The resource has an internal fault that prevents it from operating.";
      }
      enum POWER_OFF {
        description "The resource requires power to be applied and is not powered on.";
      }
      enum OFF_LINE {
        description "The resource requires a routine operation to be performed. This routine operation is to place the resource online and make it available for use. The operation may be manual or automatic, or both. The operational state is disabled.";
      }
      enum OFF_DUTY {
        description "The resource has been made inactive by an internal control process.";
      }
      enum DEPENDENCY {
        description "The resource cannot operate because some other resource on which it depends is unavailable.";
      }
      enum DEGRADED {
        description "The service available from the resource is degraded in some respect.";
      }
      enum NOT_INSTALLED {
        description "The resource represented by the managed object is not present, or is incomplete.";
      }
      enum LOG_FULL {
        description "Indicates a log full condition. The semantics are defined in CCITT Rec. X.735 | ISO/IEC 10164-6.";
      }
      enum DEPENDENCY_LOCKED {
        description "The administrative state of a resource that this resource depends on is locked. Alternatively, the availability status of the other resource is dependency locked.";
      }
      enum DEPENDENCY_FAILED {
        description "The availability status of a resource that this resource depends on is failed or dependency failed.";
      }
      enum DEPENDENCY_SHUTTINGDOWN {
        description "The administrative state of a resource that this resource depends on is shutting down. Alternatively, the availability status of the other resource is dependency shutting down.";
      }
      enum DEPENDENCY_RECOVERY {
        description "Resource that this resource depends on is undergoing a recovery procedure.";
      }
      enum DEPENDENCY_HOLDING {
        description "Resource cannot operate because some other resource on which it depends is currently unavailable. The situation is expected to be resolved. Actions to facilitate dependency resolution may be ongoing.";
      }
    }
  }
  typedef OperState {
    description "Operational states of a resource.";
    type enumeration {
      enum DISABLED {
        description "The resource is totally inoperable.";
      }
      enum ENABLED {
        description "The resource is partially or fully operable.";
      }
    }
  }
  grouping ApcEnhancedModeSetup-struct {
    description ".";
    leaf internalFanRampUpTemp {
      description "range 15..40.";
      type int32 {
        range "15..40";
      }
    }
    leaf externalFanStartTemp {
      description "range 15..40.";
      type int32 {
        range "15..40";
      }
    }
  }
  grouping Climate-attributes {
    leaf climateId {
      description "The value component of the RDN..";
      type string;
      mandatory true;
    }
    leaf controlDomainRef {
      description "The cabinet or the shelf where functions represented by this MO are deployed..";
      type string;
    }
    leaf-list availabilityStatus {
      description "The availability status. It contains details about operationalState..";
      type AvailStatus;
      min-elements 0;
    }
    leaf climateControlMode {
      description "Documentation: Specifies the mode to run the climate control..";
      type enumeration {
        enum NORMAL;
        enum BATTERY_LIFE_EXTENSION;
        enum BOOST;
        enum ECO;
        enum ENHANCED;
      }
    }
    leaf operationalState {
      description "Defines the operational state..";
      type enumeration {
        enum DISABLED;
        enum ENABLED;
      }
      config false;
    }
    leaf userLabel {
      description "Label for free use.; length 1..128.";
      type string {
        length "1..128";
      }
    }
    leaf cabinetTemperature {
      description "Temperature from SCU temp sensor. Undefined value represented by 999, indicates invalid temperature readings from the SCU.; range -55..125.";
      type int32 {
        range "-55..125";
      }
      config false;
      units "°C";
    }
    leaf fanSpeedSupervision {
      description "Time period for fan speed supervision. If fan speed is continuously high (>= 90%) during time period, an alarm is raised. Use '6' if located near households. Use '24' if fan speed supervision is needed and noise level does not matter, no neighbors. Valid values: 0: fan speed supervision off 6, 12, 24: time period in hours; Default value: 12.";
      type int32 {
        range "0 | 6 | 12 | 24";
      }
      default "12";
      units "hours";
    }
    leaf boostInternalThreshold {
      description "Threshold at which cabinet temperatures contribute to fan speed regulation. If empty, cabinet default is used.; range 10..40.";
      type int32 {
        range "10..40";
      }
      units "°C";
    }
    list enhancedModeSetup {
      key "id";
      leaf id {
        type uint32;
        description "Synthetic key for struct attribute.";
      }
      description "Setup for Enhanced Climate Control Mode..";
      uses ApcEnhancedModeSetup-struct;
    }
    leaf pmSpmBarometricAirPressure {
      description "Average differential air pressure. Unit: kPa..";
      type int32;
      config false;
    }
    leaf-list pmCabinetTemperature {
      description "Average cabinet temperature with +1000 offset. To convert to Celsius, following formula is used: (value reported - 1000). [0]: Average temperature from 0 to 299 seconds of ROP. [1]: Average temperature from 300 to 599 seconds of ROP. [2]: Average temperature from 600 to 899 seconds of ROP..";
      type int32;
      max-elements 3;
    }
    leaf pmSpmDifferentialAirPressure {
      description "Avarage differential air pressure. Unit: Pa.";
      type int32;
      config false;
    }
    leaf-list pmCabinetFanSpeedExternal {
      description "Average external fan speed. [0]: Average external fan speed from 0 to 299 seconds of ROP, % of maximum fan speed. [1]: Average internal fan speed from 300 to 599 seconds of ROP, % of maximum fan speed. [2]: Average internal fan speed from 600 to 899 seconds of ROP, % of maximum fan speed..";
      type int32;
      max-elements 3;
    }
    leaf-list pmCabinetFanSpeed {
      description "Average internal fan speed. [0]: Average internal fan speed from 0 to 299 seconds of ROP, % of maximum fan speed. [1]: Average internal fan speed from 300 to 599 seconds of ROP, % of maximum fan speed. [2]: Average internal fan speed from 600 to 899 seconds of ROP, % of maximum fan speed..";
      type int32;
      max-elements 3;
    }
  }
}
