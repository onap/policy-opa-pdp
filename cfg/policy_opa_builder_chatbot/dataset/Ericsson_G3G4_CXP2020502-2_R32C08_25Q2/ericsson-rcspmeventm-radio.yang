module ericsson-rcspmeventm-radio {
  yang-version 1.1;
  namespace "urn:com:ericsson:ecim:RcsPMEventM";
  prefix rcspmeve;
  import ietf-inet-types {
    prefix ietfinet;
  }
  import ericsson-managed-element {
    prefix emael;
  }
  description "Auto-generated from Ericsson CPI MOM XML 15554-lza7016014_33-v1uenfk.xml\nThis fragment is used to manage the event jobs on the Managed Element. Once an event job is activated the event data can be collected and sent via streaming or file transfer depending on the capabilities specified.";
  revision "2026-03-29" {
    description "Ericsson G3G4, version: CXP2020502/2-R32C08";
  }

  augment "/emael:ManagedElement/emael:SystemFunctions" {
    list PmEventM {
      description "Additional definitions from MOM:min/max-elements:1/1;root;systemCreated; The Performance Management (PM) Event Management fragment. It is used to manage the event jobs on the Managed Element. Once an event job is activated the events can be collected and sent via streaming and/or file transfer.";
      key "pmEventMId";
      leaf pmEventMId {
        type leafref {
          path "../attributes/pmEventMId";
        }
      }
      container attributes {
      uses PmEventM-attributes;
      }
    }
  }

  augment "/emael:ManagedElement/emael:SystemFunctions/rcspmeve:PmEventM/rcspmeve:EventProducer/rcspmeve:EventGroup" {
    list EventType {
      description "Additional definitions from MOM:min/max-elements:0/unbounded;systemCreated; Defines the event type that can be generated by the Managed Element.";
      key "eventTypeId";
      leaf eventTypeId {
        type leafref {
          path "../attributes/eventTypeId";
        }
      }
      container attributes {
      uses EventType-attributes;
      }
    }
  }

  augment "/emael:ManagedElement/emael:SystemFunctions/rcspmeve:PmEventM/rcspmeve:EventProducer" {
    list FilePullCapabilities {
      description "Additional definitions from MOM:min/max-elements:0/1;systemCreated; Event capabilities specific to file pull.";
      key "filePullCapabilitiesId";
      leaf filePullCapabilitiesId {
        type leafref {
          path "../attributes/filePullCapabilitiesId";
        }
      }
      container attributes {
      uses FilePullCapabilities-attributes;
      }
    }
  }

  augment "/emael:ManagedElement/emael:SystemFunctions/rcspmeve:PmEventM/rcspmeve:EventProducer" {
    list EventCapabilities {
      description "Additional definitions from MOM:min/max-elements:1/1;systemCreated; Event capabilities.";
      key "eventCapabilitiesId";
      leaf eventCapabilitiesId {
        type leafref {
          path "../attributes/eventCapabilitiesId";
        }
      }
      container attributes {
      uses EventCapabilities-attributes;
      }
    }
  }

  augment "/emael:ManagedElement/emael:SystemFunctions/rcspmeve:PmEventM/rcspmeve:EventProducer" {
    list StreamingCapabilities {
      description "Additional definitions from MOM:min/max-elements:0/1;systemCreated; Streaming capabilities.";
      key "streamCapabilitiesId";
      leaf streamCapabilitiesId {
        type leafref {
          path "../attributes/streamCapabilitiesId";
        }
      }
      container attributes {
      uses StreamingCapabilities-attributes;
      }
    }
  }

  augment "/emael:ManagedElement/emael:SystemFunctions/rcspmeve:PmEventM/rcspmeve:EventProducer" {
    list EventGroup {
      description "Additional definitions from MOM:min/max-elements:0/unbounded;systemCreated; Represents a group of related Event Types.";
      key "eventGroupId";
      leaf eventGroupId {
        type leafref {
          path "../attributes/eventGroupId";
        }
      }
      container attributes {
      uses EventGroup-attributes;
      }
    }
  }

  augment "/emael:ManagedElement/emael:SystemFunctions/rcspmeve:PmEventM/rcspmeve:EventProducer" {
    list EventFilterType {
      description "Additional definitions from MOM:min/max-elements:0/unbounded;systemCreated; Describes the available Event Filter Type definitions.";
      key "eventFilterTypeId";
      leaf eventFilterTypeId {
        type leafref {
          path "../attributes/eventFilterTypeId";
        }
      }
      container attributes {
      uses EventFilterType-attributes;
      }
    }
  }

  augment "/emael:ManagedElement/emael:SystemFunctions/rcspmeve:PmEventM/rcspmeve:EventProducer" {
    list EventJob {
      description "Additional definitions from MOM:min/max-elements:0/unbounded; Defines the information to be used to activate and configure an event job on the Managed Element.";
      key "eventJobId";
      leaf eventJobId {
        type leafref {
          path "../attributes/eventJobId";
        }
      }
      container attributes {
      uses EventJob-attributes;
      }
    }
  }

  augment "/emael:ManagedElement/emael:SystemFunctions/rcspmeve:PmEventM/rcspmeve:EventProducer" {
    list FileTypes {
      description "Additional definitions from MOM:min/max-elements:1/1;systemCreated; Configuration specified for each FileType. Usage is defined for each node type.";
      key "fileTypesId";
      leaf fileTypesId {
        type leafref {
          path "../attributes/fileTypesId";
        }
      }
      container attributes {
      uses FileTypes-attributes;
      }
    }
  }

  augment "/emael:ManagedElement/emael:SystemFunctions/rcspmeve:PmEventM/rcspmeve:EventProducer/rcspmeve:FileTypes" {
    list FileType {
      description "Additional definitions from MOM:min/max-elements:0/unbounded;systemCreated; Describes the file type collected by PM Event Producer.";
      key "fileTypeId";
      leaf fileTypeId {
        type leafref {
          path "../attributes/fileTypeId";
        }
      }
      container attributes {
      uses FileType-attributes;
      }
    }
  }

  augment "/emael:ManagedElement/emael:SystemFunctions/rcspmeve:PmEventM" {
    list EventProducer {
      description "Additional definitions from MOM:min/max-elements:0/unbounded;systemCreated; Event Producer. Allows for multiple types of Event Producer within an Application describing distinct Event functions and capabilities.";
      key "eventProducerId";
      leaf eventProducerId {
        type leafref {
          path "../attributes/eventProducerId";
        }
      }
      container attributes {
      uses EventProducer-attributes;
      }
    }
  }
  typedef CompressionTypes {
    description "Supported common File Compression Type(s).";
    type enumeration {
      enum GZIP {
        description "GNU zip file compression type.";
      }
    }
  }
  typedef DnsLookupSupport {
    description "Specifies if event producer supports DNS lookup.";
    type enumeration {
      enum DNS_LOOKUP_SUPPORTED {
        description "Event producer supports DNS lookup and streamDestination attribute under EventJob MOC can be assigned a value.";
      }
      enum DNS_LOOKUP_NOT_SUPPORTED {
        description "Event producer does not support DNS lookup and streamDestination attribute under EventJob MOC cannot be assigned a value.";
      }
    }
  }
  typedef EventStatus {
    description "Identifies the status of the Event Type";
    type enumeration {
      enum PRELIMINARY {
        description "The event is available and stepped in this version of the Managed Element, but is not yet approved.";
      }
      enum USED {
        description "The event is approved, available and stepped in this version of the Managed Element.";
      }
      enum DEPRECATED {
        description "The event is available in this version of the Managed Element, but as it is planned for removal it is not recommended for use";
      }
    }
  }
  typedef FilterMethod {
    description "Method of filter classification.";
    type enumeration {
      enum SINGLE_SELECT {
        description "Select one value only from a defined set of options.";
      }
      enum MULTI_SELECT {
        description "Select multiple values from a predefined set, separated by a space.";
      }
      enum INTERVAL {
        description "Select an interval value within the specified range.";
      }
      enum DISTINGUISHED_NAMES {
        description "Select one or more Distinguished Names (DNs).";
      }
      enum REGEXP {
        description "Regular expression.";
      }
    }
  }
  typedef JobControl {
    description "The level of MS control of the PMEvent job.";
    type enumeration {
      enum FULL {
        description "MS has Full control of the PMEvent Job. MS can create, delete, start and stop a job.";
      }
      enum STARTSTOP {
        description "<p>MS has Restricted control of the PMEvent Job. MS can stop and start a job, but cannot delete or create it.</p><p>The selection of this option for predefined jobs will indicate that no event can be added or removed. Updates can only to be done to the request state, destination attributes and job group under EventJob MOC. eventGroupRef and eventTypeRef are not modifiable in this condition.</p>";
      }
      enum VIEWONLY {
        description "MS can only view the PMEvent job.";
      }
    }
  }
  typedef JobState {
    description "Job state that has been requested.";
    type enumeration {
      enum ACTIVE {
        description "The job is requested to be activated.";
      }
      enum STOPPED {
        description "The job is requested to be stopped.";
      }
    }
  }
  typedef SessionState {
    description "Actual job state for an event job.";
    type enumeration {
      enum ACTIVATING {
        description "The job is switching from STOPPED to ACTIVE.";
      }
      enum ACTIVE {
        description "The job is producing events as intended.";
      }
      enum DEACTIVATING {
        description "The job is switching from ACTIVE to STOPPED.";
      }
      enum STOPPED {
        description "The job is passive, either by request or due to other reasons (e.g. overload conditions).";
      }
      enum FAILED {
        description "The job is permanently failed and deactivated. In this state it will not respond to further attempts to activate it. The job may however leave the FAILED state and enter the STOPPED state if the failure reason is removed.";
      }
    }
  }
  typedef TimePeriod {
    description "The different time periods associated with Event Job.";
    type enumeration {
      enum ONE_MIN {
        description "This represents a one-minute time period.";
      }
      enum FIVE_MIN {
        description "This represents a five-minute time period.";
      }
      enum FIFTEEN_MIN {
        description "This represents a 15-minute time period.";
      }
      enum THIRTY_MIN {
        description "This represents a 30-minute time period.";
      }
      enum ONE_HOUR {
        description "This represents a one-hour time period.";
      }
      enum TWELVE_HOUR {
        description "This represents a 12-hour (720-minute) time period.";
      }
      enum ONE_DAY {
        description "This represents a 24-hour (1440-minute) time period.";
      }
      enum TEN_SECONDS {
        description "This represents a 10-second time period.";
      }
      enum THIRTY_SECONDS {
        description "This represents a 30-second time period.";
      }
    }
  }
  grouping EventFilter-struct {
    description "Struct used to specify the event filter criteria.";
    leaf filterName {
      type string;
    }
    leaf filterValue {
      type string;
    }
  }
  grouping ManagedObjectClass-struct {
    description "This struct represents a Managed Object Class (MOC).";
    leaf moClassName {
      type string;
    }
    leaf mimName {
      type string;
    }
  }
  grouping EventCapabilities-attributes {
    leaf eventCapabilitiesId {
      description "Holds the name used when identifying the MO..";
      type string;
      mandatory true;
    }
    leaf maxNoOfJobs {
      description "This attribute defines the total maximum number of Event Jobs supported by the application..";
      type uint16;
      config false;
    }
    leaf fileLocation {
      description "Specifies the location or path where the Event Definition file will be stored..";
      type string;
    }
    leaf fileName {
      description "Specifies the name of the Event Definition file. This file is stored in the path specified in fileLocation attribute..";
      type string;
    }
    leaf fileVersion {
      description "Specifies the version of the Event Definition file..";
      type string;
    }
  }
  grouping EventFilterType-attributes {
    leaf eventFilterTypeId {
      description "Holds the name used when identifying the MO..";
      type string;
      mandatory true;
    }
    leaf description {
      description "Event Filter Type description..";
      type string;
      config false;
    }
    leaf filterMethod {
      description "Method of filter classification..";
      type enumeration {
        enum SINGLE_SELECT;
        enum MULTI_SELECT;
        enum INTERVAL;
        enum DISTINGUISHED_NAMES;
        enum REGEXP;
      }
      config false;
    }
    leaf valueSpec {
      description "Specifies the possible values..";
      type string;
      config false;
    }
    leaf defaultValue {
      description "Defined format of filter type value..";
      type string;
      config false;
    }
  }
  grouping EventGroup-attributes {
    leaf eventGroupId {
      description "Holds the name used when identifying the MO..";
      type string;
      mandatory true;
    }
    leaf description {
      description "Describes the content and purpose of the event group..";
      type string;
      config false;
    }
    list moClass {
      config false;
      description "The Managed Object Class that generates events belonging to the event group..";
      uses ManagedObjectClass-struct;
    }
    leaf eventGroupVersion {
      description "Event Group version identifier. Unique version identifier associated with a change to the contents of the Event Group, where new Event Types have been added..";
      type string;
      config false;
    }
    leaf-list validFilters {
      description "Defines valid filter type definitions for this Event Group..";
      type string;
      ordered-by user;
      min-elements 0;
    }
    leaf generation {
      description "The Switching domain or domains to which this measurement is applicable. For e.g. GSM, UMTS, EPS, GSM/UMTS..";
      type string;
      config false;
    }
  }
  grouping EventJob-attributes {
    leaf eventJobId {
      description "Holds the name used when identifying the MO..";
      type string;
      mandatory true;
    }
    leaf description {
      description "Describes the content and purpose of the job..";
      type string;
    }
    list eventFilter {
      key "id";
      leaf id {
        type uint32;
        description "Synthetic key for struct sequence entry.";
      }
      min-elements 0;
      uses EventFilter-struct;
    }
    leaf requestedJobState {
      description "The requested state of the job. It represents the state that the job has been ordered to reach..";
      type enumeration {
        enum ACTIVE;
        enum STOPPED;
      }
    }
    leaf currentJobState {
      description "The current state of the job..";
      type enumeration {
        enum ACTIVATING;
        enum ACTIVE;
        enum DEACTIVATING;
        enum STOPPED;
        enum FAILED;
      }
      config false;
    }
    leaf fileOutputEnabled {
      description "Indicates if event data output will be written to file..";
      type boolean;
      mandatory true;
    }
    leaf streamDestinationIpAddress {
      description "The IP address of the server that event data can be streamed to, if set. Used only for IP address values..";
      type string;
    }
    leaf streamDestinationPort {
      description "The server port that event data can be streamed to, if set..";
      type ietfinet:port-number;
    }
    leaf reportingPeriod {
      description "Specifies how often event data will be made available. Only applicable when fileOutputEnabled =true. The value must be valid according to the supportedReportingPeriods set by the Managed Element..";
      type enumeration {
        enum ONE_MIN;
        enum FIVE_MIN;
        enum FIFTEEN_MIN;
        enum THIRTY_MIN;
        enum ONE_HOUR;
        enum TWELVE_HOUR;
        enum ONE_DAY;
        enum TEN_SECONDS;
        enum THIRTY_SECONDS;
      }
    }
    leaf streamOutputEnabled {
      description "Indicates whether event data output will be streamed. Can be set to true if one of the subsequent conditions apply. - streamDestination, streamDestinationIpAddress, streamDestinationPort are set. Note: streamDestination will take precedence if all three are set. If port is not specified in streamDestination, the port specified in streamDestinationPort is used. - streamDestinationIpAddress and streamDestinationPort are set and streamDestination is not set. Note: The stream must be set up with streamDestinationIpAddress and streamDestinationPort. - streamDestination and streamDestinationPort are set and streamDestinationIpAddress is not set. Note: If streamDestination has no port specified, the port specified in streamDestinationPort is used. - streamDestination is set and streamDestinationIpAddress and streamDestinationPort are not set. Note: If streamDestination has no port specified then no stream is set up..";
      type boolean;
      mandatory true;
    }
    leaf jobControl {
      description "Describes the level of MS control of the event job..";
      type enumeration {
        enum FULL;
        enum STARTSTOP;
        enum VIEWONLY;
      }
      config false;
    }
    leaf-list eventGroupRef {
      description "The Event Group or Event Groups selected for the job. This attribute is set when an entire group or entire groups of events are to be selected for the job..";
      type string;
      ordered-by user;
      min-elements 0;
    }
    leaf-list eventTypeRef {
      description "The Event Type or Event Types selected for the job. This attribute is set when an individual event or a subset of the events within a group or groups are to be selected for the job..";
      type string;
      ordered-by user;
      min-elements 0;
    }
    leaf fileCompressionType {
      description "Compression Type to be applied to file output. Only valid when fileOutputEnabled = true. If this attribute is not set, no compression will be applied to the file output. Can only be assigned a value according to the capability supportedCompressionTypes in the FilePullCapabilities MOC..";
      type enumeration {
        enum GZIP;
      }
    }
    leaf streamCompressionType {
      description "Compression Type to be applied to stream output. Only valid when streamOutputEnabled = true. If this attribute is not set, no compression will be applied to the stream output. Can only be assigned a value according to the capability supportedCompressionTypes in the StreamingCapabilities MOC..";
      type enumeration {
        enum GZIP;
      }
    }
    leaf jobGroup {
      description "Multiple jobs which end up in common set of files, have same jobGroup. So, this identifies the job grouping. A jobGroup string is a non-empty sequence of characters matching the regexp [a-zA-Z0-9-]+.";
      type string;
    }
    leaf streamDestination {
      description "FQDN of the server that event data can be streamed to, if set. Consists of a DNS address and an optional port number. Port may be specified by appending a colon followed by the port number to the host name, for example, <DistinguishedName :PortNumber>. If no port number is provided, the value of port number should be set in streamDestinationPort. Can only be assigned a value if dnsLookupSupport in the StreamingCapabilities MOC is set to true..";
      type string;
    }
  }
  grouping EventProducer-attributes {
    leaf eventProducerId {
      description "Holds the name used when identifying the MO. This is non-empty sequence of characters matching the regexp [a-zA-Z0-9-]+.";
      type string;
      mandatory true;
    }
    leaf eventProducerName {
      description "The name of the Event Producer. This will be human readable and will have value regexp [a-zA-Z0-9-_ ]+.";
      type string;
      config false;
    }
    leaf generation {
      description "Determines if Event Producer concerns GSM, UMTS, EPS, combined (GSM+UMTS+EPS), IMS or 5GS measurements. Values are defined in 3GPP standard 32:404.";
      type string;
      config false;
    }
    leaf associatedFunction {
      description "Indicates the Managed Function that is associated to the Event Producer.";
      type string;
      config false;
    }
  }
  grouping EventType-attributes {
    leaf eventTypeId {
      description "Holds the name used when identifying the MO..";
      type string;
      mandatory true;
    }
    leaf triggerDescription {
      description "Contains information about what causes the event to be raised..";
      type string;
      config false;
    }
    leaf eventStatus {
      description "Indicates the status of the Event Type.";
      type enumeration {
        enum PRELIMINARY;
        enum USED;
        enum DEPRECATED;
      }
      config false;
    }
    leaf periodicity {
      description "Indicates the periodicity for periodic events. For non-periodic event it will not be set..";
      type uint64;
      config false;
    }
  }
  grouping FilePullCapabilities-attributes {
    leaf filePullCapabilitiesId {
      description "Holds the name used when identifying the MO..";
      type string;
      mandatory true;
    }
    leaf-list supportedReportingPeriods {
      description "Specifies the list of reporting periods supported by the ME..";
      type TimePeriod;
      min-elements 1;
    }
    leaf outputDirectory {
      description "Specifies the absolute file path to the Managed Element file system. Event files are fetched form this location..";
      type string;
      config false;
    }
    leaf maxNoOfEventFiles {
      description "Specifies the maximum number of Result Output Period (ROP) files that are maintained in the ME. If a new file is created and the limit is exceeded, the oldest file is deleted. This is an upper-system limit, and support for it cannot be guaranteed in high-load conditions..";
      type uint16;
      config false;
    }
    leaf alignedReportingPeriod {
      description "The managed element will align its reporting periods to the hour if set to true.; Default value: true.";
      type boolean;
      config false;
      default "true";
    }
    leaf-list supportedCompressionTypes {
      description "Supported file compression type or types. If this attribute is not present, compression of event data files is not supported..";
      type CompressionTypes;
      min-elements 0;
      max-elements 2;
    }
    leaf finalROP {
      description "Indicates if an event file for the last ROP is expected. When an event job is stopped, this attribute specifies whether a result file for the last ROP is expected (true), or not expected (false).; Default value: false.";
      type boolean;
      config false;
      default "false";
    }
  }
  grouping FileType-attributes {
    leaf fileTypeId {
      description "Holds the name used when identifying the MO..";
      type string;
      mandatory true;
    }
    leaf description {
      description "File type..";
      type string;
      config false;
    }
    leaf fileSizeMax {
      description "Maximum size for this file type..";
      type string;
      config false;
    }
    leaf fileSizePercent {
      description "Configurable percentage of the fileSizeMax to be used as file size..";
      type string;
      mandatory true;
    }
  }
  grouping FileTypes-attributes {
    leaf fileTypesId {
      description "Holds the name used when identifying the MO..";
      type string;
      mandatory true;
    }
    leaf userLabel {
      description "An additional descriptive text..";
      type string;
    }
  }
  grouping PmEventM-attributes {
    leaf pmEventMId {
      description "Holds the name used when identifying the MO..";
      type string;
      mandatory true;
    }
  }
  grouping StreamingCapabilities-attributes {
    leaf streamCapabilitiesId {
      description "Holds the name used when identifying the MO..";
      type string;
      mandatory true;
    }
    leaf-list supportedCompressionTypes {
      description "Supported stream compression type or types. If this attribute is not present, the compression of event data streams is not supported..";
      type CompressionTypes;
      min-elements 0;
      max-elements 2;
    }
    leaf dnsLookupSupport {
      description "Specifies whether event producer supports DNS lookup..";
      type enumeration {
        enum DNS_LOOKUP_SUPPORTED;
        enum DNS_LOOKUP_NOT_SUPPORTED;
      }
      config false;
    }
  }
}
