module ericsson-sfp-module-radio {
  yang-version 1.1;
  namespace "urn:com:ericsson:ecim:ReqSfpModule";
  prefix sfpmdrdo;
  import ericsson-equip-radio {
    prefix equiprdo;
  }
  import ericsson-field-replaceable-unit-radio {
    prefix frurdo;
  }
  import ericsson-managed-element {
    prefix emael;
  }
  description "Auto-generated from Ericsson CPI MOM XML 15554-lza7016014_33-v1uenfk.xml\nReqSfpModule.";
  revision "2026-03-29" {
    description "Ericsson G3G4, version: CXP2020502/2-R32C08";
  }

  augment "/emael:ManagedElement/equiprdo:Equipment/frurdo:FieldReplaceableUnit" {
    list SfpModule {
      description "Additional definitions from MOM:min/max-elements:0/unbounded;root;systemCreated; Created when an SFP-module is detected. Xcede-module is treated as a special type of SFP-module. The RDN of this MO is the same as for the related port MO.";
      key "sfpModuleId";
      leaf sfpModuleId {
        type leafref {
          path "../attributes/sfpModuleId";
        }
      }
      container attributes {
      uses SfpModule-attributes;
      }
    }
  }
  typedef AdmState {
    description "Administrative state of a resource.";
    type enumeration {
      enum LOCKED {
        description "The resource is administratively prohibited from performing services for its users.";
      }
      enum UNLOCKED {
        description "The resource is administratively permitted to perform services for its users. This is independent of its inherent operability.";
      }
      enum SHUTTINGDOWN {
        description "Use of the resource is administratively permitted to existing instances of use only. While the system remains in the shutting down state the manager may at any time cause the managed object to revert to the locked state.";
      }
    }
  }
  typedef AvailStatus {
    description "The availability status is used to qualify the operational state. It indicates why the operational state has changed its value.";
    type enumeration {
      enum IN_TEST {
        description "The resource is undergoing a test procedure. If the administrative state is locked or shutting down, normal users are prevented from using the resource.";
      }
      enum FAILED {
        description "The resource has an internal fault that prevents it from operating.";
      }
      enum POWER_OFF {
        description "The resource requires power to be applied and is not powered on.";
      }
      enum OFF_LINE {
        description "The resource requires a routine operation to be performed. This routine operation is to place the resource online and make it available for use. The operation may be manual or automatic, or both. The operational state is disabled.";
      }
      enum OFF_DUTY {
        description "The resource has been made inactive by an internal control process.";
      }
      enum DEPENDENCY {
        description "The resource cannot operate because some other resource on which it depends is unavailable.";
      }
      enum DEGRADED {
        description "The service available from the resource is degraded in some respect.";
      }
      enum NOT_INSTALLED {
        description "The resource represented by the managed object is not present, or is incomplete.";
      }
      enum LOG_FULL {
        description "Indicates a log full condition. The semantics are defined in CCITT Rec. X.735 | ISO/IEC 10164-6.";
      }
      enum DEPENDENCY_LOCKED {
        description "The administrative state of a resource that this resource depends on is locked. Alternatively, the availability status of the other resource is dependency locked.";
      }
      enum DEPENDENCY_FAILED {
        description "The availability status of a resource that this resource depends on is failed or dependency failed.";
      }
      enum DEPENDENCY_SHUTTINGDOWN {
        description "The administrative state of a resource that this resource depends on is shutting down. Alternatively, the availability status of the other resource is dependency shutting down.";
      }
      enum DEPENDENCY_RECOVERY {
        description "Resource that this resource depends on is undergoing a recovery procedure.";
      }
      enum DEPENDENCY_HOLDING {
        description "Resource cannot operate because some other resource on which it depends is currently unavailable. The situation is expected to be resolved. Actions to facilitate dependency resolution may be ongoing.";
      }
    }
  }
  typedef ConnectorType {
    description "Enum for connector type for sfpMediaType.";
    type enumeration {
      enum NO_SEPARABLE_CONNECTOR {
        description "Value representing a non present media type.";
      }
      enum ELECTRICAL {
        description "Value representing an electrical media type.";
      }
      enum OPTICAL {
        description "Value representing an optical media type.";
      }
      enum UNKNOWN {
        description "Value representing an unknown media type.";
      }
    }
  }
  typedef OperState {
    description "Operational states of a resource.";
    type enumeration {
      enum DISABLED {
        description "The resource is totally inoperable.";
      }
      enum ENABLED {
        description "The resource is partially or fully operable.";
      }
    }
  }
  grouping SfpProductData-struct {
    description "Sfp product data.";
    leaf manufacturerDesignation {
      description "length 0..16.";
      type string {
        length "0..16";
      }
    }
    leaf manufacturerId {
      description "length 0..16.";
      type string {
        length "0..16";
      }
    }
    leaf manufacturerRevision {
      description "length 0..8.";
      type string {
        length "0..8";
      }
    }
    leaf negotiatedBitRate {
      description "length 0..8.";
      type string {
        length "0..8";
      }
    }
    leaf productionDate {
      description "length 0..8.";
      type string {
        length "0..8";
      }
    }
    leaf productNumber {
      description "length 0..14.";
      type string {
        length "0..14";
      }
    }
    leaf productRevision {
      description "length 0..8.";
      type string {
        length "0..8";
      }
    }
    leaf serialNumber {
      description "length 0..16.";
      type string {
        length "0..16";
      }
    }
  }
  grouping SfpModule-attributes {
    leaf sfpModuleId {
      description "The value component of the RDN..";
      type string;
      mandatory true;
    }
    leaf-list availabilityStatus {
      description "It contains details about operationalState..";
      type AvailStatus;
      min-elements 0;
    }
    leaf operationalState {
      description "It contains details about operationalState..";
      type enumeration {
        enum DISABLED;
        enum ENABLED;
      }
      config false;
    }
    leaf-list reservedBy {
      description "Contains a list of MO instances that reserve this MO instance..";
      type string;
      min-elements 0;
    }
    leaf administrativeState {
      description "The administrative state. If set to SHUTTINGDOWN, the state will immediately be brought to LOCKED..";
      type enumeration {
        enum LOCKED;
        enum UNLOCKED;
        enum SHUTTINGDOWN;
      }
    }
    list productData {
      config false;
      description "Information on the installed small form-factor pluggable (SFP) module. A blank value indicates the data is currently unavailable..";
      uses SfpProductData-struct;
    }
    leaf sfpMediaType {
      description "The connector type of the attached SFP module..";
      type enumeration {
        enum NO_SEPARABLE_CONNECTOR;
        enum ELECTRICAL;
        enum OPTICAL;
        enum UNKNOWN;
      }
      config false;
    }
    leaf pmSfpTemperature {
      description "Measured temperature for SFP value is reported with offset of +1000. To convert it to Celcius degrees, use following formula: T[C] = (value_reported - 1000)/10. For example, a report value of 816 represents -18.4 degrees C, value of 1305 represents 30.5 degrees C. This counter is not applicable for Xcede Module. Counter is marked as suspect when the SFP module is not supported by Ericsson..";
      type int32;
      config false;
    }
    leaf pmSfpVoltage {
      description "Measured voltage for the SFP. Unit: 0.0001 V (100 uV). This counter is not applicable for Xcede Module. Counter is marked as suspect when the SFP module is not supported by Ericsson..";
      type int32;
      config false;
    }
  }
}
