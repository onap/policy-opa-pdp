module ericsson-equip-radio {
  yang-version 1.1;
  namespace "urn:com:ericsson:ecim:ReqEquipment";
  prefix equiprdo;
  import ericsson-managed-element {
    prefix emael;
  }
  description "Auto-generated from Ericsson CPI MOM XML 15554-lza7016014_33-v1uenfk.xml";
  revision "2026-03-29" {
    description "Ericsson G3G4, version: CXP2020502/2-R32C08";
  }

  augment "/emael:ManagedElement" {
    list Equipment {
      description "Additional definitions from MOM:min/max-elements:1/1;root;systemCreated; This MO is used as a structural element for the network element, that is, it only acts as a container for other MOs. This MO structures the equipment of the network element. This MO is created automatically and cannot be deleted. The RDN of this MO is Equipment=1.";
      key "equipmentId";
      leaf equipmentId {
        type leafref {
          path "../attributes/equipmentId";
        }
      }
      container attributes {
      uses Equipment-attributes;
      }
    }
  }
  grouping Equipment-attributes {
    leaf equipmentId {
      description "The value component of the RDN. It is set automatically when the MO instance is created..";
      type string;
      mandatory true;
    }
    leaf userLabel {
      description "userLabel.; length 1..128.";
      type string {
        length "1..128";
      }
    }
  }
}
