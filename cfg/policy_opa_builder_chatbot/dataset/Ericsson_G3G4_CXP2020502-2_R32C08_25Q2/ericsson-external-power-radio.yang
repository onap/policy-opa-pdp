module ericsson-external-power-radio {
  yang-version 1.1;
  namespace "urn:com:ericsson:ecim:ResExternalPower";
  prefix expwrdo;
  import ericsson-equipment-support-function-radio {
    prefix eqsupfnrdo;
  }
  import ericsson-managed-element {
    prefix emael;
  }
  description "Auto-generated from Ericsson CPI MOM XML 15554-lza7016014_33-v1uenfk.xml\nLogical resource providing power to radio node. One instance per radio node, child of first instance of EquipmentSupportFunction. RDN of this MO is ExternalPower=1.";
  revision "2026-03-29" {
    description "Ericsson G3G4, version: CXP2020502/2-R32C08";
  }

  augment "/emael:ManagedElement/eqsupfnrdo:EquipmentSupportFunction" {
    list ExternalPower {
      description "Additional definitions from MOM:min/max-elements:0/1;root;systemCreated; Logical resource providing power to radio node. One instance per radio node, child of first instance of EquipmentSupportFunction. RDN of this MO is ExternalPower=1.";
      key "externalPowerId";
      status deprecated;
      leaf externalPowerId {
        type leafref {
          path "../attributes/externalPowerId";
        }
        status deprecated;
      }
      container attributes {
      uses ExternalPower-attributes;
      }
    }
  }
  typedef AvailStatus {
    description "The availability status is used to qualify the operational state. It indicates why the operational state has changed its value.";
    type enumeration {
      enum IN_TEST {
        description "The resource is undergoing a test procedure. If the administrative state is locked or shutting down, normal users are prevented from using the resource.";
      }
      enum FAILED {
        description "The resource has an internal fault that prevents it from operating.";
      }
      enum POWER_OFF {
        description "The resource requires power to be applied and is not powered on.";
      }
      enum OFF_LINE {
        description "The resource requires a routine operation to be performed. This routine operation is to place the resource online and make it available for use. The operation may be manual or automatic, or both. The operational state is disabled.";
      }
      enum OFF_DUTY {
        description "The resource has been made inactive by an internal control process.";
      }
      enum DEPENDENCY {
        description "The resource cannot operate because some other resource on which it depends is unavailable.";
      }
      enum DEGRADED {
        description "The service available from the resource is degraded in some respect.";
      }
      enum NOT_INSTALLED {
        description "The resource represented by the managed object is not present, or is incomplete.";
      }
      enum LOG_FULL {
        description "Indicates a log full condition. The semantics are defined in CCITT Rec. X.735 | ISO/IEC 10164-6.";
      }
      enum DEPENDENCY_LOCKED {
        description "The administrative state of a resource that this resource depends on is locked. Alternatively, the availability status of the other resource is dependency locked.";
      }
      enum DEPENDENCY_FAILED {
        description "The availability status of a resource that this resource depends on is failed or dependency failed.";
      }
      enum DEPENDENCY_SHUTTINGDOWN {
        description "The administrative state of a resource that this resource depends on is shutting down. Alternatively, the availability status of the other resource is dependency shutting down.";
      }
      enum DEPENDENCY_RECOVERY {
        description "Resource that this resource depends on is undergoing a recovery procedure.";
      }
      enum DEPENDENCY_HOLDING {
        description "Resource cannot operate because some other resource on which it depends is currently unavailable. The situation is expected to be resolved. Actions to facilitate dependency resolution may be ongoing.";
      }
    }
  }
  typedef OperState {
    description "Operational states of a resource.";
    type enumeration {
      enum DISABLED {
        description "The resource is totally inoperable.";
      }
      enum ENABLED {
        description "The resource is partially or fully operable.";
      }
    }
  }
  grouping ExternalPower-attributes {
    leaf externalPowerId {
      description "The value component of the RDN.; MOM flags: restricted, noNotification; Status info: Since 23.Q2. Planned to be removed..";
      type string;
      mandatory true;
      status deprecated;
    }
    leaf operationalState {
      description "The operational state.; Status info: Since 23.Q2. Reflected in operationalState of dependent MOs. Planned to be removed.; Specification: ITU-T Rec. X.731.";
      type enumeration {
        enum DISABLED;
        enum ENABLED;
      }
      config false;
      status deprecated;
    }
    leaf-list availabilityStatus {
      description "The availability status. It contains details about operationalState.; Status info: Since 23.Q2. Reflected in availabilityStatus of dependent MOs. Planned to be removed.; Specification: ITU-T Rec. X.731.";
      type AvailStatus;
      min-elements 0;
    }
  }
}
