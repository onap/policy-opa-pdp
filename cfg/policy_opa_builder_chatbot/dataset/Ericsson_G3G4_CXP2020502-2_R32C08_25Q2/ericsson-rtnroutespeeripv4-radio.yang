module ericsson-rtnroutespeeripv4-radio {
  yang-version 1.1;
  namespace "urn:com:ericsson:ecim:RtnRoutesPeerIPv4";
  prefix rtnroute;
  import ericsson-l3-router-rtn-radio {
    prefix l3rtrdo;
  }
  import ietf-inet-types {
    prefix ietfinet;
  }
  import ericsson-managed-element {
    prefix emael;
  }
  description "Auto-generated from Ericsson CPI MOM XML 15554-lza7016014_33-v1uenfk.xml\nIPv4 Peer. Used when static route next hop is IP Address.";
  revision "2026-03-29" {
    description "Ericsson G3G4, version: CXP2020502/2-R32C08";
  }

  augment "/emael:ManagedElement/emael:Transport/l3rtrdo:Router" {
    list PeerIPv4 {
      description "Additional definitions from MOM:min/max-elements:0/unbounded;root; Provides IPv4 peer information.";
      key "peerIPv4Id";
      leaf peerIPv4Id {
        type leafref {
          path "../attributes/peerIPv4Id";
        }
      }
      container attributes {
      uses PeerIPv4-attributes;
      }
    }
  }
  typedef BfdStaticRoutesInterfaceType {
    description "State of bfdStaticRoutes.";
    type enumeration {
      enum DISABLED {
      }
      enum ENABLED {
      }
    }
  }
  grouping PeerIPv4-attributes {
    leaf address {
      description "IPv4 address or fully qualified domain name of peer..";
      type union {
        type ietfinet:ip-address;
        type ietfinet:domain-name;
      }
      mandatory true;
    }
    leaf bfdProfile {
      description "Reference to BfdProfile MO containing BFD parameters used for BFD sessions towards this IP peer..";
      type string;
    }
    leaf bfdStaticRoutes {
      description "Enables/disables BFD monitoring of static routes with this peer as netxthop. If set to ENABLED, BFD monitoring is enabled for static routes where address of NextHop MO is equal to address of this PeerIPv4 MO. If bfdProfile is set on this MO, BFD session uses parameters configured in referred BfdProfile MO. If bfdProfile is not set on this MO, BFD session uses parameters configured in BfdProfile MO referred from InterfaceIPv4 MO bfdProfile attribute. If bfdProfile is not set on this MO and neither InterfaceIPv4 MO, BFD monitoring is not enabled. If set to DISABLED, BFD monitoring is disabled for static routes where address of NextHop MO is equal to address of this PeerIPv4 MO. This overrides bfdStaticRoutes attribute on InterfaceIPv4 MO. If not set, BFD monitoring can still be enabled towards this peer by setting bfdStaticRoutes attribute to ENABLED on InterfaceIPv4 MO. bfdProfile on this PeerIPv4 MO is in this case not used. If BFD monitoring is enabled, all static routes with this peer as nexthop are monitored, unless explicitly disabled per NextHop MO. BFD monitoring of PBR nexthops is not controlled by this attribute. If this attribute is set to ENABLED (that is BFD monitoring for static routes is enabled for this peer) and bfdProfile is set in this PeerIPv4 MO, BfdProfile MO referred from this PeerIPv4 MO is used also for PBR nexthops..";
      type enumeration {
        enum DISABLED;
        enum ENABLED;
      }
    }
    leaf peerIPv4Id {
      description "The value component of the RDN..";
      type string;
      mandatory true;
    }
    leaf-list reservedBy {
      description "Contains a list of MO instances that reserve this MO instance..";
      type string;
      min-elements 0;
    }
  }
}
