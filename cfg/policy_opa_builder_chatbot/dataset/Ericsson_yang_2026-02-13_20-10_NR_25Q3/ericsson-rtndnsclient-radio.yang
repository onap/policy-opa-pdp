module ericsson-rtndnsclient-radio {
  yang-version 1.1;
  namespace "urn:com:ericsson:ecim:RtnDnsClient";
  prefix rtndnscl;
  import ietf-inet-types {
    prefix ietfinet;
  }
  import ericsson-l3-router-rtn-radio {
    prefix l3rtrdo;
  }
  import ericsson-managed-element {
    prefix emael;
  }
  import ericsson-yang-types {
    prefix eytypes;
  }
  description "Auto-generated from Ericsson ECIM (MOM XML).";
  revision 2026-02-13 {
    description "Initial auto-generated revision. Generated at 2026-02-13 20:11.";
  }

  augment "/emael:ManagedElement/emael:Transport/l3rtrdo:Router/DnsClient" {
    list DomainFilter {
      description "Additional definitions from MOM:min/max-elements:0/2; Represents domain filter, that enables sending DNS requests for one or more domains to special DNS server. Default DNS server is defined in DnsClient MO and DomainFilter MO can provide exceptions for specific domains.";
      key "domainFilterId";
      leaf domainFilterId {
        type leafref {
          path "../attributes/domainFilterId";
        }
      }
      container attributes {
        uses DomainFilter-attributes;
      }
    }
  }

  augment "/emael:ManagedElement/emael:Transport/l3rtrdo:Router" {
    list DnsClient {
      description "Additional definitions from MOM:min/max-elements:0/1;root; Represents DNS client.";
      key "dnsClientId";
      leaf dnsClientId {
        type leafref {
          path "../attributes/dnsClientId";
        }
      }
      container attributes {
        uses DnsClient-attributes;
      }
    }
  }
  typedef DnsConfigMode {
    type enumeration {
      enum MANUAL;
      enum AUTOMATIC;
    }
  }
  grouping DnsClient-attributes {
    leaf configurationMode {
      type enumeration {
        enum MANUAL;
        enum AUTOMATIC;
      }
    }
    leaf dnsClientId {
      type string;
      mandatory true;
    }
    leaf dscp {
      type eytypes:uint8_range_0-63;
      default "40";
      description "range 0..63; Default value: 40.";
    }
    leaf localIpAddress {
      type ietfinet:ip-address;
    }
    leaf-list reservedBy {
      type string;
    }
    leaf-list serverAddress {
      type string;
    }
    leaf-list usedServerAddress {
      type string;
    }
    leaf userLabel {
      type string {
        length "1..128";
      }
      description "length 1..128.";
    }
  }
  grouping DomainFilter-attributes {
    leaf-list domain {
      type string {
        pattern "(([a-zA-Z0-9]|[a-zA-Z0-9][a-zA-Z0-9\\-]*[a-zA-Z0-9])\\.)*([A-Za-z0-9]|[A-Za-z0-9][A-Za-z0-9\\-]*[A-Za-z0-9])";
      }
      min-elements 1;
    }
    leaf domainFilterId {
      type string;
      mandatory true;
    }
    leaf-list serverAddress {
      type string;
      min-elements 1;
    }
    leaf userLabel {
      type string {
        length "1..128";
      }
      description "length 1..128.";
    }
  }
}
