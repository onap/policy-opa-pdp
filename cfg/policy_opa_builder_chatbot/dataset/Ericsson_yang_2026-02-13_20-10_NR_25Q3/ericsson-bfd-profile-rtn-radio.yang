module ericsson-bfd-profile-rtn-radio {
  yang-version 1.1;
  namespace "urn:com:ericsson:ecim:RtnBfdProfile";
  prefix bfdpfrdo;
  import ietf-inet-types {
    prefix ietfinet;
  }
  import ericsson-l3-router-rtn-radio {
    prefix l3rtrdo;
  }
  import ericsson-managed-element {
    prefix emael;
  }
  import ericsson-yang-types {
    prefix eytypes;
  }
  description "Auto-generated from Ericsson ECIM (MOM XML).";
  revision 2026-02-13 {
    description "Initial auto-generated revision. Generated at 2026-02-13 20:11.";
  }

  augment "/emael:ManagedElement/emael:Transport" {
    list BfdProfile {
      description "Additional definitions from MOM:min/max-elements:0/unbounded;root; This class defines BFD Session Profile. Maximum number of BfdProfile MOs defined under Transport MO or under Router MO is limited to: - For Baseband in RAN Compute Group 1, 2, or 3: 64, - For Baseband in RAN Compute Group 4 or higher: 120.";
      key "bfdProfileId";
      leaf bfdProfileId {
        type leafref {
          path "../attributes/bfdProfileId";
        }
      }
      container attributes {
        uses BfdProfile-attributes;
      }
    }
  }

  augment "/emael:ManagedElement/emael:Transport/l3rtrdo:Router" {
    list BfdProfile {
      description "Additional definitions from MOM:min/max-elements:0/unbounded;root; This class defines BFD Session Profile. Maximum number of BfdProfile MOs defined under Transport MO or under Router MO is limited to: - For Baseband in RAN Compute Group 1, 2, or 3: 64, - For Baseband in RAN Compute Group 4 or higher: 120.";
      key "bfdProfileId";
      leaf bfdProfileId {
        type leafref {
          path "../attributes/bfdProfileId";
        }
      }
      container attributes {
        uses BfdProfile-attributes;
      }
    }
  }
  grouping BfdProfile-attributes {
    leaf bfdProfileId {
      type string;
      mandatory true;
    }
    leaf detectionMultiplier {
      type ietfinet:ip-address;
      description "range 1..10; Default value: 5.";
    }
    leaf dscp {
      type eytypes:uint8_range_0-63;
      default "48";
      description "range 0..63; Default value: 48.";
    }
    leaf intervalRxMinRequired {
      type uint32 {
        range "10..60000";
      }
      default "100";
      units "ms";
      description "range 10..60000; Default value: 100.";
    }
    leaf intervalTxMinDesired {
      type uint32 {
        range "10..60000";
      }
      default "100";
      units "ms";
      description "range 10..60000; Default value: 100.";
    }
    leaf intervalTxSessionDown {
      type uint32 {
        range "1000..30000";
      }
      default "2000";
      units "ms";
      description "range 1000..30000; Default value: 2000.";
    }
    leaf-list reservedBy {
      type string;
    }
  }
}
