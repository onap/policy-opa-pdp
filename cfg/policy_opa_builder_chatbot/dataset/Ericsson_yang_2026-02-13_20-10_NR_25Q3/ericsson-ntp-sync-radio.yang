module ericsson-ntp-sync-radio {
  yang-version 1.1;
  namespace "urn:com:ericsson:ecim:RsyncNtp";
  prefix ntprdo;
  import ietf-inet-types {
    prefix ietfinet;
  }
  import ericsson-managed-element {
    prefix emael;
  }
  import ericsson-yang-types {
    prefix eytypes;
  }
  description "Auto-generated from Ericsson ECIM (MOM XML).";
  revision 2026-02-13 {
    description "Initial auto-generated revision. Generated at 2026-02-13 20:11.";
  }

  augment "/emael:ManagedElement/emael:Transport" {
    list Ntp {
      description "Additional definitions from MOM:min/max-elements:0/1;root; This MO class is the top class for NTP management.";
      key "ntpId";
      leaf ntpId {
        type leafref {
          path "../attributes/ntpId";
        }
      }
      container attributes {
        uses Ntp-attributes;
      }
    }
  }

  augment "/emael:ManagedElement/emael:Transport/Ntp" {
    list NtpFrequencySync {
      description "Additional definitions from MOM:min/max-elements:0/8; This MO class models a NTP frequency reference used for Network Synchronization. The addressIPv4Reference attribute is the reference to the source IPv4 address to be used in NTP protocol exchange with NTP server.";
      key "ntpFrequencySyncId";
      leaf ntpFrequencySyncId {
        type leafref {
          path "../attributes/ntpFrequencySyncId";
        }
      }
      container attributes {
        uses NtpFrequencySync-attributes;
      }
    }
  }
  typedef AvailStatus {
    type enumeration {
      enum IN_TEST;
      enum FAILED;
      enum POWER_OFF;
      enum OFF_LINE;
      enum OFF_DUTY;
      enum DEPENDENCY;
      enum DEGRADED;
      enum NOT_INSTALLED;
      enum LOG_FULL;
      enum DEPENDENCY_LOCKED;
      enum DEPENDENCY_FAILED;
      enum DEPENDENCY_SHUTTINGDOWN;
    }
  }
  typedef NtpFrequencySyncStatus {
    type enumeration {
      enum UNKNOWN;
      enum NO_FAULT;
      enum PDV_PROBLEM;
      enum UNREACHABLE_REFERENCE;
      enum HIGH_PACKET_DROP;
      enum LOW_STRATUM;
      enum LI_ERROR;
      enum QL_TOO_LOW;
      enum UNRESOLVED_SERVER_ADDRESS;
    }
  }
  typedef OperState {
    type enumeration {
      enum DISABLED;
      enum ENABLED;
    }
  }
  grouping Ntp-attributes {
    leaf ntpId {
      type string;
      mandatory true;
    }
  }
  grouping NtpFrequencySync-attributes {
    leaf addressIPv4Reference {
      type ietfinet:ipv4-address;
      mandatory true;
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
      }
    }
    leaf cachedIpAddress {
      type ietfinet:ip-address;
      config false;
    }
    leaf dscp {
      type eytypes:uint8_range_0-63;
      default "54";
      description "range 0..63; Default value: 54.";
    }
    leaf ingressUdpPort {
      type ietfinet:port-number;
      config false;
    }
    leaf ntpFrequencySyncId {
      type string;
      mandatory true;
    }
    leaf-list ntpFrequencySyncStatus {
      type enumeration {
        enum UNKNOWN;
        enum NO_FAULT;
        enum PDV_PROBLEM;
        enum UNREACHABLE_REFERENCE;
        enum HIGH_PACKET_DROP;
        enum LOW_STRATUM;
        enum LI_ERROR;
        enum QL_TOO_LOW;
        enum UNRESOLVED_SERVER_ADDRESS;
      }
    }
    leaf operationalState {
      type enumeration {
        enum DISABLED;
        enum ENABLED;
      }
      config false;
    }
    leaf-list reservedBy {
      type string;
    }
    leaf syncServerNtpIpAddress {
      type ietfinet:ip-address;
      mandatory true;
    }
  }
}
