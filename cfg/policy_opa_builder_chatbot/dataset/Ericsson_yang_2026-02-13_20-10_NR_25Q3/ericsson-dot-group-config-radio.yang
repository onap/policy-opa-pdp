module ericsson-dot-group-config-radio {
  yang-version 1.1;
  namespace "urn:com:ericsson:ecim:ReqDotGroupConfig";
  prefix dgrpcfrdo;
  import ericsson-field-replaceable-unit-radio {
    prefix frurdo;
  }
  import ericsson-managed-element {
    prefix emael;
  }
  import ericsson-equip-radio {
    prefix equiprdo;
  }
  description "Auto-generated from Ericsson ECIM (MOM XML).";
  revision 2026-02-13 {
    description "Initial auto-generated revision. Generated at 2026-02-13 20:11.";
  }

  augment "/emael:ManagedElement/equiprdo:Equipment/frurdo:FieldReplaceableUnit" {
    list DotGroupConfig {
      description "Additional definitions from MOM:min/max-elements:0/1;root; Configuration of radio dot groups. Created automatically for IRU which supports Radio Dot grouping. Can also be created manually. MO can only be deleted when parent FieldReplaceableUnit MO has administrativeState LOCKED. When created automatically, the RDN of this MO is DotGroupConfig=1.";
      key "dotGroupConfigId";
      leaf dotGroupConfigId {
        type leafref {
          path "../attributes/dotGroupConfigId";
        }
      }
      container attributes {
        uses DotGroupConfig-attributes;
      }
    }
  }
  typedef AvailStatus {
    type enumeration {
      enum IN_TEST;
      enum FAILED;
      enum POWER_OFF;
      enum OFF_LINE;
      enum OFF_DUTY;
      enum DEPENDENCY;
      enum DEGRADED;
      enum NOT_INSTALLED;
      enum LOG_FULL;
      enum DEPENDENCY_LOCKED;
      enum DEPENDENCY_FAILED;
      enum DEPENDENCY_SHUTTINGDOWN;
      enum DEPENDENCY_RECOVERY;
      enum DEPENDENCY_HOLDING;
    }
  }
  typedef OperState {
    type enumeration {
      enum DISABLED;
      enum ENABLED;
    }
  }
  grouping DotGroupConfig-attributes {
    leaf dotGroupConfigId {
      type string;
      mandatory true;
    }
    list dotGroup {
      key "id";
      leaf id {
        type uint32;
        description "Synthetic key for struct entry.";
      }
      container attributes {
      leaf noOfBranchesInGrp3 {
        type int32;
        default "0";
        description "Default value: 0.";
      }
      leaf noOfBranchesInGrp4 {
        type int32;
        default "0";
        description "Default value: 0.";
      }
      leaf noOfBranchesInGrp1 {
        type int32;
        default "0";
        description "Default value: 0.";
      }
      leaf noOfBranchesInGrp2 {
        type int32;
        default "0";
        description "Default value: 0.";
      }
      }
    }
    leaf operationalState {
      type enumeration {
        enum DISABLED;
        enum ENABLED;
      }
      config false;
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
  }
}
