module ericsson-over-the-air-sync-radio {
  yang-version 1.1;
  namespace "urn:com:ericsson:ecim:RsyncOverTheAirSync";
  prefix otardo;
  import ericsson-synchronization-sync-radio {
    prefix syncrdo;
  }
  import ericsson-managed-element {
    prefix emael;
  }
  description "Auto-generated from Ericsson ECIM (MOM XML).";
  revision 2026-02-13 {
    description "Initial auto-generated revision. Generated at 2026-02-13 20:11.";
  }

  augment "/emael:ManagedElement/emael:Transport/syncrdo:Synchronization" {
    list OverTheAirSync {
      description "Additional definitions from MOM:min/max-elements:0/1;root; Represents properties of termination of Over-The-Air (OTA) synchronization.";
      key "overTheAirSyncId";
      leaf overTheAirSyncId {
        type leafref {
          path "../attributes/overTheAirSyncId";
        }
      }
      container attributes {
        uses OverTheAirSync-attributes;
      }
    }
  }
  typedef OverTheAirSyncStatus {
    type enumeration {
      enum UNKNOWN;
      enum NO_FAULT;
      enum NO_MEASUREMENTS;
      enum UNSTABLE_MEASUREMENTS;
    }
  }
  grouping OverTheAirSync-attributes {
    leaf overTheAirSyncId {
      type string;
      mandatory true;
    }
    leaf-list overTheAirSyncStatus {
      type enumeration {
        enum UNKNOWN;
        enum NO_FAULT;
        enum NO_MEASUREMENTS;
        enum UNSTABLE_MEASUREMENTS;
      }
    }
    leaf-list reservedBy {
      type string;
    }
  }
}
