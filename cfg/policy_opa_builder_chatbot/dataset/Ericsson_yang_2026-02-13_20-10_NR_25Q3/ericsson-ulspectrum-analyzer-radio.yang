module ericsson-ulspectrum-analyzer-radio {
  yang-version 1.1;
  namespace "urn:com:ericsson:ecim:RmeUlSpectrumAnalyzer";
  prefix ulspcanrdo;
  import ietf-inet-types {
    prefix ietfinet;
  }
  import ericsson-rmesupport-radio {
    prefix rmesuppo;
  }
  import ericsson-managed-element {
    prefix emael;
  }
  description "Auto-generated from Ericsson ECIM (MOM XML).";
  revision 2026-02-13 {
    description "Initial auto-generated revision. Generated at 2026-02-13 20:11.";
  }

  augment "/emael:ManagedElement/rmesuppo:NodeSupport" {
    list UlSpectrumAnalyzer {
      description "Additional definitions from MOM:min/max-elements:0/4;root; This MO is used when requesting UL spectrum sampling for one specified radio unit and to store the sampling result file(s) in a SMRS Server. The MO also allows queries to be sent to any radio unit for availible UL spectrum sampling capabilities.";
      key "ulSpectrumAnalyzerId";
      leaf ulSpectrumAnalyzerId {
        type leafref {
          path "../attributes/ulSpectrumAnalyzerId";
        }
      }
      container attributes {
        uses UlSpectrumAnalyzer-attributes;
      }
    }
  }
  typedef InfoType {
    type enumeration {
      enum UNDEFINED;
      enum PARAMETERS_NOT_SUPPORTED;
      enum TIMEOUT_AT_FILE_UPLOAD;
      enum NO_CARRIERS_SETUP_ON_RADIO;
      enum CONDITIONAL_MEASUREMENT_TIMEOUT;
      enum RADIO_IS_BUSY_WITH_ANOTHER_SAMPLING;
      enum NO_CONTACT_WITH_RADIO;
      enum NO_RESOURCES;
      enum NO_CONTACT_WITH_RADIO_MEASUREMENT_SERVER;
      enum NO_VALID_LICENSE;
      enum PARTIALLY_FINISHED;
    }
  }
  typedef TcpStatus {
    type enumeration {
      enum UNKNOWN;
      enum STARTED;
      enum FINISHED;
      enum FAILED;
      enum STOPPED;
    }
  }
  typedef UlSpectrumSamplingType {
    type enumeration {
      enum SNAPSHOT_SAMPLING;
      enum CONTINUOUS_SAMPLING;
      enum CONDITIONAL_SAMPLING;
    }
  }
  grouping UlSpectrumAnalyzer-attributes {
    leaf ulSpectrumAnalyzerId {
      type string;
      mandatory true;
    }
    leaf targetRfPort {
      type ietfinet:port-number;
      config false;
      status deprecated;
      description "MOM flags: noNotification; Status info: Since 20.Q4. Replaced by targetMeasurementPort. Planned to be removed..";
    }
    leaf targetMeasurementPort {
      type ietfinet:port-number;
      config false;
    }
    leaf samplingType {
      type enumeration {
        enum SNAPSHOT_SAMPLING;
        enum CONTINUOUS_SAMPLING;
        enum CONDITIONAL_SAMPLING;
      }
      config false;
    }
    leaf ulSpectrumSamplingStatus {
      type enumeration {
        enum UNKNOWN;
        enum STARTED;
        enum FINISHED;
        enum FAILED;
        enum STOPPED;
      }
      config false;
    }
    leaf info {
      type enumeration {
        enum UNDEFINED;
        enum PARAMETERS_NOT_SUPPORTED;
        enum TIMEOUT_AT_FILE_UPLOAD;
        enum NO_CARRIERS_SETUP_ON_RADIO;
        enum CONDITIONAL_MEASUREMENT_TIMEOUT;
        enum RADIO_IS_BUSY_WITH_ANOTHER_SAMPLING;
        enum NO_CONTACT_WITH_RADIO;
        enum NO_RESOURCES;
        enum NO_CONTACT_WITH_RADIO_MEASUREMENT_SERVER;
        enum NO_VALID_LICENSE;
        enum PARTIALLY_FINISHED;
      }
      config false;
    }
    leaf filename {
      type string;
      config false;
    }
  }
}
