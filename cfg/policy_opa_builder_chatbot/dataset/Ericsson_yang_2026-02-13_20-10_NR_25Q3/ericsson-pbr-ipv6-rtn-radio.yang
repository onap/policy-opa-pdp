module ericsson-pbr-ipv6-rtn-radio {
  yang-version 1.1;
  namespace "urn:com:ericsson:ecim:RtnPBRIPv6";
  prefix pbrv6rdo;
  import ietf-inet-types {
    prefix ietfinet;
  }
  import ericsson-l3-router-rtn-radio {
    prefix l3rtrdo;
  }
  import ericsson-managed-element {
    prefix emael;
  }
  description "Auto-generated from Ericsson ECIM (MOM XML).";
  revision 2026-02-13 {
    description "Initial auto-generated revision. Generated at 2026-02-13 20:11.";
  }

  augment "/emael:ManagedElement/emael:Transport/l3rtrdo:Router" {
    list RoutingPolicyIpv6 {
      description "Additional definitions from MOM:min/max-elements:0/64;root; Represents IPv6 routing-policy used for PBR. Referring to routing-policy from IP interface, incoming packets on that IP interface are routed according to classification configured in routing-policy. Referring to routing-policy from Router MO, packets generated by Router MO are routed according to classification configured in routing-policy. Routing policy comprises list of each policy rules, which contains set of criterions and forwarding action. Dependencies: Maximum total number of RoutingPolicyIpv4 and RoutingPolicyIpv6 MOs in node is limited to 64.";
      key "routingPolicyIpv6Id";
      leaf routingPolicyIpv6Id {
        type leafref {
          path "../attributes/routingPolicyIpv6Id";
        }
      }
      container attributes {
        uses RoutingPolicyIpv6-attributes;
      }
    }
  }

  augment "/emael:ManagedElement/emael:Transport/l3rtrdo:Router/RoutingPolicyIpv6" {
    list RoutingRuleIpv6 {
      description "Additional definitions from MOM:min/max-elements:0/16; IPv6 routing rule, which contains criterions and forwarding action attributes.";
      key "routingRuleIpv6Id";
      leaf routingRuleIpv6Id {
        type leafref {
          path "../attributes/routingRuleIpv6Id";
        }
      }
      container attributes {
        uses RoutingRuleIpv6-attributes;
      }
    }
  }

  augment "/emael:ManagedElement/emael:Transport/l3rtrdo:Router/RoutingPolicyIpv6/RoutingRuleIpv6" {
    list NextHop {
      description "Additional definitions from MOM:min/max-elements:1/2; Route information defined by this NextHop MO and its parent RoutingRuleIpv6 MO.";
      key "nextHopId";
      leaf nextHopId {
        type leafref {
          path "../attributes/nextHopId";
        }
      }
      container attributes {
        uses NextHop-attributes;
      }
    }
  }
  typedef PBRNextHopState {
    type enumeration {
      enum UNREACHABLE;
      enum AVAILABLE;
      enum ACTIVE;
    }
  }
  grouping NextHop-attributes {
    leaf address {
      type string;
    }
    leaf adminDistance {
      type string;
    }
    leaf bfdMonitoring {
      type boolean;
      default "true";
      description "Default value: true.";
    }
    leaf nextHopId {
      type string;
      mandatory true;
    }
    leaf nextHopState {
      type enumeration {
        enum UNREACHABLE;
        enum AVAILABLE;
        enum ACTIVE;
      }
      config false;
    }
    leaf reference {
      type string;
    }
  }
  grouping RoutingPolicyIpv6-attributes {
    leaf-list reservedBy {
      type string;
    }
    leaf routingPolicyIpv6Id {
      type ietfinet:ipv6-address;
      mandatory true;
    }
    leaf userLabel {
      type string {
        length "1..128";
      }
      description "length 1..128.";
    }
  }
  grouping RoutingRuleIpv6-attributes {
    leaf addrDst {
      type string;
    }
    leaf addrSrc {
      type string;
    }
    leaf priority {
      type string;
      mandatory true;
    }
    leaf routingRuleIpv6Id {
      type ietfinet:ipv6-address;
      mandatory true;
    }
    leaf userLabel {
      type string {
        length "1..128";
      }
      description "length 1..128.";
    }
  }
}
