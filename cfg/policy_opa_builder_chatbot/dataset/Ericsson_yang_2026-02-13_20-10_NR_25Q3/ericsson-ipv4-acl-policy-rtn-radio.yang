module ericsson-ipv4-acl-policy-rtn-radio {
  yang-version 1.1;
  namespace "urn:com:ericsson:ecim:RtnIPv4ACLPolicy";
  prefix v4aclplrdo;
  import ietf-inet-types {
    prefix ietfinet;
  }
  import ericsson-l3-router-rtn-radio {
    prefix l3rtrdo;
  }
  import ericsson-managed-element {
    prefix emael;
  }
  description "Auto-generated from Ericsson ECIM (MOM XML).";
  revision 2026-02-13 {
    description "Initial auto-generated revision. Generated at 2026-02-13 20:11.";
  }

  augment "/emael:ManagedElement/emael:Transport/l3rtrdo:Router/AclIpv4" {
    list AclEntryIpv4 {
      description "Additional definitions from MOM:min/max-elements:0/unbounded; This MOC is used to configure entry in Access Control List. It contains set of filters for ACL entry as well as action and priority. All filters refer to fields in IP protocol header. When ACL entries are configured, ACL entry must be added for default action, otherwise non-matching packets will be silently discarded. Maximum number of AclEntryIPv4 MO in node is limited to 256. Maximum number of AclEntryIPv4 MO per AclIPv4 MO is limited to 64.";
      key "aclEntryIpv4Id";
      leaf aclEntryIpv4Id {
        type leafref {
          path "../attributes/aclEntryIpv4Id";
        }
      }
      container attributes {
        uses AclEntryIpv4-attributes;
      }
    }
  }

  augment "/emael:ManagedElement/emael:Transport/l3rtrdo:Router" {
    list AclIpv4 {
      description "Additional definitions from MOM:min/max-elements:0/unbounded;root; Represents ordered list of ACL entries. See attribute priority in AclEntryIpv4 MO for details on ordering. Maximum number of AclIPv4 MO in node is limited to 32.";
      key "aclIpv4Id";
      leaf aclIpv4Id {
        type leafref {
          path "../attributes/aclIpv4Id";
        }
      }
      container attributes {
        uses AclIpv4-attributes;
      }
    }
  }
  typedef AclAction {
    type enumeration {
      enum PERMIT;
      enum DENY;
    }
  }
  typedef FragmentType {
    type enumeration {
      enum NOTFRAGMENTED;
      enum FRAGFIRST;
      enum FRAGLAST;
      enum FRAGMENT;
      enum INITIAL;
      enum NONINITIAL;
    }
  }
  grouping AclEntryIpv4-attributes {
    leaf aclEntryIpv4Id {
      type ietfinet:ipv4-address;
      mandatory true;
    }
    leaf action {
      type enumeration {
        enum PERMIT;
        enum DENY;
      }
      mandatory true;
    }
    leaf-list addrDst {
      type string;
    }
    leaf-list addrSrc {
      type string;
    }
    leaf-list dscp {
      type string;
    }
    leaf fragmentType {
      type enumeration {
        enum NOTFRAGMENTED;
        enum FRAGFIRST;
        enum FRAGLAST;
        enum FRAGMENT;
        enum INITIAL;
        enum NONINITIAL;
      }
    }
    leaf-list icmpType {
      type string;
      ordered-by user;
    }
    leaf-list ipProtocol {
      type ietfinet:ip-address;
    }
    leaf-list portDst {
      type ietfinet:port-number;
    }
    leaf-list portSrc {
      type ietfinet:port-number;
    }
    leaf priority {
      type string;
      mandatory true;
    }
    leaf userLabel {
      type string {
        length "1..128";
      }
      description "length 1..128.";
    }
    leaf aclEntryPackets {
      type uint64;
      config false;
    }
  }
  grouping AclIpv4-attributes {
    leaf aclIpv4Id {
      type ietfinet:ipv4-address;
      mandatory true;
    }
    leaf-list reservedBy {
      type string;
    }
    leaf userLabel {
      type string {
        length "1..128";
      }
      description "length 1..128.";
    }
    leaf aclTotalDiscards {
      type uint64;
      config false;
    }
  }
}
