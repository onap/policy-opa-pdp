module ericsson-rcssecm-radio {
  yang-version 1.1;
  namespace "urn:com:ericsson:ecim:RcsSecM";
  prefix rcssecm;
  import ietf-inet-types {
    prefix ietfinet;
  }
  import ietf-yang-types {
    prefix ietfyang;
  }
  import ericsson-managed-element {
    prefix emael;
  }
  description "Auto-generated from Ericsson ECIM (MOM XML).";
  revision 2026-02-13 {
    description "Initial auto-generated revision. Generated at 2026-02-13 20:11.";
  }

  augment "/emael:ManagedElement/emael:SystemFunctions" {
    list SecM {
      description "Additional definitions from MOM:min/max-elements:1/1;root;systemCreated; Security Management root MOC.";
      key "secMId";
      leaf secMId {
        type leafref {
          path "../attributes/secMId";
        }
      }
      container attributes {
        uses SecM-attributes;
      }
    }
  }

  augment "/emael:ManagedElement/emael:SystemFunctions/SecM" {
    list UserManagement {
      description "Additional definitions from MOM:min/max-elements:1/1;systemCreated; User Management MOC.";
      key "userManagementId";
      leaf userManagementId {
        type leafref {
          path "../attributes/userManagementId";
        }
      }
      container attributes {
        uses UserManagement-attributes;
      }
    }
  }

  augment "/emael:ManagedElement/emael:SystemFunctions/SecM" {
    list Tls {
      description "Additional definitions from MOM:min/max-elements:0/1;systemCreated; Configures system-wide properties of Transport Layer Security (TLS).";
      key "tlsId";
      leaf tlsId {
        type leafref {
          path "../attributes/tlsId";
        }
      }
      container attributes {
        uses Tls-attributes;
      }
    }
  }

  augment "/emael:ManagedElement/emael:SystemFunctions/SecM" {
    list Dtls {
      description "Additional definitions from MOM:min/max-elements:0/8; Configures properties of Datagram Transport Layer Security (DTLS).";
      key "dtlsId";
      leaf dtlsId {
        type leafref {
          path "../attributes/dtlsId";
        }
      }
      container attributes {
        uses Dtls-attributes;
      }
    }
  }

  augment "/emael:ManagedElement/emael:SystemFunctions/SecM" {
    list Ssh {
      description "Additional definitions from MOM:min/max-elements:0/1;systemCreated; Configures system-wide properties of Secure Shell Transport Layer Protocol (SSH).";
      key "sshId";
      leaf sshId {
        type leafref {
          path "../attributes/sshId";
        }
      }
      container attributes {
        uses Ssh-attributes;
      }
    }
  }

  augment "/emael:ManagedElement/emael:SystemFunctions/SecM/Ssh" {
    list ServerKey {
      description "Additional definitions from MOM:min/max-elements:0/unbounded;systemCreated; Represents an SSH server key.";
      key "serverKeyId";
      leaf serverKeyId {
        type leafref {
          path "../attributes/serverKeyId";
        }
      }
      container attributes {
        uses ServerKey-attributes;
      }
    }
  }

  augment "/emael:ManagedElement/emael:SystemFunctions/SecM/UserManagement" {
    list AuthenticationOrder {
      description "Additional definitions from MOM:min/max-elements:0/1;systemCreated; MO Class used to view the order of authentication methods.";
      key "authenticationOrderId";
      leaf authenticationOrderId {
        type leafref {
          path "../attributes/authenticationOrderId";
        }
      }
      container attributes {
        uses AuthenticationOrder-attributes;
      }
    }
  }

  augment "/emael:ManagedElement/emael:SystemFunctions/SecM/UserManagement" {
    list AuthorizationOrder {
      description "Additional definitions from MOM:min/max-elements:0/1;systemCreated; MO Class used to view the order of authorization methods.";
      key "authorizationOrderId";
      leaf authorizationOrderId {
        type leafref {
          path "../attributes/authorizationOrderId";
        }
      }
      container attributes {
        uses AuthorizationOrder-attributes;
      }
    }
  }
  typedef SshKeyAlgorithm {
    type enumeration {
      enum DSA_1024;
      enum RSA_1024;
      enum RSA_2048;
      enum RSA_3072;
      enum RSA_4096;
      enum ECDSA_SECP_256_R1;
      enum ECDSA_SECP_384_R1;
      enum ECDSA_SECP_521_R1;
    }
  }
  typedef SshKeyFormat {
    type enumeration {
      enum OPENSSH;
      enum RFC4716;
    }
  }
  grouping AuthenticationOrder-attributes {
    leaf authenticationOrderId {
      type string;
      mandatory true;
    }
    list authenticationMethodOrder {
      config false;
      container attributes {
      leaf orderNumber {
        type string;
      }
      leaf methodReference {
        type string;
      }
      leaf userLabel {
        type string;
      }
      }
    }
    leaf userLabel {
      type string;
    }
  }
  grouping AuthorizationOrder-attributes {
    leaf authorizationOrderId {
      type string;
      mandatory true;
    }
    list authorizationMethodOrder {
      config false;
      container attributes {
      leaf orderNumber {
        type string;
      }
      leaf methodReference {
        type string;
      }
      leaf userLabel {
        type string;
      }
      }
    }
    leaf userLabel {
      type string;
    }
  }
  grouping Dtls-attributes {
    leaf dtlsId {
      type string;
      mandatory true;
    }
    list enabledCiphers {
      config false;
      container attributes {
      leaf keyExchange {
        type string;
      }
      leaf authentication {
        type string;
      }
      leaf encryption {
        type string;
      }
      leaf mac {
        type ietfyang:mac-address;
      }
      leaf export {
        type ietfinet:port-number;
      }
      leaf name {
        type string;
      }
      }
    }
    leaf cipherFilter {
      type ietfinet:ip-address;
    }
    list supportedCiphers {
      config false;
      container attributes {
      leaf keyExchange {
        type string;
      }
      leaf authentication {
        type string;
      }
      leaf encryption {
        type string;
      }
      leaf mac {
        type ietfyang:mac-address;
      }
      leaf export {
        type ietfinet:port-number;
      }
      leaf name {
        type string;
      }
      }
    }
    leaf-list selectedProtocolVersion {
      type string;
    }
    leaf-list supportedProtocolVersion {
      type ietfinet:port-number;
    }
    leaf-list reservedBy {
      type string;
    }
  }
  grouping SecM-attributes {
    leaf secMId {
      type string;
      mandatory true;
    }
  }
  grouping ServerKey-attributes {
    leaf serverKeyId {
      type string;
      mandatory true;
    }
    leaf userLabel {
      type string;
    }
    leaf publicKey {
      type string;
      config false;
    }
    leaf publicKeyFormat {
      type enumeration {
        enum OPENSSH;
        enum RFC4716;
      }
      config false;
    }
    leaf keyType {
      type enumeration {
        enum DSA_1024;
        enum RSA_1024;
        enum RSA_2048;
        enum RSA_3072;
        enum RSA_4096;
        enum ECDSA_SECP_256_R1;
        enum ECDSA_SECP_384_R1;
        enum ECDSA_SECP_521_R1;
      }
      mandatory true;
    }
    leaf fingerprint {
      type string;
      config false;
    }
  }
  grouping Ssh-attributes {
    leaf sshId {
      type string;
      mandatory true;
    }
    leaf-list selectedCiphers {
      type ietfinet:ip-address;
      min-elements 1;
    }
    leaf-list supportedCiphers {
      type ietfinet:ip-address;
    }
    leaf-list selectedKeyExchanges {
      type string;
      min-elements 1;
    }
    leaf-list supportedKeyExchanges {
      type ietfinet:port-number;
    }
    leaf-list selectedMacs {
      type ietfyang:mac-address;
      min-elements 1;
    }
    leaf-list supportedMacs {
      type ietfinet:port-number;
    }
  }
  grouping Tls-attributes {
    leaf tlsId {
      type string;
      mandatory true;
    }
    leaf-list enabledEllipticCurves {
      type ietfinet:ip-address;
    }
    leaf ellipticCurveFilter {
      type ietfinet:ip-address;
    }
    leaf-list supportedEllipticCurves {
      type ietfinet:ip-address;
    }
    list enabledCiphers {
      config false;
      container attributes {
      leaf protocolVersion {
        type string;
      }
      leaf keyExchange {
        type string;
      }
      leaf authentication {
        type string;
      }
      leaf encryption {
        type string;
      }
      leaf mac {
        type ietfyang:mac-address;
      }
      leaf export {
        type ietfinet:port-number;
      }
      leaf name {
        type string;
      }
      }
    }
    leaf cipherFilter {
      type ietfinet:ip-address;
      mandatory true;
    }
    list supportedCiphers {
      config false;
      container attributes {
      leaf protocolVersion {
        type string;
      }
      leaf keyExchange {
        type string;
      }
      leaf authentication {
        type string;
      }
      leaf encryption {
        type string;
      }
      leaf mac {
        type ietfyang:mac-address;
      }
      leaf export {
        type ietfinet:port-number;
      }
      leaf name {
        type string;
      }
      }
    }
  }
  grouping UserManagement-attributes {
    leaf userManagementId {
      type string;
      mandatory true;
    }
    leaf legalNotice {
      type string;
      default "WARNING: This system is restricted solely to authorized users for legitimate business purposes only. The actual or attempted unauthorized access, use, or modification of this system is strictly prohibited. Unauthorized users are subject to appropriate disciplinary proceedings and/or criminal and civil penalties under state, federal, or other applicable domestic and foreign laws. The use of this system may be monitored and recorded for administrative and security reasons. Anyone accessing this system expressly consents to such monitoring and is advised that if monitoring reveals possible evidence of criminal activity, the owner of this equipment may provide the evidence of such activity to law enforcement officials. All authorized users shall comply with the security policies, instructions and requirements related to the business purpose and in case of doubt shall seek advice from his/her manager.";
      description "Default value: WARNING: This system is restricted solely to authorized users for legitimate business purposes only. The actual or attempted unauthorized access, use, or modification of this system is strictly prohibited. Unauthorized users are subject to appropriate disciplinary proceedings and/or criminal and civil penalties under state, federal, or other applicable domestic and foreign laws. The use of this system may be monitored and recorded for administrative and security reasons. Anyone accessing this system expressly consents to such monitoring and is advised that if monitoring reveals possible evidence of criminal activity, the owner of this equipment may provide the evidence of such activity to law enforcement officials. All authorized users shall comply with the security policies, instructions and requirements related to the business purpose and in case of doubt shall seek advice from his/her manager..";
    }
    leaf loginFailureDelay {
      type uint8 {
        range "1..max";
      }
      default "5";
      units "seconds";
      description "range 1..max; Default value: 5.";
    }
    leaf-list targetType {
      type string {
        pattern "(\\\\[a-fA-F0-9]{2}|[A-Za-z0-9!$%&'./:=?@^_`{|}~-])((\\\\[a-fA-F0-9]{2}|[A-Za-z0-9!$%&'./:=?@^_`{|}~# -])*(\\\\[a-fA-F0-9]{2}|[A-Za-z0-9!$%&'./:=?@^_`{|}~#-]))?";
      }
    }
    leaf userLabel {
      type string;
    }
    leaf privacyNotice {
      type string;
      default "The misuse of personal data may generate considerable harm to the data subjects. Be reminded of the confidentiality obligations you have when accessing this kind of data and the disciplinary consequences of improper handling.";
      description "Default value: The misuse of personal data may generate considerable harm to the data subjects. Be reminded of the confidentiality obligations you have when accessing this kind of data and the disciplinary consequences of improper handling..";
    }
  }
}
