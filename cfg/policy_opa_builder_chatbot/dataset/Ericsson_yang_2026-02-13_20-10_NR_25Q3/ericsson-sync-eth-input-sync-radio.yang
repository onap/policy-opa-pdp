module ericsson-sync-eth-input-sync-radio {
  yang-version 1.1;
  namespace "urn:com:ericsson:ecim:RsyncSyncEthInput";
  prefix syncethinrdo;
  import ericsson-synchronization-sync-radio {
    prefix syncrdo;
  }
  import ericsson-managed-element {
    prefix emael;
  }
  description "Auto-generated from Ericsson ECIM (MOM XML).";
  revision 2026-02-13 {
    description "Initial auto-generated revision. Generated at 2026-02-13 20:11.";
  }

  augment "/emael:ManagedElement/emael:Transport/syncrdo:Synchronization" {
    list SyncEthInput {
      description "Additional definitions from MOM:min/max-elements:0/8;root; Represents synchronous Ethernet properties of Ethernet interface configured for synchronization.";
      key "syncEthInputId";
      leaf syncEthInputId {
        type leafref {
          path "../attributes/syncEthInputId";
        }
      }
      container attributes {
        uses SyncEthInput-attributes;
      }
    }
  }
  typedef AvailStatus {
    type enumeration {
      enum IN_TEST;
      enum FAILED;
      enum POWER_OFF;
      enum OFF_LINE;
      enum OFF_DUTY;
      enum DEPENDENCY;
      enum DEGRADED;
      enum NOT_INSTALLED;
      enum LOG_FULL;
      enum DEPENDENCY_LOCKED;
      enum DEPENDENCY_FAILED;
      enum DEPENDENCY_SHUTTINGDOWN;
    }
  }
  typedef EecFrom {
    type enumeration {
      enum RECEIVED_TLV;
      enum ADMIN_TLV1;
    }
  }
  typedef OperState {
    type enumeration {
      enum DISABLED;
      enum ENABLED;
    }
  }
  typedef SyncEthPhysical {
    type enumeration {
      enum SFP_UNKNOWN;
      enum SFP_DAC;
      enum SFP_OPTICAL;
      enum SFP_CAT_X_CABLE;
      enum CAT_X_CABLE;
    }
  }
  typedef SyncEthStatus {
    type enumeration {
      enum UNKNOWN;
      enum NO_FAULT;
      enum NO_SUPPORT_SFP_CAT_X_CABLE;
      enum LOSS_OF_SIGNAL;
      enum LOSS_OF_ESMC;
      enum RJ45_1000_BASE_T_NOT_SLAVE;
    }
  }
  grouping SyncEthInput-attributes {
    leaf adminCascadedEec {
      type uint8 {
        range "0..100";
      }
      default "0";
      description "range 0..100; Default value: 0.";
    }
    leaf adminCascadedEnhancedEec {
      type uint8 {
        range "0..100";
      }
      default "0";
      description "range 0..100; Default value: 0.";
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
      }
    }
    leaf encapsulation {
      type string;
      mandatory true;
    }
    leaf mixedEecEnhancedEec {
      type boolean;
      config false;
    }
    leaf numberCascadedEec {
      type uint8;
      config false;
    }
    leaf numberCascadedEnhancedEec {
      type uint8;
      config false;
    }
    leaf operationalState {
      type enumeration {
        enum DISABLED;
        enum ENABLED;
      }
      config false;
    }
    leaf partialChain {
      type boolean;
      config false;
    }
    leaf receivedSsmCode {
      type string;
      config false;
    }
    leaf-list reservedBy {
      type string;
    }
    leaf syncEMasterId {
      type string;
      config false;
    }
    leaf syncEthInputId {
      type string;
      mandatory true;
    }
    leaf syncEthPhysical {
      type enumeration {
        enum SFP_UNKNOWN;
        enum SFP_DAC;
        enum SFP_OPTICAL;
        enum SFP_CAT_X_CABLE;
        enum CAT_X_CABLE;
      }
      config false;
    }
    leaf syncEthStatus {
      type enumeration {
        enum UNKNOWN;
        enum NO_FAULT;
        enum NO_SUPPORT_SFP_CAT_X_CABLE;
        enum LOSS_OF_SIGNAL;
        enum LOSS_OF_ESMC;
        enum RJ45_1000_BASE_T_NOT_SLAVE;
      }
      config false;
    }
    leaf useNumberEecFrom {
      type enumeration {
        enum RECEIVED_TLV;
        enum ADMIN_TLV1;
      }
    }
  }
}
