module ericsson-ri-network-radio {
  yang-version 1.1;
  namespace "urn:com:ericsson:ecim:ReqRiNetwork";
  prefix rinwrkrdo;
  import ericsson-managed-element {
    prefix emael;
  }
  import ericsson-equip-radio {
    prefix equiprdo;
  }
  description "Auto-generated from Ericsson ECIM (MOM XML).";
  revision 2026-02-13 {
    description "Initial auto-generated revision. Generated at 2026-02-13 20:11.";
  }

  augment "/emael:ManagedElement/equiprdo:Equipment" {
    list RiNetwork {
      description "Additional definitions from MOM:min/max-elements:0/unbounded;root; Generic switch equipment providing multipoint-to-multipoint connectivity for RiLink MOs.";
      key "riNetworkId";
      leaf riNetworkId {
        type leafref {
          path "../attributes/riNetworkId";
        }
      }
      container attributes {
        uses RiNetwork-attributes;
      }
    }
  }
  typedef AdmState {
    type enumeration {
      enum LOCKED;
      enum UNLOCKED;
      enum SHUTTINGDOWN;
    }
  }
  typedef AvailStatus {
    type enumeration {
      enum IN_TEST;
      enum FAILED;
      enum POWER_OFF;
      enum OFF_LINE;
      enum OFF_DUTY;
      enum DEPENDENCY;
      enum DEGRADED;
      enum NOT_INSTALLED;
      enum LOG_FULL;
      enum DEPENDENCY_LOCKED;
      enum DEPENDENCY_FAILED;
      enum DEPENDENCY_SHUTTINGDOWN;
      enum DEPENDENCY_RECOVERY;
      enum DEPENDENCY_HOLDING;
    }
  }
  typedef OperState {
    type enumeration {
      enum DISABLED;
      enum ENABLED;
    }
  }
  grouping RiNetwork-attributes {
    leaf riNetworkId {
      type string;
      mandatory true;
    }
    leaf-list reservedBy {
      type string;
    }
    leaf operationalState {
      type enumeration {
        enum DISABLED;
        enum ENABLED;
      }
      config false;
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf administrativeState {
      type enumeration {
        enum LOCKED;
        enum UNLOCKED;
        enum SHUTTINGDOWN;
      }
    }
  }
}
