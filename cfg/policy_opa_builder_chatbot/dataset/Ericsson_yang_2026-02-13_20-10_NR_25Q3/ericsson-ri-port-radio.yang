module ericsson-ri-port-radio {
  yang-version 1.1;
  namespace "urn:com:ericsson:ecim:ReqRiPort";
  prefix riportrdo;
  import ietf-inet-types {
    prefix ietfinet;
  }
  import ietf-yang-types {
    prefix ietfyang;
  }
  import ericsson-managed-element {
    prefix emael;
  }
  import ericsson-field-replaceable-unit-radio {
    prefix frurdo;
  }
  import ericsson-equip-radio {
    prefix equiprdo;
  }
  description "Auto-generated from Ericsson ECIM (MOM XML).";
  revision 2026-02-13 {
    description "Initial auto-generated revision. Generated at 2026-02-13 20:11.";
  }

  augment "/emael:ManagedElement/equiprdo:Equipment/frurdo:FieldReplaceableUnit" {
    list RiPort {
      description "Additional definitions from MOM:min/max-elements:0/unbounded;root; Radio Interface (RI) Port.";
      key "riPortId";
      leaf riPortId {
        type leafref {
          path "../attributes/riPortId";
        }
      }
      container attributes {
        uses RiPort-attributes;
      }
    }
  }

  augment "/emael:ManagedElement/equiprdo:Equipment/frurdo:FieldReplaceableUnit/RiPort" {
    list RiEthernetPort {
      description "Additional definitions from MOM:min/max-elements:0/1; Ethernet performance monitoring. RiEthernetPort MO is created automatically when the link starts in Ethernet mode. The RDN of this MO is RiEthernetPort=1.";
      key "riEthernetPortId";
      status deprecated;
      leaf riEthernetPortId {
        type leafref {
          path "../attributes/riEthernetPortId";
        }
        status deprecated;
      }
      container attributes {
        uses RiEthernetPort-attributes;
      }
    }
  }
  typedef AdmState {
    type enumeration {
      enum LOCKED;
      enum UNLOCKED;
      enum SHUTTINGDOWN;
    }
  }
  typedef AvailStatus {
    type enumeration {
      enum IN_TEST;
      enum FAILED;
      enum POWER_OFF;
      enum OFF_LINE;
      enum OFF_DUTY;
      enum DEPENDENCY;
      enum DEGRADED;
      enum NOT_INSTALLED;
      enum LOG_FULL;
      enum DEPENDENCY_LOCKED;
      enum DEPENDENCY_FAILED;
      enum DEPENDENCY_SHUTTINGDOWN;
      enum DEPENDENCY_RECOVERY;
      enum DEPENDENCY_HOLDING;
    }
  }
  typedef OperState {
    type enumeration {
      enum DISABLED;
      enum ENABLED;
    }
  }
  typedef TransmissionStandard {
    type enumeration {
      enum CPRI;
      enum ETHERNET;
    }
  }
  grouping RiEthernetPort-attributes {
    leaf riEthernetPortId {
      type ietfinet:port-number;
      mandatory true;
      status deprecated;
      description "MOM flags: restricted, noNotification; Status info: Since 23.Q3. Replaced by EthernetPort.ethernetPortId. Planned to be removed..";
    }
    leaf macAddress {
      type ietfyang:mac-address;
      config false;
      status deprecated;
      description "MOM flags: isNillable=true; Status info: Since 23.Q3. Replaced by EthernetPort.macAddress. Planned to be removed..";
    }
    leaf ifHCOutMulticastPkts {
      type uint64;
      config false;
      status deprecated;
      description "MOM flags: noNotification.";
    }
    leaf ifHCOutOctets {
      type uint64;
      config false;
      status deprecated;
      description "MOM flags: noNotification.";
    }
    leaf ifOutErrors {
      type uint64;
      config false;
      status deprecated;
      description "MOM flags: noNotification.";
    }
    leaf ifHCInUcastPkts {
      type uint64;
      config false;
      status deprecated;
      description "MOM flags: noNotification.";
    }
    leaf ifHCOutUcastPkts {
      type uint64;
      config false;
      status deprecated;
      description "MOM flags: noNotification.";
    }
    leaf ifHCInOctets {
      type uint64;
      config false;
      status deprecated;
      description "MOM flags: noNotification.";
    }
    leaf ifHCInBroadcastPkts {
      type uint64;
      config false;
      status deprecated;
      description "MOM flags: noNotification.";
    }
    leaf ifInDiscards {
      type uint64;
      config false;
    }
    leaf ifInErrors {
      type uint64;
      config false;
      status deprecated;
      description "MOM flags: noNotification.";
    }
    leaf ifOutDiscards {
      type uint64;
      config false;
    }
    leaf ifHCInMulticastPkts {
      type uint64;
      config false;
      status deprecated;
      description "MOM flags: noNotification.";
    }
    leaf ifHCOutBroadcastPkts {
      type uint64;
      config false;
      status deprecated;
      description "MOM flags: noNotification.";
    }
  }
  grouping RiPort-attributes {
    leaf riPortId {
      type ietfinet:ip-address;
      mandatory true;
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf operationalState {
      type enumeration {
        enum DISABLED;
        enum ENABLED;
      }
      config false;
    }
    leaf-list reservedBy {
      type string;
    }
    list sfpData {
      config false;
      container attributes {
      leaf manufacturerDesignation {
        type string {
          length "0..16";
        }
        description "length 0..16.";
      }
      leaf manufacturerId {
        type string {
          length "0..16";
        }
        description "length 0..16.";
      }
      leaf manufacturerRevision {
        type string {
          length "0..8";
        }
        description "length 0..8.";
      }
      leaf negotiatedBitRate {
        type string {
          length "0..8";
        }
        description "length 0..8.";
      }
      leaf productionDate {
        type string {
          length "0..7";
        }
        description "length 0..7.";
      }
      leaf productNumber {
        type string {
          length "0..13";
        }
        description "length 0..13.";
      }
      leaf productRevision {
        type string {
          length "0..8";
        }
        description "length 0..8.";
      }
      leaf serialNumber {
        type string {
          length "0..15";
        }
        description "length 0..15.";
      }
      }
    }
    leaf sfpModuleRef {
      type string;
      config false;
    }
    leaf transmissionStandard {
      type enumeration {
        enum CPRI;
        enum ETHERNET;
      }
      config false;
    }
    leaf administrativeState {
      type enumeration {
        enum LOCKED;
        enum UNLOCKED;
        enum SHUTTINGDOWN;
      }
    }
    leaf preferredSfpProductNumber {
      type string {
        length "1..13";
      }
      description "length 1..13.";
    }
    leaf-list channelRef {
      type string;
    }
    leaf pmLossOfFrame {
      type uint32;
      config false;
    }
    leaf-list pmBitError {
      type uint32;
    }
    leaf pmLossOfSignal {
      type uint32;
      config false;
    }
  }
}
