module ericsson-authentication-server-rtn-radio {
  yang-version 1.1;
  namespace "urn:com:ericsson:ecim:RtnAuthenticationServer";
  prefix authsrvrdo;
  import ericsson-l3-router-rtn-radio {
    prefix l3rtrdo;
  }
  import ericsson-managed-element {
    prefix emael;
  }
  description "Auto-generated from Ericsson ECIM (MOM XML).";
  revision 2026-02-13 {
    description "Initial auto-generated revision. Generated at 2026-02-13 20:11.";
  }

  augment "/emael:ManagedElement/emael:Transport/l3rtrdo:Router" {
    list AuthenticationServer {
      description "Additional definitions from MOM:min/max-elements:0/unbounded;root; Provides access to redundant remote authentication servers.";
      key "authenticationServerId";
      leaf authenticationServerId {
        type leafref {
          path "../attributes/authenticationServerId";
        }
      }
      container attributes {
        uses AuthenticationServer-attributes;
      }
    }
  }
  grouping AuthenticationServer-attributes {
    leaf authenticationServerId {
      type string;
      mandatory true;
    }
    leaf-list reservedBy {
      type string;
    }
    leaf-list serverAddress {
      type string;
      min-elements 1;
    }
    leaf-list usedServerAddress {
      type string;
    }
    leaf userLabel {
      type string {
        length "1..128";
      }
      description "length 1..128.";
    }
  }
}
