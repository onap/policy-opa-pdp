module ericsson-routes-static-route-ipv6-rtn-radio {
  yang-version 1.1;
  namespace "urn:com:ericsson:ecim:RtnRoutesStaticRouteIPv6";
  prefix rtsstv6rdo;
  import ietf-inet-types {
    prefix ietfinet;
  }
  import ericsson-l3-router-rtn-radio {
    prefix l3rtrdo;
  }
  import ericsson-managed-element {
    prefix emael;
  }
  description "Auto-generated from Ericsson ECIM (MOM XML).";
  revision 2026-02-13 {
    description "Initial auto-generated revision. Generated at 2026-02-13 20:11.";
  }

  augment "/emael:ManagedElement/emael:Transport/l3rtrdo:Router" {
    list RouteTableIPv6Static {
      description "Additional definitions from MOM:min/max-elements:0/1;root; Contains manually defined IPv6 static routes defined by Dst MOs and their child NextHop MOs.";
      key "routeTableIPv6StaticId";
      leaf routeTableIPv6StaticId {
        type leafref {
          path "../attributes/routeTableIPv6StaticId";
        }
      }
      container attributes {
        uses RouteTableIPv6Static-attributes;
      }
    }
  }

  augment "/emael:ManagedElement/emael:Transport/l3rtrdo:Router/RouteTableIPv6Static/Dst" {
    list NextHop {
      description "Additional definitions from MOM:min/max-elements:0/unbounded; Contains information about route defined by this MO and its parent Dst MO. Dependencies: Max number of NextHop MOs are 10000 within all RouteTableIpv6Static MOs in node.";
      key "nextHopId";
      leaf nextHopId {
        type leafref {
          path "../attributes/nextHopId";
        }
      }
      container attributes {
        uses NextHop-attributes;
      }
    }
  }

  augment "/emael:ManagedElement/emael:Transport/l3rtrdo:Router/RouteTableIPv6Static" {
    list Dst {
      description "Additional definitions from MOM:min/max-elements:0/unbounded; Represents IPv6 destination of routes defined by one or more NextHop child MOs.";
      key "dstId";
      leaf dstId {
        type leafref {
          path "../attributes/dstId";
        }
      }
      container attributes {
        uses Dst-attributes;
      }
    }
  }
  grouping Dst-attributes {
    leaf dst {
      type string;
      mandatory true;
    }
    leaf dstId {
      type string;
      mandatory true;
    }
  }
  grouping NextHop-attributes {
    leaf address {
      type string;
    }
    leaf adminDistance {
      type string;
    }
    leaf bfdMonitoring {
      type boolean;
      default "true";
      description "Default value: true.";
    }
    leaf discard {
      type boolean;
    }
    leaf nextHopId {
      type string;
      mandatory true;
    }
    leaf reference {
      type string;
    }
  }
  grouping RouteTableIPv6Static-attributes {
    leaf routeTableIPv6StaticId {
      type ietfinet:ipv6-address;
      mandatory true;
    }
  }
}
