module ericsson-rcsfiletpm-radio {
  yang-version 1.1;
  namespace "urn:com:ericsson:ecim:RcsFileTPM";
  prefix rcsfilet;
  import ietf-inet-types {
    prefix ietfinet;
  }
  import ietf-yang-types {
    prefix ietfyang;
  }
  import ericsson-managed-element {
    prefix emael;
  }
  import ericsson-rcssysm-radio {
    prefix rcssysm;
  }
  description "Auto-generated from Ericsson ECIM (MOM XML).";
  revision 2026-02-13 {
    description "Initial auto-generated revision. Generated at 2026-02-13 20:11.";
  }

  augment "/emael:ManagedElement/emael:SystemFunctions/rcssysm:SysM/FileTPM" {
    list FtpServer {
      description "Additional definitions from MOM:min/max-elements:0/1;systemCreated; Generic configuration options for a file transfer server.";
      key "ftpServerId";
      leaf ftpServerId {
        type leafref {
          path "../attributes/ftpServerId";
        }
      }
      container attributes {
        uses FtpServer-attributes;
      }
    }
  }

  augment "/emael:ManagedElement/emael:SystemFunctions/rcssysm:SysM/FileTPM" {
    list FtpTls {
      description "Additional definitions from MOM:min/max-elements:0/1;systemCreated; Represents the common configuration parameters of FTP over Transport Layer Security (TLS) clients on the ME.";
      key "ftpTlsId";
      leaf ftpTlsId {
        type leafref {
          path "../attributes/ftpTlsId";
        }
      }
      container attributes {
        uses FtpTls-attributes;
      }
    }
  }

  augment "/emael:ManagedElement/emael:SystemFunctions/rcssysm:SysM/FileTPM" {
    list Sftp {
      description "Additional definitions from MOM:min/max-elements:0/1;systemCreated; Represents the common configuration parameters of Secure Shell File Transfer Protocol (SFTP) clients on the ME.";
      key "sftpId";
      leaf sftpId {
        type leafref {
          path "../attributes/sftpId";
        }
      }
      container attributes {
        uses Sftp-attributes;
      }
    }
  }

  augment "/emael:ManagedElement/emael:SystemFunctions/rcssysm:SysM/FileTPM/FtpServer" {
    list FtpTlsServer {
      description "Additional definitions from MOM:min/max-elements:0/1;systemCreated; Represents the FTP over Transport Layer Security (TLS) server of the ME. The server only accepts FTP sessions that are explicitly requesting a TLS layer by the \"AUTH TLS\" command.";
      key "ftpTlsServerId";
      leaf ftpTlsServerId {
        type leafref {
          path "../attributes/ftpTlsServerId";
        }
      }
      container attributes {
        uses FtpTlsServer-attributes;
      }
    }
  }

  augment "/emael:ManagedElement/emael:SystemFunctions/rcssysm:SysM/FileTPM/FtpServer" {
    list SftpServer {
      description "Additional definitions from MOM:min/max-elements:0/1;systemCreated; Represents the Secure Shell File Transfer Protocol (SFTP) server of the ME.";
      key "sftpServerId";
      leaf sftpServerId {
        type leafref {
          path "../attributes/sftpServerId";
        }
      }
      container attributes {
        uses SftpServer-attributes;
      }
    }
  }

  augment "/emael:ManagedElement/emael:SystemFunctions/rcssysm:SysM" {
    list FileTPM {
      description "Additional definitions from MOM:min/max-elements:1/1;root;systemCreated; The top class for server and client configuration of different protocols implementing file transfer. Lists the protocols supported by the ME by any file transfer client or server.";
      key "fileTPMId";
      leaf fileTPMId {
        type leafref {
          path "../attributes/fileTPMId";
        }
      }
      container attributes {
        uses FileTPM-attributes;
      }
    }
  }
  typedef BasicAdmState {
    type enumeration {
      enum LOCKED;
      enum UNLOCKED;
    }
  }
  grouping FileTPM-attributes {
    leaf fileTPMId {
      type string;
      mandatory true;
    }
  }
  grouping FtpServer-attributes {
    leaf ftpServerId {
      type string;
      mandatory true;
    }
    leaf idleTimer {
      type uint16 {
        range "10..3600";
      }
      default "600";
      units "seconds";
      description "range 10..3600; Default value: 600.";
    }
  }
  grouping FtpTls-attributes {
    leaf ftpTlsId {
      type string;
      mandatory true;
    }
    leaf nodeCredential {
      type string;
    }
    leaf trustCategory {
      type string;
    }
  }
  grouping FtpTlsServer-attributes {
    leaf ftpTlsServerId {
      type string;
      mandatory true;
    }
    leaf administrativeState {
      type enumeration {
        enum LOCKED;
        enum UNLOCKED;
      }
      mandatory true;
    }
    leaf nodeCredential {
      type string;
    }
    leaf trustCategory {
      type string;
    }
    leaf port {
      type ietfinet:port-number;
      default "9921";
      description "Default value: 9921.";
    }
    leaf minDataPort {
      type ietfinet:port-number;
    }
    leaf maxDataPort {
      type ietfinet:port-number;
    }
  }
  grouping Sftp-attributes {
    leaf sftpId {
      type string;
      mandatory true;
    }
    leaf-list selectedCiphers {
      type ietfinet:ip-address;
      min-elements 1;
    }
    leaf-list selectedKeyExchanges {
      type string;
      min-elements 1;
    }
    leaf-list selectedMacs {
      type ietfyang:mac-address;
      min-elements 1;
    }
    leaf-list supportedCiphers {
      type ietfinet:ip-address;
    }
    leaf-list supportedKeyExchanges {
      type ietfinet:port-number;
    }
    leaf-list supportedMacs {
      type ietfinet:port-number;
    }
  }
  grouping SftpServer-attributes {
    leaf sftpServerId {
      type string;
      mandatory true;
    }
    leaf administrativeState {
      type enumeration {
        enum LOCKED;
        enum UNLOCKED;
      }
      mandatory true;
    }
    leaf port {
      type ietfinet:port-number;
      default "2024";
      description "Default value: 2024.";
    }
  }
}
