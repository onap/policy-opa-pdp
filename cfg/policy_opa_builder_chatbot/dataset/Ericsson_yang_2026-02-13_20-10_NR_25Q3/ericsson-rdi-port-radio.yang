module ericsson-rdi-port-radio {
  yang-version 1.1;
  namespace "urn:com:ericsson:ecim:ReqRdiPort";
  prefix rdiptrdo;
  import ietf-inet-types {
    prefix ietfinet;
  }
  import ericsson-field-replaceable-unit-radio {
    prefix frurdo;
  }
  import ericsson-managed-element {
    prefix emael;
  }
  import ericsson-equip-radio {
    prefix equiprdo;
  }
  description "Auto-generated from Ericsson ECIM (MOM XML).";
  revision 2026-02-13 {
    description "Initial auto-generated revision. Generated at 2026-02-13 20:11.";
  }

  augment "/emael:ManagedElement/equiprdo:Equipment/frurdo:FieldReplaceableUnit" {
    list RdiPort {
      description "Additional definitions from MOM:min/max-elements:0/unbounded;root; This MO represents a port on the FieldReplaceableUnit. The port is used for communication between IRU and RD units.";
      key "rdiPortId";
      leaf rdiPortId {
        type leafref {
          path "../attributes/rdiPortId";
        }
      }
      container attributes {
        uses RdiPort-attributes;
      }
    }
  }
  typedef AvailStatus {
    type enumeration {
      enum IN_TEST;
      enum FAILED;
      enum POWER_OFF;
      enum OFF_LINE;
      enum OFF_DUTY;
      enum DEPENDENCY;
      enum DEGRADED;
      enum NOT_INSTALLED;
      enum LOG_FULL;
      enum DEPENDENCY_LOCKED;
      enum DEPENDENCY_FAILED;
      enum DEPENDENCY_SHUTTINGDOWN;
      enum DEPENDENCY_RECOVERY;
      enum DEPENDENCY_HOLDING;
    }
  }
  typedef OperState {
    type enumeration {
      enum DISABLED;
      enum ENABLED;
    }
  }
  grouping RdiPort-attributes {
    leaf rdiPortId {
      type ietfinet:ip-address;
      mandatory true;
    }
    leaf remoteRdiPortRef {
      type ietfinet:ip-address;
    }
    leaf-list reservedBy {
      type string;
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf operationalState {
      type enumeration {
        enum DISABLED;
        enum ENABLED;
      }
      config false;
    }
    leaf sfpModuleRef {
      type string;
      config false;
    }
    leaf-list channelRef {
      type string;
    }
    leaf preferredSfpProductNumber {
      type string {
        length "1..13";
      }
      description "length 1..13.";
    }
  }
}
