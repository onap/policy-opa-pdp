module ericsson-transceiver-radio {
  yang-version 1.1;
  namespace "urn:com:ericsson:ecim:ReqTransceiver";
  prefix trsvrrdo;
  import ericsson-field-replaceable-unit-radio {
    prefix frurdo;
  }
  import ericsson-managed-element {
    prefix emael;
  }
  import ericsson-yang-types {
    prefix eytypes;
  }
  import ericsson-equip-radio {
    prefix equiprdo;
  }
  description "Auto-generated from Ericsson ECIM (MOM XML).";
  revision 2026-02-13 {
    description "Initial auto-generated revision. Generated at 2026-02-13 20:11.";
  }

  augment "/emael:ManagedElement/equiprdo:Equipment/frurdo:FieldReplaceableUnit" {
    list Transceiver {
      description "Additional definitions from MOM:min/max-elements:0/unbounded;root; This MO models the UL and DL antenna streams in a radio with an embedded antenna system.";
      key "transceiverId";
      leaf transceiverId {
        type leafref {
          path "../attributes/transceiverId";
        }
      }
      container attributes {
        uses Transceiver-attributes;
      }
    }
  }
  typedef AvailStatus {
    type enumeration {
      enum IN_TEST;
      enum FAILED;
      enum POWER_OFF;
      enum OFF_LINE;
      enum OFF_DUTY;
      enum DEPENDENCY;
      enum DEGRADED;
      enum NOT_INSTALLED;
      enum LOG_FULL;
      enum DEPENDENCY_LOCKED;
      enum DEPENDENCY_FAILED;
      enum DEPENDENCY_SHUTTINGDOWN;
      enum DEPENDENCY_RECOVERY;
      enum DEPENDENCY_HOLDING;
    }
  }
  typedef MicroSleepTxRadioCapability {
    type enumeration {
      enum NO_SUPPORT;
      enum FULL_SUPPORT;
      enum LIMITED_SUPPORT;
    }
  }
  typedef MicroSleepTxRadioStatus {
    type enumeration {
      enum ENABLED;
      enum DISABLED;
    }
  }
  typedef OperState {
    type enumeration {
      enum DISABLED;
      enum ENABLED;
    }
  }
  grouping Transceiver-attributes {
    leaf transceiverId {
      type string;
      mandatory true;
    }
    leaf-list reservedBy {
      type string;
    }
    leaf operationalState {
      type enumeration {
        enum DISABLED;
        enum ENABLED;
      }
      config false;
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf dlFrequencyRanges {
      type string {
        length "0..256";
      }
      config false;
      description "length 0..256.";
    }
    leaf ulFrequencyRanges {
      type string {
        length "0..256";
      }
      config false;
      description "length 0..256.";
    }
    leaf microSleepTxRadioStatus {
      type enumeration {
        enum ENABLED;
        enum DISABLED;
      }
      config false;
    }
    leaf microSleepTxRadioCapability {
      type enumeration {
        enum NO_SUPPORT;
        enum FULL_SUPPORT;
        enum LIMITED_SUPPORT;
      }
      config false;
    }
    leaf retSubUnitRef {
      type string;
    }
    leaf mechanicalAntennaTilt {
      type eytypes:int32_range_-900-900-50;
      default "0";
      units "°";
      description "range -900..900; Default value: 0.";
    }
    leaf maxTotalTilt {
      type eytypes:int32_range_-900-900-50;
      default "900";
      units "°";
      description "range -900..900; Default value: 900.";
    }
    leaf minTotalTilt {
      type eytypes:int32_range_-900-900-50;
      default "-900";
      units "°";
      description "range -900..900; Default value: -900.";
    }
    leaf totalTilt {
      type eytypes:int32_range_-900-900-50;
      config false;
      units "°";
      description "range -900..900.";
    }
    leaf interleavedAirInstallation {
      type boolean;
      default "false";
      description "Default value: false.";
    }
    leaf-list pmTxOffRatio2 {
      type int32;
    }
    leaf pmTxOffTime4 {
      type uint32;
      config false;
    }
    leaf-list pmTxOffRatio1 {
      type int32;
    }
    leaf pmTxOffTime3 {
      type uint32;
      config false;
    }
    leaf pmTxOffTime2 {
      type uint32;
      config false;
    }
    leaf-list pmTxOffRatio4 {
      type int32;
    }
    leaf pmTxOffTime1 {
      type uint32;
      config false;
    }
    leaf-list pmTxOffRatio3 {
      type int32;
    }
  }
}
