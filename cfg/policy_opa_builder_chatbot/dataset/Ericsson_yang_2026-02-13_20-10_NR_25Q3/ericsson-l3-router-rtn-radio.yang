module ericsson-l3-router-rtn-radio {
  yang-version 1.1;
  namespace "urn:com:ericsson:ecim:RtnL3Router";
  prefix l3rtrdo;
  import ietf-inet-types {
    prefix ietfinet;
  }
  import ericsson-managed-element {
    prefix emael;
  }
  import ericsson-yang-types {
    prefix eytypes;
  }
  description "Auto-generated from Ericsson ECIM (MOM XML).";
  revision 2026-02-13 {
    description "Initial auto-generated revision. Generated at 2026-02-13 20:11.";
  }

  augment "/emael:ManagedElement/emael:Transport" {
    list Router {
      description "Additional definitions from MOM:min/max-elements:0/unbounded;root; IP routing domain instance. It provides data plane isolation of routed traffic and control plane isolation of routing entities from other routing instances. It allows for further fragmentation of routing domain. Maximum number of Router MOs in node is limited to: - For Baseband in RAN Compute Group 1, 2, or 3: 8, - For Baseband in RAN Compute Group 4 or higher: 60.";
      key "routerId";
      leaf routerId {
        type leafref {
          path "../attributes/routerId";
        }
      }
      container attributes {
        uses Router-attributes;
      }
    }
  }
  grouping Router-attributes {
    leaf hopLimit {
      type eytypes:int32_range_0-255;
      default "64";
      description "range 0..255; Default value: 64.";
    }
    leaf pathMtuExpiresIPv6 {
      type ietfinet:ipv6-address;
      units "s";
      description "range 300..21474836; Default value: 86400.";
    }
    leaf-list reservedBy {
      type string;
    }
    leaf routerId {
      type string;
      mandatory true;
    }
    leaf routingPolicyLocal {
      type string;
    }
    leaf routingPolicyLocalIPv6 {
      type ietfinet:ipv6-address;
    }
    leaf ttl {
      type eytypes:int32_range_1-255;
      default "64";
      description "range 1..255; Default value: 64.";
    }
    leaf userLabel {
      type string {
        length "1..128";
      }
      description "length 1..128.";
    }
  }
}
