module ericsson-adb-radio {
  yang-version 1.1;
  namespace "urn:com:ericsson:ecim:ReqAdb";
  prefix adbrdo;
  import ericsson-managed-element {
    prefix emael;
  }
  import ericsson-antenna-radio {
    prefix antrdo;
  }
  import ericsson-equip-radio {
    prefix equiprdo;
  }
  description "Auto-generated from Ericsson ECIM (MOM XML).";
  revision 2026-02-13 {
    description "Initial auto-generated revision. Generated at 2026-02-13 20:11.";
  }

  augment "/emael:ManagedElement/equiprdo:Equipment/antrdo:AntennaUnitGroup/antrdo:AntennaNearUnit" {
    list AdbSubUnit {
      description "Additional definitions from MOM:min/max-elements:0/1;root;systemCreated; Antenna database subunit stores data about antenna, contained arrays, installation and site mapping. MO created by system if parent MO is AISG 3.0. MO deleted by the system if parent MO changes AISG version from 3.0 to 2.0. The RDN of this MO is AdbSubUnit=1.";
      key "adbSubUnitId";
      leaf adbSubUnitId {
        type leafref {
          path "../attributes/adbSubUnitId";
        }
      }
      container attributes {
        uses AdbSubUnit-attributes;
      }
    }
  }
  typedef AvailStatus {
    type enumeration {
      enum IN_TEST;
      enum FAILED;
      enum POWER_OFF;
      enum OFF_LINE;
      enum OFF_DUTY;
      enum DEPENDENCY;
      enum DEGRADED;
      enum NOT_INSTALLED;
      enum LOG_FULL;
      enum DEPENDENCY_LOCKED;
      enum DEPENDENCY_FAILED;
      enum DEPENDENCY_SHUTTINGDOWN;
      enum DEPENDENCY_RECOVERY;
      enum DEPENDENCY_HOLDING;
    }
  }
  typedef GetArraysDataStatus {
    type enumeration {
      enum IDLE;
      enum STARTED;
      enum FINISHED;
      enum FAILED;
    }
  }
  typedef OperState {
    type enumeration {
      enum DISABLED;
      enum ENABLED;
    }
  }
  grouping AdbSubUnit-attributes {
    leaf adbSubUnitId {
      type string;
      mandatory true;
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf operationalState {
      type enumeration {
        enum DISABLED;
        enum ENABLED;
      }
      config false;
    }
    leaf subunitNumber {
      type int32;
      config false;
    }
    leaf userLabel {
      type string {
        length "1..128";
      }
      description "length 1..128.";
    }
    leaf getArraysDataStatus {
      type enumeration {
        enum IDLE;
        enum STARTED;
        enum FINISHED;
        enum FAILED;
      }
      config false;
    }
    list configuredAisgAdbVersion {
      config false;
      container attributes {
      leaf majorVersion {
        type string;
      }
      leaf minorVersion {
        type string;
      }
      leaf releaseVersion {
        type string;
      }
      }
    }
    list supportedAisgAdbVersion {
      config false;
      container attributes {
      leaf majorVersion {
        type string;
      }
      leaf minorVersion {
        type string;
      }
      leaf releaseVersion {
        type string;
      }
      }
    }
  }
}
