module ericsson-rcshcm-radio {
  yang-version 1.1;
  namespace "urn:com:ericsson:ecim:RcsHcm";
  prefix rcshcm;
  import ietf-inet-types {
    prefix ietfinet;
  }
  import ericsson-managed-element {
    prefix emael;
  }
  description "Auto-generated from Ericsson ECIM (MOM XML).";
  revision 2026-02-13 {
    description "Initial auto-generated revision. Generated at 2026-02-13 20:11.";
  }

  augment "/emael:ManagedElement/emael:SystemFunctions" {
    list HealthCheckM {
      description "Additional definitions from MOM:min/max-elements:1/1;root;systemCreated; Root MOC for Health Check Management function. Health Check Management function reports summary views of the managed element current state highlighting any deviations from a normal behavior. Can be used to attend upgrades and to support preventive maintenance and problem resolution. Health status is obtained by verifying a set of rules according to severity, grouped in predefined categories. For instance, if result of at least one critical rule is not as expected, node status is evaluated as not healthy, and requires immediate action. Rule categories of Health Check Management function are system-installed. Health check job can be created selecting one or more rule categories that evaluate ME health. Report file is generated for each executed health check job and stored in predefined folder with a compressed archive file. This file contains logs used for rule evaluations to be used for further investigation.";
      key "healthCheckMId";
      leaf healthCheckMId {
        type leafref {
          path "../attributes/healthCheckMId";
        }
      }
      container attributes {
        uses HealthCheckM-attributes;
      }
    }
  }

  augment "/emael:ManagedElement/emael:SystemFunctions/HealthCheckM/HcJob" {
    list HcRuleFailed {
      description "Additional definitions from MOM:min/max-elements:0/unbounded;systemCreated; Failed health check rule result from last job execution. An MO is created for each failed health check rule when health check is completed. When a new health check is executed for the same HcJob, all HcRuleFailed MOs are deleted. New MOs are created again when health check is completed. The RDNs of these MOs are hcRuleFailedId=1, 2, 3, and so on.";
      key "hcRuleFailedId";
      leaf hcRuleFailedId {
        type leafref {
          path "../attributes/hcRuleFailedId";
        }
      }
      container attributes {
        uses HcRuleFailed-attributes;
      }
    }
  }

  augment "/emael:ManagedElement/emael:SystemFunctions/HealthCheckM/HcJob" {
    list HcRuleSuccess {
      description "Additional definitions from MOM:min/max-elements:0/unbounded;systemCreated; Successful health check rule result from last job execution. An MO is created for each successful health check rule when health check is completed. When a new health check is executed for the same HcJob all HcRuleSuccess MOs are deleted. New MOs are created again when health check is completed. The RDNs of these MOs are hcRuleSuccessId=1, 2, 3, and so on.";
      key "hcRuleSuccessId";
      leaf hcRuleSuccessId {
        type leafref {
          path "../attributes/hcRuleSuccessId";
        }
      }
      container attributes {
        uses HcRuleSuccess-attributes;
      }
    }
  }

  augment "/emael:ManagedElement/emael:SystemFunctions/HealthCheckM/HcJob" {
    list HcRuleLocked {
      description "Additional definitions from MOM:min/max-elements:0/unbounded;systemCreated; Locked health check rule from last job execution. An MO is created for each locked health check rule when health check is completed. When a new health check is executed for the same HcJob all HcRuleLocked MOs are deleted. New MOs are created again when health check is completed. The RDNs of these MOs are hcRuleLockedId=1, 2, 3, and so on.";
      key "hcRuleLockedId";
      leaf hcRuleLockedId {
        type leafref {
          path "../attributes/hcRuleLockedId";
        }
      }
      container attributes {
        uses HcRuleLocked-attributes;
      }
    }
  }

  augment "/emael:ManagedElement/emael:SystemFunctions/HealthCheckM/HcJob/HcRuleFailed" {
    list FailedHcRuleEntity {
      description "Additional definitions from MOM:min/max-elements:0/unbounded;systemCreated; Entity result for failed health check rule. An MO is created for each entity that a failed health check rule checks. When a new health check is executed for the same HcJob all FailedHcRuleEntity MOs are deleted. New MOs are created again when health check is completed. The RDNs of these MOs are failedHcRuleEntityId=1, 2, 3, and so on.";
      key "failedHcRuleEntityId";
      leaf failedHcRuleEntityId {
        type leafref {
          path "../attributes/failedHcRuleEntityId";
        }
      }
      container attributes {
        uses FailedHcRuleEntity-attributes;
      }
    }
  }

  augment "/emael:ManagedElement/emael:SystemFunctions/HealthCheckM/HcJob/HcRuleSuccess" {
    list SuccessHcRuleEntity {
      description "Additional definitions from MOM:min/max-elements:0/unbounded;systemCreated; Entity result for successful health check rule. An MO is created for each entity that a successful health check rule checks. When new health check is executed for the same HcJob all SuccessHcRuleEntity MOs are deleted. New MOs are created again when health check is completed. The RDNs of these MOs are successHcRuleEntityId=1, 2, 3, and so on.";
      key "successHcRuleEntityId";
      leaf successHcRuleEntityId {
        type leafref {
          path "../attributes/successHcRuleEntityId";
        }
      }
      container attributes {
        uses SuccessHcRuleEntity-attributes;
      }
    }
  }

  augment "/emael:ManagedElement/emael:SystemFunctions/HealthCheckM" {
    list HcJob {
      description "Additional definitions from MOM:min/max-elements:0/unbounded; Health check job which can be executed on ME. Supports execution of one or more categories of health check rules. After each job execution, HealthCheckM::lastUpdateTime and HealthCheckM::lastStatus attributes are updated accordingly. Job can be executed on demand or by a scheduler. Report file is generated for each executed health check job and stored in predefined folder with compressed archive file containing logs for further investigation.";
      key "hcJobId";
      leaf hcJobId {
        type leafref {
          path "../attributes/hcJobId";
        }
      }
      container attributes {
        uses HcJob-attributes;
      }
    }
  }

  augment "/emael:ManagedElement/emael:SystemFunctions/HealthCheckM" {
    list HcRule {
      description "Additional definitions from MOM:min/max-elements:0/unbounded;systemCreated; Health check rule. Provides detailed information about individual health check rules. Each rule belongs to one or more health check categories. Each rule is associated with severity value, warning or critical, which affects evaluation of overall NE health. For example, if result of at least one critical rule is not as expected, node status is evaluated as not healthy, and requires immediate action. Some health check rules accept optional parameters as input for evaluation. If no values are provided, system default input parameters are used. Some health check rules provide optional output parameters with measurement data or other specific information. The RDNs of these MOs are HcRule=<unique identifier for application>_<specific rule name or number>. Example: HcRule=CommonFunction_CheckVswrStatus.";
      key "hcRuleId";
      leaf hcRuleId {
        type leafref {
          path "../attributes/hcRuleId";
        }
      }
      container attributes {
        uses HcRule-attributes;
      }
    }
  }
  typedef ActionResultType {
    type enumeration {
      enum SUCCESS;
      enum FAILURE;
      enum NOT_AVAILABLE;
    }
  }
  typedef ActionStateType {
    type enumeration {
      enum CANCELLING;
      enum RUNNING;
      enum FINISHED;
      enum CANCELLED;
    }
  }
  typedef BasicAdmState {
    type enumeration {
      enum LOCKED;
      enum UNLOCKED;
    }
  }
  typedef DeletionType {
    type enumeration {
      enum AUTOMATIC_DELETION;
      enum MANUAL_DELETION;
    }
  }
  typedef EntityResult {
    type enumeration {
      enum SUCCESS;
      enum FAILED;
      enum LOCKED;
    }
  }
  typedef HcCategory {
    type enumeration {
      enum BACKOFFICE;
      enum DAILY;
      enum MANDATORY;
      enum POSTUPDATE;
      enum POSTUPGRADE;
      enum PREINSTALL;
      enum PREUPDATE;
      enum PREUPGRADE;
      enum SHORT;
      enum TROUBLESHOOT;
      enum OTHER;
    }
  }
  typedef HealthStatus {
    type enumeration {
      enum HEALTHY;
      enum NOT_HEALTHY;
      enum WARNING;
      enum NOT_AVAILABLE;
    }
  }
  typedef LockedInfo {
    type enumeration {
      enum LOCKED_BY_ADMINISTRATIVE_STATE;
      enum LOCKED_BY_INPUT_PARAMETER;
    }
  }
  typedef RuleSeverity {
    type enumeration {
      enum CRITICAL;
      enum WARNING;
    }
  }
  grouping FailedHcRuleEntity-attributes {
    leaf failedHcRuleEntityId {
      type string;
      mandatory true;
    }
    leaf entity {
      type string;
      config false;
    }
    leaf resultInfo {
      type string;
      config false;
    }
    list outputParameters {
      config false;
      container attributes {
      leaf name {
        type string;
      }
      leaf value {
        type string;
      }
      }
    }
    leaf entityResult {
      type enumeration {
        enum SUCCESS;
        enum FAILED;
        enum LOCKED;
      }
      config false;
    }
  }
  grouping HcJob-attributes {
    leaf hcJobId {
      type string;
      mandatory true;
    }
    list progressReport {
      config false;
      container attributes {
      leaf actionName {
        type string;
      }
      leaf additionalInfo {
        type string;
      }
      leaf progressInfo {
        type string;
      }
      leaf progressPercentage {
        type string;
      }
      leaf result {
        type enumeration {
          enum SUCCESS;
          enum FAILURE;
          enum NOT_AVAILABLE;
        }
      }
      leaf resultInfo {
        type string;
      }
      leaf state {
        type enumeration {
          enum CANCELLING;
          enum RUNNING;
          enum FINISHED;
          enum CANCELLED;
        }
      }
      leaf actionId {
        type string;
      }
      leaf timeActionStarted {
        type string;
      }
      leaf timeActionCompleted {
        type string;
      }
      leaf timeOfLastStatusUpdate {
        type string;
      }
      }
    }
    leaf lastReportFileName {
      type ietfinet:port-number;
      config false;
    }
    leaf status {
      type enumeration {
        enum HEALTHY;
        enum NOT_HEALTHY;
        enum WARNING;
        enum NOT_AVAILABLE;
      }
      config false;
    }
    leaf-list rulesCategories {
      type enumeration {
        enum BACKOFFICE;
        enum DAILY;
        enum MANDATORY;
        enum POSTUPDATE;
        enum POSTUPGRADE;
        enum PREINSTALL;
        enum PREUPDATE;
        enum PREUPGRADE;
        enum SHORT;
        enum TROUBLESHOOT;
        enum OTHER;
      }
      description "Status info: Since 19.Q4. Replaced by ruleCategoryList. Planned to be removed..";
    }
    leaf lastRunTime {
      type string;
      config false;
    }
    leaf jobToTrigger {
      type string;
    }
    list failedRules {
      config false;
      description "Status info: Since 21.Q1. Replaced by child MOs HcRuleFailed and FailedHcRuleEntity. Planned to be removed..";
      container attributes {
      leaf hcRule {
        type string;
      }
      leaf reason {
        type string;
      }
      leaf severity {
        type enumeration {
          enum CRITICAL;
          enum WARNING;
        }
      }
      leaf entity {
        type string;
      }
      }
    }
    leaf localFileStorePath {
      type string;
      config false;
    }
    list inputParameters {
      key "id";
      leaf id {
        type uint32;
        description "Synthetic key for struct sequence entry.";
      }
      container attributes {
      leaf name {
        type string;
      }
      leaf value {
        type string;
      }
      leaf hcRule {
        type string;
      }
      }
    }
    leaf-list ruleCategoryList {
      type string;
    }
    list subTypeStatus {
      config false;
      container attributes {
      leaf subTypeName {
        type string;
      }
      leaf status {
        type enumeration {
          enum HEALTHY;
          enum NOT_HEALTHY;
          enum WARNING;
          enum NOT_AVAILABLE;
        }
      }
      }
    }
    list typeStatus {
      config false;
      container attributes {
      leaf typeName {
        type string;
      }
      leaf status {
        type enumeration {
          enum HEALTHY;
          enum NOT_HEALTHY;
          enum WARNING;
          enum NOT_AVAILABLE;
        }
      }
      }
    }
    leaf deletionPolicy {
      type enumeration {
        enum AUTOMATIC_DELETION;
        enum MANUAL_DELETION;
      }
    }
  }
  grouping HcRule-attributes {
    leaf hcRuleId {
      type string;
      mandatory true;
    }
    leaf description {
      type ietfinet:ip-address;
      config false;
    }
    leaf name {
      type string;
      config false;
    }
    leaf recommendedAction {
      type string;
      config false;
    }
    leaf severity {
      type enumeration {
        enum CRITICAL;
        enum WARNING;
      }
      config false;
    }
    list inputParameters {
      config false;
      container attributes {
      leaf name {
        type string;
      }
      leaf value {
        type string;
      }
      leaf description {
        type ietfinet:ip-address;
      }
      }
    }
    leaf administrativeState {
      type enumeration {
        enum LOCKED;
        enum UNLOCKED;
      }
    }
    leaf-list categories {
      type enumeration {
        enum BACKOFFICE;
        enum DAILY;
        enum MANDATORY;
        enum POSTUPDATE;
        enum POSTUPGRADE;
        enum PREINSTALL;
        enum PREUPDATE;
        enum PREUPGRADE;
        enum SHORT;
        enum TROUBLESHOOT;
        enum OTHER;
      }
      description "Status info: Since 19.Q4. Replaced by categoryList. Planned to be removed..";
    }
    list categoryList {
      config false;
      container attributes {
      leaf category {
        type string;
      }
      leaf description {
        type ietfinet:ip-address;
      }
      }
    }
    list ruleType {
      config false;
      container attributes {
      leaf subTypeDescription {
        type ietfinet:ip-address;
      }
      leaf typeName {
        type string;
      }
      leaf subTypeName {
        type string;
      }
      }
    }
    list outputParameters {
      config false;
      container attributes {
      leaf description {
        type ietfinet:ip-address;
      }
      leaf name {
        type string;
      }
      }
    }
  }
  grouping HcRuleFailed-attributes {
    leaf hcRuleFailedId {
      type string;
      mandatory true;
    }
    leaf hcRule {
      type string;
      config false;
    }
    leaf severity {
      type enumeration {
        enum CRITICAL;
        enum WARNING;
      }
      config false;
    }
    leaf resultInfo {
      type string;
      config false;
    }
    list usedInputParameters {
      config false;
      container attributes {
      leaf name {
        type string;
      }
      leaf value {
        type string;
      }
      }
    }
  }
  grouping HcRuleLocked-attributes {
    leaf hcRuleLockedId {
      type string;
      mandatory true;
    }
    leaf hcRule {
      type string;
      config false;
    }
    leaf lockedInfo {
      type enumeration {
        enum LOCKED_BY_ADMINISTRATIVE_STATE;
        enum LOCKED_BY_INPUT_PARAMETER;
      }
      config false;
    }
    list usedInputParameters {
      config false;
      container attributes {
      leaf name {
        type string;
      }
      leaf value {
        type string;
      }
      }
    }
  }
  grouping HcRuleSuccess-attributes {
    leaf hcRuleSuccessId {
      type string;
      mandatory true;
    }
    leaf hcRule {
      type string;
      config false;
    }
    leaf resultInfo {
      type string;
      config false;
    }
    list usedInputParameters {
      config false;
      container attributes {
      leaf name {
        type string;
      }
      leaf value {
        type string;
      }
      }
    }
  }
  grouping HealthCheckM-attributes {
    leaf healthCheckMId {
      type string;
      mandatory true;
    }
    leaf lastUpdateTime {
      type string;
      config false;
    }
    leaf lastExecutedJob {
      type string;
      config false;
    }
    leaf lastStatus {
      type enumeration {
        enum HEALTHY;
        enum NOT_HEALTHY;
        enum WARNING;
        enum NOT_AVAILABLE;
      }
      config false;
    }
    leaf maxNoOfReportFiles {
      type ietfinet:port-number;
      default "10";
      description "Default value: 10.";
    }
    list supportedCategories {
      config false;
      container attributes {
      leaf category {
        type string;
      }
      leaf description {
        type ietfinet:ip-address;
      }
      }
    }
  }
  grouping SuccessHcRuleEntity-attributes {
    leaf successHcRuleEntityId {
      type string;
      mandatory true;
    }
    leaf entity {
      type string;
      config false;
    }
    list outputParameters {
      config false;
      container attributes {
      leaf name {
        type string;
      }
      leaf value {
        type string;
      }
      }
    }
    leaf entityResult {
      type enumeration {
        enum SUCCESS;
        enum FAILED;
        enum LOCKED;
      }
      config false;
    }
    leaf resultInfo {
      type string;
      config false;
    }
  }
}
