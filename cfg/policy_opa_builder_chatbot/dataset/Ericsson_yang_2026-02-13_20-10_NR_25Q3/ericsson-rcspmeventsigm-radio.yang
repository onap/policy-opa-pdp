module ericsson-rcspmeventsigm-radio {
  yang-version 1.1;
  namespace "urn:com:ericsson:ecim:RcsPMEventSigM";
  prefix rcspmeve;
  import ietf-inet-types {
    prefix ietfinet;
  }
  import ericsson-managed-element {
    prefix emael;
  }
  description "Auto-generated from Ericsson ECIM (MOM XML).";
  revision 2026-02-13 {
    description "Initial auto-generated revision. Generated at 2026-02-13 20:11.";
  }

  augment "/emael:ManagedElement/emael:SystemFunctions" {
    list PmEventSigM {
      description "Additional definitions from MOM:min/max-elements:1/1;root;systemCreated; Performance management (PM) event fragment for signalling based event jobs. It is used to provide event producer specific provisioning of event jobs controlled by signalling based activation from the core network.";
      key "pmEventSigMId";
      leaf pmEventSigMId {
        type leafref {
          path "../attributes/pmEventSigMId";
        }
      }
      container attributes {
        uses PmEventSigM-attributes;
      }
    }
  }

  augment "/emael:ManagedElement/emael:SystemFunctions/PmEventSigM/EventProducerS/EventGroupS" {
    list EventTypeS {
      description "Additional definitions from MOM:min/max-elements:0/unbounded;systemCreated; Event type generated by ME. The RDN of this MO is EventTypeS=<ID>.";
      key "eventTypeSId";
      leaf eventTypeSId {
        type leafref {
          path "../attributes/eventTypeSId";
        }
      }
      container attributes {
        uses EventTypeS-attributes;
      }
    }
  }

  augment "/emael:ManagedElement/emael:SystemFunctions/PmEventSigM/EventProducerS" {
    list EventGroupS {
      description "Additional definitions from MOM:min/max-elements:0/unbounded;systemCreated; A group of related event types. The RDN of this MO is EventGroupS=<ID>.";
      key "eventGroupSId";
      leaf eventGroupSId {
        type leafref {
          path "../attributes/eventGroupSId";
        }
      }
      container attributes {
        uses EventGroupS-attributes;
      }
    }
  }

  augment "/emael:ManagedElement/emael:SystemFunctions/PmEventSigM" {
    list EventProducerS {
      description "Additional definitions from MOM:min/max-elements:0/unbounded;systemCreated; Event producer. Allows for multiple types of event producer within an application describing distinct event functions. The RDN of this MO is EventProducerS=<ID>.";
      key "eventProducerSId";
      leaf eventProducerSId {
        type leafref {
          path "../attributes/eventProducerSId";
        }
      }
      container attributes {
        uses EventProducerS-attributes;
      }
    }
  }
  typedef EventStatus {
    type enumeration {
      enum PRELIMINARY;
      enum USED;
      enum DEPRECATED;
      enum OBSOLETE;
    }
  }
  grouping EventGroupS-attributes {
    leaf eventGroupSId {
      type string;
      mandatory true;
    }
    leaf description {
      type ietfinet:ip-address;
      config false;
    }
    leaf eventGroupVersion {
      type string;
      config false;
    }
    leaf-list ueTraceEventBlacklist {
      type string;
      description "Status info: Since 23.Q1. Replaced by ueTraceEventFilterlist. Planned to be removed..";
    }
    leaf-list ueTraceEventFilterlist {
      type string;
    }
  }
  grouping EventProducerS-attributes {
    leaf eventProducerSId {
      type string;
      mandatory true;
    }
    leaf name {
      type string;
      config false;
    }
    leaf generation {
      type string;
      config false;
    }
    leaf streamDestinationPort {
      type ietfinet:port-number;
      default "51544";
      description "Default value: 51544.";
    }
  }
  grouping EventTypeS-attributes {
    leaf eventTypeSId {
      type string;
      mandatory true;
    }
    leaf eventStatus {
      type enumeration {
        enum PRELIMINARY;
        enum USED;
        enum DEPRECATED;
        enum OBSOLETE;
      }
      config false;
    }
  }
  grouping PmEventSigM-attributes {
    leaf pmEventSigMId {
      type string;
      mandatory true;
    }
    leaf userLabel {
      type string;
    }
  }
}
