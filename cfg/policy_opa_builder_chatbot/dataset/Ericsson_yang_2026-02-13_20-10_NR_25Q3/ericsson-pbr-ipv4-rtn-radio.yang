module ericsson-pbr-ipv4-rtn-radio {
  yang-version 1.1;
  namespace "urn:com:ericsson:ecim:RtnPBRIPv4";
  prefix pbrv4rdo;
  import ietf-inet-types {
    prefix ietfinet;
  }
  import ericsson-l3-router-rtn-radio {
    prefix l3rtrdo;
  }
  import ericsson-managed-element {
    prefix emael;
  }
  description "Auto-generated from Ericsson ECIM (MOM XML).";
  revision 2026-02-13 {
    description "Initial auto-generated revision. Generated at 2026-02-13 20:11.";
  }

  augment "/emael:ManagedElement/emael:Transport/l3rtrdo:Router" {
    list RoutingPolicyIpv4 {
      description "Additional definitions from MOM:min/max-elements:0/64;root; Represents IPv4 routing-policy used for PBR. Referring to routing-policy from IP interface, incoming packets on that IP interface are routed according to classification configured in routing-policy. Referring to routing-policy from Router MO, packets generated by Router MO are routed according to classification configured in routing-policy. Routing policy comprises list of each policy rules, which contains set of criterions and forwarding action. Dependencies: Maximum total number of RoutingPolicyIpv4 and RoutingPolicyIpv6 MOs in node is limited to 64.";
      key "routingPolicyIpv4Id";
      leaf routingPolicyIpv4Id {
        type leafref {
          path "../attributes/routingPolicyIpv4Id";
        }
      }
      container attributes {
        uses RoutingPolicyIpv4-attributes;
      }
    }
  }

  augment "/emael:ManagedElement/emael:Transport/l3rtrdo:Router/RoutingPolicyIpv4" {
    list RoutingRuleIpv4 {
      description "Additional definitions from MOM:min/max-elements:0/16; IPv4 routing rule, which contains criterions and forwarding action attributes.";
      key "routingRuleIpv4Id";
      leaf routingRuleIpv4Id {
        type leafref {
          path "../attributes/routingRuleIpv4Id";
        }
      }
      container attributes {
        uses RoutingRuleIpv4-attributes;
      }
    }
  }

  augment "/emael:ManagedElement/emael:Transport/l3rtrdo:Router/RoutingPolicyIpv4/RoutingRuleIpv4" {
    list NextHop {
      description "Additional definitions from MOM:min/max-elements:1/2; Route information defined by this NextHop MO and its parent RoutingRuleIpv4 MO.";
      key "nextHopId";
      leaf nextHopId {
        type leafref {
          path "../attributes/nextHopId";
        }
      }
      container attributes {
        uses NextHop-attributes;
      }
    }
  }
  typedef PBRNextHopState {
    type enumeration {
      enum UNREACHABLE;
      enum AVAILABLE;
      enum ACTIVE;
    }
  }
  grouping NextHop-attributes {
    leaf address {
      type string;
    }
    leaf adminDistance {
      type string;
    }
    leaf bfdMonitoring {
      type boolean;
      default "true";
      description "Default value: true.";
    }
    leaf nextHopId {
      type string;
      mandatory true;
    }
    leaf nextHopState {
      type enumeration {
        enum UNREACHABLE;
        enum AVAILABLE;
        enum ACTIVE;
      }
      config false;
    }
    leaf reference {
      type string;
    }
  }
  grouping RoutingPolicyIpv4-attributes {
    leaf-list reservedBy {
      type string;
    }
    leaf routingPolicyIpv4Id {
      type ietfinet:ipv4-address;
      mandatory true;
    }
    leaf userLabel {
      type string {
        length "1..128";
      }
      description "length 1..128.";
    }
  }
  grouping RoutingRuleIpv4-attributes {
    leaf addrDst {
      type string;
    }
    leaf addrSrc {
      type string;
    }
    leaf priority {
      type string;
      mandatory true;
    }
    leaf routingRuleIpv4Id {
      type ietfinet:ipv4-address;
      mandatory true;
    }
    leaf userLabel {
      type string {
        length "1..128";
      }
      description "length 1..128.";
    }
  }
}
