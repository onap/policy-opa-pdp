module ericsson-twamp-rtn-radio {
  yang-version 1.1;
  namespace "urn:com:ericsson:ecim:RtnTwamp";
  prefix twrdo;
  import ietf-inet-types {
    prefix ietfinet;
  }
  import ericsson-l3-router-rtn-radio {
    prefix l3rtrdo;
  }
  import ericsson-managed-element {
    prefix emael;
  }
  description "Auto-generated from Ericsson ECIM (MOM XML).";
  revision 2026-02-13 {
    description "Initial auto-generated revision. Generated at 2026-02-13 20:11.";
  }

  augment "/emael:ManagedElement/emael:Transport/l3rtrdo:Router" {
    list TwampLightResponder {
      description "Additional definitions from MOM:min/max-elements:0/8;root; Two Way Active Measurement Protocol Responder. This MO represents the session responder functionality (according to RFC 5357) in a TWAMP light architecture. When created, the node reflects TWAMP packets received on the specified UDP port.";
      key "twampLightResponderId";
      leaf twampLightResponderId {
        type leafref {
          path "../attributes/twampLightResponderId";
        }
      }
      container attributes {
        uses TwampLightResponder-attributes;
      }
    }
  }
  typedef ResponderType {
    type enumeration {
      enum LIGHT;
      enum LIGHT_SL;
    }
  }
  grouping TwampLightResponder-attributes {
    leaf ipAddress {
      type ietfinet:ip-address;
      mandatory true;
    }
    leaf responderType {
      type enumeration {
        enum LIGHT;
        enum LIGHT_SL;
      }
      config false;
    }
    leaf twampLightResponderId {
      type string;
      mandatory true;
    }
    leaf udpPort {
      type ietfinet:port-number;
      mandatory true;
    }
    leaf userLabel {
      type string {
        length "1..128";
      }
      description "length 1..128.";
    }
  }
}
