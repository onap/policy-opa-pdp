module ericsson-battery-backup-radio {
  yang-version 1.1;
  namespace "urn:com:ericsson:ecim:ResBatteryBackup";
  prefix btbckrdo;
  import ericsson-equipment-support-function-radio {
    prefix eqsupfnrdo;
  }
  import ericsson-managed-element {
    prefix emael;
  }
  import ericsson-yang-types {
    prefix eytypes;
  }
  description "Auto-generated from Ericsson ECIM (MOM XML).";
  revision 2026-02-13 {
    description "Initial auto-generated revision. Generated at 2026-02-13 20:11.";
  }

  augment "/emael:ManagedElement/eqsupfnrdo:EquipmentSupportFunction" {
    list BatteryBackup {
      description "Additional definitions from MOM:min/max-elements:0/unbounded;root; This MO models a battery backup controlled by a BFU or BPA unit. The functionality represented by this MO is dependent on the existence of a FieldReplaceableUnit MO of type BFU or BPA. From 18.Q1 the reservedBy attribute must be empty before MO can be deleted..";
      key "batteryBackupId";
      leaf batteryBackupId {
        type leafref {
          path "../attributes/batteryBackupId";
        }
      }
      container attributes {
        uses BatteryBackup-attributes;
      }
    }
  }
  typedef ApcBatteryTestInitiation {
    type enumeration {
      enum UNDEFINED;
      enum AUTOMATIC_PERIODIC;
      enum CONFIGURED_PERIODIC;
      enum MAINS_FAILURE_PERIODIC;
      enum ON_DEMAND;
      enum ON_DEMAND_FORCED;
    }
  }
  typedef ApcBatteryTestMode {
    type enumeration {
      enum AUTOMATIC;
      enum CONFIGURED;
      enum DISABLED;
    }
  }
  typedef ApcBatteryTestOutcome {
    type enumeration {
      enum UNDEFINED;
      enum PASSED;
      enum FAILED;
    }
  }
  typedef ApcBatteryTestState {
    type enumeration {
      enum UNDEFINED;
      enum PENDING;
      enum IN_PROGRESS;
    }
  }
  typedef ApcBatteryTestType {
    type enumeration {
      enum PERIODIC;
      enum ON_DEMAND;
    }
  }
  typedef ApcBatteryType {
    type enumeration {
      enum UNKNOWN;
      enum TYPE01;
      enum TYPE02;
    }
  }
  typedef ApcChargingMode {
    type enumeration {
      enum AUTOMATIC;
      enum USER_DEFINED;
    }
  }
  typedef ApcMonth {
    type enumeration {
      enum JANUARY;
      enum FEBRUARY;
      enum MARCH;
      enum APRIL;
      enum JUNE;
      enum JULY;
      enum AUGUST;
      enum MAY;
      enum SEPTEMBER;
      enum OCTOBER;
      enum NOVEMBER;
      enum DECEMBER;
    }
  }
  typedef AvailStatus {
    type enumeration {
      enum IN_TEST;
      enum FAILED;
      enum POWER_OFF;
      enum OFF_LINE;
      enum OFF_DUTY;
      enum DEPENDENCY;
      enum DEGRADED;
      enum NOT_INSTALLED;
      enum LOG_FULL;
      enum DEPENDENCY_LOCKED;
      enum DEPENDENCY_FAILED;
      enum DEPENDENCY_SHUTTINGDOWN;
      enum DEPENDENCY_RECOVERY;
      enum DEPENDENCY_HOLDING;
    }
  }
  typedef OperState {
    type enumeration {
      enum DISABLED;
      enum ENABLED;
    }
  }
  grouping BatteryBackup-attributes {
    leaf batteryBackupId {
      type string;
      mandatory true;
    }
    leaf batteryCurrent {
      type int32 {
        range "-9999 | -1000..1000";
      }
      config false;
      units "A";
    }
    leaf batteryDisconnectTempCeaseOffset {
      type int32 {
        range "1..20";
      }
      default "5";
      units "°C";
      description "range 1..20; Default value: 5.";
    }
    leaf batteryInstallationDate {
      type string {
        length "8";
      }
      status deprecated;
      description "length 8..8; MOM flags: isNillable=true; Status info: Since 18A. Replaced by installationDate in MO BatteryUnit. Planned to be removed..";
    }
    leaf batteryTemperature {
      type int32 {
        range "-55..125";
      }
      config false;
      units "°C";
      description "range -55..125.";
    }
    leaf batteryTestIsRunning {
      type boolean;
      config false;
    }
    leaf batteryType {
      type enumeration {
        enum UNKNOWN;
        enum TYPE01;
        enum TYPE02;
      }
      status deprecated;
      default "TYPE01";
      description "Default value: TYPE01; Status info: Deprecated since 16A.";
    }
    leaf batteryVoltage {
      type int32 {
        range "-600..-380 | 0";
      }
      config false;
      units "V";
    }
    leaf boostChargeTime {
      type int32 {
        range "0..48";
      }
      default "5";
      units "h";
      description "range 0..48; Default value: 5.";
    }
    leaf boostChargeTriggerVoltage {
      type int32 {
        range "-500..-420";
      }
      default "-470";
      units "V";
      description "range -500..-420; Default value: -470.";
    }
    leaf chargeMaxCurrent {
      type int32 {
        range "20..1000";
      }
      default "80";
      units "A";
      description "range 20..1000; Default value: 80.";
    }
    leaf chargingMode {
      type enumeration {
        enum AUTOMATIC;
        enum USER_DEFINED;
      }
    }
    leaf chargingVoltage {
      type eytypes:int32_range_-570--480;
      status deprecated;
      default "-545";
      units "V";
      description "range -570..-480; Default value: -545; Status info: Deprecated since 16A, replaced by FloatChargeVoltage.";
    }
    leaf equalizeChargeCyclicInterval {
      type int32 {
        range "0..365";
      }
      default "30";
      units "day";
      description "range 0..365; Default value: 30.";
    }
    leaf equalizeChargeTime {
      type int32 {
        range "0..24";
      }
      default "4";
      units "h";
      description "range 0..24; Default value: 4.";
    }
    leaf increasedChargeVoltage {
      type int32 {
        range "-585..-555";
      }
      status deprecated;
      default "-564";
      units "V";
      description "range -585..-555; Default value: -564; Status info: Deprecated since 16A, replaced by ElevatedChargeVoltage.";
    }
    leaf intermittentChargeConnectTime {
      type int32 {
        range "0..72";
      }
      default "0";
      units "h";
      description "range 0..72; Default value: 0.";
    }
    leaf intermittentChargeConnectVoltage {
      type int32 {
        range "-530..-460";
      }
      default "-500";
      units "V";
      description "range -530..-460; Default value: -500.";
    }
    leaf intermittentChargeDisconnectTime {
      type int32 {
        range "0..2400";
      }
      default "0";
      units "h";
      description "range 0..2400; Default value: 0.";
    }
    leaf minimumBackupTime {
      type int32 {
        range "0..10080";
      }
      default "60";
      units "minute";
      description "range 0..10080; Default value: 60.";
    }
    leaf minimumStateOfHealth {
      type eytypes:int32_range_0-100;
      default "70";
      units "percent";
      description "range 0..100; Default value: 70.";
    }
    leaf nextScheduledTestDate {
      type string {
        length "8";
      }
      config false;
      description "length 8..8.";
    }
    leaf nominalTemp {
      type int32 {
        range "170..280";
      }
      default "250";
      units "°C";
      description "range 170..280; Default value: 250.";
    }
    leaf referenceBatteryCapacity {
      type eytypes:int32_range_-1-999999;
      config false;
      units "Ah";
      description "range -1..999999.";
    }
    leaf sharedBattery {
      type boolean;
      default "false";
      description "Default value: false.";
    }
    leaf tempCompMaxVoltage {
      type eytypes:int32_range_-570--480;
      default "-569";
      units "V";
      description "range -570..-480; Default value: -569.";
    }
    leaf tempCompMinVoltage {
      type eytypes:int32_range_-570--480;
      default "-528";
      units "V";
      description "range -570..-480; Default value: -528.";
    }
    leaf tempCompVoltageSlope {
      type int32 {
        range "-10000..0";
      }
      default "-96";
      units "V/°C";
      description "range -10000..0; Default value: -96.";
    }
    leaf testMode {
      type enumeration {
        enum AUTOMATIC;
        enum CONFIGURED;
        enum DISABLED;
      }
    }
    leaf testStartDay {
      type eytypes:int32_range_1-31;
      default "25";
      description "range 1..31; Default value: 25.";
    }
    leaf-list testStartMonths {
      type enumeration {
        enum JANUARY;
        enum FEBRUARY;
        enum MARCH;
        enum APRIL;
        enum JUNE;
        enum JULY;
        enum AUGUST;
        enum MAY;
        enum SEPTEMBER;
        enum OCTOBER;
        enum NOVEMBER;
        enum DECEMBER;
      }
    }
    leaf testStartTime {
      type string {
        length "5";
      }
      default "01:00";
      description "length 5..5; Default value: 01:00.";
    }
    leaf userLabel {
      type string {
        length "1..128";
      }
      description "length 1..128.";
    }
    leaf operationalState {
      type enumeration {
        enum DISABLED;
        enum ENABLED;
      }
      config false;
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf extendedSoftwareControl {
      type boolean;
      config false;
    }
    leaf batteryDisconnectTemp {
      type int32 {
        range "40..70";
      }
      status deprecated;
      default "60";
      units "°C";
      description "range 40..70; Default value: 60; Status info: Deprecated since 16A, replaced by BatteryDisconnectHighTemp.";
    }
    leaf elevatedChargeVoltage {
      type int32 {
        range "-573..-555";
      }
      default "-570";
      units "V";
      description "range -573..-555; Default value: -570.";
    }
    leaf floatChargeVoltage {
      type int32 {
        range "-555..-510";
      }
      default "-545";
      units "V";
      description "range -555..-510; Default value: -545.";
    }
    leaf batteryDisconnectHighTemp {
      type int32 {
        range "40..60";
      }
      default "60";
      units "°C";
      description "range 40..60; Default value: 60.";
    }
    leaf controlDomainRef {
      type string;
    }
    leaf-list reservedBy {
      type string;
    }
    leaf batteryDisconnectLevel {
      type eytypes:int32_range_-1-100;
      default "5";
      units "percent";
      description "range -1..100; Default value: 5.";
    }
    leaf capacityAlarmLevel {
      type eytypes:int32_range_-1-100;
      default "40";
      units "percent";
      description "range -1..100; Default value: 40.";
    }
    leaf estimatedRemainingBackupTime {
      type int32 {
        range "-1..999999";
      }
      config false;
      units "minute";
      description "range -1..999999.";
    }
    leaf fullyChargedCapacity {
      type eytypes:int32_range_-1-999999;
      config false;
      units "Ah";
      description "range -1..999999.";
    }
    leaf mainLoadDisconnectLevel {
      type eytypes:int32_range_-1-100;
      default "25";
      units "percent";
      description "range -1..100; Default value: 25.";
    }
    leaf stateOfHealth {
      type eytypes:int32_range_-1-100;
      config false;
      units "percent";
      description "range -1..100.";
    }
    leaf-list pmBatteryDepthOfDischargeDistr {
      type uint32;
    }
    leaf-list pmBatteryMainLoadUnderVoltDiscTimeDistr {
      type uint32;
    }
    leaf pmBatteryCapacityTotalDelivered {
      type uint32;
      config false;
    }
    leaf-list pmBatteryTemperatureDistr {
      type uint32;
    }
    leaf-list pmBatteryDischargeTimeDistr {
      type uint32;
    }
  }
}
