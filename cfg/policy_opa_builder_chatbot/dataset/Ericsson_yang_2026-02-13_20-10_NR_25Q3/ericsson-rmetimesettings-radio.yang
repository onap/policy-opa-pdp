module ericsson-rmetimesettings-radio {
  yang-version 1.1;
  namespace "urn:com:ericsson:ecim:RmeTimeSettings";
  prefix rmetimes;
  import ericsson-rmesupport-radio {
    prefix rmesuppo;
  }
  import ericsson-managed-element {
    prefix emael;
  }
  description "Auto-generated from Ericsson ECIM (MOM XML).";
  revision 2026-02-13 {
    description "Initial auto-generated revision. Generated at 2026-02-13 20:11.";
  }

  augment "/emael:ManagedElement/rmesuppo:NodeSupport" {
    list TimeSettings {
      description "Additional definitions from MOM:min/max-elements:1/1;root;systemCreated; This MO class contain configuration for time zone information broadcast. The settings in this MO do not affect the system local time zone.";
      key "timeSettingsId";
      leaf timeSettingsId {
        type leafref {
          path "../attributes/timeSettingsId";
        }
      }
      container attributes {
        uses TimeSettings-attributes;
      }
    }
  }
  typedef DstMonth {
    type enumeration {
      enum JANUARY;
      enum FEBRUARY;
      enum MARCH;
      enum APRIL;
      enum MAY;
      enum JUNE;
      enum JULY;
      enum AUGUST;
      enum SEPTEMBER;
      enum OCTOBER;
      enum NOVEMBER;
      enum DECEMBER;
    }
  }
  grouping TimeSettings-attributes {
    leaf timeSettingsId {
      type string;
      mandatory true;
    }
    list daylightSavingTimeEndDate {
      key "id";
      leaf id {
        type uint32;
        description "Synthetic key for struct entry.";
      }
      container attributes {
      leaf month {
        type enumeration {
          enum JANUARY;
          enum FEBRUARY;
          enum MARCH;
          enum APRIL;
          enum MAY;
          enum JUNE;
          enum JULY;
          enum AUGUST;
          enum SEPTEMBER;
          enum OCTOBER;
          enum NOVEMBER;
          enum DECEMBER;
        }
      }
      leaf dayRule {
        type string;
      }
      leaf time {
        type string {
          length "5";
          pattern "(([0-1][0-9])|(2[0-4])):[0-5][0-9]";
        }
        description "length 5..5.";
      }
      }
    }
    leaf daylightSavingTimeOffset {
      type string {
        length "4";
        pattern "[0-9]:[0-5][0-9]";
      }
      default "1:00";
      description "length 4..4; Default value: 1:00.";
    }
    list daylightSavingTimeStartDate {
      key "id";
      leaf id {
        type uint32;
        description "Synthetic key for struct entry.";
      }
      container attributes {
      leaf month {
        type enumeration {
          enum JANUARY;
          enum FEBRUARY;
          enum MARCH;
          enum APRIL;
          enum MAY;
          enum JUNE;
          enum JULY;
          enum AUGUST;
          enum SEPTEMBER;
          enum OCTOBER;
          enum NOVEMBER;
          enum DECEMBER;
        }
      }
      leaf dayRule {
        type string;
      }
      leaf time {
        type string {
          length "5";
          pattern "(([0-1][0-9])|(2[0-4])):[0-5][0-9]";
        }
        description "length 5..5.";
      }
      }
    }
    leaf gpsToUtcLeapSeconds {
      type int16 {
        range "-1000..1000";
      }
      description "range -1000..1000.";
    }
    leaf gpsToUtcLeapSecondsChangeDate {
      type string {
        pattern "-*[1-9][0-9]{3}-(1[0-2]|0[1-9])-(0[1-9]|[1|2][0-9]|3[0-1])";
      }
    }
    leaf timeOffset {
      type string {
        length "5..6";
        pattern "[+-](([0-1][0-9])|(2[0-4])):([0-5][0-9])";
      }
      default "+00:00";
      description "length 5..6; Default value: +00:00.";
    }
  }
}
