module ericsson-rtndhcprelayipv6-radio {
  yang-version 1.1;
  namespace "urn:com:ericsson:ecim:RtnDhcpRelayIPv6";
  prefix rtndhcpr;
  import ietf-inet-types {
    prefix ietfinet;
  }
  import ericsson-l3-router-rtn-radio {
    prefix l3rtrdo;
  }
  import ericsson-managed-element {
    prefix emael;
  }
  description "Auto-generated from Ericsson ECIM (MOM XML).";
  revision 2026-02-13 {
    description "Initial auto-generated revision. Generated at 2026-02-13 20:11.";
  }

  augment "/emael:ManagedElement/emael:Transport/l3rtrdo:Router" {
    list DhcpRelayIPv6 {
      description "Additional definitions from MOM:min/max-elements:0/unbounded;root; Represents DHCP relay agent, that can relay IPv6 DHCP messages between DHCP clients and servers, which are not attached to same link.";
      key "dhcpRelayIPv6Id";
      leaf dhcpRelayIPv6Id {
        type leafref {
          path "../attributes/dhcpRelayIPv6Id";
        }
      }
      container attributes {
        uses DhcpRelayIPv6-attributes;
      }
    }
  }
  grouping DhcpRelayIPv6-attributes {
    leaf dhcpRelayIPv6Id {
      type ietfinet:ipv6-address;
      mandatory true;
    }
    leaf-list linkAddress {
      type string;
      min-elements 1;
    }
    leaf-list server {
      type string;
      min-elements 1;
    }
    leaf dhcpv6InClientMsgsHC {
      type uint64;
      config false;
    }
    leaf dhcpv6OutClientMsgsHC {
      type uint64;
      config false;
    }
    leaf dhcpv6InServerErrorsHC {
      type uint64;
      config false;
    }
    leaf dhcpv6InClientErrorsHC {
      type uint64;
      config false;
    }
    leaf dhcpv6OutServerMsgsHC {
      type uint64;
      config false;
    }
    leaf dhcpv6InServerMsgsHC {
      type uint64;
      config false;
    }
  }
}
