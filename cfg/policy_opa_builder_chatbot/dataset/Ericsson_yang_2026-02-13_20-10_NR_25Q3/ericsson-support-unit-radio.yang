module ericsson-support-unit-radio {
  yang-version 1.1;
  namespace "urn:com:ericsson:ecim:ReqSupportUnit";
  prefix supurdo;
  import ietf-inet-types {
    prefix ietfinet;
  }
  import ericsson-managed-element {
    prefix emael;
  }
  import ericsson-equip-radio {
    prefix equiprdo;
  }
  description "Auto-generated from Ericsson ECIM (MOM XML).";
  revision 2026-02-13 {
    description "Initial auto-generated revision. Generated at 2026-02-13 20:11.";
  }

  augment "/emael:ManagedElement/equiprdo:Equipment" {
    list SupportUnit {
      description "Additional definitions from MOM:min/max-elements:0/unbounded;root;systemCreated; A unit that provides support to adjacent units, in terms of power, climate and/or external alarms. RDNs of these MOs are SupportUnit=1, SupportUnit=2 and so on. Autocreated when the support unit is detected by the system.";
      key "supportUnitId";
      leaf supportUnitId {
        type leafref {
          path "../attributes/supportUnitId";
        }
      }
      container attributes {
        uses SupportUnit-attributes;
      }
    }
  }
  typedef AdmState {
    type enumeration {
      enum LOCKED;
      enum UNLOCKED;
      enum SHUTTINGDOWN;
    }
  }
  typedef AvailStatus {
    type enumeration {
      enum IN_TEST;
      enum FAILED;
      enum POWER_OFF;
      enum OFF_LINE;
      enum OFF_DUTY;
      enum DEPENDENCY;
      enum DEGRADED;
      enum NOT_INSTALLED;
      enum LOG_FULL;
      enum DEPENDENCY_LOCKED;
      enum DEPENDENCY_FAILED;
      enum DEPENDENCY_SHUTTINGDOWN;
      enum DEPENDENCY_RECOVERY;
      enum DEPENDENCY_HOLDING;
    }
  }
  typedef IndicatorStatus {
    type enumeration {
      enum NOT_APPLICABLE;
      enum NOT_AVAILABLE;
      enum OFF;
      enum STEADY_ON;
      enum SLOW_BLINK;
      enum FAST_BLINK;
      enum DOUBLE_FLASH_AND_STEADY_ON;
      enum DOUBLE_FLASH_AND_OFF;
    }
  }
  typedef OperState {
    type enumeration {
      enum DISABLED;
      enum ENABLED;
    }
  }
  typedef ProvidedServices {
    type enumeration {
      enum POWER_SUPPLY;
      enum POWER_DISTRIBUTION;
      enum FAN;
      enum EXTERNAL_ALARM_PORTS;
      enum BATTERY_BACKUP;
      enum GENERIC_DEVICE;
    }
  }
  typedef TempMeasType {
    type enumeration {
      enum NOT_SUPPORTED;
      enum AIR_INLET_TEMP;
      enum AIR_OUTLET_TEMP;
    }
  }
  grouping SupportUnit-attributes {
    leaf supportUnitId {
      type ietfinet:port-number;
      mandatory true;
    }
    leaf administrativeState {
      type enumeration {
        enum LOCKED;
        enum UNLOCKED;
        enum SHUTTINGDOWN;
      }
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf operationalState {
      type enumeration {
        enum DISABLED;
        enum ENABLED;
      }
      config false;
    }
    leaf faultIndicator {
      type enumeration {
        enum NOT_APPLICABLE;
        enum NOT_AVAILABLE;
        enum OFF;
        enum STEADY_ON;
        enum SLOW_BLINK;
        enum FAST_BLINK;
        enum DOUBLE_FLASH_AND_STEADY_ON;
        enum DOUBLE_FLASH_AND_OFF;
      }
      config false;
    }
    leaf operationalIndicator {
      type enumeration {
        enum NOT_APPLICABLE;
        enum NOT_AVAILABLE;
        enum OFF;
        enum STEADY_ON;
        enum SLOW_BLINK;
        enum FAST_BLINK;
        enum DOUBLE_FLASH_AND_STEADY_ON;
        enum DOUBLE_FLASH_AND_OFF;
      }
      config false;
    }
    list productData {
      config false;
      container attributes {
      leaf productionDate {
        type string {
          length "5..8";
        }
        description "length 5..8.";
      }
      leaf productName {
        type string {
          length "1..32";
        }
        description "length 1..32.";
      }
      leaf productNumber {
        type string {
          length "1..24";
        }
        description "length 1..24.";
      }
      leaf productRevision {
        type string {
          length "1..7";
        }
        description "length 1..7.";
      }
      leaf serialNumber {
        type string {
          length "1..13";
        }
        description "length 1..13.";
      }
      }
    }
    leaf-list providedServices {
      type enumeration {
        enum POWER_SUPPLY;
        enum POWER_DISTRIBUTION;
        enum FAN;
        enum EXTERNAL_ALARM_PORTS;
        enum BATTERY_BACKUP;
        enum GENERIC_DEVICE;
      }
    }
    leaf-list reservedBy {
      type string;
    }
    list specialIndicator {
      config false;
      container attributes {
      leaf indicatorStatus {
        type enumeration {
          enum NOT_APPLICABLE;
          enum NOT_AVAILABLE;
          enum OFF;
          enum STEADY_ON;
          enum SLOW_BLINK;
          enum FAST_BLINK;
          enum DOUBLE_FLASH_AND_STEADY_ON;
          enum DOUBLE_FLASH_AND_OFF;
        }
      }
      leaf indicatorName {
        type string {
          length "0..128";
        }
        description "length 0..128.";
      }
      }
    }
    list suAddressInfo {
      config false;
      container attributes {
      leaf hostObjectReference {
        type string;
      }
      leaf hostPortNumber {
        type ietfinet:port-number;
      }
      leaf supportUnitBusAddress {
        type ietfinet:port-number;
      }
      leaf supportUnitHostPortNumber {
        type ietfinet:port-number;
      }
      leaf hostedSupportUnitReference {
        type ietfinet:port-number;
        description "range 0..8.";
      }
      }
    }
    leaf commandResult {
      type string {
        length "1..64";
      }
      config false;
      description "length 1..64.";
    }
    leaf fanTrayTemperatureMeasurementType {
      type enumeration {
        enum NOT_SUPPORTED;
        enum AIR_INLET_TEMP;
        enum AIR_OUTLET_TEMP;
      }
      config false;
    }
    leaf-list pmFanSpeed {
      type int32;
    }
    leaf-list pmFanOperatingTemperature {
      type int32;
    }
  }
}
