module ericsson-rtnroutespeeripv6-radio {
  yang-version 1.1;
  namespace "urn:com:ericsson:ecim:RtnRoutesPeerIPv6";
  prefix rtnroute;
  import ietf-inet-types {
    prefix ietfinet;
  }
  import ericsson-l3-router-rtn-radio {
    prefix l3rtrdo;
  }
  import ericsson-managed-element {
    prefix emael;
  }
  description "Auto-generated from Ericsson ECIM (MOM XML).";
  revision 2026-02-13 {
    description "Initial auto-generated revision. Generated at 2026-02-13 20:11.";
  }

  augment "/emael:ManagedElement/emael:Transport/l3rtrdo:Router" {
    list PeerIPv6 {
      description "Additional definitions from MOM:min/max-elements:0/unbounded;root; Provides IPv6 peer information.";
      key "peerIPv6Id";
      leaf peerIPv6Id {
        type leafref {
          path "../attributes/peerIPv6Id";
        }
      }
      container attributes {
        uses PeerIPv6-attributes;
      }
    }
  }
  typedef BfdStaticRoutesInterfaceType {
    type enumeration {
      enum DISABLED;
      enum ENABLED;
    }
  }
  grouping PeerIPv6-attributes {
    leaf address {
      type string;
      mandatory true;
    }
    leaf bfdProfile {
      type string;
    }
    leaf bfdStaticRoutes {
      type enumeration {
        enum DISABLED;
        enum ENABLED;
      }
    }
    leaf peerIPv6Id {
      type ietfinet:ipv6-address;
      mandatory true;
    }
    leaf-list reservedBy {
      type string;
    }
  }
}
