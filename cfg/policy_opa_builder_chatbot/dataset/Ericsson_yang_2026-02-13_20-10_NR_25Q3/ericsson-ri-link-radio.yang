module ericsson-ri-link-radio {
  yang-version 1.1;
  namespace "urn:com:ericsson:ecim:ReqRiLink";
  prefix rilinkrdo;
  import ietf-inet-types {
    prefix ietfinet;
  }
  import ericsson-managed-element {
    prefix emael;
  }
  import ericsson-yang-types {
    prefix eytypes;
  }
  import ericsson-equip-radio {
    prefix equiprdo;
  }
  description "Auto-generated from Ericsson ECIM (MOM XML).";
  revision 2026-02-13 {
    description "Initial auto-generated revision. Generated at 2026-02-13 20:11.";
  }

  augment "/emael:ManagedElement/equiprdo:Equipment" {
    list RiLink {
      description "Additional definitions from MOM:min/max-elements:0/unbounded;root; This Managed Object (MO) is used to configure and monitor a Radio Interface (RI) link. It contains references to the two Radio Interface Ports (RiPort) comprising the link. On a link to an ORadio, following apply: - the link end on the Baseband refers to an RiPort MO. - and the link end on the ORadio refers to an ORiPort MO. On a link to a third-party radio, following apply: - the link end on the Baseband refers to an RiPort MO. - and the link end on the third-party radio refers to a ThirdPartyRiPort MO. The two port references must be provided to make the configuration of the radio interface connection complete.";
      key "riLinkId";
      leaf riLinkId {
        type leafref {
          path "../attributes/riLinkId";
        }
      }
      container attributes {
        uses RiLink-attributes;
      }
    }
  }
  typedef AvailStatus {
    type enumeration {
      enum IN_TEST;
      enum FAILED;
      enum POWER_OFF;
      enum OFF_LINE;
      enum OFF_DUTY;
      enum DEPENDENCY;
      enum DEGRADED;
      enum NOT_INSTALLED;
      enum LOG_FULL;
      enum DEPENDENCY_LOCKED;
      enum DEPENDENCY_FAILED;
      enum DEPENDENCY_SHUTTINGDOWN;
      enum DEPENDENCY_RECOVERY;
      enum DEPENDENCY_HOLDING;
    }
  }
  typedef FronthaulDeviceLineRate {
    type enumeration {
      enum NOT_SET;
      enum CPRI_LINE_RATE_2;
      enum CPRI_LINE_RATE_3;
      enum CPRI_LINE_RATE_5;
      enum CPRI_LINE_RATE_7;
      enum CPRI_LINE_RATE_8;
      enum ECPRI_LINE_RATE_25G_RS_FEC;
    }
  }
  typedef OperState {
    type enumeration {
      enum DISABLED;
      enum ENABLED;
    }
  }
  typedef RbsTransportType {
    type enumeration {
      enum CPRI_OVER_DWDM_LINEAR;
      enum CPRI_OVER_DWDM_RING;
      enum CPRI_OVER_CWDM_LINEAR;
      enum CPRI_OVER_CWDM_RING;
      enum CPRI_OVER_MICROWAVE_PTOP;
      enum CPRI_OVER_MICROWAVE_PTOM;
      enum CPRI_OVER_GIGABIT_ETHERNET;
      enum NOT_SET;
      enum CPRI_OVER_DIRECT_CABLE;
      enum ETHERNET_OVER_E_LINE;
    }
  }
  grouping RiLink-attributes {
    leaf riLinkId {
      type string;
      mandatory true;
    }
    leaf operationalState {
      type enumeration {
        enum DISABLED;
        enum ENABLED;
      }
      config false;
    }
    leaf riPortRef1 {
      type ietfinet:ip-address;
      mandatory true;
    }
    leaf riPortRef2 {
      type ietfinet:ip-address;
      mandatory true;
    }
    leaf linkRate {
      type int32 {
        range "0..53100";
      }
      config false;
      units "Mbps";
      description "range 0..53100.";
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf transportType {
      type ietfinet:port-number;
    }
    leaf linkTag {
      type eytypes:int64_range_0-4294967295;
      config false;
      description "range 0..4294967295.";
    }
    leaf fronthaulDeviceLineRate {
      type enumeration {
        enum NOT_SET;
        enum CPRI_LINE_RATE_2;
        enum CPRI_LINE_RATE_3;
        enum CPRI_LINE_RATE_5;
        enum CPRI_LINE_RATE_7;
        enum CPRI_LINE_RATE_8;
        enum ECPRI_LINE_RATE_25G_RS_FEC;
      }
    }
    leaf-list reservedBy {
      type string;
    }
    leaf operationalStateChangeTime {
      type string;
      config false;
    }
    leaf pmLinkRestart {
      type uint32;
      config false;
    }
    leaf pmCableDelayHigh {
      type int32;
      config false;
    }
    leaf pmLinkDelayHigh {
      type int32;
      config false;
    }
    leaf pmCableDelayLow {
      type int32;
      config false;
    }
    leaf pmLinkStabilityError {
      type uint32;
      config false;
    }
    leaf pmLinkDelayLow {
      type int32;
      config false;
    }
  }
}
