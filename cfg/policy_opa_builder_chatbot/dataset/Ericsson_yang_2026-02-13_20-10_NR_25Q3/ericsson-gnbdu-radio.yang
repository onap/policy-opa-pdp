module ericsson-gnbdu-radio {
  yang-version 1.1;
  namespace "urn:com:ericsson:ecim:GNBDU";
  prefix gnbdu;
  import ietf-inet-types {
    prefix ietfinet;
  }
  import ietf-yang-types {
    prefix ietfyang;
  }
  import ericsson-managed-element {
    prefix emael;
  }
  import ericsson-yang-types {
    prefix eytypes;
  }
  description "Auto-generated from Ericsson ECIM (MOM XML).";
  revision 2026-02-13 {
    description "Initial auto-generated revision. Generated at 2026-02-13 20:11.";
  }

  augment "/emael:ManagedElement" {
    list GNBDUFunction {
      description "Additional definitions from MOM:min/max-elements:0/unbounded;root; Represents gNodeB-DU function. Cannot be deleted if there are NRSectorCarrier instances configured.";
      key "gNBDUFunctionId";
      leaf gNBDUFunctionId {
        type leafref {
          path "../attributes/gNBDUFunctionId";
        }
      }
      container attributes {
        uses GNBDUFunction-attributes;
      }
    }
  }

  augment "/emael:ManagedElement/GNBDUFunction/AdmissionControl" {
    list CchLoadProfile {
      description "Additional definitions from MOM:min/max-elements:0/16; Control channel load metric profile for a cell. Instance CchLoadProfile=Default is created automatically when parent MO instance is created, unless created manually in same transaction. NRCellDU::cchLoadProfileRef is automatically set to CchLoadProfile=Default instance, unless manually set to refer to another MO instance. Precondition: Instance CchLoadProfile=Default can only be created in same transaction as parent MO instance and cannot be deleted unless parent MO instance is deleted. Other instances can be created and deleted at any time. Maximum 15 CchLoadProfile instances, with RDN different from Default, can be created under parent MO instance.";
      key "cchLoadProfileId";
      leaf cchLoadProfileId {
        type leafref {
          path "../attributes/cchLoadProfileId";
        }
      }
      container attributes {
        uses CchLoadProfile-attributes;
      }
    }
  }

  augment "/emael:ManagedElement/GNBDUFunction/DUQos/AutomatedQos" {
    list RrpController {
      description "Additional definitions from MOM:min/max-elements:0/16; Performance metrics for Automated RRP. Instance RrpController=NO_AUTO_CONTROL is created automatically when parent MO instance is created, unless created manually in same transaction. ResourceAllocationPolicy::rrpControllerRef and ServicePolicy::rrpControllerRef are automatically set to RrpController=NO_AUTO_CONTROL instance, unless manually set to refer to another MO instance. Precondition: Instance RrpController=NO_AUTO_CONTROL can only be created in same transaction as parent MO instance and cannot be deleted unless parent MO instance is deleted. Other instances can be created and deleted manually. Maximum 15 RrpController instances, with RDN different from NO_AUTO_CONTROL, can be created under parent MO instance.";
      key "rrpControllerId";
      leaf rrpControllerId {
        type leafref {
          path "../attributes/rrpControllerId";
        }
      }
      container attributes {
        uses RrpController-attributes;
      }
    }
  }

  augment "/emael:ManagedElement/GNBDUFunction/BWPSet" {
    list BWPSetUeCfg {
      description "Additional definitions from MOM:min/max-elements:1/8; Configuration of UE-specific capabilities within BWPSet instance.";
      key "bWPSetUeCfgId";
      leaf bWPSetUeCfgId {
        type leafref {
          path "../attributes/bWPSetUeCfgId";
        }
      }
      container attributes {
        uses BWPSetUeCfg-attributes;
      }
    }
  }

  augment "/emael:ManagedElement/GNBDUFunction/BWPSet" {
    list DynPowerOpt {
      description "Additional definitions from MOM:min/max-elements:0/12; Configuration of UE power saving through search space adaption for BWP.";
      key "dynPowerOptId";
      leaf dynPowerOptId {
        type leafref {
          path "../attributes/dynPowerOptId";
        }
      }
      container attributes {
        uses DynPowerOpt-attributes;
      }
    }
  }

  augment "/emael:ManagedElement/GNBDUFunction/BWPSet/BWPSetUeCfg" {
    list BWPSetCfg {
      description "Additional definitions from MOM:min/max-elements:1/4; Configuration of individual BWP within BWPSet instance. If BWPSet instance is configured for FDD cell in bWPSetRef, maximum 3 BWPSetCfg instances can be created under parent MO instance. If BWPSet instance is configured for TDD cell in bWPSetRef, maximum 4 BWPSetCfg instances can be created under parent MO instance. For each unique BWP frequency width, at least one BWPSetCfg instance must be created under parent MO instance.";
      key "bWPSetCfgId";
      leaf bWPSetCfgId {
        type leafref {
          path "../attributes/bWPSetCfgId";
        }
      }
      container attributes {
        uses BWPSetCfg-attributes;
      }
    }
  }

  augment "/emael:ManagedElement/GNBDUFunction/UeCC/Bsr" {
    list BsrUeCfg {
      description "Additional definitions from MOM:min/max-elements:0/8; BSR profile used for current UE. Instance BsrUeCfg=Base is created automatically when parent MO instance is created, unless created manually in same transaction. UeBbProfileUeCfg::bsrUeCfgRef is automatically set to BsrUeCfg=Base instance, unless manually set to refer to another MO instance. Precondition: Instance BsrUeCfg=Base can only be created in same transaction as parent MO instance and cannot be deleted unless parent MO instance is deleted. Other instances can be created and deleted at any time. Maximum 7 BsrUeCfg instances, with RDN different from Base, can be created under parent MO instance.";
      key "bsrUeCfgId";
      leaf bsrUeCfgId {
        type leafref {
          path "../attributes/bsrUeCfgId";
        }
      }
      container attributes {
        uses BsrUeCfg-attributes;
      }
    }
  }

  augment "/emael:ManagedElement/GNBDUFunction/UeCA/CaSCellHandling" {
    list CaSCellHandlingUeCfg {
      description "Additional definitions from MOM:min/max-elements:0/8; SCell handling parameters in NR Carrier Aggregation for UE groups. Instance CaSCellHandlingUeCfg=Base is created automatically when parent MO instance is created, unless created manually in same transaction. Attributes prefUeGroupList, ueGroupList and ueConfGroupList must be empty in instance CaSCellHandlingUeCfg=Base but cannot all be empty in any other instance of CaSCellHandlingUeCfg under same parent CaSCellHandling instance. Precondition: Instance CaSCellHandlingUeCfg=Base can only be created in same transaction as parent MO instance and cannot be deleted unless parent MO instance is deleted. Other instances can be created and deleted at any time. Maximum 7 CaSCellHandlingUeCfg instances, with RDN different from Base, can be created under parent MO instance.";
      key "caSCellHandlingUeCfgId";
      leaf caSCellHandlingUeCfgId {
        type leafref {
          path "../attributes/caSCellHandlingUeCfgId";
        }
      }
      container attributes {
        uses CaSCellHandlingUeCfg-attributes;
      }
    }
  }

  augment "/emael:ManagedElement/GNBDUFunction/ResourceAllocationPolicies/CellResourceMapping" {
    list PartitionMapping {
      description "Additional definitions from MOM:min/max-elements:0/13; Mapping of resource quotas to resource partition.";
      key "partitionMappingId";
      leaf partitionMappingId {
        type leafref {
          path "../attributes/partitionMappingId";
        }
      }
      container attributes {
        uses PartitionMapping-attributes;
      }
    }
  }

  augment "/emael:ManagedElement/GNBDUFunction/UeCC/CgSwitch" {
    list CgSwitchUeCfg {
      description "Additional definitions from MOM:min/max-elements:0/8; Cell group switch UE configuration group. Instance CgSwitchUeCfg=Base is created automatically when parent MO instance is created, unless created manually in same transaction. Each UE configuration group identifier can only be defined in one ueConfGroupList among CgSwitchUeCfg instances contained under parent CgSwitch instance. Any combination of one UE group identifier in ueGroupList and one preference UE group identifier in prefUeGroupList must be unique among CgSwitchUeCfg instances contained under parent CgSwitch instance. Attributes prefUeGroupList, ueGroupList and ueConfGroupList must be empty in instance CgSwitchUeCfg=Base but cannot all be empty in any other instance of CgSwitchUeCfg under same parent CgSwitch instance. Precondition: Instance CgSwitchUeCfg=Base can only be created in same transaction as parent MO instance and cannot be deleted unless parent MO instance is deleted. Other instances can be created and deleted at any time. Maximum 7 CgSwitchUeCfg instances, with RDN different from Base, can be created under parent MO instance.";
      key "cgSwitchUeCfgId";
      leaf cgSwitchUeCfgId {
        type leafref {
          path "../attributes/cgSwitchUeCfgId";
        }
      }
      container attributes {
        uses CgSwitchUeCfg-attributes;
      }
    }
  }

  augment "/emael:ManagedElement/GNBDUFunction/NRSectorCarrier/CommonBeamforming" {
    list Beam {
      description "Additional definitions from MOM:min/max-elements:0/64;systemCreated; SSB beam used by NRSectorCarrier. Created when NRCellDU::administrativeState is changed to UNLOCKED. The RDN of this MO is Beam=[wideBeamIndex]. Length of RDN value is up to 2 characters. Instance can be created without a preceding user-initiated transaction.";
      key "beamId";
      leaf beamId {
        type leafref {
          path "../attributes/beamId";
        }
      }
      container attributes {
        uses Beam-attributes;
      }
    }
  }

  augment "/emael:ManagedElement/GNBDUFunction/UeCC/ConfiguredGrant" {
    list ConfiguredGrantUeCfg {
      description "Additional definitions from MOM:min/max-elements:0/8; Configured grant configuration profile for UE groups. Instance ConfiguredGrantUeCfg=Base is created automatically when parent MO instance is created, unless created manually in same transaction. UeBbProfileUeCfg::configuredGrantUeCfgRef is automatically set to ConfiguredGrantUeCfg=Base instance, unless manually set to refer to another MO instance. Precondition: Instance ConfiguredGrantUeCfg=Base can only be created in same transaction as parent MO instance and cannot be deleted unless parent MO instance is deleted. Other instances can be created and deleted at any time. Maximum 7 ConfiguredGrantUeCfg instances, with RDN different from Base, can be created under parent MO instance.";
      key "configuredGrantUeCfgId";
      leaf configuredGrantUeCfgId {
        type leafref {
          path "../attributes/configuredGrantUeCfgId";
        }
      }
      container attributes {
        uses ConfiguredGrantUeCfg-attributes;
      }
    }
  }

  augment "/emael:ManagedElement/GNBDUFunction/ContentionControl" {
    list SessionLimit {
      description "Additional definitions from MOM:min/max-elements:0/16; Session limit definition. Instance SessionLimit=Default is created automatically when parent MO instance is created, unless created manually in same transaction. TrafficSet::sessionLimitRef is automatically set to SessionLimit=Default instance, unless manually set to refer to another MO instance. Precondition: Instance SessionLimit=Default can only be created in same transaction as parent MO instance and cannot be deleted unless parent MO instance is deleted. Other instances can be created and deleted at any time. Maximum 15 SessionLimit instances, with RDN different from Default, can be created under parent MO instance.";
      key "sessionLimitId";
      leaf sessionLimitId {
        type leafref {
          path "../attributes/sessionLimitId";
        }
      }
      container attributes {
        uses SessionLimit-attributes;
      }
    }
  }

  augment "/emael:ManagedElement/GNBDUFunction/UeCC/CsiProfile" {
    list CsiProfileUeCfg {
      description "Additional definitions from MOM:min/max-elements:0/4; Channel State Information profile configurations for UE groups. Instance CsiProfileUeCfg=Base is created automatically when parent MO instance is created, unless created manually in same transaction. UeBbProfileUeCfg::csiProfileUeCfgRef is automatically set to CsiProfileUeCfg=Base instance, unless manually set to refer to another MO instance. Precondition: Instance CsiProfileUeCfg=Base can only be created in same transaction as parent MO instance and cannot be deleted unless parent MO instance is deleted. Other instances can be created and deleted at any time. Maximum 3 CsiProfileUeCfg instances, with RDN different from Base, can be created under parent MO instance.";
      key "csiProfileUeCfgId";
      leaf csiProfileUeCfgId {
        type leafref {
          path "../attributes/csiProfileUeCfgId";
        }
      }
      container attributes {
        uses CsiProfileUeCfg-attributes;
      }
    }
  }

  augment "/emael:ManagedElement/GNBDUFunction/DU5qiTable" {
    list DU5qi {
      description "Additional definitions from MOM:min/max-elements:1/29; QoS configuration for each 5QI profile. Each profile can be present once in each table.";
      key "dU5qiId";
      leaf dU5qiId {
        type leafref {
          path "../attributes/dU5qiId";
        }
      }
      container attributes {
        uses DU5qi-attributes;
      }
    }
  }

  augment "/emael:ManagedElement/GNBDUFunction/DUQosModifier/DUModified5qi" {
    list DUModified5qiUeCfg {
      description "Additional definitions from MOM:min/max-elements:0/15; QoS modification version of parent 5QI profile. Value 0 is no longer allowed and is planned to be removed from the valid range of prefUeGroupList and ueGroupList.";
      key "dUModified5qiUeCfgId";
      leaf dUModified5qiUeCfgId {
        type leafref {
          path "../attributes/dUModified5qiUeCfgId";
        }
      }
      container attributes {
        uses DUModified5qiUeCfg-attributes;
      }
    }
  }

  augment "/emael:ManagedElement/GNBDUFunction/DUQos" {
    list AutomatedQos {
      description "Additional definitions from MOM:min/max-elements:0/1; Container class for Automated QoS attributes and classes. Instance AutomatedQos=1 is created automatically when parent MO instance is created, unless created manually in same transaction. The RDN of this MO must be AutomatedQos=1. Precondition: Instance AutomatedQos=1 can only be created in same transaction as parent MO instance and cannot be deleted unless parent MO instance is deleted.";
      key "automatedQosId";
      leaf automatedQosId {
        type leafref {
          path "../attributes/automatedQosId";
        }
      }
      container attributes {
        uses AutomatedQos-attributes;
      }
    }
  }

  augment "/emael:ManagedElement/GNBDUFunction/DUQos" {
    list ExtCaPriority {
      description "Additional definitions from MOM:min/max-elements:0/8; Carrier Aggregation QoS for external data. Not applicable in High-Band cells. Instance ExtCaPriority=Default is created automatically when parent MO instance is created, unless created manually in same transaction. NRCellDU::extCaPriorityRef is automatically set to ExtCaPriority=Default instance, unless manually set to refer to another MO instance. Precondition: Instance ExtCaPriority=Default can only be created in same transaction as parent MO instance and cannot be deleted unless parent MO instance is deleted. Other instances can be created and deleted at any time. Maximum 7 ExtCaPriority instances, with RDN different from Default, can be created under parent MO instance.";
      key "extCaPriorityId";
      leaf extCaPriorityId {
        type leafref {
          path "../attributes/extCaPriorityId";
        }
      }
      container attributes {
        uses ExtCaPriority-attributes;
      }
    }
  }

  augment "/emael:ManagedElement/GNBDUFunction/DUQos" {
    list QosPriorityShift {
      description "Additional definitions from MOM:min/max-elements:0/1; Container class for QoS priority shift attributes and classes.";
      key "qosPriorityShiftId";
      leaf qosPriorityShiftId {
        type leafref {
          path "../attributes/qosPriorityShiftId";
        }
      }
      container attributes {
        uses QosPriorityShift-attributes;
      }
    }
  }

  augment "/emael:ManagedElement/GNBDUFunction/DUQosModifier" {
    list DUModified5qi {
      description "Additional definitions from MOM:min/max-elements:0/29; QoS modification for a certain 5QI.";
      key "dUModified5qiId";
      leaf dUModified5qiId {
        type leafref {
          path "../attributes/dUModified5qiId";
        }
      }
      container attributes {
        uses DUModified5qi-attributes;
      }
    }
  }

  augment "/emael:ManagedElement/GNBDUFunction/UeCC/DlBeamOptProfile" {
    list DlBeamOptProfileUeCfg {
      description "Additional definitions from MOM:min/max-elements:0/4; Downlink Beamforming optimization profile configurations for UE groups. Instance DlBeamOptProfileUeCfg=Base is created automatically when parent MO instance is created, unless created manually in same transaction. UeBbProfileUeCfg::dlBeamOptProfileUeCfgRef is automatically set to DlBeamOptProfileUeCfg=Base instance, unless manually set to refer to another MO instance. Precondition: Instance DlBeamOptProfileUeCfg=Base can only be created in same transaction as parent MO instance and cannot be deleted unless parent MO instance is deleted. Other instances can be created and deleted at any time. Maximum 3 DlBeamOptProfileUeCfg instances, with RDN different from Base, can be created under parent MO instance.";
      key "dlBeamOptProfileUeCfgId";
      leaf dlBeamOptProfileUeCfgId {
        type leafref {
          path "../attributes/dlBeamOptProfileUeCfgId";
        }
      }
      container attributes {
        uses DlBeamOptProfileUeCfg-attributes;
      }
    }
  }

  augment "/emael:ManagedElement/GNBDUFunction/UeCC/DlMimo" {
    list DlMimoUeCfg {
      description "Additional definitions from MOM:min/max-elements:0/8; Downlink MIMO configuration profile used for current UE. Applies to UEs that use cell as SpCell. Attributes are used on cell level. For all attributes except srsImpactHandling, instances other than DlMimoUeCfg=Base are only applicable if license for Service-Adaptive Massive MIMO Low/Mid-Band is present and feature is active. Instance DlMimoUeCfg=Base is created automatically when parent MO instance is created, unless created manually in same transaction. UeBbProfileUeCfg::dlMimoUeCfgRef is automatically set to DlMimoUeCfg=Base instance, unless manually set to refer to another MO instance. Precondition: Instance DlMimoUeCfg=Base can only be created in same transaction as parent MO instance and cannot be deleted unless parent MO instance is deleted. Other instances can be created and deleted at any time. Maximum 7 DlMimoUeCfg instances, with RDN different from Base, can be created under parent MO instance.";
      key "dlMimoUeCfgId";
      leaf dlMimoUeCfgId {
        type leafref {
          path "../attributes/dlMimoUeCfgId";
        }
      }
      container attributes {
        uses DlMimoUeCfg-attributes;
      }
    }
  }

  augment "/emael:ManagedElement/GNBDUFunction/UeCC/RadioLinkControl/DrbRlc" {
    list DrbRlcUeCfg {
      description "Additional definitions from MOM:min/max-elements:0/4; Configuration of data radio bearer radio link control profile for UE groups. Instance DrbRlcUeCfg=Base is created automatically when parent MO instance is created, unless created manually in same transaction. Attributes prefUeGroupList, ueGroupList and ueConfGroupList must be empty in instance DrbRlcUeCfg=Base but cannot all be empty in any other instance of DrbRlcUeCfg under same parent DrbRlc instance. A combination of an element of ueGroupList and an element of prefUeGroupList in DrbRlcUeCfg instance must be unique under DrbRlc instance. Precondition: Instance DrbRlcUeCfg=Base can only be created in same transaction as parent MO instance and cannot be deleted unless parent MO instance is deleted. Other instances can be created and deleted at any time. Maximum 3 DrbRlcUeCfg instances, with RDN different from Base, can be created under parent MO instance.";
      key "drbRlcUeCfgId";
      leaf drbRlcUeCfgId {
        type leafref {
          path "../attributes/drbRlcUeCfgId";
        }
      }
      container attributes {
        uses DrbRlcUeCfg-attributes;
      }
    }
  }

  augment "/emael:ManagedElement/GNBDUFunction/UeCC/DrbUp" {
    list DrbUpUeCfg {
      description "Additional definitions from MOM:min/max-elements:0/8; Configuration of data radio bearer user plane UE profile for UE groups. Instance DrbUpUeCfg=Base is created automatically when parent MO instance is created, unless created manually in same transaction. Each UE configuration group identifier can be defined in only one ueConfGroupList among DrbUpUeCfg instances contained under same parent DrbUp instance. Any combination of one UE group identifier in ueGroupList and one preference UE group identifier in prefUeGroupList must be unique among DrbUpUeCfg instances contained under parent DrbUp instance. Attributes prefUeGroupList, ueGroupList and ueConfGroupList must be empty in instance DrbUpUeCfg=Base but cannot all be empty in any other instance of DrbUpUeCfg under same parent DrbUp instance. Only applicable when GNBDUFunction::altDepHServAdapUPProfEnabled is true. Precondition: Instance DrbUpUeCfg=Base can only be created in same transaction as parent MO instance and cannot be deleted unless parent MO instance is deleted. Other instances can be created and deleted at any time. Maximum 7 DrbUpUeCfg instances, with RDN different from Base, can be created under parent MO instance. To be able to create an instance, the total number of instances, including all auto created instances, must be less than the total allowed number of instances under a GNBCUCPFunction instance that is 32.";
      key "drbUpUeCfgId";
      leaf drbUpUeCfgId {
        type leafref {
          path "../attributes/drbUpUeCfgId";
        }
      }
      container attributes {
        uses DrbUpUeCfg-attributes;
      }
    }
  }

  augment "/emael:ManagedElement/GNBDUFunction/UeCC/DrxProfile" {
    list DrxProfileUeCfg {
      description "Additional definitions from MOM:min/max-elements:0/8; Configuration of DRX profile for UE groups. Instance DrxProfileUeCfg=Base is created automatically when parent MO instance is created, unless created manually in same transaction. Attributes prefUeGroupList, ueGroupList and ueConfGroupList must be empty in instance DrxProfileUeCfg=Base but cannot all be empty in any other instance of DrxProfileUeCfg under same parent DrxProfile instance. Value 0 is no longer allowed and is planned to be removed from the valid range of prefUeGroupList and ueGroupList. Precondition: Instance DrxProfileUeCfg=Base can only be created in same transaction as parent MO instance and cannot be deleted unless parent MO instance is deleted. Other instances can be created and deleted at any time. Maximum 7 DrxProfileUeCfg instances, with RDN different from Base, can be created under parent MO instance.";
      key "drxProfileUeCfgId";
      leaf drxProfileUeCfgId {
        type leafref {
          path "../attributes/drxProfileUeCfgId";
        }
      }
      container attributes {
        uses DrxProfileUeCfg-attributes;
      }
    }
  }

  augment "/emael:ManagedElement/GNBDUFunction/UeCC/DrxProfile/DrxProfileUeCfg" {
    list PuschRepRel16Drx {
      description "Additional definitions from MOM:min/max-elements:0/1; Configuration of PUSCH Repetition specific DRX parameters. Only applicable to Low-Band and Mid-Band cells.";
      key "puschRepRel16DrxId";
      leaf puschRepRel16DrxId {
        type leafref {
          path "../attributes/puschRepRel16DrxId";
        }
      }
      container attributes {
        uses PuschRepRel16Drx-attributes;
      }
    }
  }

  augment "/emael:ManagedElement/GNBDUFunction/EndpointResource" {
    list LocalIpEndpoint {
      description "Additional definitions from MOM:min/max-elements:0/unbounded; Local transport network endpoint for user plane interface.";
      key "localIpEndpointId";
      leaf localIpEndpointId {
        type leafref {
          path "../attributes/localIpEndpointId";
        }
      }
      container attributes {
        uses LocalIpEndpoint-attributes;
      }
    }
  }

  augment "/emael:ManagedElement/GNBDUFunction/EndpointResource" {
    list LocalSctpEndpoint {
      description "Additional definitions from MOM:min/max-elements:0/unbounded; Local transport network endpoint for control plane interface.";
      key "localSctpEndpointId";
      leaf localSctpEndpointId {
        type leafref {
          path "../attributes/localSctpEndpointId";
        }
      }
      container attributes {
        uses LocalSctpEndpoint-attributes;
      }
    }
  }

  augment "/emael:ManagedElement/GNBDUFunction/EnergyEfficiency" {
    list EnergyOptPwrAlloc {
      description "Additional definitions from MOM:min/max-elements:0/8; Energy-Optimized Power Allocation profile used for current UE. Container class for Energy-Optimized Power Allocation (EOPA) attributes and classes. Instance EnergyOptPwrAlloc=Default is created automatically when parent MO instance is created, unless created manually in same transaction. NRCellDU::energyOptPwrAllocRef is automatically set to EnergyOptPwrAlloc=Default instance, unless manually set to refer to another MO instance. Only applicable to Low-Band and Mid-Band cells. Precondition: Instance EnergyOptPwrAlloc=Default can only be created in same transaction as parent MO instance and cannot be deleted unless parent MO instance is deleted. Other instances can be created and deleted at any time. Maximum 7 EnergyOptPwrAlloc instance, with RDN different from Default, can be created under parent MO instance.";
      key "energyOptPwrAllocId";
      leaf energyOptPwrAllocId {
        type leafref {
          path "../attributes/energyOptPwrAllocId";
        }
      }
      container attributes {
        uses EnergyOptPwrAlloc-attributes;
      }
    }
  }

  augment "/emael:ManagedElement/GNBDUFunction/EnergyEfficiency" {
    list EnergyOptSymAlloc {
      description "Additional definitions from MOM:min/max-elements:0/2; Container class for Energy Optimized Symbol Allocation (EOSA) attributes and classes. Instance EnergyOptSymAlloc=Default is created automatically when parent MO instance is created, unless created manually in same transaction. NRCellDU::energyOptSymAllocRef is automatically set to EnergyOptSymAlloc=Default instance, unless manually set to refer to another MO instance. If license for NR Flexible Channel Bandwidth feature is present and feature is active, applicable to following cells: - Low-Band cells with bandwidth greater than 10 Mhz - Mid-Band cells with bandwidth greater than 20 Mhz Otherwise, applicable to following cells: - Low-Band cells with bandwidth greater than 5 Mhz - Mid-Band cells with bandwidth greater than 15 Mhz Precondition: Instance EnergyOptSymAlloc=Default can only be created in same transaction as parent MO instance and cannot be deleted unless parent MO instance is deleted. Other instances can be created and deleted at any time. Maximum 1 EnergyOptSymAlloc instance, with RDN different from Default, can be created under parent MO instance.";
      key "energyOptSymAllocId";
      leaf energyOptSymAllocId {
        type leafref {
          path "../attributes/energyOptSymAllocId";
        }
      }
      container attributes {
        uses EnergyOptSymAlloc-attributes;
      }
    }
  }

  augment "/emael:ManagedElement/GNBDUFunction/EnergyEfficiency/EnergyOptPwrAlloc" {
    list EnergyOptPwrAllocUeCfg {
      description "Additional definitions from MOM:min/max-elements:0/8; Energy-Optimized Power Allocation profile for UE groups. Instance EnergyOptPwrAllocUeCfg=Base is created automatically when parent MO instance is created, unless created manually in same transaction. Attributes prefUeGroupList, ueGroupList and ueConfGroupList must be empty in instance EnergyOptPwrAllocUeCfg=Base but cannot all be empty in any other instance of EnergyOptPwrAllocUeCfg under same parent EnergyOptPwrAlloc instance. Precondition: Instance EnergyOptPwrAllocUeCfg=Base can only be created in same transaction as parent MO instance and cannot be deleted unless parent MO instance is deleted. Other instances can be created and deleted at any time. Maximum 7 EnergyOptPwrAllocUeCfg instance, with RDN different from Base, can be created under parent MO instance.";
      key "energyOptPwrAllocUeCfgId";
      leaf energyOptPwrAllocUeCfgId {
        type leafref {
          path "../attributes/energyOptPwrAllocUeCfgId";
        }
      }
      container attributes {
        uses EnergyOptPwrAllocUeCfg-attributes;
      }
    }
  }

  augment "/emael:ManagedElement/GNBDUFunction/ExtENodeBPartnerFunction" {
    list LteInterMeLink {
      description "Additional definitions from MOM:min/max-elements:0/1;systemCreated; Elastic RAN link between a local ME and a neighboring ME. Created when an inter-ME link is established. Deleted when an inter-ME link is released. The RDN of this MO is LteInterMeLink=1. Length of RDN value is 1 character. Instance can be created without a preceding user-initiated transaction.";
      key "lteInterMeLinkId";
      leaf lteInterMeLinkId {
        type leafref {
          path "../attributes/lteInterMeLinkId";
        }
      }
      container attributes {
        uses LteInterMeLink-attributes;
      }
    }
  }

  augment "/emael:ManagedElement/GNBDUFunction/ExtGNBDUPartnerFunction" {
    list InterMeLink {
      description "Additional definitions from MOM:min/max-elements:0/9;systemCreated; ERAN Link between a local ME and a neighboring ME. Created when an inter ME link is established. Deleted when an inter ME link is released. The RDNs of these MOs are InterMeLink=1 to InterMeLink=9. Length of RDN value is 1 character. Instance can be created without a preceding user-initiated transaction.";
      key "interMeLinkId";
      leaf interMeLinkId {
        type leafref {
          path "../attributes/interMeLinkId";
        }
      }
      container attributes {
        uses InterMeLink-attributes;
      }
    }
  }

  augment "/emael:ManagedElement/GNBDUFunction" {
    list AdmissionControl {
      description "Additional definitions from MOM:min/max-elements:1/1;systemCreated; Contains parameters for admission control function. The RDN of this MO is AdmissionControl=1.";
      key "admissionControlId";
      leaf admissionControlId {
        type leafref {
          path "../attributes/admissionControlId";
        }
      }
      container attributes {
        uses AdmissionControl-attributes;
      }
    }
  }

  augment "/emael:ManagedElement/GNBDUFunction" {
    list Aes {
      description "Additional definitions from MOM:min/max-elements:0/1; Controls Automated Energy Saver feature for NR Massive MIMO Sleep Mode feature. The RDN of this MO must be Aes=1.";
      key "aesId";
      leaf aesId {
        type leafref {
          path "../attributes/aesId";
        }
      }
      container attributes {
        uses Aes-attributes;
      }
    }
  }

  augment "/emael:ManagedElement/GNBDUFunction" {
    list BWP {
      description "Additional definitions from MOM:min/max-elements:0/unbounded; Bandwidth Part (BWP) definition. BWP is related to downlink or uplink resource grids, and is defined by its subcarrier spacing (SCS), cyclic prefix and location and size related to the common resource grid for the applicable SCS. A BWP can be either an initial BWP used for initial access, or other (\"regular\") BWP configured for relevant UEs that support the BWP's characteristics.";
      key "bWPId";
      leaf bWPId {
        type leafref {
          path "../attributes/bWPId";
        }
      }
      container attributes {
        uses BWP-attributes;
      }
    }
  }

  augment "/emael:ManagedElement/GNBDUFunction" {
    list BWPSet {
      description "Additional definitions from MOM:min/max-elements:0/12; Configuration of regular BWP.";
      key "bWPSetId";
      leaf bWPSetId {
        type leafref {
          path "../attributes/bWPSetId";
        }
      }
      container attributes {
        uses BWPSet-attributes;
      }
    }
  }

  augment "/emael:ManagedElement/GNBDUFunction" {
    list CardinalityLimits {
      description "Additional definitions from MOM:min/max-elements:1/1;systemCreated; Cardinality limits for current deployment. Listed cardinality limits is maximum number of MO instances that can be created. The RDN of this MO is CardinalityLimits=1.";
      key "cardinalityLimitsId";
      leaf cardinalityLimitsId {
        type leafref {
          path "../attributes/cardinalityLimitsId";
        }
      }
      container attributes {
        uses CardinalityLimits-attributes;
      }
    }
  }

  augment "/emael:ManagedElement/GNBDUFunction" {
    list ContentionControl {
      description "Additional definitions from MOM:min/max-elements:0/1; Container class for contention control definitions. Instance ContentionControl=1 is created automatically when parent MO instance is created, unless created manually in same transaction. The RDN of this MO must be ContentionControl=1. Precondition: Instance ContentionControl=1 can only be created in same transaction as parent MO instance and cannot be deleted unless parent MO instance is deleted.";
      key "contentionControlId";
      leaf contentionControlId {
        type leafref {
          path "../attributes/contentionControlId";
        }
      }
      container attributes {
        uses ContentionControl-attributes;
      }
    }
  }

  augment "/emael:ManagedElement/GNBDUFunction" {
    list DU5qiTable {
      description "Additional definitions from MOM:min/max-elements:0/36; Mapping from 5G QoS Identifier to parameters that have impact on QoS. At least one DU5qi instance must be created in same transaction when a DU5qiTable instance is created.";
      key "dU5qiTableId";
      leaf dU5qiTableId {
        type leafref {
          path "../attributes/dU5qiTableId";
        }
      }
      container attributes {
        uses DU5qiTable-attributes;
      }
    }
  }

  augment "/emael:ManagedElement/GNBDUFunction" {
    list DUQos {
      description "Additional definitions from MOM:min/max-elements:0/1; Container class for QoS attributes and classes. Instance DUQos=1 is created automatically when parent MO instance is created, unless created manually in same transaction. The RDN of this MO must be DUQos=1. Precondition: Instance DUQos=1 can only be created in same transaction as parent MO instance and cannot be deleted unless parent MO instance is deleted.";
      key "dUQosId";
      leaf dUQosId {
        type leafref {
          path "../attributes/dUQosId";
        }
      }
      container attributes {
        uses DUQos-attributes;
      }
    }
  }

  augment "/emael:ManagedElement/GNBDUFunction" {
    list DUQosModifier {
      description "Additional definitions from MOM:min/max-elements:0/1; QoS modification mapping to 5QI. The RDN of this MO must be DUQosModifier=1.";
      key "dUQosModifierId";
      leaf dUQosModifierId {
        type leafref {
          path "../attributes/dUQosModifierId";
        }
      }
      container attributes {
        uses DUQosModifier-attributes;
      }
    }
  }

  augment "/emael:ManagedElement/GNBDUFunction" {
    list EndpointResource {
      description "Additional definitions from MOM:min/max-elements:0/unbounded; Transport network endpoints for RAN interfaces. Configuration is valid for an entity that refers to an instance of this MO.";
      key "endpointResourceId";
      leaf endpointResourceId {
        type leafref {
          path "../attributes/endpointResourceId";
        }
      }
      container attributes {
        uses EndpointResource-attributes;
      }
    }
  }

  augment "/emael:ManagedElement/GNBDUFunction" {
    list EnergyEfficiency {
      description "Additional definitions from MOM:min/max-elements:0/1; Container class for Energy Efficiency and Management attributes and classes. Instance EnergyEfficiency=1 is created automatically when parent MO instance is created, unless created manually in same transaction. The RDN of this MO must be EnergyEfficiency=1. Precondition: Instance EnergyEfficiency=1 can only be created in same transaction as parent MO instance and cannot be deleted unless parent MO instance is deleted.";
      key "energyEfficiencyId";
      leaf energyEfficiencyId {
        type leafref {
          path "../attributes/energyEfficiencyId";
        }
      }
      container attributes {
        uses EnergyEfficiency-attributes;
      }
    }
  }

  augment "/emael:ManagedElement/GNBDUFunction" {
    list ExtENodeBPartnerFunction {
      description "Additional definitions from MOM:min/max-elements:0/256; List of candidate external eNodeBs that can be used as partner for PIM-A E5 tunnel.";
      key "extENodeBPartnerFunctionId";
      leaf extENodeBPartnerFunctionId {
        type leafref {
          path "../attributes/extENodeBPartnerFunctionId";
        }
      }
      container attributes {
        uses ExtENodeBPartnerFunction-attributes;
      }
    }
  }

  augment "/emael:ManagedElement/GNBDUFunction" {
    list ExtGNBDUPartnerFunction {
      description "Additional definitions from MOM:min/max-elements:0/18; Grouping point of ERAN links to a partner gNodeB distributed unit.";
      key "extGNBDUPartnerFunctionId";
      leaf extGNBDUPartnerFunctionId {
        type leafref {
          path "../attributes/extGNBDUPartnerFunctionId";
        }
      }
      container attributes {
        uses ExtGNBDUPartnerFunction-attributes;
      }
    }
  }

  augment "/emael:ManagedElement/GNBDUFunction" {
    list MassiveMimoSleep {
      description "Additional definitions from MOM:min/max-elements:0/1; Configuration and supervision support for Massive MIMO Sleep-related function. Instance MassiveMimoSleep=1 is created automatically when parent MO instance is created, unless created manually in same transaction. The RDN of this MO must be MassiveMimoSleep=1. Precondition: Instance MassiveMimoSleep=1 can only be created in same transaction as parent MO instance and cannot be deleted unless parent MO instance is deleted.";
      key "massiveMimoSleepId";
      leaf massiveMimoSleepId {
        type leafref {
          path "../attributes/massiveMimoSleepId";
        }
      }
      container attributes {
        uses MassiveMimoSleep-attributes;
      }
    }
  }

  augment "/emael:ManagedElement/GNBDUFunction" {
    list NRCellDU {
      description "Additional definitions from MOM:min/max-elements:0/unbounded; NR Cell representation in gNodeB-DU. Precondition: MO instance must be locked before deletion. Lock must be done in separate transaction. If TheftDeterrence::thdStatus is LOCKED or LOCKED_PERMANENTLY, this instance can only be created if all PLMN IDs on pLMNIdList are part of Lock Token or Operator List.";
      key "nRCellDUId";
      leaf nRCellDUId {
        type leafref {
          path "../attributes/nRCellDUId";
        }
      }
      container attributes {
        uses NRCellDU-attributes;
      }
    }
  }

  augment "/emael:ManagedElement/GNBDUFunction" {
    list NRSectorCarrier {
      description "Additional definitions from MOM:min/max-elements:0/unbounded; Power and frequency use of SectorEquipmentFunction that covers an area. Cannot be deleted once txPowerPersistentLock has been set to true. See description of txPowerPersistentLock.";
      key "nRSectorCarrierId";
      leaf nRSectorCarrierId {
        type leafref {
          path "../attributes/nRSectorCarrierId";
        }
      }
      container attributes {
        uses NRSectorCarrier-attributes;
      }
    }
  }

  augment "/emael:ManagedElement/GNBDUFunction" {
    list NRSynchronization {
      description "Additional definitions from MOM:min/max-elements:1/1;systemCreated; Top class for synchronization within NR. The RDN of this MO is NRSynchronization=1.";
      key "nRSynchronizationId";
      leaf nRSynchronizationId {
        type leafref {
          path "../attributes/nRSynchronizationId";
        }
      }
      container attributes {
        uses NRSynchronization-attributes;
      }
    }
  }

  augment "/emael:ManagedElement/GNBDUFunction" {
    list Paging {
      description "Additional definitions from MOM:min/max-elements:1/1;systemCreated; Configuration parameters for Paging in the RBS. The RDN of this MO is Paging=1.";
      key "pagingId";
      leaf pagingId {
        type leafref {
          path "../attributes/pagingId";
        }
      }
      container attributes {
        uses Paging-attributes;
      }
    }
  }

  augment "/emael:ManagedElement/GNBDUFunction" {
    list QosPriorityMapping {
      description "Additional definitions from MOM:min/max-elements:0/1; Mapping from 5G QoS priorities to parameters that have impact on QoS.";
      key "qosPriorityMappingId";
      leaf qosPriorityMappingId {
        type leafref {
          path "../attributes/qosPriorityMappingId";
        }
      }
      container attributes {
        uses QosPriorityMapping-attributes;
      }
    }
  }

  augment "/emael:ManagedElement/GNBDUFunction" {
    list RadioBearerTable {
      description "Additional definitions from MOM:min/max-elements:1/1;systemCreated; Container for radio bearer configurations. The RDN of this MO is RadioBearerTable=1.";
      key "radioBearerTableId";
      leaf radioBearerTableId {
        type leafref {
          path "../attributes/radioBearerTableId";
        }
      }
      container attributes {
        uses RadioBearerTable-attributes;
      }
    }
  }

  augment "/emael:ManagedElement/GNBDUFunction" {
    list ResourceAllocationPolicies {
      description "Additional definitions from MOM:min/max-elements:0/1; Container class for resource allocation attributes and classes. The RDN of this MO must be ResourceAllocationPolicies=1.";
      key "resourceAllocationPoliciesId";
      leaf resourceAllocationPoliciesId {
        type leafref {
          path "../attributes/resourceAllocationPoliciesId";
        }
      }
      container attributes {
        uses ResourceAllocationPolicies-attributes;
      }
    }
  }

  augment "/emael:ManagedElement/GNBDUFunction" {
    list ResourcePartitions {
      description "Additional definitions from MOM:min/max-elements:0/1; Set of resource partitions.";
      key "resourcePartitionsId";
      leaf resourcePartitionsId {
        type leafref {
          path "../attributes/resourcePartitionsId";
        }
      }
      container attributes {
        uses ResourcePartitions-attributes;
      }
    }
  }

  augment "/emael:ManagedElement/GNBDUFunction" {
    list RimRSGlobal {
      description "Additional definitions from MOM:min/max-elements:0/unbounded; Remote Interference Management Reference Signal (RIM RS) resource allocated for whole network. Resource for RIM RS transmission is defined by sequence domain resource, time domain resource, and frequency resource. Configured parameters of RIM RS resource are applied to all sets of RIM RS resources across cells in gNodeBs. Instance RimRSGlobal=1 is created automatically when parent MO instance is created, unless created manually in same transaction. Precondition: Instance RimRSGlobal=1 can only be created in same transaction as parent MO instance and cannot be deleted unless parent MO instance is deleted.";
      key "rimRSGlobalId";
      leaf rimRSGlobalId {
        type leafref {
          path "../attributes/rimRSGlobalId";
        }
      }
      container attributes {
        uses RimRSGlobal-attributes;
      }
    }
  }

  augment "/emael:ManagedElement/GNBDUFunction" {
    list Rrc {
      description "Additional definitions from MOM:min/max-elements:1/1;systemCreated; Manageable RRC protocol characteristics. The RDN of this MO is Rrc=1.";
      key "rrcId";
      leaf rrcId {
        type leafref {
          path "../attributes/rrcId";
        }
      }
      container attributes {
        uses Rrc-attributes;
      }
    }
  }

  augment "/emael:ManagedElement/GNBDUFunction" {
    list SrPeriodicityPoolSet {
      description "Additional definitions from MOM:min/max-elements:0/8; Configuration of Scheduling Request periodicity pools 1-5 at NR cell representation in gNodeB-DU.";
      key "srPeriodicityPoolSetId";
      leaf srPeriodicityPoolSetId {
        type leafref {
          path "../attributes/srPeriodicityPoolSetId";
        }
      }
      container attributes {
        uses SrPeriodicityPoolSet-attributes;
      }
    }
  }

  augment "/emael:ManagedElement/GNBDUFunction" {
    list SssgSwitch {
      description "Additional definitions from MOM:min/max-elements:0/unbounded; Profile for Search Space Set Group (SSSG) switch. At least one SssgSwitchPwrOpt instance must be created in same transaction when a SssgSwitch instance is created. At least one SssgSwitchUeCfg instance must be created in same transaction when a SssgSwitch instance is created.";
      key "sssgSwitchId";
      leaf sssgSwitchId {
        type leafref {
          path "../attributes/sssgSwitchId";
        }
      }
      container attributes {
        uses SssgSwitch-attributes;
      }
    }
  }

  augment "/emael:ManagedElement/GNBDUFunction" {
    list TermPointToGNBCUCP {
      description "Additional definitions from MOM:min/max-elements:0/1; Models an F1-C link to a gNodeB-CU-CP.";
      key "termPointToGNBCUCPId";
      leaf termPointToGNBCUCPId {
        type leafref {
          path "../attributes/termPointToGNBCUCPId";
        }
      }
      container attributes {
        uses TermPointToGNBCUCP-attributes;
      }
    }
  }

  augment "/emael:ManagedElement/GNBDUFunction" {
    list TrafficDefinitions {
      description "Additional definitions from MOM:min/max-elements:0/1; Container class for traffic definitions. Instance TrafficDefinitions=1 is created automatically when parent MO instance is created, unless created manually in same transaction. The RDN of this MO must be TrafficDefinitions=1. Precondition: Instance TrafficDefinitions=1 can only be created in same transaction as parent MO instance and cannot be deleted unless parent MO instance is deleted.";
      key "trafficDefinitionsId";
      leaf trafficDefinitionsId {
        type leafref {
          path "../attributes/trafficDefinitionsId";
        }
      }
      container attributes {
        uses TrafficDefinitions-attributes;
      }
    }
  }

  augment "/emael:ManagedElement/GNBDUFunction" {
    list TrafficGroups {
      description "Additional definitions from MOM:min/max-elements:0/1; Container class for traffic groups definitions. Instance TrafficGroups=1 is created automatically when parent MO instance is created, unless created manually in same transaction. The RDN of this MO must be TrafficGroups=1. Precondition: Instance TrafficGroups=1 can only be created in same transaction as parent MO instance and cannot be deleted unless parent MO instance is deleted.";
      key "trafficGroupsId";
      status deprecated;
      leaf trafficGroupsId {
        type leafref {
          path "../attributes/trafficGroupsId";
        }
        status deprecated;
      }
      container attributes {
        uses TrafficGroups-attributes;
      }
    }
  }

  augment "/emael:ManagedElement/GNBDUFunction" {
    list UeCA {
      description "Additional definitions from MOM:min/max-elements:0/1; Container class for UE Carrier Aggregation profile classes. Instance UeCA=1 is created automatically when parent MO instance is created, unless created manually in same transaction. The RDN of this MO must be UeCA=1. Precondition: Instance UeCA=1 can only be created in same transaction as parent MO instance and cannot be deleted unless parent MO instance is deleted.";
      key "ueCAId";
      leaf ueCAId {
        type leafref {
          path "../attributes/ueCAId";
        }
      }
      container attributes {
        uses UeCA-attributes;
      }
    }
  }

  augment "/emael:ManagedElement/GNBDUFunction" {
    list UeCC {
      description "Additional definitions from MOM:min/max-elements:0/1; Container class for UE connection control attributes and profile classes. Instance UeCC=1 is created automatically when parent MO instance is created, unless created manually in same transaction. The RDN of this MO must be UeCC=1. Precondition: Instance UeCC=1 can only be created in same transaction as parent MO instance and cannot be deleted unless parent MO instance is deleted.";
      key "ueCCId";
      leaf ueCCId {
        type leafref {
          path "../attributes/ueCCId";
        }
      }
      container attributes {
        uses UeCC-attributes;
      }
    }
  }

  augment "/emael:ManagedElement/GNBDUFunction/UeCC/Harq" {
    list HarqUeCfg {
      description "Additional definitions from MOM:min/max-elements:0/8; HARQ profile used for current UE. Instance HarqUeCfg=Base is created automatically when parent MO instance is created, unless created manually in same transaction. UeBbProfileUeCfg::harqUeCfgRef is automatically set to HarqUeCfg=Base instance, unless manually set to refer to another MO instance. Precondition: Instance HarqUeCfg=Base can only be created in same transaction as parent MO instance and cannot be deleted unless parent MO instance is deleted. Other instances can be created and deleted at any time. Maximum 7 HarqUeCfg instances, with RDN different from Base, can be created under parent MO instance.";
      key "harqUeCfgId";
      leaf harqUeCfgId {
        type leafref {
          path "../attributes/harqUeCfgId";
        }
      }
      container attributes {
        uses HarqUeCfg-attributes;
      }
    }
  }

  augment "/emael:ManagedElement/GNBDUFunction/UeCC/LinkAdaptation" {
    list LinkAdaptationUeCfg {
      description "Additional definitions from MOM:min/max-elements:0/8; Link adaptation profile used for current UE. Instance LinkAdaptationUeCfg=Base is created automatically when parent MO instance is created, unless created manually in same transaction. UeBbProfileUeCfg::linkAdaptationUeCfgRef is automatically set to LinkAdaptationUeCfg=Base instance, unless manually set to refer to another MO instance. Precondition: Instance LinkAdaptationUeCfg=Base can only be created in same transaction as parent MO instance and cannot be deleted unless parent MO instance is deleted. Other instances can be created and deleted at any time. Maximum 7 LinkAdaptationUeCfg instances, with RDN different from Base, can be created under parent MO instance.";
      key "linkAdaptationUeCfgId";
      leaf linkAdaptationUeCfgId {
        type leafref {
          path "../attributes/linkAdaptationUeCfgId";
        }
      }
      container attributes {
        uses LinkAdaptationUeCfg-attributes;
      }
    }
  }

  augment "/emael:ManagedElement/GNBDUFunction/UeCC/LinkAdaptation/LinkAdaptationUeCfg" {
    list DlLinkAdaptation {
      description "Additional definitions from MOM:min/max-elements:0/1; DL link adaptation profile used for current UE. Instance DlLinkAdaptation=1 is created automatically when parent MO instance is created, unless created manually in same transaction. DlLinkAdaptation values only apply if linkAdaptationUeMode=CUSTOM in parent MO instance. The RDN of this MO must be DlLinkAdaptation=1. Precondition: Instance DlLinkAdaptation=1 can only be created in same transaction as parent MO instance and cannot be deleted unless parent MO instance is deleted.";
      key "dlLinkAdaptationId";
      leaf dlLinkAdaptationId {
        type leafref {
          path "../attributes/dlLinkAdaptationId";
        }
      }
      container attributes {
        uses DlLinkAdaptation-attributes;
      }
    }
  }

  augment "/emael:ManagedElement/GNBDUFunction/UeCC/LinkAdaptation/LinkAdaptationUeCfg" {
    list PdcchLinkAdaptation {
      description "Additional definitions from MOM:min/max-elements:0/1; PDCCH link adaptation profile used for current UE. Instance PdcchLinkAdaptation=1 is created automatically when parent MO instance is created, unless created manually in same transaction. PdcchLinkAdaptation values only apply if linkAdaptationUeMode=CUSTOM in parent MO instance. The RDN of this MO must be PdcchLinkAdaptation=1. Precondition: Instance PdcchLinkAdaptation=1 can only be created in same transaction as parent MO instance and cannot be deleted unless parent MO instance is deleted.";
      key "pdcchLinkAdaptationId";
      leaf pdcchLinkAdaptationId {
        type leafref {
          path "../attributes/pdcchLinkAdaptationId";
        }
      }
      container attributes {
        uses PdcchLinkAdaptation-attributes;
      }
    }
  }

  augment "/emael:ManagedElement/GNBDUFunction/UeCC/LinkAdaptation/LinkAdaptationUeCfg" {
    list UlLinkAdaptation {
      description "Additional definitions from MOM:min/max-elements:0/1; UL link adaptation profile used for current UE. Instance UlLinkAdaptation=1 is created automatically when parent MO instance is created, unless created manually in same transaction. UlLinkAdaptation values only apply if linkAdaptationUeMode=CUSTOM in parent MO instance. The RDN of this MO must be UlLinkAdaptation=1. Precondition: Instance UlLinkAdaptation=1 can only be created in same transaction as parent MO instance and cannot be deleted unless parent MO instance is deleted.";
      key "ulLinkAdaptationId";
      leaf ulLinkAdaptationId {
        type leafref {
          path "../attributes/ulLinkAdaptationId";
        }
      }
      container attributes {
        uses UlLinkAdaptation-attributes;
      }
    }
  }

  augment "/emael:ManagedElement/GNBDUFunction/UeCC/LogicalChannel" {
    list LogicalChannelUeCfg {
      description "Additional definitions from MOM:min/max-elements:0/4; Logical channel configuration for current DRB. Instance LogicalChannelUeCfg=Base is created automatically when parent MO instance is created, unless created manually in same transaction. Attributes prefUeGroupList, ueGroupList and ueConfGroupList must be empty in instance LogicalChannelUeCfg=Base but cannot all be empty in any other instance of LogicalChannelUeCfg under same parent LogicalChannel instance. A combination of an element of ueGroupList and an element of prefUeGroupList in LogicalChannelUeCfg instance must be unique under LogicalChannel instance. Precondition: Instance LogicalChannelUeCfg=Base can only be created in same transaction as parent MO instance and cannot be deleted unless parent MO instance is deleted. Other instances can be created and deleted at any time. Maximum 3 LogicalChannelUeCfg instances, with RDN different from Base, can be created under parent MO instance.";
      key "logicalChannelUeCfgId";
      leaf logicalChannelUeCfgId {
        type leafref {
          path "../attributes/logicalChannelUeCfgId";
        }
      }
      container attributes {
        uses LogicalChannelUeCfg-attributes;
      }
    }
  }

  augment "/emael:ManagedElement/GNBDUFunction/MassiveMimoSleep/MMimoSleepTimeGroup" {
    list MMimoSleepTimeWindow {
      description "Additional definitions from MOM:min/max-elements:0/96; Periods of time when a given event occurs.";
      key "mMimoSleepTimeWindowId";
      leaf mMimoSleepTimeWindowId {
        type leafref {
          path "../attributes/mMimoSleepTimeWindowId";
        }
      }
      container attributes {
        uses MMimoSleepTimeWindow-attributes;
      }
    }
  }

  augment "/emael:ManagedElement/GNBDUFunction/MassiveMimoSleep" {
    list MMimoSleepProfile {
      description "Additional definitions from MOM:min/max-elements:0/50; Massive MIMO Sleep profile for the specified period of time.";
      key "mMimoSleepProfileId";
      leaf mMimoSleepProfileId {
        type leafref {
          path "../attributes/mMimoSleepProfileId";
        }
      }
      container attributes {
        uses MMimoSleepProfile-attributes;
      }
    }
  }

  augment "/emael:ManagedElement/GNBDUFunction/MassiveMimoSleep" {
    list MMimoSleepTimeGroup {
      description "Additional definitions from MOM:min/max-elements:0/96; Container class for Massive MIMO Sleep time windows. Each MMimoSleepTimeWindow instance, with dayOfWeek, startTime and stopTime, defines a time window. Time windows under same MMimoSleepTimeGroup instance cannot overlap. Time windows overlap if: Value of dayOfWeek is the same (including dayOfWeek value ALL) and 1) startTime of given time window is greater than or equal to startTime of other time window, and lesser than or equal to stopTime of that other time window, or 2) stopTime of given time window is greater than or equal to startTime of other time window, and lesser than or equal to stopTime of that other time window.";
      key "mMimoSleepTimeGroupId";
      leaf mMimoSleepTimeGroupId {
        type leafref {
          path "../attributes/mMimoSleepTimeGroupId";
        }
      }
      container attributes {
        uses MMimoSleepTimeGroup-attributes;
      }
    }
  }

  augment "/emael:ManagedElement/GNBDUFunction/NRCellDU" {
    list AdditionalPLMNInfo {
      description "Additional definitions from MOM:min/max-elements:0/11; PLMN-related information that can be additionally served by NR cell. Precondition: If TheftDeterrence::thdStatus is LOCKED or LOCKED_PERMANENTLY, this instance can only be created if all PLMN IDs on pLMNIdList are part of Lock Token or Operator List.";
      key "additionalPLMNInfoId";
      leaf additionalPLMNInfoId {
        type leafref {
          path "../attributes/additionalPLMNInfoId";
        }
      }
      container attributes {
        uses AdditionalPLMNInfo-attributes;
      }
    }
  }

  augment "/emael:ManagedElement/GNBDUFunction/NRCellDU" {
    list CellPortionRd {
      description "Additional definitions from MOM:min/max-elements:0/192;systemCreated; Represents a Radio Dot and coverage area of a Radio Dot in a cell. Created when cell is unlocked and precondition is true. Deleted at next cell unlock if precondition no longer is true. Only applicable to Mid-Band cells. The RDNs of these MOs are CellPortionRd=1 to CellPortionRd=192. Length of RDN value is up to 3 characters. Instance can be created without a preceding user-initiated transaction. Precondition: License for Advanced RDS Location Support for Private 5G is present and feature is active. NRCellDU::rdsUeAdvancedPosEnabled is true.";
      key "cellPortionRdId";
      leaf cellPortionRdId {
        type leafref {
          path "../attributes/cellPortionRdId";
        }
      }
      container attributes {
        uses CellPortionRd-attributes;
      }
    }
  }

  augment "/emael:ManagedElement/GNBDUFunction/NRCellDU" {
    list DlOuterLoop {
      description "Additional definitions from MOM:min/max-elements:1/1;systemCreated; Configuration of downlink outer loops. Only applicable to Low-Band cells. The RDN of this MO is DlOuterLoop=1.";
      key "dlOuterLoopId";
      leaf dlOuterLoopId {
        type leafref {
          path "../attributes/dlOuterLoopId";
        }
      }
      container attributes {
        uses DlOuterLoop-attributes;
      }
    }
  }

  augment "/emael:ManagedElement/GNBDUFunction/NRSectorCarrier" {
    list AesMMimoSleep {
      description "Additional definitions from MOM:min/max-elements:0/1;systemCreated; Threshold information for NR Massive MIMO Sleep Mode feature updated by Automated Energy Saver. Created when all following conditions are fulfilled: - Aes::aesEnabled is true. - NRSectorCarrier::massiveMimoSleepEnabled is ENABLED or DETECTION. - License for Automated Energy Saver is present and feature is active. Deleted when Aes::aesEnabled is false or NRSectorCarrier::massiveMimoSleepEnabled is DISABLED. Only applicable to Mid-Band sector carriers. The RDN of this MO is AesMMimoSleep is 1. Length of RDN value is 1 character. Instance can be created without a preceding user-initiated transaction.";
      key "aesMMimoSleepId";
      leaf aesMMimoSleepId {
        type leafref {
          path "../attributes/aesMMimoSleepId";
        }
      }
      container attributes {
        uses AesMMimoSleep-attributes;
      }
    }
  }

  augment "/emael:ManagedElement/GNBDUFunction/NRSectorCarrier" {
    list CommonBeamforming {
      description "Additional definitions from MOM:min/max-elements:0/1; Configuration parameters related to common beamforming. Created automatically when administrativeState under parent MO instance is changed to UNLOCKED. Can also be created and deleted manually. When created automatically, the RDN of this MO is CommonBeamforming=1. Length of RDN value is 1 character for automatically created instance. Instance can be created without a preceding user-initiated transaction. Precondition: Can only be deleted when parent NRSectorCarrier::administrativeState is LOCKED.";
      key "commonBeamformingId";
      leaf commonBeamformingId {
        type leafref {
          path "../attributes/commonBeamformingId";
        }
      }
      container attributes {
        uses CommonBeamforming-attributes;
      }
    }
  }

  augment "/emael:ManagedElement/GNBDUFunction/NRSectorCarrier" {
    list NRPimCancellationConfig {
      description "Additional definitions from MOM:min/max-elements:0/72; Configuration data for PIM cancellation of NRSectorCarrier attribute. Only one NRPimCancellationConfig instance can refer to same PimCancellationFunction instance. Among NRPimCancellationConfig instances that have same createdBy value, only one NRPimCancellationConfig instance can have ulPimCancellationMode value that is not EXCLUDED. When createdBy is SYSTEM, operator is not allowed to modify attributes. Only takes effect for CPRI-based radio equipment that does not support AAS functions. Not applicable to High-Band sector carriers. High-Band only supports AAS functions. Automatic configuration is active when GNBDUFunction::pimCancAutoConfigEnabled is true. Then instance is - created automatically when PIM victim is identified. - deleted automatically when PIM victim is no longer valid. Automatically created instances are deleted when GNBDUFunction::pimCancAutoConfigEnabled is false. Can also be created and deleted manually. When created automatically, the RDNs of these MOs are NRPimCancellationConfig=auto1, auto2 and so on. RDN value matches RDN value of PimCancellationFunction instance that this NRPimCancellationConfig instance refers to. Length of RDN value is up to 6 characters for automatically created instance. Instance can be created without a preceding user-initiated transaction. When created manually, RDN value must not start with 'auto'.";
      key "nRPimCancellationConfigId";
      leaf nRPimCancellationConfigId {
        type leafref {
          path "../attributes/nRPimCancellationConfigId";
        }
      }
      container attributes {
        uses NRPimCancellationConfig-attributes;
      }
    }
  }

  augment "/emael:ManagedElement/GNBDUFunction/NRSectorCarrier" {
    list PowerBackoff {
      description "Additional definitions from MOM:min/max-elements:0/1; Configuration parameters for EMF Power Lock Mid-Band feature. The feature intends to reduce radio safety distance in massive MIMO products. Power backoff is sector carrier-wide, same in all directions. Only applicable to Mid-Band sector carriers. Precondition: Parent MO must be locked when this MO is created or deleted. Cannot be created if PowerBackoffDir instance exists.";
      key "powerBackoffId";
      leaf powerBackoffId {
        type leafref {
          path "../attributes/powerBackoffId";
        }
      }
      container attributes {
        uses PowerBackoff-attributes;
      }
    }
  }

  augment "/emael:ManagedElement/GNBDUFunction/NRSectorCarrier" {
    list PowerBackoffDir {
      description "Additional definitions from MOM:min/max-elements:0/1; Configuration parameters related to NR Directional Control for EMF Power Lock Mid-Band feature. Only applicable to Mid-Band sector carriers. Creating this MO on NRSectorCarrier instance with non-C2 sector carrier type or Remote radio units will result in an alarm. Precondition: Parent MO must be locked when this MO is created or deleted. Cannot be created if PowerBackoff MO exists or radio is not TDD.";
      key "powerBackoffDirId";
      leaf powerBackoffDirId {
        type leafref {
          path "../attributes/powerBackoffDirId";
        }
      }
      container attributes {
        uses PowerBackoffDir-attributes;
      }
    }
  }

  augment "/emael:ManagedElement/GNBDUFunction/NRSectorCarrier" {
    list UlBranchInterference {
      description "Additional definitions from MOM:min/max-elements:0/1;systemCreated; Contains RF branch information used for Uplink Noise and Interference on Antenna Branch feature. Created when configured NRSectorCarrier::ipnMeasurementBranchRef is valid and sector carrier is active. Deleted when measurement is stopped for this antenna branch. The RDN of this MO is UlBranchInterference=RfBranch_<antennaUnitGroupId>_<rfBranchId>, where antennaUnitGroupId is RDN value of AntennaUnitGroup instance, and rfBranchId is RDN value of RfBranch instance. They are extracted from LDN of measured antenna branch. Length of RDN value is up to 79 characters. Truncated if exceeding maximum length. Instance can be created without a preceding user-initiated transaction.";
      key "ulBranchInterferenceId";
      leaf ulBranchInterferenceId {
        type leafref {
          path "../attributes/ulBranchInterferenceId";
        }
      }
      container attributes {
        uses UlBranchInterference-attributes;
      }
    }
  }

  augment "/emael:ManagedElement/GNBDUFunction/UeCC/OutOfCov" {
    list OutOfCovUeCfg {
      description "Additional definitions from MOM:min/max-elements:0/3; Out of coverage (OOC) profile used for current UE. Instance OutOfCovUeCfg=Base is created automatically when parent MO instance is created, unless created manually in same transaction as parent MO. UeBbProfileUeCfg::outOfCovUeCfgRef is automatically set to OutOfCovUeCfg=Base instance, unless manually set to refer to another MO instance. Precondition: Instance OutOfCovUeCfg=Base can only be created in same transaction as parent MO instance and cannot be deleted unless parent MO instance is deleted. Other instances can be created and deleted at any time. Maximum 2 OutOfCovUeCfg instances, with RDN different from Base, can be created under parent MO instance.";
      key "outOfCovUeCfgId";
      leaf outOfCovUeCfgId {
        type leafref {
          path "../attributes/outOfCovUeCfgId";
        }
      }
      container attributes {
        uses OutOfCovUeCfg-attributes;
      }
    }
  }

  augment "/emael:ManagedElement/GNBDUFunction/UeCC/PdcchReuseForPdsch" {
    list PdcchReuseForPdschUeCfg {
      description "Additional definitions from MOM:min/max-elements:0/8; Configuration of PDCCH and PDSCH Frequency Division Multiplexing profile for UE groups. Instance PdcchReuseForPdschUeCfg=Base is created automatically when parent MO instance is created, unless created manually in same transaction. Attributes prefUeGroupList, ueGroupList and ueConfGroupList must be empty in instance PdcchReuseForPdschUeCfg=Base but cannot all be empty in any other instance of PdcchReuseForPdschUeCfg under same parent PdcchReuseForPdsch instance. A combination of an element of ueGroupList and an element of prefUeGroupList in PdcchReuseForPdschUeCfg instance must be unique under PdcchReuseForPdsch instance. Precondition: Instance PdcchReuseForPdschUeCfg=Base can only be created in same transaction as parent MO instance and cannot be deleted unless parent MO instance is deleted. Other instances can be created and deleted at any time. Maximum 7 PdcchReuseForPdschUeCfg instances, with RDN different from Base, can be created under parent MO instance.";
      key "pdcchReuseForPdschUeCfgId";
      leaf pdcchReuseForPdschUeCfgId {
        type leafref {
          path "../attributes/pdcchReuseForPdschUeCfgId";
        }
      }
      container attributes {
        uses PdcchReuseForPdschUeCfg-attributes;
      }
    }
  }

  augment "/emael:ManagedElement/GNBDUFunction/UeCC/PowerControl" {
    list PowerControlUeCfg {
      description "Additional definitions from MOM:min/max-elements:0/8; Power control profile used for current UE. Instance PowerControlUeCfg=Base is created automatically when parent MO instance is created, unless created manually in same transaction. UeBbProfileUeCfg::powerControlUeCfgRef is automatically set to PowerControlUeCfg=Base instance, unless manually set to refer to another MO instance. Precondition: Instance PowerControlUeCfg=Base can only be created in same transaction as parent MO instance and cannot be deleted unless parent MO instance is deleted. Other instances can be created and deleted at any time. Maximum 7 PowerControlUeCfg instances, with RDN different from Base, can be created under parent MO instance.";
      key "powerControlUeCfgId";
      leaf powerControlUeCfgId {
        type leafref {
          path "../attributes/powerControlUeCfgId";
        }
      }
      container attributes {
        uses PowerControlUeCfg-attributes;
      }
    }
  }

  augment "/emael:ManagedElement/GNBDUFunction/UeCC/Prescheduling" {
    list PreschedulingUeCfg {
      description "Additional definitions from MOM:min/max-elements:0/8; Configuration of prescheduling mode for UE groups. Instance PreschedulingUeCfg=Base is created automatically when parent MO instance is created, unless created manually in same transaction. UeBbProfileUeCfg::preschedulingUeCfgRef is automatically set to PreschedulingUeCfg=Base instance, unless manually set to refer to another MO instance. Precondition: Instance PreschedulingUeCfg=Base can only be created in same transaction as parent MO instance and cannot be deleted unless parent MO instance is deleted. Other instances can be created and deleted at any time. Maximum 7 PreschedulingUeCfg instances, with RDN different from Base, can be created under parent MO instance.";
      key "preschedulingUeCfgId";
      leaf preschedulingUeCfgId {
        type leafref {
          path "../attributes/preschedulingUeCfgId";
        }
      }
      container attributes {
        uses PreschedulingUeCfg-attributes;
      }
    }
  }

  augment "/emael:ManagedElement/GNBDUFunction/UeCC/PuschRep" {
    list PuschRepUeCfg {
      description "Additional definitions from MOM:min/max-elements:0/4; Configuration of PUSCH repetition profile for UE groups. Instance PuschRepUeCfg=Base is created automatically when parent MO instance is created, unless created manually in same transaction. Attributes prefUeGroupList, ueGroupList and ueConfGroupList must be empty in instance PuschRepUeCfg=Base but cannot all be empty in any other instance of PuschRepUeCfg under same parent PuschRep instance. Precondition: Instance PuschRepUeCfg=Base can only be created in same transaction as parent MO instance and cannot be deleted unless parent MO instance is deleted. Other instances can be created and deleted at any time. Maximum 3 PuschRepUeCfg instances, with RDN different from Base, can be created under parent MO instance.";
      key "puschRepUeCfgId";
      leaf puschRepUeCfgId {
        type leafref {
          path "../attributes/puschRepUeCfgId";
        }
      }
      container attributes {
        uses PuschRepUeCfg-attributes;
      }
    }
  }

  augment "/emael:ManagedElement/GNBDUFunction/QosPriorityMapping" {
    list PriorityDomainMapping {
      description "Additional definitions from MOM:min/max-elements:0/64; Mapping from 5G QoS priority level to internal parameters that have absolute priority realization.";
      key "priorityDomainMappingId";
      leaf priorityDomainMappingId {
        type leafref {
          path "../attributes/priorityDomainMappingId";
        }
      }
      container attributes {
        uses PriorityDomainMapping-attributes;
      }
    }
  }

  augment "/emael:ManagedElement/GNBDUFunction/DUQos/QosPriorityShift" {
    list CellPriorityShift {
      description "Additional definitions from MOM:min/max-elements:0/8; Cell-level parameters for delay-based priority shift. If NRCellDU::cellPriorityShiftRef is non-empty, attributes from referenced MO instance are used. If NRCellDU::cellPriorityShiftRef is empty, attribute default values according to CellPriorityShift MO class definition are used.";
      key "cellPriorityShiftId";
      leaf cellPriorityShiftId {
        type leafref {
          path "../attributes/cellPriorityShiftId";
        }
      }
      container attributes {
        uses CellPriorityShift-attributes;
      }
    }
  }

  augment "/emael:ManagedElement/GNBDUFunction/UeCC/Rach" {
    list RachUeCfg {
      description "Additional definitions from MOM:min/max-elements:0/4; Rach configuration profile for UE groups. Instance RachUeCfg=Base is created automatically when parent MO instance is created, unless created manually in same transaction. Attributes prefUeGroupList, ueGroupList and ueConfGroupList must be empty in instance RachUeCfg=Base but cannot all be empty in any other instance of RachUeCfg under same parent Rach instance. Precondition: Instance RachUeCfg=Base can only be created in same transaction as parent MO instance and cannot be deleted unless parent MO instance is deleted. Other instances can be created and deleted at any time. Maximum 3 RachUeCfg instances, with RDN different from Base, can be created under parent MO instance.";
      key "rachUeCfgId";
      leaf rachUeCfgId {
        type leafref {
          path "../attributes/rachUeCfgId";
        }
      }
      container attributes {
        uses RachUeCfg-attributes;
      }
    }
  }

  augment "/emael:ManagedElement/GNBDUFunction/RadioBearerTable" {
    list DataRadioBearer {
      description "Additional definitions from MOM:min/max-elements:1/1;systemCreated; Data radio bearer configuration. The RDN of this MO is DataRadioBearer=1.";
      key "dataRadioBearerId";
      leaf dataRadioBearerId {
        type leafref {
          path "../attributes/dataRadioBearerId";
        }
      }
      container attributes {
        uses DataRadioBearer-attributes;
      }
    }
  }

  augment "/emael:ManagedElement/GNBDUFunction/RadioBearerTable" {
    list SignalingRadioBearer {
      description "Additional definitions from MOM:min/max-elements:1/1;systemCreated; Parameters related to Signaling Radio Bearer. The RDN of this MO is SignalingRadioBearer=1.";
      key "signalingRadioBearerId";
      leaf signalingRadioBearerId {
        type leafref {
          path "../attributes/signalingRadioBearerId";
        }
      }
      container attributes {
        uses SignalingRadioBearer-attributes;
      }
    }
  }

  augment "/emael:ManagedElement/GNBDUFunction/UeCC/RadioLinkControl" {
    list DrbRlc {
      description "Additional definitions from MOM:min/max-elements:0/12; Data radio bearer radio link control profile used for current UE. Instance DrbRlc=Default is created automatically when parent MO instance is created, unless created manually in same transaction. DU5qi::drbRlcRef is automatically set to DrbRlc=Default instance, unless manually set to refer to another MO instance. Precondition: Instance DrbRlc=Default can only be created in same transaction as parent MO instance and cannot be deleted unless parent MO instance is deleted. Other instances can be created and deleted at any time. Maximum 11 DrbRlc instances, with RDN different from Default, can be created under same parent MO instance.";
      key "drbRlcId";
      leaf drbRlcId {
        type leafref {
          path "../attributes/drbRlcId";
        }
      }
      container attributes {
        uses DrbRlc-attributes;
      }
    }
  }

  augment "/emael:ManagedElement/GNBDUFunction/UeCC/RadioLinkControl" {
    list UeAdaptiveRlc {
      description "Additional definitions from MOM:min/max-elements:0/1; Adaptive radio link control poll retransmission profile for current UE. Instance UeAdaptiveRlc=1 is created automatically when parent MO instance is created, unless created manually in same transaction. The RDN of this MO must be UeAdaptiveRlc=1. Precondition: Instance UeAdaptiveRlc=Default can only be created in same transaction as parent MO instance and cannot be deleted unless parent MO instance is deleted.";
      key "ueAdaptiveRlcId";
      leaf ueAdaptiveRlcId {
        type leafref {
          path "../attributes/ueAdaptiveRlcId";
        }
      }
      container attributes {
        uses UeAdaptiveRlc-attributes;
      }
    }
  }

  augment "/emael:ManagedElement/GNBDUFunction/UeCC/ResourceAllocTypeDl" {
    list ResourceAllocTypeDlUeCfg {
      description "Additional definitions from MOM:min/max-elements:0/3; Configuration of downlink resource allocation profile for UE groups. Instance ResourceAllocTypeDlUeCfg=Base is created automatically when parent MO instance is created, unless created manually in same transaction. Attributes prefUeGroupList, ueGroupList and ueConfGroupList must be empty in instance ResourceAllocTypeDlUeCfg=Base but cannot all be empty in other instance of ResourceAllocTypeDlUeCfg under same parent ResourceAllocTypeDl instance. Precondition: Instance ResourceAllocTypeDlUeCfg=Base can only be created in same transaction as parent MO instance and cannot be deleted unless parent MO instance is deleted. Other instances can be created and deleted at any time. Maximum 2 ResourceAllocTypeDlUeCfg instances, with RDN different from Base, can be created under parent MO instance.";
      key "resourceAllocTypeDlUeCfgId";
      leaf resourceAllocTypeDlUeCfgId {
        type leafref {
          path "../attributes/resourceAllocTypeDlUeCfgId";
        }
      }
      container attributes {
        uses ResourceAllocTypeDlUeCfg-attributes;
      }
    }
  }

  augment "/emael:ManagedElement/GNBDUFunction/ResourceAllocationPolicies" {
    list CellResourceMapping {
      description "Additional definitions from MOM:min/max-elements:0/8; Cell mappings of resource quotas to resource partitions. Not applicable to High-Band cells.";
      key "cellResourceMappingId";
      leaf cellResourceMappingId {
        type leafref {
          path "../attributes/cellResourceMappingId";
        }
      }
      container attributes {
        uses CellResourceMapping-attributes;
      }
    }
  }

  augment "/emael:ManagedElement/GNBDUFunction/ResourceAllocationPolicies" {
    list ResourceAllocationPolicy {
      description "Additional definitions from MOM:min/max-elements:0/32; Resource usage quotas for partitioned resources.";
      key "resourceAllocationPolicyId";
      leaf resourceAllocationPolicyId {
        type leafref {
          path "../attributes/resourceAllocationPolicyId";
        }
      }
      container attributes {
        uses ResourceAllocationPolicy-attributes;
      }
    }
  }

  augment "/emael:ManagedElement/GNBDUFunction/ResourceAllocationPolicies" {
    list ResourceShareLimit {
      description "Additional definitions from MOM:min/max-elements:0/16; Resource share limit for Automated RRP. If ResourceAllocationPolicy::resourceShareLimitRef or ServicePolicy::resourceShareLimitRef is non-empty, attributes from referenced MO instance are used. If ResourceAllocationPolicy::resourceShareLimitRef or ServicePolicy::resourceShareLimitRef is empty, none of following features is operable for partition: - Load-based Automated Radio Resource Partitioning. - Automated Radio Resource Partitioning.";
      key "resourceShareLimitId";
      leaf resourceShareLimitId {
        type leafref {
          path "../attributes/resourceShareLimitId";
        }
      }
      container attributes {
        uses ResourceShareLimit-attributes;
      }
    }
  }

  augment "/emael:ManagedElement/GNBDUFunction/ResourceAllocationPolicies/ResourceAllocationPolicy" {
    list ServicePolicy {
      description "Additional definitions from MOM:min/max-elements:0/2; Resource usage quotas of resources for services within a resource partition. Services defined with 5QI values.";
      key "servicePolicyId";
      leaf servicePolicyId {
        type leafref {
          path "../attributes/servicePolicyId";
        }
      }
      container attributes {
        uses ServicePolicy-attributes;
      }
    }
  }

  augment "/emael:ManagedElement/GNBDUFunction/ResourcePartitions/ResourcePartition" {
    list ResourcePartitionMember {
      description "Additional definitions from MOM:min/max-elements:0/36; Set of member information of resource partition.";
      key "resourcePartitionMemberId";
      leaf resourcePartitionMemberId {
        type leafref {
          path "../attributes/resourcePartitionMemberId";
        }
      }
      container attributes {
        uses ResourcePartitionMember-attributes;
      }
    }
  }

  augment "/emael:ManagedElement/GNBDUFunction/ResourcePartitions" {
    list ResourcePartition {
      description "Additional definitions from MOM:min/max-elements:0/36; Combination of attributes specifying in which resource partition a UE is included.";
      key "resourcePartitionId";
      leaf resourcePartitionId {
        type leafref {
          path "../attributes/resourcePartitionId";
        }
      }
      container attributes {
        uses ResourcePartition-attributes;
      }
    }
  }

  augment "/emael:ManagedElement/GNBDUFunction/UeCC/RimOffload" {
    list RimOffloadUeCfg {
      description "Additional definitions from MOM:min/max-elements:0/8; Remote interference triggered offload configurations. Instance RimOffloadUeCfg=Base is created automatically when parent MO instance is created, unless created manually in same transaction. UeBbProfileUeCfg::rimOffloadUeCfgRef is automatically set to RimOffloadUeCfg=Base instance, unless manually set to refer to another MO instance. Precondition: Instance RimOffloadUeCfg=Base can only be created in same transaction as parent MO instance and cannot be deleted unless parent MO instance is deleted. Other instances can be created and deleted at any time. Maximum 7 RimOffloadUeCfg instances, with RDN different from Base, can be created under parent MO instance.";
      key "rimOffloadUeCfgId";
      leaf rimOffloadUeCfgId {
        type leafref {
          path "../attributes/rimOffloadUeCfgId";
        }
      }
      container attributes {
        uses RimOffloadUeCfg-attributes;
      }
    }
  }

  augment "/emael:ManagedElement/GNBDUFunction/RimRSGlobal" {
    list RimRSSet {
      description "Additional definitions from MOM:min/max-elements:0/unbounded; Configuration data for Remote Interference Management Reference Signal (RIM RS).";
      key "rimRSSetId";
      leaf rimRSSetId {
        type leafref {
          path "../attributes/rimRSSetId";
        }
      }
      container attributes {
        uses RimRSSet-attributes;
      }
    }
  }

  augment "/emael:ManagedElement/GNBDUFunction/UeCC/SchedulingProfile" {
    list DlDelayBasedPriority {
      description "Additional definitions from MOM:min/max-elements:0/1; Parameters for delay-based priority shift for downlink.";
      key "dlDelayBasedPriorityId";
      leaf dlDelayBasedPriorityId {
        type leafref {
          path "../attributes/dlDelayBasedPriorityId";
        }
      }
      container attributes {
        uses DlDelayBasedPriority-attributes;
      }
    }
  }

  augment "/emael:ManagedElement/GNBDUFunction/UeCC/SchedulingProfile" {
    list DlLatencyBasedPriority {
      description "Additional definitions from MOM:min/max-elements:0/1; Latency-based priority shift for downlink.";
      key "dlLatencyBasedPriorityId";
      leaf dlLatencyBasedPriorityId {
        type leafref {
          path "../attributes/dlLatencyBasedPriorityId";
        }
      }
      container attributes {
        uses DlLatencyBasedPriority-attributes;
      }
    }
  }

  augment "/emael:ManagedElement/GNBDUFunction/UeCC/SchedulingProfile" {
    list DlRateBasedPriority {
      description "Additional definitions from MOM:min/max-elements:0/1; Parameters for rate-based priority shift for downlink. The RDN of this MO must be DlRateBasedPriority=1.";
      key "dlRateBasedPriorityId";
      leaf dlRateBasedPriorityId {
        type leafref {
          path "../attributes/dlRateBasedPriorityId";
        }
      }
      container attributes {
        uses DlRateBasedPriority-attributes;
      }
    }
  }

  augment "/emael:ManagedElement/GNBDUFunction/UeCC/SchedulingProfile" {
    list DlResourceBasedPriority {
      description "Additional definitions from MOM:min/max-elements:0/1; Parameters for resource-based priority for downlink.";
      key "dlResourceBasedPriorityId";
      leaf dlResourceBasedPriorityId {
        type leafref {
          path "../attributes/dlResourceBasedPriorityId";
        }
      }
      container attributes {
        uses DlResourceBasedPriority-attributes;
      }
    }
  }

  augment "/emael:ManagedElement/GNBDUFunction/UeCC/SchedulingProfile" {
    list UlDelayBasedPriority {
      description "Additional definitions from MOM:min/max-elements:0/1; Parameters for delay-based priority shift for uplink.";
      key "ulDelayBasedPriorityId";
      leaf ulDelayBasedPriorityId {
        type leafref {
          path "../attributes/ulDelayBasedPriorityId";
        }
      }
      container attributes {
        uses UlDelayBasedPriority-attributes;
      }
    }
  }

  augment "/emael:ManagedElement/GNBDUFunction/UeCC/SchedulingProfile" {
    list UlLatencyBasedPriority {
      description "Additional definitions from MOM:min/max-elements:0/1; Latency-based priority shift for uplink.";
      key "ulLatencyBasedPriorityId";
      leaf ulLatencyBasedPriorityId {
        type leafref {
          path "../attributes/ulLatencyBasedPriorityId";
        }
      }
      container attributes {
        uses UlLatencyBasedPriority-attributes;
      }
    }
  }

  augment "/emael:ManagedElement/GNBDUFunction/UeCC/SchedulingProfile" {
    list UlRateBasedPriority {
      description "Additional definitions from MOM:min/max-elements:0/1; Parameters for rate-based priority shift for uplink. The RDN of this MO must be UlRateBasedPriority=1.";
      key "ulRateBasedPriorityId";
      leaf ulRateBasedPriorityId {
        type leafref {
          path "../attributes/ulRateBasedPriorityId";
        }
      }
      container attributes {
        uses UlRateBasedPriority-attributes;
      }
    }
  }

  augment "/emael:ManagedElement/GNBDUFunction/UeCC/SchedulingProfile" {
    list UlResourceBasedPriority {
      description "Additional definitions from MOM:min/max-elements:0/1; Parameters for resource-based priority for uplink.";
      key "ulResourceBasedPriorityId";
      leaf ulResourceBasedPriorityId {
        type leafref {
          path "../attributes/ulResourceBasedPriorityId";
        }
      }
      container attributes {
        uses UlResourceBasedPriority-attributes;
      }
    }
  }

  augment "/emael:ManagedElement/GNBDUFunction/ContentionControl/SessionLimit" {
    list FlowLimit {
      description "Additional definitions from MOM:min/max-elements:0/12; Flow limit definition. Instance FlowLimit=Default is created automatically when parent MO instance is created, unless created manually in same transaction. Precondition: Instance FlowLimit=Default can only be created in same transaction as parent MO instance and cannot be deleted unless parent MO instance is deleted. Other instances can be created and deleted at any time. Maximum 11 FlowLimit instances, with RDN different from Default, can be created under parent MO instance.";
      key "flowLimitId";
      leaf flowLimitId {
        type leafref {
          path "../attributes/flowLimitId";
        }
      }
      container attributes {
        uses FlowLimit-attributes;
      }
    }
  }

  augment "/emael:ManagedElement/GNBDUFunction/UeCC/SoftAcAssist" {
    list SoftAcAssistUeCfg {
      description "Additional definitions from MOM:min/max-elements:0/2; Configuration of Soft Antenna Calibration UE. Instance SoftAcAssistUeCfg=Base is created automatically when parent MO instance is created, unless created manually in same transaction. Attributes prefUeGroupList, ueGroupList and ueConfGroupList must be empty in instance SoftAcAssistUeCfg=Base but cannot all be empty in any other instance of SoftAcAssistUeCfg under same parent SoftAcAssist instance. Precondition: Instance SoftAcAssistUeCfg=Base can only be created in same transaction as parent MO instance and cannot be deleted unless parent MO instance is deleted. Other instances can be created and deleted at any time. Maximum 1 SoftAcAssistUeCfg instance, with RDN different from Base, can be created under parent MO instance.";
      key "softAcAssistUeCfgId";
      leaf softAcAssistUeCfgId {
        type leafref {
          path "../attributes/softAcAssistUeCfgId";
        }
      }
      container attributes {
        uses SoftAcAssistUeCfg-attributes;
      }
    }
  }

  augment "/emael:ManagedElement/GNBDUFunction/UeCC/SrHandling" {
    list SrHandlingUeCfg {
      description "Additional definitions from MOM:min/max-elements:0/4; Scheduling Request configuration profile for UE groups. Instance SrHandlingUeCfg=Base is created automatically when parent MO instance is created, unless created manually in same transaction. Attributes prefUeGroupList, ueGroupList and ueConfGroupList must be empty in instance SrHandlingUeCfg=Base but cannot all be empty in any other instance of SrHandlingUeCfg under same parent SrHandling instance. Precondition: Instance SrHandlingUeCfg=Base can only be created in same transaction as parent MO instance and cannot be deleted unless parent MO instance is deleted. Other instances can be created and deleted at any time. Maximum 3 SrHandlingUeCfg instances, with RDN different from Base, can be created under parent MO instance.";
      key "srHandlingUeCfgId";
      leaf srHandlingUeCfgId {
        type leafref {
          path "../attributes/srHandlingUeCfgId";
        }
      }
      container attributes {
        uses SrHandlingUeCfg-attributes;
      }
    }
  }

  augment "/emael:ManagedElement/GNBDUFunction/UeCC/SrPeriodicity" {
    list SrPeriodicityCovAdaptUeCfg {
      description "Additional definitions from MOM:min/max-elements:0/8; Configuration of Scheduling Request periodicity profile for UE groups. Instance SrPeriodicityCovAdaptUeCfg=Base is created automatically when parent MO instance is created, unless created manually in same transaction. Attributes prefUeGroupList, ueGroupList and ueConfGroupList must be empty in instance SrPeriodicityCovAdaptUeCfg=Base but cannot all be empty in other instance of SrPeriodicityCovAdaptUeCfg under same parent SrPeriodicity instance. A combination of an element of ueGroupList and an element of prefUeGroupList in SrPeriodicityCovAdaptUeCfg instance must be unique under SrPeriodicity instance. Precondition: Instance SrPeriodicityCovAdaptUeCfg=Base can only be created in same transaction as parent MO instance and cannot be deleted unless parent MO instance is deleted. Other instances can be created and deleted at any time. Maximum 7 SrPeriodicityCovAdaptUeCfg instances, with RDN different from Base, can be created under parent MO instance.";
      key "srPeriodicityCovAdaptUeCfgId";
      leaf srPeriodicityCovAdaptUeCfgId {
        type leafref {
          path "../attributes/srPeriodicityCovAdaptUeCfgId";
        }
      }
      container attributes {
        uses SrPeriodicityCovAdaptUeCfg-attributes;
      }
    }
  }

  augment "/emael:ManagedElement/GNBDUFunction/UeCC/SrPeriodicity" {
    list SrPeriodicityUeCfg {
      description "Additional definitions from MOM:min/max-elements:0/8; Configuration of Scheduling Request periodicity profile for UE groups. Instance SrPeriodicityUeCfg=Base is created automatically when parent MO instance is created, unless created manually in same transaction. Attributes prefUeGroupList, ueGroupList and ueConfGroupList must be empty in instance SrPeriodicityUeCfg=Base but cannot all be empty in other instance of SrPeriodicityUeCfg under same parent SrPeriodicity instance. A combination of an element of ueGroupList and an element of prefUeGroupList in SrPeriodicityUeCfg instance must be unique under SrPeriodicity instance. Precondition: Instance SrPeriodicityUeCfg=Base can only be created in same transaction as parent MO instance and cannot be deleted unless parent MO instance is deleted. Other instances can be created and deleted at any time. Maximum 7 SrPeriodicityUeCfg instances, with RDN different from Base, can be created under parent MO instance.";
      key "srPeriodicityUeCfgId";
      leaf srPeriodicityUeCfgId {
        type leafref {
          path "../attributes/srPeriodicityUeCfgId";
        }
      }
      container attributes {
        uses SrPeriodicityUeCfg-attributes;
      }
    }
  }

  augment "/emael:ManagedElement/GNBDUFunction/UeCC/SrbPriority" {
    list SrbPriorityUeCfg {
      description "Additional definitions from MOM:min/max-elements:0/8; Configuration of SRB priority profile for UE groups. Instance SrbPriorityUeCfg=Base is created automatically when parent MO instance is created, unless created manually in same transaction. Attributes prefUeGroupList, ueGroupList and ueConfGroupList must be empty in instance SrbPriorityUeCfg=Base but cannot all be empty in other instance of SrbPriorityUeCfg under same parent SrbPriority instance. A combination of an element of ueGroupList and an element of prefUeGroupList in SrbPriorityUeCfg instance must be unique under SrbPriority instance. Only applicable to Low-Band and Mid-Band cells. Precondition: Instance SrbPriorityUeCfg=Base can only be created in same transaction as parent MO instance and cannot be deleted unless parent MO instance is deleted. Other instances can be created and deleted at any time. Maximum 7 SrbPriorityUeCfg instances, with RDN different from Base, can be created under parent MO instance.";
      key "srbPriorityUeCfgId";
      leaf srbPriorityUeCfgId {
        type leafref {
          path "../attributes/srbPriorityUeCfgId";
        }
      }
      container attributes {
        uses SrbPriorityUeCfg-attributes;
      }
    }
  }

  augment "/emael:ManagedElement/GNBDUFunction/SssgSwitch" {
    list SssgSwitchPwrOpt {
      description "Additional definitions from MOM:min/max-elements:1/8; Configuration of UE power saving through Search Space Set Group (SSSG) switch.";
      key "sssgSwitchPwrOptId";
      leaf sssgSwitchPwrOptId {
        type leafref {
          path "../attributes/sssgSwitchPwrOptId";
        }
      }
      container attributes {
        uses SssgSwitchPwrOpt-attributes;
      }
    }
  }

  augment "/emael:ManagedElement/GNBDUFunction/SssgSwitch" {
    list SssgSwitchUeCfg {
      description "Additional definitions from MOM:min/max-elements:1/8; Configuration profile for Search Space Set Group (SSSG) switch. Attributes prefUeGroupList, ueGroupList and ueConfGroupList can be empty in exactly one instance of SssgSwitchUeCfg under parent SssgSwitch instance. Only one SssgSwitchUeCfg instance can have sssgSwitchPwrOptRef empty under parent SssgSwitch instance.";
      key "sssgSwitchUeCfgId";
      leaf sssgSwitchUeCfgId {
        type leafref {
          path "../attributes/sssgSwitchUeCfgId";
        }
      }
      container attributes {
        uses SssgSwitchUeCfg-attributes;
      }
    }
  }

  augment "/emael:ManagedElement/GNBDUFunction/TrafficDefinitions/TrafficDefinition" {
    list TrafficSet {
      description "Additional definitions from MOM:min/max-elements:0/36; Traffic set definitions. Instances TrafficSet=Default and Default_ENDC are created automatically when parent MO instance is created, unless created manually in same transaction. Precondition: Instance TrafficSet=Default can only be created in same transaction as parent MO instance and cannot be deleted unless parent MO instance is deleted. Instance TrafficSet=Default_ENDC can only be deleted if it has no child TrafficSetMember=Default_ENDC instance or if parent MO instance is deleted. Other instances can be created and deleted at any time. Maximum 34 TrafficSet instances, with RDN different from Default and Default_ENDC, can be created under parent MO instance.";
      key "trafficSetId";
      leaf trafficSetId {
        type leafref {
          path "../attributes/trafficSetId";
        }
      }
      container attributes {
        uses TrafficSet-attributes;
      }
    }
  }

  augment "/emael:ManagedElement/GNBDUFunction/TrafficDefinitions" {
    list TrafficDefinition {
      description "Additional definitions from MOM:min/max-elements:0/16; Traffic definition. Instance TrafficDefinition=Default is created automatically when parent MO instance is created, unless created manually in same transaction. NRCellDU::trafficDefinitionRef is automatically set to TrafficDefinition=Default instance, unless manually set to refer to another MO instance. Precondition: Instance TrafficDefinition=Default can only be created in same transaction as parent MO instance and cannot be deleted unless parent MO instance is deleted. Other instances can be created and deleted at any time. Maximum 15 TrafficDefinition instances, with RDN different from Default, can be created under parent MO instance.";
      key "trafficDefinitionId";
      leaf trafficDefinitionId {
        type leafref {
          path "../attributes/trafficDefinitionId";
        }
      }
      container attributes {
        uses TrafficDefinition-attributes;
      }
    }
  }

  augment "/emael:ManagedElement/GNBDUFunction/TrafficGroups/TrafficGroup" {
    list TrafficGroupMember {
      description "Additional definitions from MOM:min/max-elements:0/36; Traffic group member definition. Instances TrafficGroupMember=Defaut_SA and Default_ENDC are created automatically when parent MO instance is created, unless created manually in same transaction. Instance TrafficGroupMember=Default_ENDC is created with trafficCategory=ENDC. Precondition: Instances TrafficGroupMember=Default_SA and Default_ENDC can only be created in same transaction as parent MO instance and cannot be deleted unless parent MO instance is deleted. Other instances can be created and deleted at any time. Maximum 34 TrafficGroupMember instances, with RDN different from Default_SA and Default_ENDC, can be created under parent MO instance. Instance TrafficGroupMember=Default_SA must have trafficCategory=SA. Instance TrafficGroupMember=Default_ENDC must have trafficCategory=ENDC.";
      key "trafficGroupMemberId";
      status deprecated;
      leaf trafficGroupMemberId {
        type leafref {
          path "../attributes/trafficGroupMemberId";
        }
        status deprecated;
      }
      container attributes {
        uses TrafficGroupMember-attributes;
      }
    }
  }

  augment "/emael:ManagedElement/GNBDUFunction/TrafficGroups" {
    list TrafficGroup {
      description "Additional definitions from MOM:min/max-elements:0/16; Traffic group definitions. Instance TrafficGroup=Default is created automatically when parent MO instance is created, unless created manually in same transaction. NRCellDU::trafficGroupRef is automatically set to TrafficGroup=Default instance, unless manually set to refer to another MO instance. Precondition: Instance TrafficGroup=Default can only be created in same transaction as parent MO instance and cannot be deleted unless parent MO instance is deleted. Other instances can be created and deleted at any time. Maximum 15 TrafficGroup instances, with RDN different from Default, can be created under parent MO instance.";
      key "trafficGroupId";
      status deprecated;
      leaf trafficGroupId {
        type leafref {
          path "../attributes/trafficGroupId";
        }
        status deprecated;
      }
      container attributes {
        uses TrafficGroup-attributes;
      }
    }
  }

  augment "/emael:ManagedElement/GNBDUFunction/TrafficDefinitions/TrafficDefinition/TrafficSet" {
    list TrafficSetMember {
      description "Additional definitions from MOM:min/max-elements:0/4; Definition of traffic set member. Instances TrafficSetMember=Default_SA and Default_ENDC are created automatically when parent MO instance is created, unless created manually in same transaction. Instance TrafficSetMember=Default_SA is created automatically when TrafficSet=Default instance is created, unless created manually in same transaction. Instance TrafficSetMember=Default_ENDC is created automatically when TrafficSet=Default_ENDC instance is created, unless created manually in same transaction. But only if Default_ENDC instance does not already exist as a sibling under TrafficDefinition instance. Attributes sNSSAIList, pLMNIdList and spidRfspList must be empty in instance TrafficSetMember=Default_SA or TrafficSetMember=Default_ENDC but cannot all be empty in any other instance of TrafficSetMember under same parent TrafficSet instance. Precondition: Instance TrafficSetMember=Default_SA can only be created in same transaction as parent MO instance and cannot be deleted unless parent MO instance is deleted. Instance TrafficSetMember=Default_ENDC can be deleted only if it is in same transaction created in another MO instance sibling to its parent or only if parent MO instance is deleted. Other instances can be created and deleted at any time. Maximum 3 TrafficSetMember instances, with RDN different from Default_ENDC, can be created under parent TrafficSet=Default_ENDC instance. Maximum 3 TrafficSetMember instances, with RDN different from Default_SA, can be created under parent TrafficSet=Default instance. Instance TrafficSetMember=Default_SA must have trafficCategory set to SA. Instance TrafficSetMember=Default_ENDC must have trafficCategory set to ENDC. Maximum one TrafficSetMember=Default_SA instance can be created under same TrafficDefinition instance. Maximum one TrafficSetMember=Default_ENDC instance can be created under same TrafficDefinition instance. Instance TrafficSetMember=Default_SA must be created under TrafficSet=Default instance. Instance TrafficSetMember=Default_ENDC must be created under TrafficSet=Default or Default_ENDC instance.";
      key "trafficSetMemberId";
      leaf trafficSetMemberId {
        type leafref {
          path "../attributes/trafficSetMemberId";
        }
      }
      container attributes {
        uses TrafficSetMember-attributes;
      }
    }
  }

  augment "/emael:ManagedElement/GNBDUFunction/UeCC/RadioLinkControl/UeAdaptiveRlc" {
    list UeAdaptiveRlcUeCfg {
      description "Additional definitions from MOM:min/max-elements:0/4; Configuration of adaptive radio link control poll retransmission profile for UE groups. Attributes prefUeGroupList, ueGroupList and ueConfGroupList must be empty in instance UeAdaptiveRlcUeCfg=Base but cannot all be empty in any other instance of UeAdaptiveRlcUeCfg under same parent UeAdaptiveRlc instance. A combination of an element of ueGroupList and an element of prefUeGroupList in UeAdaptiveRlcUeCfg instance must be unique under UeAdaptiveRlc instance. Instance UeAdaptiveRlcUeCfg=Base is created automatically when parent MO instance is created, unless created manually in same transaction. Precondition: Instance UeAdaptiveRlcUeCfg=Base can only be created in same transaction as parent MO instance and cannot be deleted unless parent MO instance is deleted. Other instances can be created and deleted at any time. Maximum 3 UeAdaptiveRlcUeCfg instances, with RDN different from Base, can be created under parent MO instance.";
      key "ueAdaptiveRlcUeCfgId";
      leaf ueAdaptiveRlcUeCfgId {
        type leafref {
          path "../attributes/ueAdaptiveRlcUeCfgId";
        }
      }
      container attributes {
        uses UeAdaptiveRlcUeCfg-attributes;
      }
    }
  }

  augment "/emael:ManagedElement/GNBDUFunction/UeCC/UeBb" {
    list UeBbProfile {
      description "Additional definitions from MOM:min/max-elements:0/4; UE Baseband profile used for current UE. Instance UeBbProfile=Default is created automatically when parent MO instance is created, unless created manually in same transaction. NRCellDU::ueBbProfileRef is automatically set to UeBbProfile=Default instance, unless manually set to refer to another MO instance. Precondition: Instance UeBbProfile=Default can only be created in same transaction as parent MO instance and cannot be deleted unless parent MO instance is deleted. Other instances can be created and deleted at any time. Maximum 3 UeBbProfile instances, with RDN different from Default, can be created under same parent MO instance. When creating an instance there must be possible to create a child UeBbProfileUeCfg=Base among total allowed instances of that MO class that is 64.";
      key "ueBbProfileId";
      leaf ueBbProfileId {
        type leafref {
          path "../attributes/ueBbProfileId";
        }
      }
      container attributes {
        uses UeBbProfile-attributes;
      }
    }
  }

  augment "/emael:ManagedElement/GNBDUFunction/UeCC/UeBb/UeBbProfile" {
    list UeBbProfileUeCfg {
      description "Additional definitions from MOM:min/max-elements:0/16; Configuration of UE Baseband profile for UE groups. Instance UeBbProfileUeCfg=Base is created automatically when parent MO instance is created, unless created manually in same transaction. Attributes prefUeGroupList, ueGroupList and ueConfGroupList must be empty in instance UeBbProfileUeCfg=Base but cannot all be empty in any other instance of UeBbProfileUeCfg under same parent UeBbProfile instance. A combination of an element of ueGroupList and an element of prefUeGroupList in UeBbProfileUeCfg instance must be unique under UeBbProfile instance. Value 0 is no longer allowed and is planned to be removed from the valid range of prefUeGroupList and ueGroupList. Precondition: Instance UeBbProfileUeCfg=Base can only be created in same transaction as parent MO instance and cannot be deleted unless parent MO instance is deleted. Other instances can be created and deleted at any time. Maximum 15 UeBbProfileUeCfg instances, with RDN different from Base, can be created under parent MO instance. To be able to create an instance, the total number of instances, including all auto created instances, must be less than the total allowed number of instances under a GNBDUFunction instance that is 64.";
      key "ueBbProfileUeCfgId";
      leaf ueBbProfileUeCfgId {
        type leafref {
          path "../attributes/ueBbProfileUeCfgId";
        }
      }
      container attributes {
        uses UeBbProfileUeCfg-attributes;
      }
    }
  }

  augment "/emael:ManagedElement/GNBDUFunction/UeCA" {
    list CaSCellHandling {
      description "Additional definitions from MOM:min/max-elements:0/4; SCell handling profile for UEs configured for NR carrier aggregation. Instance CaSCellHandling=Default is created automatically when parent MO instance is created, unless created manually in same transaction. If NRCellDU::caSCellHandlingRef is non-empty, attributes from referenced MO instance are used. If NRCellDU::caSCellHandlingRef is empty, attribute default values according to CaSCellHandling and CaSCellHandlingUeCfg MO class definitions are used. Precondition: Instance CaSCellHandling=Default can only be created in same transaction as parent MO instance and cannot be deleted unless parent MO instance is deleted. Other instances can be created and deleted at any time. Maximum 3 CaSCellHandling instances, with RDN different from Default, can be created under parent MO instance.";
      key "caSCellHandlingId";
      leaf caSCellHandlingId {
        type leafref {
          path "../attributes/caSCellHandlingId";
        }
      }
      container attributes {
        uses CaSCellHandling-attributes;
      }
    }
  }

  augment "/emael:ManagedElement/GNBDUFunction/UeCC" {
    list AqmCfg {
      description "Additional definitions from MOM:min/max-elements:0/32; Automatic queue management configuration selection profile. Instances AqmCfg=Default_conversational_media instance, Default_application_signaling, and Default_other are created automatically when parent MO instance is created, unless created manually in same transaction. DrbUpUeCfg::aqmCfgRef is automatically set to following MO instance: - AqmCfg=Default_conversational_media instance, if DrbUpUeCfg instance is created under parent DrbUp=Default_conversational_media instance. - AqmCfg=Default_application_signaling, if DrbUpUeCfg instance is created under parent DrbUp=Default_application_signaling instance. - AqmCfg=Default_other, if DrbUpUeCfg instance is created under other parent Drb instance. Unless manually set to refer to another MO instance. Only applicable when GNBDUFunction::altDepHServAdapUPProfEnabled is true. Precondition: Instances AqmCfg=Default_application_signaling, Default_conversational_media, and Default_other can only be created in same transaction as parent MO instance and cannot be deleted unless parent MO instance is deleted. Other instances can be created and deleted manually. Maximum 29 AqmCfg instances, with RDN different from Default_application_signaling, Default_conversational_media, or Default_other can be created under same parent MO instance.";
      key "aqmCfgId";
      leaf aqmCfgId {
        type leafref {
          path "../attributes/aqmCfgId";
        }
      }
      container attributes {
        uses AqmCfg-attributes;
      }
    }
  }

  augment "/emael:ManagedElement/GNBDUFunction/UeCC" {
    list Bsr {
      description "Additional definitions from MOM:min/max-elements:0/1; BSR profile used for current UE. Instance Bsr=1 is created automatically when parent MO instance is created, unless created manually in same transaction. The RDN of this MO must be Bsr=1. Precondition: Instance Bsr=1 can only be created in same transaction as parent MO instance and cannot be deleted unless parent MO instance is deleted.";
      key "bsrId";
      leaf bsrId {
        type leafref {
          path "../attributes/bsrId";
        }
      }
      container attributes {
        uses Bsr-attributes;
      }
    }
  }

  augment "/emael:ManagedElement/GNBDUFunction/UeCC" {
    list CgSwitch {
      description "Additional definitions from MOM:min/max-elements:0/49; Cell group switch profile. Instance CgSwitch=Default is created automatically when parent MO instance is created, unless created manually in same transaction. NRCellDU::endcCgSwitchRef and NRCellDU::nrdcCgSwitchRef are automatically set to CgSwitch=Default instance, unless manually set to refer to another MO instance. Precondition: Instance CgSwitch=Default can only be created in same transaction as parent MO instance and cannot be deleted unless parent MO instance is deleted. Other instances can be created and deleted at any time. Maximum 48 CgSwitch instances, with RDN different from Default, can be created under parent MO instance.";
      key "cgSwitchId";
      leaf cgSwitchId {
        type leafref {
          path "../attributes/cgSwitchId";
        }
      }
      container attributes {
        uses CgSwitch-attributes;
      }
    }
  }

  augment "/emael:ManagedElement/GNBDUFunction/UeCC" {
    list CgSwitchCfg {
      description "Additional definitions from MOM:min/max-elements:0/49; Cell group switch configuration. Instance CgSwitchCfg=Default is created automatically when parent MO instance is created, unless created manually in same transaction. CgSwitchUeCfg::cgSwitchCfgRef is automatically set to CgSwitchCfg=Default instance, unless manually set to refer to another MO instance. Precondition: Instance CgSwitchCfg=Default can only be created in same transaction as parent MO instance and cannot be deleted unless parent MO instance is deleted. Other instances can be created and deleted at any time. Maximum 48 CgSwitchCfg instances, with RDN different from Default, can be created under parent MO instance.";
      key "cgSwitchCfgId";
      leaf cgSwitchCfgId {
        type leafref {
          path "../attributes/cgSwitchCfgId";
        }
      }
      container attributes {
        uses CgSwitchCfg-attributes;
      }
    }
  }

  augment "/emael:ManagedElement/GNBDUFunction/UeCC" {
    list ConfiguredGrant {
      description "Additional definitions from MOM:min/max-elements:0/1; Configured grant profile used for current UE. Instance ConfiguredGrant=1 is created automatically when parent MO instance is created, unless created manually in same transaction. The RDN of this MO must be ConfiguredGrant=1. Precondition: Instance ConfiguredGrant=1 can only be created in same transaction as parent MO instance and cannot be deleted unless parent MO instance is deleted.";
      key "configuredGrantId";
      leaf configuredGrantId {
        type leafref {
          path "../attributes/configuredGrantId";
        }
      }
      container attributes {
        uses ConfiguredGrant-attributes;
      }
    }
  }

  augment "/emael:ManagedElement/GNBDUFunction/UeCC" {
    list CsiProfile {
      description "Additional definitions from MOM:min/max-elements:0/1; Channel State Information profile used for current UE. Instance CsiProfile=1 is created automatically when parent MO instance is created, unless created manually in same transaction. The RDN of this MO must be CsiProfile=1. Precondition: Instance CsiProfile=1 can only be created in same transaction as parent MO instance and cannot be deleted unless parent MO instance is deleted.";
      key "csiProfileId";
      leaf csiProfileId {
        type leafref {
          path "../attributes/csiProfileId";
        }
      }
      container attributes {
        uses CsiProfile-attributes;
      }
    }
  }

  augment "/emael:ManagedElement/GNBDUFunction/UeCC" {
    list DlBeamOptProfile {
      description "Additional definitions from MOM:min/max-elements:0/1; Downlink Beamforming optimization profile used for current UE. Instance DlBeamOptProfile=1 is created automatically when parent MO instance is created, unless created manually in same transaction. The RDN of this MO must be DlBeamOptProfile=1. Precondition: Instance DlBeamOptProfile=1 can only be created in same transaction as parent MO instance and cannot be deleted unless parent MO instance is deleted.";
      key "dlBeamOptProfileId";
      leaf dlBeamOptProfileId {
        type leafref {
          path "../attributes/dlBeamOptProfileId";
        }
      }
      container attributes {
        uses DlBeamOptProfile-attributes;
      }
    }
  }

  augment "/emael:ManagedElement/GNBDUFunction/UeCC" {
    list DlMimo {
      description "Additional definitions from MOM:min/max-elements:0/1; Container class for downlink MIMO configuration profile used for current UE. Instance DlMimo=1 is created automatically when parent MO instance is created, unless created manually in same transaction. The RDN of this MO must be DlMimo=1. Precondition: Instance DlMimo=1 can only be created in same transaction as parent MO instance and cannot be deleted unless parent MO instance is deleted.";
      key "dlMimoId";
      leaf dlMimoId {
        type leafref {
          path "../attributes/dlMimoId";
        }
      }
      container attributes {
        uses DlMimo-attributes;
      }
    }
  }

  augment "/emael:ManagedElement/GNBDUFunction/UeCC" {
    list DrbUp {
      description "Additional definitions from MOM:min/max-elements:0/32; Data radio bearer user plane profile. Instances DrbUp=Default_application_signaling, Default_conversational_media, and Default_other are created automatically when parent MO instance is created, unless created manually in same transaction. DU5qi::drbUpRef is automatically set to following MO instance: - DrbUp=Default_application_signaling instance for DU5qi instances for which profile5qi is 5 or 69. - DrbUp=Default_conversational_media instance for DU5qi instances for which profile5qi is 1, 65, or 66. - DrbUp=Default_other instance for all other DU5qi instances. Unless manually set to refer to another MO instance. DrbUp=Default_application_signaling, Default_conversational_media, and Default_other instances are used for DRBs when DU5qi instance with matching profile5qi does not exist. Only applicable when GNBDUFunction::altDepHServAdapUPProfEnabled is true. Precondition: Instances DrbUp=Default_application_signaling, Default_conversational_media, and Default_other can only be created in same transaction as parent MO instance and cannot be deleted unless parent MO instance is deleted. Other instances can be created and deleted at any time. Maximum 29 DrbUp instances, with RDN different from Default_application_signaling, Default_conversational_media, and Default_other, can be created under parent MO instance.";
      key "drbUpId";
      leaf drbUpId {
        type leafref {
          path "../attributes/drbUpId";
        }
      }
      container attributes {
        uses DrbUp-attributes;
      }
    }
  }

  augment "/emael:ManagedElement/GNBDUFunction/UeCC" {
    list DrxProfile {
      description "Additional definitions from MOM:min/max-elements:0/4; DRX profile used for current UE. Instance DrxProfile=Default is created automatically when parent MO instance is created, unless created manually in same transaction. If NRCellDU::drxProfileRef is non-empty, attributes from referenced MO instance are used. If NRCellDU::drxProfileRef is empty, attribute default values according to DrxProfile and DrxProfileUeCfg MO class definitions are used. Precondition: Instance DrxProfile=Default can only be created in same transaction as parent MO instance and cannot be deleted unless parent MO instance is deleted. Other instances can be created and deleted at any time. Maximum 3 DrxProfile instances, with RDN different from Default, can be created under parent MO instance.";
      key "drxProfileId";
      leaf drxProfileId {
        type leafref {
          path "../attributes/drxProfileId";
        }
      }
      container attributes {
        uses DrxProfile-attributes;
      }
    }
  }

  augment "/emael:ManagedElement/GNBDUFunction/UeCC" {
    list Harq {
      description "Additional definitions from MOM:min/max-elements:0/1; HARQ profile used for current UE. Instance Harq=1 is created automatically when parent MO instance is created, unless created manually in same transaction. The RDN of this MO must be Harq=1. Precondition: Instance Harq=1 can only be created in same transaction as parent MO instance and cannot be deleted unless parent MO instance is deleted.";
      key "harqId";
      leaf harqId {
        type leafref {
          path "../attributes/harqId";
        }
      }
      container attributes {
        uses Harq-attributes;
      }
    }
  }

  augment "/emael:ManagedElement/GNBDUFunction/UeCC" {
    list L4sCfg {
      description "Additional definitions from MOM:min/max-elements:0/8; Container for L4S configuration attributes. Only applicable if license for UL RAN Assisted Rate Adaptation is present and feature is active. If DUModified5qiUeCfg::l4sCfgRef is non-empty, attributes from referenced MO instance are used. If DUModified5qiUeCfg::l4sCfgRef is empty, l4sCfgRef in DU5qi instance is used. If DU5qi::l4sCfgRef is non-empty, attributes from referenced MO instance are used. If DU5qi::l4sCfgRef is empty, attribute default values according to MO class definition are used.";
      key "l4sCfgId";
      leaf l4sCfgId {
        type leafref {
          path "../attributes/l4sCfgId";
        }
      }
      container attributes {
        uses L4sCfg-attributes;
      }
    }
  }

  augment "/emael:ManagedElement/GNBDUFunction/UeCC" {
    list LinkAdaptation {
      description "Additional definitions from MOM:min/max-elements:0/1; Link adaptation profile used for current UE. Instance LinkAdaptation=1 is created automatically when parent MO instance is created, unless created manually in same transaction. The RDN of this MO must be LinkAdaptation=1. Precondition: Instance LinkAdaptation=1 can only be created in same transaction as parent MO instance and cannot be deleted unless parent MO instance is deleted.";
      key "linkAdaptationId";
      leaf linkAdaptationId {
        type leafref {
          path "../attributes/linkAdaptationId";
        }
      }
      container attributes {
        uses LinkAdaptation-attributes;
      }
    }
  }

  augment "/emael:ManagedElement/GNBDUFunction/UeCC" {
    list LogicalChannel {
      description "Additional definitions from MOM:min/max-elements:0/8; Container class for logical channel configurations. Instances LogicalChannel=Default and IMS_Voice are created automatically when parent MO instance is created, unless created manually in same transaction. DU5qi::logicalChannelRef and DUModified5qiUeCfg::logicalChannelRef are automatically set to following MO instance: - LogicalChannel=IMS_Voice instance for DU5qi instances which profile5qi is 1 or 5. - LogicalChannel=IMS_Voice instance for DUModified5qiUeCfg instances which modifiedProfile5qi is 1 or 5. - LogicalChannel=Default instance for all other DU5qi and DUModified5qiUeCfg instances. Unless manually set to refer to another MO instance. Precondition: Instances LogicalChannel=Default and IMS_Voice can only be created in same transaction as parent MO instance and cannot be deleted unless parent MO instance is deleted. Other instances can be created and deleted at any time. Maximum 6 LogicalChannel instances, with RDN different from Default and IMS_Voice, can be created under parent MO instance.";
      key "logicalChannelId";
      leaf logicalChannelId {
        type leafref {
          path "../attributes/logicalChannelId";
        }
      }
      container attributes {
        uses LogicalChannel-attributes;
      }
    }
  }

  augment "/emael:ManagedElement/GNBDUFunction/UeCC" {
    list OutOfCov {
      description "Additional definitions from MOM:min/max-elements:0/1; Out of coverage (OOC) profile used for current UE. Instance OutOfCov=1 is created automatically when parent MO instance is created, unless created manually in same transaction as parent MO. The RDN of this MO must be OutOfCov=1. Precondition: Instance OutOfCov=1 can only be created in same transaction as parent MO instance and cannot be deleted unless parent MO instance is deleted.";
      key "outOfCovId";
      leaf outOfCovId {
        type leafref {
          path "../attributes/outOfCovId";
        }
      }
      container attributes {
        uses OutOfCov-attributes;
      }
    }
  }

  augment "/emael:ManagedElement/GNBDUFunction/UeCC" {
    list PdcchReuseForPdsch {
      description "Additional definitions from MOM:min/max-elements:0/2; PDCCH and PDSCH Frequency Division Multiplexing profile used for current UE. Instance PdcchReuseForPdsch=Default is created automatically when parent MO instance is created, unless created manually in same transaction. NRCellDU::pdcchReuseForPdschRef is automatically set to PdcchReuseForPdsch=Default instance, unless manually set to refer to another MO instance. Only applicable to Low-Band and Mid-Band cells. Precondition: Instance PdcchReuseForPdsch=Default can only be created in same transaction as parent MO instance and cannot be deleted unless parent MO instance is deleted. Other instances can be created and deleted at any time. Maximum 1 PdcchReuseForPdsch instance, with RDN different from Default, can be created under parent MO instance.";
      key "pdcchReuseForPdschId";
      leaf pdcchReuseForPdschId {
        type leafref {
          path "../attributes/pdcchReuseForPdschId";
        }
      }
      container attributes {
        uses PdcchReuseForPdsch-attributes;
      }
    }
  }

  augment "/emael:ManagedElement/GNBDUFunction/UeCC" {
    list PowerControl {
      description "Additional definitions from MOM:min/max-elements:0/1; Power control profile used for current UE. Instance PowerControl=1 is created automatically when parent MO instance is created, unless created manually in same transaction. The RDN of this MO must be PowerControl=1. Precondition: Instance PowerControl=1 can only be created in same transaction as parent MO instance and cannot be deleted unless parent MO instance is deleted.";
      key "powerControlId";
      leaf powerControlId {
        type leafref {
          path "../attributes/powerControlId";
        }
      }
      container attributes {
        uses PowerControl-attributes;
      }
    }
  }

  augment "/emael:ManagedElement/GNBDUFunction/UeCC" {
    list Prescheduling {
      description "Additional definitions from MOM:min/max-elements:0/1; Prescheduling mode used for current UE. Instance Prescheduling=1 is created automatically when parent MO instance is created, unless created manually in same transaction. The RDN of this MO must be Prescheduling=1. Precondition: Instance Prescheduling=1 can only be created in same transaction as parent MO instance and cannot be deleted unless parent MO instance is deleted.";
      key "preschedulingId";
      leaf preschedulingId {
        type leafref {
          path "../attributes/preschedulingId";
        }
      }
      container attributes {
        uses Prescheduling-attributes;
      }
    }
  }

  augment "/emael:ManagedElement/GNBDUFunction/UeCC" {
    list PuschRep {
      description "Additional definitions from MOM:min/max-elements:0/4; PUSCH repetition profile used in each 5QI. Instance PuschRep=Default is created automatically when parent MO instance is created, unless created manually in same transaction. DU5qi::puschRepRef is automatically set to PuschRep=Default instance, unless manually set to refer to another MO instance. Precondition: Instance PuschRep=Default can only be created in same transaction as parent MO instance and cannot be deleted unless parent MO instance is deleted. Other instances can be created and deleted at any time. Maximum 3 PuschRep instances, with RDN different from Default, can be created under parent MO instance.";
      key "puschRepId";
      leaf puschRepId {
        type leafref {
          path "../attributes/puschRepId";
        }
      }
      container attributes {
        uses PuschRep-attributes;
      }
    }
  }

  augment "/emael:ManagedElement/GNBDUFunction/UeCC" {
    list Rach {
      description "Additional definitions from MOM:min/max-elements:0/4; Rach profile used for current UE. Instance Rach=Default is created automatically when parent MO instance is created, unless created manually in same transaction. NRCellDU::rachRef is automatically set to Rach=Default instance, unless manually set to refer to another MO instance. Precondition: Instance Rach=Default can only be created in same transaction as parent MO instance and cannot be deleted unless parent MO instance is deleted. Other instances can be created and deleted at any time. Maximum 3 Rach instances, with RDN different from Default, can be created under parent MO instance.";
      key "rachId";
      leaf rachId {
        type leafref {
          path "../attributes/rachId";
        }
      }
      container attributes {
        uses Rach-attributes;
      }
    }
  }

  augment "/emael:ManagedElement/GNBDUFunction/UeCC" {
    list RadioLinkControl {
      description "Additional definitions from MOM:min/max-elements:0/1; Container class for data radio bearer radio link control attributes and profile classes. Instance RadioLinkControl=1 is created automatically when parent MO instance is created, unless created manually in same transaction. The RDN of this MO must be RadioLinkControl=1. Precondition: Instance RadioLinkControl=1 can only be created in same transaction as parent MO instance and cannot be deleted unless parent MO instance is deleted.";
      key "radioLinkControlId";
      leaf radioLinkControlId {
        type leafref {
          path "../attributes/radioLinkControlId";
        }
      }
      container attributes {
        uses RadioLinkControl-attributes;
      }
    }
  }

  augment "/emael:ManagedElement/GNBDUFunction/UeCC" {
    list ResourceAllocTypeDl {
      description "Additional definitions from MOM:min/max-elements:0/3; Downlink resource allocation profile. Instance ResourceAllocTypeDl=Default is created automatically when parent MO instance is created, unless created manually in same transaction. NRCellDU::resourceAllocTypeDlRef is automatically set to ResourceAllocTypeDl=Default instance, unless manually set to refer to another MO instance. Precondition: Instance ResourceAllocTypeDl=Default can only be created in same transaction as parent MO instance and cannot be deleted unless parent MO instance is deleted. Other instances can be created and deleted at any time. Maximum 2 ResourceAllocTypeDl instances, with RDN different from Default, can be created under parent MO instance.";
      key "resourceAllocTypeDlId";
      leaf resourceAllocTypeDlId {
        type leafref {
          path "../attributes/resourceAllocTypeDlId";
        }
      }
      container attributes {
        uses ResourceAllocTypeDl-attributes;
      }
    }
  }

  augment "/emael:ManagedElement/GNBDUFunction/UeCC" {
    list RimOffload {
      description "Additional definitions from MOM:min/max-elements:0/1; Container class for remote interference triggered offload configurations. Instance RimOffload=1 is created automatically when parent MO instance is created, unless created manually in same transaction. The RDN of this MO must be RimOffload=1.";
      key "rimOffloadId";
      leaf rimOffloadId {
        type leafref {
          path "../attributes/rimOffloadId";
        }
      }
      container attributes {
        uses RimOffload-attributes;
      }
    }
  }

  augment "/emael:ManagedElement/GNBDUFunction/UeCC" {
    list SchedulingProfile {
      description "Additional definitions from MOM:min/max-elements:0/32; Scheduling profile used for current connection. If DUModified5qiUeCfg::schedulingProfileRef is non-empty, attributes from referenced MO instance are used. If DUModified5qiUeCfg::schedulingProfileRef is empty, schedulingProfileRef in DU5qi instance is used. If DU5qi::schedulingProfileRef is non-empty, attributes from referenced MO instance are used. If DU5qi::schedulingProfileRef is empty, attribute default values according to MO class definition are used.";
      key "schedulingProfileId";
      leaf schedulingProfileId {
        type leafref {
          path "../attributes/schedulingProfileId";
        }
      }
      container attributes {
        uses SchedulingProfile-attributes;
      }
    }
  }

  augment "/emael:ManagedElement/GNBDUFunction/UeCC" {
    list SoftAcAssist {
      description "Additional definitions from MOM:min/max-elements:0/1; Container class for Soft Antenna Calibration UE Assisted attributes and configuration classes. Instance SoftAcAssist=1 is created automatically when parent MO instance is created, unless created manually in same transaction. The RDN of this MO must be SoftAcAssist=1. Precondition: Instance SoftAcAssist=1 can only be created in same transaction as parent MO instance and cannot be deleted unless parent MO instance is deleted.";
      key "softAcAssistId";
      leaf softAcAssistId {
        type leafref {
          path "../attributes/softAcAssistId";
        }
      }
      container attributes {
        uses SoftAcAssist-attributes;
      }
    }
  }

  augment "/emael:ManagedElement/GNBDUFunction/UeCC" {
    list SrbPriority {
      description "Additional definitions from MOM:min/max-elements:0/4; SRB priority profile used for current UE. Instance SrbPriority=Default is created automatically when parent MO instance is created, unless created manually in same transaction. NRCellDU::srbPriorityRef is automatically set to SrbPriority=Default instance, unless manually set to refer to another MO instance. Only applicable to Low-Band and Mid-Band cells. Precondition: Instance SrbPriority=Default can only be created in same transaction as parent MO instance and cannot be deleted unless parent MO instance is deleted. Other instances can be created and deleted at any time. Maximum 3 SrbPriority instances, with RDN different from Default, can be created under parent MO instance.";
      key "srbPriorityId";
      leaf srbPriorityId {
        type leafref {
          path "../attributes/srbPriorityId";
        }
      }
      container attributes {
        uses SrbPriority-attributes;
      }
    }
  }

  augment "/emael:ManagedElement/GNBDUFunction/UeCC" {
    list SrHandling {
      description "Additional definitions from MOM:min/max-elements:0/8; Scheduling Request profile used for current connection. Instance SrHandling=Default is created automatically when parent MO instance is created, unless created manually in same transaction. DU5qi::srHandlingRef is automatically set to SrHandling=Default instance, unless manually set to refer to another MO instance. DUModified5qiUeCfg::srHandlingRef is automatically set to SrHandling=Default instance, unless manually set to refer to another MO instance. Precondition: Instance SrHandling=Default can only be created in same transaction as parent MO instance and cannot be deleted unless parent MO instance is deleted. Other instances can be created and deleted at any time.";
      key "srHandlingId";
      leaf srHandlingId {
        type leafref {
          path "../attributes/srHandlingId";
        }
      }
      container attributes {
        uses SrHandling-attributes;
      }
    }
  }

  augment "/emael:ManagedElement/GNBDUFunction/UeCC" {
    list SrPeriodicity {
      description "Additional definitions from MOM:min/max-elements:0/4; Scheduling Request periodicity profile used for current UE. Instance SrPeriodicity=Default is created automatically when parent MO instance is created, unless created manually in same transaction. NRCellDU::srPeriodicityRef is automatically set to SrPeriodicity=Default instance, unless manually set to refer to another MO instance. Precondition: Instance SrPeriodicity=Default can only be created in same transaction as parent MO instance and cannot be deleted unless parent MO instance is deleted. Other instances can be created and deleted at any time. Maximum 3 SrPeriodicity instances, with RDN different from Default, can be created under parent MO instance.";
      key "srPeriodicityId";
      leaf srPeriodicityId {
        type leafref {
          path "../attributes/srPeriodicityId";
        }
      }
      container attributes {
        uses SrPeriodicity-attributes;
      }
    }
  }

  augment "/emael:ManagedElement/GNBDUFunction/UeCC" {
    list UeBb {
      description "Additional definitions from MOM:min/max-elements:0/1; Container class for UE Baseband attributes and profile classes. Instance UeBb=1 is created automatically when parent MO instance is created, unless created manually in same transaction. The RDN of this MO must be UeBb=1. Precondition: Instance UeBb=1 can only be created in same transaction as parent MO instance and cannot be deleted unless parent MO instance is deleted.";
      key "ueBbId";
      leaf ueBbId {
        type leafref {
          path "../attributes/ueBbId";
        }
      }
      container attributes {
        uses UeBb-attributes;
      }
    }
  }

  augment "/emael:ManagedElement/GNBDUFunction/UeCC" {
    list UlCgSwitch {
      description "Additional definitions from MOM:min/max-elements:0/49; Cell group switch profile for uplink. Instance UlCgSwitch=Default is created automatically when parent MO instance is created, unless created manually in same transaction. NRCellDU::endcUlCgSwitchRef and NRCellDU::nrdcUlCgSwitchRef are automatically set to UlCgSwitch=Default instance, unless manually set to refer to another MO instance. Precondition: Instance UlCgSwitch=Default can only be created in same transaction as parent MO instance and cannot be deleted unless parent MO instance is deleted. Other instances can be created and deleted at any time. Maximum 48 CgSwitch instances, with RDN different from Default, can be created under parent MO instance.";
      key "ulCgSwitchId";
      leaf ulCgSwitchId {
        type leafref {
          path "../attributes/ulCgSwitchId";
        }
      }
      container attributes {
        uses UlCgSwitch-attributes;
      }
    }
  }

  augment "/emael:ManagedElement/GNBDUFunction/UeCC" {
    list UlCgSwitchCfg {
      description "Additional definitions from MOM:min/max-elements:0/49; Cell group switch configuration for uplink. Instance UlCgSwitchCfg=Default is created automatically when parent MO instance is created, unless created manually in same transaction. UlCgSwitchUeCfg::ulCgSwitchCfgRef is automatically set to UlCgSwitchCfg=Default instance, unless manually set to refer to another MO instance. Precondition: Instance UlCgSwitchCfg=Default can only be created in same transaction as parent MO instance and cannot be deleted unless parent MO instance is deleted. Other instances can be created and deleted at any time. Maximum 48 UlCgSwitchCfg instances, with RDN different from Default, can be created under parent MO instance.";
      key "ulCgSwitchCfgId";
      leaf ulCgSwitchCfgId {
        type leafref {
          path "../attributes/ulCgSwitchCfgId";
        }
      }
      container attributes {
        uses UlCgSwitchCfg-attributes;
      }
    }
  }

  augment "/emael:ManagedElement/GNBDUFunction/UeCC" {
    list UlServiceDefinition {
      description "Additional definitions from MOM:min/max-elements:0/1; Container class for uplink service definition profile used for current UE. Instance UlServiceDefinition=1 is created automatically when parent MO instance is created, unless created manually in same transaction. Only applicable to Low-Band and Mid-Band cells. The RDN of this MO must be UlServiceDefinition=1. Precondition: Instance UlServiceDefinition=1 can only be created in same transaction as parent MO instance and cannot be deleted unless parent MO instance is deleted.";
      key "ulServiceDefinitionId";
      leaf ulServiceDefinitionId {
        type leafref {
          path "../attributes/ulServiceDefinitionId";
        }
      }
      container attributes {
        uses UlServiceDefinition-attributes;
      }
    }
  }

  augment "/emael:ManagedElement/GNBDUFunction/UeCC" {
    list UlWfPortSwitch {
      description "Additional definitions from MOM:min/max-elements:0/1; Uplink waveform and port switch profile used for current UE. Instance UlWfPortSwitch=1 is created automatically when parent MO instance is created, unless created manually in same transaction. The RDN of this MO must be UlWfPortSwitch=1. Precondition: Instance UlWfPortSwitch=1 can only be created in same transaction as parent MO instance and cannot be deleted unless parent MO instance is deleted.";
      key "ulWfPortSwitchId";
      leaf ulWfPortSwitchId {
        type leafref {
          path "../attributes/ulWfPortSwitchId";
        }
      }
      container attributes {
        uses UlWfPortSwitch-attributes;
      }
    }
  }

  augment "/emael:ManagedElement/GNBDUFunction/UeCC/UlCgSwitch" {
    list UlCgSwitchUeCfg {
      description "Additional definitions from MOM:min/max-elements:0/8; Cell group switch UE configuration group for uplink. Instance UlCgSwitchUeCfg=Base is created automatically when parent MO instance is created, unless created manually in same transaction. Each UE configuration group identifier can only be defined in one ueConfGroupList among UlCgSwitchUeCfg instances contained under parent UlCgSwitch instance. Any combination of one UE group identifier in ueGroupList and one preference UE group identifier in prefUeGroupList must be unique among UlCgSwitchUeCfg instances contained under parent UlCgSwitch instance. Attributes prefUeGroupList, ueGroupList and ueConfGroupList must be empty in instance UlCgSwitchUeCfg=Base but cannot all be empty in any other instance of UlCgSwitchUeCfg under same parent UlCgSwitch instance. Precondition: Instance UlCgSwitchUeCfg=Base can only be created in same transaction as parent MO instance and cannot be deleted unless parent MO instance is deleted. Other instances can be created and deleted at any time. Maximum 7 UlCgSwitchUeCfg instances, with RDN different from Base, can be created under parent MO instance.";
      key "ulCgSwitchUeCfgId";
      leaf ulCgSwitchUeCfgId {
        type leafref {
          path "../attributes/ulCgSwitchUeCfgId";
        }
      }
      container attributes {
        uses UlCgSwitchUeCfg-attributes;
      }
    }
  }

  augment "/emael:ManagedElement/GNBDUFunction/UeCC/UlServiceDefinition" {
    list UlServiceDefinitionUeCfg {
      description "Additional definitions from MOM:min/max-elements:0/8; Uplink service definition profile used for current UE. Instance UlServiceDefinitionUeCfg=Base is created automatically when parent MO instance is created, unless created manually in same transaction. UeBbProfileUeCfg::ulServiceDefinitionUeCfgRef is automatically set to UlServiceDefinitionUeCfg=Base instance, unless manually set to refer to another MO instance. Only applicable to Low-Band and Mid-Band cells. Precondition: Instance UlServiceDefinitionUeCfg=Base can only be created in same transaction as parent MO instance and cannot be deleted unless parent MO instance is deleted. Other instances can be created and deleted at any time. Maximum 7 UlServiceDefinitionUeCfg instances, with RDN different from Base, can be created under parent MO instance.";
      key "ulServiceDefinitionUeCfgId";
      leaf ulServiceDefinitionUeCfgId {
        type leafref {
          path "../attributes/ulServiceDefinitionUeCfgId";
        }
      }
      container attributes {
        uses UlServiceDefinitionUeCfg-attributes;
      }
    }
  }

  augment "/emael:ManagedElement/GNBDUFunction/UeCC/UlServiceDefinition/UlServiceDefinitionUeCfg" {
    list UlService {
      description "Additional definitions from MOM:min/max-elements:0/1; Uplink service profile used for current UE. Instance UlService=1 is created automatically when parent MO instance is created, unless created manually in same transaction. Only applicable to Low-Band and Mid-Band cells. The RDN of this MO must be UlService=1. Precondition: Instance UlService=1 can only be created in same transaction as parent MO instance and cannot be deleted unless parent MO instance is deleted.";
      key "ulServiceId";
      leaf ulServiceId {
        type leafref {
          path "../attributes/ulServiceId";
        }
      }
      container attributes {
        uses UlService-attributes;
      }
    }
  }

  augment "/emael:ManagedElement/GNBDUFunction/UeCC/UlWfPortSwitch" {
    list UlWfPortSwitchUeCfg {
      description "Additional definitions from MOM:min/max-elements:0/8; Uplink waveform and port switch profile used for current UE. Instance UlWfPortSwitchUeCfg=Base is created automatically when parent MO instance is created, unless created manually in same transaction. UeBbProfileUeCfg::ulWfPortSwitchUeCfgRef is automatically set to UlWfPortSwitchUeCfg=Base instance, unless manually set to refer to another MO instance. Precondition: Instance UlWfPortSwitchUeCfg=Base can only be created in same transaction as parent MO instance and cannot be deleted unless parent MO instance is deleted. Other instances can be created and deleted at any time. Maximum 7 UlWfPortSwitchUeCfg instances, with RDN different from Base, can be created under parent MO instance.";
      key "ulWfPortSwitchUeCfgId";
      leaf ulWfPortSwitchUeCfgId {
        type leafref {
          path "../attributes/ulWfPortSwitchUeCfgId";
        }
      }
      container attributes {
        uses UlWfPortSwitchUeCfg-attributes;
      }
    }
  }
  typedef AdjustedPriorityMode {
    type enumeration {
      enum STATIC_PRIO_WITHOUT_POLICING;
      enum STATIC_PRIO_WITH_POLICING;
      enum DYNAMIC_PRIO;
    }
  }
  typedef AdmState {
    type enumeration {
      enum LOCKED;
      enum UNLOCKED;
      enum SHUTTINGDOWN;
    }
  }
  typedef AilgModType {
    type enumeration {
      enum AILG_MOD_QPSK;
      enum AILG_MOD_16QAM;
      enum AILG_MOD_64QAM;
      enum AILG_MOD_256QAM;
    }
  }
  typedef AqmMode {
    type enumeration {
      enum OFF;
      enum MODE1;
      enum MODE2;
    }
  }
  typedef AutoLockAction {
    type enumeration {
      enum NO_LOCK;
      enum IMMEDIATE_LOCK;
      enum SOFT_LOCK;
    }
  }
  typedef AvailStatus {
    type enumeration {
      enum IN_TEST;
      enum FAILED;
      enum POWER_OFF;
      enum OFF_LINE;
      enum OFF_DUTY;
      enum DEPENDENCY;
      enum DEGRADED;
      enum NOT_INSTALLED;
      enum LOG_FULL;
      enum DEPENDENCY_LOCKED;
      enum DEPENDENCY_FAILED;
      enum DEPENDENCY_SHUTTINGDOWN;
      enum DEPENDENCY_RECOVERY;
      enum DEPENDENCY_HOLDING;
    }
  }
  typedef BWPContext {
    type enumeration {
      enum DOWNLINK;
      enum UPLINK;
    }
  }
  typedef BWPSetContext {
    type enumeration {
      enum DL_AND_UL;
      enum DL;
    }
  }
  typedef BackoffMode {
    type enumeration {
      enum AUTO;
      enum OFF;
      enum STATIC;
    }
  }
  typedef BucketSizeDuration {
    type enumeration {
      enum MS_5;
      enum MS_10;
      enum MS_20;
      enum MS_50;
      enum MS_100;
      enum MS_150;
      enum MS_300;
      enum MS_500;
      enum MS_1000;
    }
  }
  typedef CapacityAllocationPolicy {
    type enumeration {
      enum SYSTEM_SELECTED;
      enum CAPACITY_PRIORITIZATION;
      enum CAPACITY_PRIORITIZATION_TDD;
    }
  }
  typedef CbfMacroTaperType {
    type enumeration {
      enum STANDARD;
      enum HIGHEIRP;
      enum HIGHSLS;
    }
  }
  typedef CbrsPriority {
    type enumeration {
      enum NORMAL;
      enum HIGH;
    }
  }
  typedef CellBarred {
    type enumeration {
      enum BARRED;
      enum NOT_BARRED;
    }
  }
  typedef CellBarredReason {
    type enumeration {
      enum MANUAL;
      enum CELL_SOFT_LOCK;
      enum BOOSTER_CARRIER_SLEEP;
    }
  }
  typedef CellReservedForOperator {
    type enumeration {
      enum RESERVED;
      enum NOT_RESERVED;
    }
  }
  typedef CgSwitchMode {
    type enumeration {
      enum DISABLED;
      enum ENABLED;
    }
  }
  typedef ConfiguredGrantConfMode {
    type enumeration {
      enum CELL_CG_PERIODICITY;
      enum CG_PROFILE_CG_PERIODICITY;
    }
  }
  typedef ConfiguredGrantMode {
    type enumeration {
      enum DEACTIVATED;
      enum SINGLE;
    }
  }
  typedef CoverageShape {
    type enumeration {
      enum PRODUCT_DEFAULT;
      enum MACRO_1;
      enum HIGHRISE_1;
      enum HOTSPOT_1;
      enum MACRO_120_20;
      enum HOTSPOT_120_30;
      enum MACRO_120_15;
      enum STREET_COVERAGE_1;
      enum STREET_HOTSPOT_1;
      enum STREET_HOTSPOT_WIDE_1;
      enum FLEXIBLE_COVERAGE_1;
      enum MACRO_WIDE_1;
    }
  }
  typedef CreatedBy {
    type enumeration {
      enum SYSTEM;
      enum OPERATOR;
    }
  }
  typedef CsiBufferThresh {
    type enumeration {
      enum OFF;
      enum LOW;
      enum MEDIUM;
      enum HIGH;
    }
  }
  typedef CsiReportFormat {
    type enumeration {
      enum CQI_WB_PMI_WB;
      enum CQI_WB_PMI_SB;
      enum CQI_SB_PMI_WB;
      enum CQI_SB_PMI_SB;
    }
  }
  typedef CsiRptPeriodAdd {
    type enumeration {
      enum OFF;
      enum LOW;
      enum HIGH;
    }
  }
  typedef CsiRsActivePortConfig {
    type enumeration {
      enum PORT_2;
      enum PORT_4;
      enum PORT_8;
      enum PORT_16;
      enum PORT_32;
    }
  }
  typedef CsiRsControl16Ports {
    type enumeration {
      enum OFF;
      enum EIGHT_ONE_N1AZ;
      enum FOUR_TWO_N1AZ;
      enum FOUR_TWO_N1EL;
    }
  }
  typedef CsiRsControl2Ports {
    type enumeration {
      enum OFF;
      enum ON;
    }
  }
  typedef CsiRsControl32Ports {
    type enumeration {
      enum OFF;
      enum EIGHT_TWO_N1AZ;
      enum FOUR_FOUR;
    }
  }
  typedef CsiRsControl4Ports {
    type enumeration {
      enum OFF;
      enum TWO_ONE;
    }
  }
  typedef CsiRsControl8Ports {
    type enumeration {
      enum OFF;
      enum FOUR_ONE_N1AZ;
      enum FOUR_ONE_N1EL;
      enum TWO_TWO;
    }
  }
  typedef CsiRsResourceShifting {
    type enumeration {
      enum DEACTIVATED;
      enum ACTIVATED_AUTOMATIC;
    }
  }
  typedef CtsFeatureState {
    type enumeration {
      enum __UNDEFINED__;
    }
  }
  typedef DayOfWeek {
    type enumeration {
      enum ALL;
      enum MONDAY;
      enum TUESDAY;
      enum WEDNESDAY;
      enum THURSDAY;
      enum FRIDAY;
      enum SATURDAY;
      enum SUNDAY;
    }
  }
  typedef DlCaSchedulingMode {
    type enumeration {
      enum UNLIMITED;
      enum PCELL_ONLY;
    }
  }
  typedef DlCalibrationMethod {
    type enumeration {
      enum NONE;
      enum INTERNAL;
    }
  }
  typedef DlCalibrationStatus {
    type enumeration {
      enum INACTIVE;
      enum CONVERGING;
      enum CALIBRATED;
      enum FAILED;
    }
  }
  typedef DlChannelScramblingIdentity {
    type enumeration {
      enum PCI;
      enum GENERATED;
    }
  }
  typedef DlMuMimoMode {
    type enumeration {
      enum __UNDEFINED__;
    }
  }
  typedef DlSmallDataRobustnessMode {
    type enumeration {
      enum OFF;
      enum ON;
    }
  }
  typedef DlUlSwitchingPeriod {
    type enumeration {
      enum MS0P5;
      enum MS0P625;
      enum MS1;
      enum MS1P25;
      enum MS2;
      enum MS2P5;
      enum MS3;
      enum MS4;
      enum MS5;
      enum MS10;
      enum MS20;
    }
  }
  typedef DrbOverloadHandling {
    type enumeration {
      enum BASIC;
      enum REJECT;
    }
  }
  typedef DrxInactivityTimer {
    type enumeration {
      enum INACTIVITYTIMER_0MS;
      enum INACTIVITYTIMER_1MS;
      enum INACTIVITYTIMER_2MS;
      enum INACTIVITYTIMER_3MS;
      enum INACTIVITYTIMER_4MS;
      enum INACTIVITYTIMER_5MS;
      enum INACTIVITYTIMER_6MS;
      enum INACTIVITYTIMER_8MS;
      enum INACTIVITYTIMER_10MS;
      enum INACTIVITYTIMER_20MS;
      enum INACTIVITYTIMER_30MS;
      enum INACTIVITYTIMER_40MS;
      enum INACTIVITYTIMER_50MS;
      enum INACTIVITYTIMER_60MS;
      enum INACTIVITYTIMER_80MS;
      enum INACTIVITYTIMER_100MS;
      enum INACTIVITYTIMER_200MS;
      enum INACTIVITYTIMER_300MS;
      enum INACTIVITYTIMER_500MS;
      enum INACTIVITYTIMER_750MS;
      enum INACTIVITYTIMER_1280MS;
      enum INACTIVITYTIMER_1920MS;
      enum INACTIVITYTIMER_2560MS;
    }
  }
  typedef DrxLongCycle {
    type enumeration {
      enum LONGCYCLE_10MS;
      enum LONGCYCLE_20MS;
      enum LONGCYCLE_32MS;
      enum LONGCYCLE_40MS;
      enum LONGCYCLE_60MS;
      enum LONGCYCLE_64MS;
      enum LONGCYCLE_70MS;
      enum LONGCYCLE_80MS;
      enum LONGCYCLE_128MS;
      enum LONGCYCLE_160MS;
      enum LONGCYCLE_256MS;
      enum LONGCYCLE_320MS;
      enum LONGCYCLE_512MS;
      enum LONGCYCLE_640MS;
      enum LONGCYCLE_1024MS;
      enum LONGCYCLE_1280MS;
      enum LONGCYCLE_2048MS;
      enum LONGCYCLE_2560MS;
      enum LONGCYCLE_5120MS;
      enum LONGCYCLE_10240MS;
    }
  }
  typedef DrxOnDurationTimer {
    type enumeration {
      enum ONDURATIONTIMER_1SUBMS;
      enum ONDURATIONTIMER_2SUBMS;
      enum ONDURATIONTIMER_3SUBMS;
      enum ONDURATIONTIMER_4SUBMS;
      enum ONDURATIONTIMER_5SUBMS;
      enum ONDURATIONTIMER_6SUBMS;
      enum ONDURATIONTIMER_7SUBMS;
      enum ONDURATIONTIMER_8SUBMS;
      enum ONDURATIONTIMER_9SUBMS;
      enum ONDURATIONTIMER_10SUBMS;
      enum ONDURATIONTIMER_11SUBMS;
      enum ONDURATIONTIMER_12SUBMS;
      enum ONDURATIONTIMER_13SUBMS;
      enum ONDURATIONTIMER_14SUBMS;
      enum ONDURATIONTIMER_15SUBMS;
      enum ONDURATIONTIMER_16SUBMS;
      enum ONDURATIONTIMER_17SUBMS;
      enum ONDURATIONTIMER_18SUBMS;
      enum ONDURATIONTIMER_19SUBMS;
      enum ONDURATIONTIMER_20SUBMS;
      enum ONDURATIONTIMER_21SUBMS;
      enum ONDURATIONTIMER_22SUBMS;
      enum ONDURATIONTIMER_23SUBMS;
      enum ONDURATIONTIMER_24SUBMS;
      enum ONDURATIONTIMER_25SUBMS;
      enum ONDURATIONTIMER_26SUBMS;
      enum ONDURATIONTIMER_27SUBMS;
      enum ONDURATIONTIMER_28SUBMS;
      enum ONDURATIONTIMER_29SUBMS;
      enum ONDURATIONTIMER_30SUBMS;
      enum ONDURATIONTIMER_31SUBMS;
      enum ONDURATIONTIMER_1MS;
      enum ONDURATIONTIMER_2MS;
      enum ONDURATIONTIMER_3MS;
      enum ONDURATIONTIMER_4MS;
      enum ONDURATIONTIMER_5MS;
      enum ONDURATIONTIMER_6MS;
      enum ONDURATIONTIMER_8MS;
      enum ONDURATIONTIMER_10MS;
      enum ONDURATIONTIMER_20MS;
      enum ONDURATIONTIMER_30MS;
      enum ONDURATIONTIMER_40MS;
      enum ONDURATIONTIMER_50MS;
      enum ONDURATIONTIMER_60MS;
      enum ONDURATIONTIMER_80MS;
      enum ONDURATIONTIMER_100MS;
      enum ONDURATIONTIMER_200MS;
      enum ONDURATIONTIMER_300MS;
      enum ONDURATIONTIMER_400MS;
      enum ONDURATIONTIMER_500MS;
      enum ONDURATIONTIMER_600MS;
      enum ONDURATIONTIMER_800MS;
      enum ONDURATIONTIMER_1000MS;
      enum ONDURATIONTIMER_1200MS;
      enum ONDURATIONTIMER_1600MS;
    }
  }
  typedef EdrxMode {
    type enumeration {
      enum DISABLED;
      enum IDLE;
    }
  }
  typedef EnergyOptPwrAllocCellMode {
    type enumeration {
      enum DISABLED;
      enum ENABLED;
    }
  }
  typedef EnergyOptPwrAllocMode {
    type enumeration {
      enum DISABLED;
      enum ENABLED;
    }
  }
  typedef EnergyOptSchedMode {
    type enumeration {
      enum __UNDEFINED__;
    }
  }
  typedef EnergyOptSchedOffset {
    type enumeration {
      enum __UNDEFINED__;
    }
  }
  typedef EnergyOptSymAllocMode {
    type enumeration {
      enum DISABLED;
      enum ENABLED;
    }
  }
  typedef EnoughNotEnoughIndication {
    type enumeration {
      enum DISABLED;
      enum ENABLED;
    }
  }
  typedef EssMbsfnSubframeVariant {
    type enumeration {
      enum NSA_BASIC;
      enum SA_BASIC;
      enum SA_SIB_ROBUST_15_PERCENT;
      enum NSA_25_PERCENT;
      enum SA_25_PERCENT;
      enum NSA_SA_35_PERCENT;
      enum NSA_SA_45_PERCENT;
      enum NSA_SA_55_PERCENT;
    }
  }
  typedef EssPdschEarlyStartConfig {
    type enumeration {
      enum NO_PDSCH_EARLY_START;
      enum ADAPT_MIN_SECOND;
    }
  }
  typedef EssResourceAllocationMode {
    type enumeration {
      enum SCHED_POLICY;
      enum DEMAND_WEIGHTED_RP;
    }
  }
  typedef FddTddUlDlPatternType {
    type enumeration {
      enum TDD_ULDL_PATTERN_00;
      enum TDD_ULDL_PATTERN_01;
      enum TDD_ULDL_PATTERN_02;
      enum TDD_ULDL_PATTERN_03;
      enum TDD_ULDL_PATTERN_04;
      enum TDD_ULDL_PATTERN_05;
      enum TDD_ULDL_PATTERN_06;
      enum TDD_ULDL_PATTERN_07;
      enum TDD_ULDL_PATTERN_08;
      enum FDD;
    }
  }
  typedef FixWideBeamsForPeriodicSrType {
    type enumeration {
      enum FIX_WB_FOR_PERIODIC_SR_NONE;
      enum FIX_WB_FOR_PERIODIC_SR_LOW;
      enum FIX_WB_FOR_PERIODIC_SR_MEDIUM;
      enum FIX_WB_FOR_PERIODIC_SR_HIGH;
    }
  }
  typedef HarqMode {
    type enumeration {
      enum HARQ_NORMAL;
      enum HARQ_VONR;
      enum HARQ_ROBUST;
    }
  }
  typedef IntMitigationDlSched {
    type enumeration {
      enum DEACTIVATED;
      enum PM_ONLY;
      enum ACTIVATED;
    }
  }
  typedef InterfaceName {
    type enumeration {
      enum C5;
      enum E1;
      enum E6;
      enum F1;
      enum NG;
      enum S1;
      enum XN;
      enum X2;
    }
  }
  typedef IpnMeasurementStatus {
    type enumeration {
      enum BRANCH_INVALID_OR_DISABLED;
      enum BRANCH_ENABLED_BUT_NOT_USED;
      enum INACTIVE;
      enum ACTIVE;
    }
  }
  typedef L4sMode {
    type enumeration {
      enum DISABLED;
      enum QUEUE_BASED;
    }
  }
  typedef LinkActive {
    type enumeration {
      enum NOT_ACTIVE;
      enum ACTIVE;
    }
  }
  typedef LinkAdaptationMode {
    type enumeration {
      enum GENERAL;
      enum ROBUST_BASIC;
      enum ROBUST_HIGH;
      enum CUSTOM;
      enum ROBUST_MCS;
    }
  }
  typedef MassiveMimoSleepEnabled {
    type enumeration {
      enum DISABLED;
      enum ENABLED;
      enum DETECTION;
    }
  }
  typedef MassiveMimoSleepMode {
    type enumeration {
      enum TXMUTE;
      enum ECO;
    }
  }
  typedef MassiveMimoSleepState {
    type enumeration {
      enum DEACTIVATED;
      enum TXMUTE;
      enum ECO;
      enum ECO_PENDING;
    }
  }
  typedef MaxUeSpeed {
    type enumeration {
      enum UP_TO_10KMPH;
      enum UP_TO_50KMPH;
      enum UP_TO_100KMPH;
      enum UP_TO_200KMPH;
      enum UP_TO_350KMPH;
      enum UP_TO_500KMPH;
    }
  }
  typedef McsTable {
    type enumeration {
      enum QAM64;
      enum QAM256;
      enum LOW_SE_QAM64;
    }
  }
  typedef MeasGapUseCase {
    type enumeration {
      enum OFF;
      enum EUTRAN_3MS;
      enum NR_FR1_3MS;
      enum ALL_3MS;
    }
  }
  typedef ModulationOrder {
    type enumeration {
      enum QAM_64;
      enum QAM_256;
    }
  }
  typedef NRCellServiceState {
    type enumeration {
      enum OUT_OF_SERVICE;
      enum IN_SERVICE;
    }
  }
  typedef NRCellState {
    type enumeration {
      enum IDLE;
      enum INACTIVE;
      enum ACTIVE;
    }
  }
  typedef NRSectorCarrierAcsAction {
    type enumeration {
      enum NO_ACTION;
      enum SC_AND_CELL_RESTART;
    }
  }
  typedef NValue {
    type enumeration {
      enum T;
      enum T1_2;
      enum T1_4;
      enum T1_8;
      enum T1_16;
    }
  }
  typedef NearFarIndication {
    type enumeration {
      enum DISABLED;
      enum ENABLED;
    }
  }
  typedef NullSteeringMode {
    type enumeration {
      enum ALL;
      enum COMMON_BEAMFORMING;
      enum CSI_RS_MAPPING;
    }
  }
  typedef NullWidth {
    type enumeration {
      enum NARROW;
      enum MEDIUM;
      enum WIDE;
    }
  }
  typedef OperState {
    type enumeration {
      enum DISABLED;
      enum ENABLED;
    }
  }
  typedef PagingPriority {
    type enumeration {
      enum OFF;
      enum PRIO_LEVEL_1;
      enum PRIO_LEVEL_2;
      enum PRIO_LEVEL_3;
      enum PRIO_LEVEL_4;
      enum PRIO_LEVEL_5;
      enum PRIO_LEVEL_6;
      enum PRIO_LEVEL_7;
      enum PRIO_LEVEL_8;
    }
  }
  typedef PdcchBeamOptMode {
    type enumeration {
      enum OFF;
      enum SLOW;
      enum NORMAL;
      enum FAST;
    }
  }
  typedef PdcchLaOlaType {
    type enumeration {
      enum NO_OLA;
      enum PDSCH_OLA;
    }
  }
  typedef PdcchSymbConfig {
    type enumeration {
      enum MINIMUM;
      enum STATIC_2;
      enum ADAPT_MAX_2;
      enum ADAPT_MAX_3;
      enum STATIC_3;
    }
  }
  typedef PimAvoidLevel {
    type enumeration {
      enum DISABLED;
      enum LOW;
      enum MEDIUM;
      enum HIGH;
    }
  }
  typedef PimAvoidanceModeStatus {
    type enumeration {
      enum AGGRESSOR;
      enum VICTIM;
      enum AGGRESSOR_VICTIM;
    }
  }
  typedef PrefSrPeriodicityPool {
    type enumeration {
      enum SR_PERIODICITY_POOL_1;
      enum SR_PERIODICITY_POOL_2;
      enum SR_PERIODICITY_POOL_3;
      enum SR_PERIODICITY_POOL_4;
      enum SR_PERIODICITY_POOL_5;
    }
  }
  typedef PreschedulingMode {
    type enumeration {
      enum DISABLE;
      enum BASIC;
      enum HIGH_PRIORITY;
      enum DEFAULT;
    }
  }
  typedef PrioritisedBitRate {
    type enumeration {
      enum KBPS_0;
      enum KBPS_8;
      enum KBPS_16;
      enum KBPS_32;
      enum KBPS_64;
      enum KBPS_128;
      enum KBPS_256;
      enum KBPS_512;
      enum KBPS_1024;
      enum KBPS_2048;
      enum KBPS_4096;
      enum KBPS_8192;
      enum KBPS_16384;
      enum KBPS_32768;
      enum KBPS_65536;
      enum INFINITY;
    }
  }
  typedef PriorityShiftLevel {
    type enumeration {
      enum LOW;
      enum HIGH;
    }
  }
  typedef PuschModeOnFddSCell {
    type enumeration {
      enum LONG;
      enum SHORT_SRS_CONSEC_SL_OVERLAP;
      enum SHORT_SRS_OVERLAP;
      enum SHORT_CONSEC_SL_OVERLAP;
    }
  }
  typedef PuschPowerControlMode {
    type enumeration {
      enum OLPC;
      enum POWER_BASED_CLPC;
    }
  }
  typedef PuschRepDrxModeType {
    type enumeration {
      enum ACTIVE;
      enum FORCED;
    }
  }
  typedef PuschRepModeType {
    type enumeration {
      enum NOT_ALLOWED;
      enum DYNAMIC;
    }
  }
  typedef QueueRrcRequestMode {
    type enumeration {
      enum __UNDEFINED__;
    }
  }
  typedef RachPreambleFormatType {
    type enumeration {
      enum RACH_PREAMBLE_FORMAT_00;
      enum RACH_PREAMBLE_FORMAT_01;
      enum RACH_PREAMBLE_FORMAT_02;
      enum RACH_PREAMBLE_FORMAT_03;
      enum RACH_PREAMBLE_FORMAT_04;
    }
  }
  typedef RachRestrictedSetConfig {
    type enumeration {
      enum UNRESTRICTED_SET;
      enum RESTRICTED_SET_TYPE_A;
      enum RESTRICTED_SET_TYPE_B;
    }
  }
  typedef RadioOperatingModeEnhanced {
    type enumeration {
      enum COVERAGE;
      enum CAPACITY;
      enum COVERAGE_GREEN;
      enum CAPACITY_GREEN;
    }
  }
  typedef RedCapUeLimit {
    type enumeration {
      enum NONE;
      enum BASIC;
      enum ADVANCED;
      enum MAXIMUM;
    }
  }
  typedef RelativePriorityMode {
    type enumeration {
      enum RP_ONLY;
      enum PDB_ONLY;
      enum RP_AND_PDB;
    }
  }
  typedef ResourceAllocationType {
    type enumeration {
      enum RESOURCE_ALLOCATION_TYPE_0;
      enum DYNAMIC_SWITCH_FB_TYPE_0;
      enum RESOURCE_ALLOCATION_TYPE_1;
      enum DYNAMIC_SWITCH_FB_TYPE_1;
    }
  }
  typedef ResourceControlLevel {
    type enumeration {
      enum LEVEL_0;
      enum LEVEL_1;
      enum LEVEL_2;
      enum LEVEL_3;
      enum LEVEL_4;
      enum LEVEL_5;
    }
  }
  typedef ResourceLimitMode {
    type enumeration {
      enum NO_LIMIT;
      enum LIMITED;
      enum LIMITED_TO_CELL_LIMIT;
    }
  }
  typedef RimPdschSlotBlankMode {
    type enumeration {
      enum DISABLED;
      enum AUTO_MODE;
      enum SPECIAL_SLOT;
      enum SPECIAL_DL_SLOT;
      enum AUTO_RS1;
      enum AUTO_RS1_PC;
      enum SPECIAL_2DL_SLOT;
    }
  }
  typedef RimSetType {
    type enumeration {
      enum RS_1;
      enum RS_2;
    }
  }
  typedef RimSlopeFrontSymIndex {
    type enumeration {
      enum SS_LAST_UL;
      enum SS_2LAST_UL;
      enum SS_3LAST_UL;
      enum SS_4LAST_UL;
      enum UL1_FRONT_DMRS;
      enum UL1_END_DMRS;
      enum UL2_FRONT_DMRS;
    }
  }
  typedef RlcAckPduDelayMode {
    type enumeration {
      enum NO_DELAY;
      enum VERY_LOW;
      enum LOW;
      enum BALANCED;
      enum HIGH;
    }
  }
  typedef RrpControllerMode {
    type enumeration {
      enum NO_AUTO_CONTROL;
      enum AUTO_CONTROL_1;
      enum AUTO_CONTROL_2;
    }
  }
  typedef RrpOperation {
    type enumeration {
      enum BALANCED;
      enum FAIRNESS_FAVORED;
    }
  }
  typedef RrpSchedulingPriority {
    type enumeration {
      enum DEMOTED_NORMAL;
      enum DEMOTED_LOW;
    }
  }
  typedef SchedulingAlgorithm {
    type enumeration {
      enum RESOURCE_FAIR;
      enum PRIORITIZED_RATE;
      enum SOFT_RATE_THROTTLING;
      enum ELEVATION_TIME;
      enum LATENCY_PRIORITIZED;
      enum LATENCY_PRIORITIZED_TCC;
    }
  }
  typedef SetIdAllocation {
    type enumeration {
      enum G_NODE_B;
      enum CELL;
    }
  }
  typedef ShareAdjustmentMode {
    type enumeration {
      enum ABSOLUTE;
      enum GENERAL_COMPENSATION;
    }
  }
  typedef ShareInheritance {
    type enumeration {
      enum NONE;
      enum HIERARCHICAL;
    }
  }
  typedef SiBroadcastStatus {
    type enumeration {
      enum BROADCASTING;
    }
  }
  typedef SrGrantSizeMode {
    type enumeration {
      enum STATIC;
      enum ADAPTIVE;
    }
  }
  typedef SrGrantSizeOpt {
    type enumeration {
      enum THROUGHPUT_OPTIMIZED;
      enum BALANCED;
      enum RESOURCE_OPTIMIZED;
    }
  }
  typedef SrHandlingMode {
    type enumeration {
      enum DISABLED;
      enum SR_PRIO_5QI;
    }
  }
  typedef SrMode {
    type enumeration {
      enum __UNDEFINED__;
    }
  }
  typedef SrPeriodicityValue {
    type enumeration {
      enum SR_PERIODICITY_SYM2;
      enum SR_PERIODICITY_SYM6_OR_7;
      enum SR_PERIODICITY_SL1;
      enum SR_PERIODICITY_SL2;
      enum SR_PERIODICITY_SL4;
      enum SR_PERIODICITY_SL5;
      enum SR_PERIODICITY_SL8;
      enum SR_PERIODICITY_SL10;
      enum SR_PERIODICITY_SL16;
      enum SR_PERIODICITY_SL20;
      enum SR_PERIODICITY_SL40;
      enum SR_PERIODICITY_SL80;
      enum SR_PERIODICITY_SL160;
      enum SR_PERIODICITY_SL320;
      enum SR_PERIODICITY_SL640;
    }
  }
  typedef SrbToConfGrantMapType {
    type enumeration {
      enum UNRESTRICTED;
      enum NOT_ALLOWED;
    }
  }
  typedef SrsHoppingBandwidth {
    type enumeration {
      enum FULL;
      enum HALF;
    }
  }
  typedef SrsImpactHandling {
    type enumeration {
      enum DISABLED;
      enum ENABLED;
    }
  }
  typedef SrsSymbolCombSelectionMode {
    type enumeration {
      enum DEFAULT;
      enum COMMON;
    }
  }
  typedef SrsUeMode {
    type enumeration {
      enum __UNDEFINED__;
    }
  }
  typedef SsbBeams {
    type enumeration {
      enum PRODUCT_DEFAULT;
      enum SSB_BEAMS_12;
      enum SSB_BEAMS_24;
      enum SSB_BEAMS_4;
      enum SSB_BEAMS_6;
      enum SSB_BEAMS_8;
    }
  }
  typedef StartPrbStrategy {
    type enumeration {
      enum START_LOWER_EDGE;
      enum START_HIGHER_EDGE;
      enum RANDOM_START_LOWER_OR_HIGHER;
      enum RANDOM_START_WITHIN_BAND;
    }
  }
  typedef TddBorderVersion {
    type enumeration {
      enum DISABLED;
      enum VERSION_1;
    }
  }
  typedef TddSpecialSlotPatternType {
    type enumeration {
      enum TDD_SPECIAL_SLOT_PATTERN_00;
      enum TDD_SPECIAL_SLOT_PATTERN_01;
      enum TDD_SPECIAL_SLOT_PATTERN_02;
      enum TDD_SPECIAL_SLOT_PATTERN_03;
      enum TDD_SPECIAL_SLOT_PATTERN_04;
      enum TDD_SPECIAL_SLOT_PATTERN_05;
      enum TDD_SPECIAL_SLOT_PATTERN_06;
      enum TDD_SPECIAL_SLOT_PATTERN_07;
    }
  }
  typedef TddUlDlPatternType {
    type enumeration {
      enum TDD_ULDL_PATTERN_00;
      enum TDD_ULDL_PATTERN_01;
      enum TDD_ULDL_PATTERN_02;
      enum TDD_ULDL_PATTERN_03;
      enum TDD_ULDL_PATTERN_04;
      enum TDD_ULDL_PATTERN_05;
      enum TDD_ULDL_PATTERN_06;
      enum TDD_ULDL_PATTERN_07;
      enum TDD_ULDL_PATTERN_08;
    }
  }
  typedef TermPointType {
    type enumeration {
      enum __UNDEFINED__;
    }
  }
  typedef TrafficCategory {
    type enumeration {
      enum SA;
      enum ENDC;
    }
  }
  typedef TrsConfigMode {
    type enumeration {
      enum AUTO;
      enum FULL_BW;
      enum PRB_52;
      enum FULL_BW_MUTE;
    }
  }
  typedef TrsResourceShifting {
    type enumeration {
      enum DEACTIVATED;
      enum ACTIVATED;
    }
  }
  typedef TxDirection {
    type enumeration {
      enum DL_AND_UL;
      enum DL;
    }
  }
  typedef TxPowerState {
    type enumeration {
      enum INVALID;
      enum STABLE;
      enum CHANGING;
    }
  }
  typedef UeAdaptiveRlcRetxMode {
    type enumeration {
      enum ENABLED;
      enum DISABLED;
    }
  }
  typedef UeAmbrMethod {
    type enumeration {
      enum __UNDEFINED__;
    }
  }
  typedef UeAmbrRestRateType {
    type enumeration {
      enum __UNDEFINED__;
    }
  }
  typedef UeAssistedPrecodingOptStatus {
    type enumeration {
      enum INACTIVE;
      enum ACTIVE_NO_UPDATE;
      enum ACTIVE_FAILED;
      enum ACTIVE_CALIBRATED;
      enum ACTIVE_CALIBRATED_UPDATING;
    }
  }
  typedef UeConfGroupType {
    type enumeration {
      enum UE_MOBILITY_GROUP;
      enum UE_SERVICE_GROUP;
      enum UE_ADMISSION_GROUP;
    }
  }
  typedef UeSpecificDrxMode {
    type enumeration {
      enum ENABLED;
      enum DISABLED;
    }
  }
  typedef UlCaTimeAlignmentMode {
    type enumeration {
      enum N_TA_O_STANDARD;
      enum N_TA_O_39936;
    }
  }
  typedef UlCalibrationMethod {
    type enumeration {
      enum NONE;
      enum INTERNAL;
    }
  }
  typedef UlCalibrationStatus {
    type enumeration {
      enum INACTIVE;
      enum CONVERGING;
      enum CALIBRATED;
      enum FAILED;
    }
  }
  typedef UlPacketPredictionMode {
    type enumeration {
      enum DEACTIVATED;
      enum BASIC;
    }
  }
  typedef UlPimCancellationMode {
    type enumeration {
      enum EXCLUDED;
      enum DEACTIVATED;
      enum ACTIVATED;
    }
  }
  typedef UlPortLayerSwitchMetric {
    type enumeration {
      enum UL_WB_SINR;
      enum UL_SINR_MAX;
      enum UL_SINR_MIN;
    }
  }
  typedef UlPortSwitchFr1Mode {
    type enumeration {
      enum PORT_FIXED_PC_DIFF;
      enum PORT_SWITCHED;
      enum PORT_SWITCHED_ONLY_PC1_5;
      enum PORT_SWITCHED_INIT_2_PORT;
    }
  }
  typedef UlWfSwitchFr1Mode {
    type enumeration {
      enum CP_OFDM_NOSWITCH;
      enum DFTS_OFDM_NOSWITCH;
      enum WAVEFORM_SWITCH;
    }
  }
  typedef WeightOffset {
    type enumeration {
      enum ZERO;
      enum LOW;
      enum MEDIUM;
      enum HIGH;
    }
  }
  grouping AdditionalPLMNInfo-attributes {
    leaf additionalPLMNInfoId {
      type string;
      mandatory true;
    }
    leaf cellReservedForOperator {
      type enumeration {
        enum RESERVED;
        enum NOT_RESERVED;
      }
    }
    leaf nRTAC {
      type eytypes:int32_range_0-16777215;
      mandatory true;
      description "range 0..16777215.";
    }
    leaf nRTACInSib1Enabled {
      type boolean;
    }
    list pLMNIdList {
      key "id";
      leaf id {
        type uint32;
        description "Synthetic key for struct sequence entry.";
      }
      ordered-by user;
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
  }
  grouping AdmissionControl-attributes {
    leaf admissionControlId {
      type string;
      mandatory true;
    }
    leaf admissionPrioThreshold {
      type eytypes:int32_range_1-12;
      default "1";
      description "range 1..12; Default value: 1.";
    }
    leaf pagingPrioThreshold {
      type enumeration {
        enum OFF;
        enum PRIO_LEVEL_1;
        enum PRIO_LEVEL_2;
        enum PRIO_LEVEL_3;
        enum PRIO_LEVEL_4;
        enum PRIO_LEVEL_5;
        enum PRIO_LEVEL_6;
        enum PRIO_LEVEL_7;
        enum PRIO_LEVEL_8;
      }
    }
    leaf rrcEmergencyPrio {
      type eytypes:int32_range_1-12;
      default "12";
      description "range 1..12; Default value: 12.";
    }
    leaf rrcHighPriorityAccessPrio {
      type eytypes:int32_range_1-12;
      default "12";
      description "range 1..12; Default value: 12.";
    }
    leaf rrcMcsPriorityAccessPrio {
      type eytypes:int32_range_1-12;
      default "12";
      description "range 1..12; Default value: 12.";
    }
    leaf rrcMoDataPrio {
      type eytypes:int32_range_1-12;
      default "12";
      description "range 1..12; Default value: 12.";
    }
    leaf rrcMoSignalingPrio {
      type eytypes:int32_range_1-12;
      default "12";
      description "range 1..12; Default value: 12.";
    }
    leaf rrcMoSmsPrio {
      type eytypes:int32_range_1-12;
      default "12";
      description "range 1..12; Default value: 12.";
    }
    leaf rrcMoVideoCallPrio {
      type eytypes:int32_range_1-12;
      default "12";
      description "range 1..12; Default value: 12.";
    }
    leaf rrcMoVoiceCallPrio {
      type eytypes:int32_range_1-12;
      default "12";
      description "range 1..12; Default value: 12.";
    }
    leaf rrcMpsPriorityAccessPrio {
      type eytypes:int32_range_1-12;
      default "12";
      description "range 1..12; Default value: 12.";
    }
    leaf rrcMtAccessPrio {
      type eytypes:int32_range_1-12;
      default "12";
      description "range 1..12; Default value: 12.";
    }
    leaf rrcReestablishmentPrio {
      type eytypes:int32_range_1-12;
      default "1";
      description "range 1..12; Default value: 1.";
    }
    leaf rrcRnaUpdatePrio {
      type eytypes:int32_range_1-12;
      default "12";
      description "range 1..12; Default value: 12.";
    }
  }
  grouping Aes-attributes {
    leaf aesEnabled {
      type boolean;
      default "false";
      description "Default value: false.";
    }
    leaf aesId {
      type string;
      mandatory true;
    }
    leaf targetUeDlThroughput {
      type int32 {
        range "5 | 10 | 15 | 20 | 30 | 50 | 70 | 100 | 150 | 200 | 300 | 500";
      }
      default "30";
      units "Mbps";
      description "Default value: 30.";
    }
    leaf targetUeRatio {
      type eytypes:int32_range_1-100;
      default "70";
      units "percent";
      description "range 1..100; Default value: 70.";
    }
  }
  grouping AesMMimoSleep-attributes {
    leaf aesActive {
      type boolean;
      config false;
    }
    leaf aesMMimoSleepId {
      type string;
      mandatory true;
    }
    leaf switchDownPrbThreshDl {
      type eytypes:int32_range_0-100;
      config false;
      units "percent";
      description "range 0..100.";
    }
    leaf switchDownRrcConnThresh {
      type eytypes:int32_range_0-5000;
      config false;
      description "range 0..5000.";
    }
    leaf switchUpPrbThreshDl {
      type eytypes:int32_range_0-100;
      config false;
      units "percent";
      description "range 0..100.";
    }
    leaf switchUpRrcConnThresh {
      type eytypes:int32_range_0-5000;
      config false;
      description "range 0..5000.";
    }
  }
  grouping AqmCfg-attributes {
    leaf aqmCfgId {
      type string;
      mandatory true;
    }
    leaf aqmMode {
      type enumeration {
        enum OFF;
        enum MODE1;
        enum MODE2;
      }
    }
    leaf estimatedE2ERTT {
      type eytypes:int32_range_0-1023;
      default "50";
      units "ms";
      description "range 0..1023; Default value: 50.";
    }
    leaf-list reservedBy {
      type string;
    }
    leaf tDiscardDl {
      type int32 {
        range "0..2046";
      }
      default "200";
      units "ms";
      description "range 0..2046; Default value: 200.";
    }
    leaf userLabel {
      type string;
    }
  }
  grouping AutomatedQos-attributes {
    leaf automatedQosId {
      type string;
      mandatory true;
    }
  }
  grouping Beam-attributes {
    leaf beamId {
      type string;
      mandatory true;
    }
    leaf wideBeamIndex {
      type int32;
      config false;
    }
    leaf-list pmRadioSsbRsrpDistr {
      type uint64;
    }
    leaf-list pmRadioSsbSinrPuschDistr {
      type uint64;
    }
    leaf pmRadioRaCbFailMsg1Ooc {
      type uint64;
      config false;
    }
    leaf-list pmRadioSsbSinrPucchF0Distr {
      type uint64;
    }
    leaf-list pmRadioRaAttTaDistr {
      type uint64;
    }
    leaf-list pmRadioSsbSinrPucchF2Distr {
      type uint64;
    }
    leaf-list pmRadioEirpDlDistr {
      type uint64;
    }
  }
  grouping Bsr-attributes {
    leaf bsrId {
      type string;
      mandatory true;
    }
  }
  grouping BsrUeCfg-attributes {
    leaf bsrUeCfgId {
      type string;
      mandatory true;
    }
    leaf-list reservedBy {
      type string;
    }
    leaf reTxBsrTimer {
      type int32 {
        range "10 | 20 | 40 | 80 | 160 | 320 | 640 | 1280 | 2560 | 5120 | 10240";
      }
      default "1280";
      units "subframe";
      description "Default value: 1280.";
    }
    leaf srDelayTimer {
      type int32 {
        range "20 | 40 | 64 | 128 | 512 | 1024 | 2560";
      }
      default "40";
      units "subframe";
      description "Default value: 40.";
    }
    leaf srGrantSize {
      type int32 {
        range "8..8000";
      }
      default "32";
      units "bit";
      description "range 8..8000; Default value: 32.";
    }
    leaf srGrantSizeMode {
      type enumeration {
        enum STATIC;
        enum ADAPTIVE;
      }
    }
    leaf srGrantSizeOpt {
      type enumeration {
        enum THROUGHPUT_OPTIMIZED;
        enum BALANCED;
        enum RESOURCE_OPTIMIZED;
      }
    }
  }
  grouping BWP-attributes {
    leaf bwpContext {
      type enumeration {
        enum DOWNLINK;
        enum UPLINK;
      }
    }
    leaf bWPId {
      type string;
      mandatory true;
    }
    leaf isInitialBwp {
      type boolean;
      default "true";
      description "Default value: true.";
    }
    leaf numberOfRBs {
      type int32 {
        range "24..275";
      }
      default "106";
      units "PRB";
      description "range 24..275; Default value: 106.";
    }
    leaf-list reservedBy {
      type string;
    }
    leaf startRB {
      type int32 {
        range "0..275";
      }
      default "0";
      units "PRB";
      description "range 0..275; Default value: 0.";
    }
    leaf userLabel {
      type string;
    }
  }
  grouping BWPSet-attributes {
    leaf-list allBWPRegularRef {
      type string;
      ordered-by user;
    }
    leaf bwpSetContext {
      type enumeration {
        enum DL_AND_UL;
        enum DL;
      }
    }
    leaf bWPSetId {
      type string;
      mandatory true;
    }
    leaf-list reservedBy {
      type string;
    }
    leaf startBWPDlRef {
      type string;
    }
    leaf startBWPUlRef {
      type string;
    }
    leaf ueConfGroupType {
      type enumeration {
        enum UE_MOBILITY_GROUP;
        enum UE_SERVICE_GROUP;
        enum UE_ADMISSION_GROUP;
      }
    }
    leaf userLabel {
      type string;
    }
  }
  grouping BWPSetCfg-attributes {
    leaf bWPDlRef {
      type string;
      mandatory true;
    }
    leaf bWPSetCfgId {
      type string;
      mandatory true;
    }
    leaf bWPUlRef {
      type string;
    }
    leaf dynPowerOptRef {
      type string;
    }
    leaf userLabel {
      type string;
    }
  }
  grouping BWPSetUeCfg-attributes {
    leaf bWPSetUeCfgId {
      type string;
      mandatory true;
    }
    leaf bwpSwitchingFilterRelaxation {
      type boolean;
      default "false";
      description "Default value: false.";
    }
    leaf-list prefUeGroupList {
      type eytypes:int32_range_1-255;
      ordered-by user;
    }
    leaf-list ueConfGroupList {
      type eytypes:int32_range_1-255;
      ordered-by user;
    }
    leaf-list ueGroupList {
      type eytypes:int32_range_1-255;
      ordered-by user;
    }
    leaf userLabel {
      type string;
    }
  }
  grouping CardinalityLimits-attributes {
    leaf cardinalityLimitsId {
      type string;
      mandatory true;
    }
    leaf maxNRCellDU {
      type int32;
      config false;
    }
    leaf maxNRSectorCarrier {
      type int32;
      config false;
    }
    leaf noOfNRCellDU {
      type int32;
      config false;
    }
    leaf noOfNRSectorCarrier {
      type int32;
      config false;
    }
  }
  grouping CaSCellHandling-attributes {
    leaf caSCellHandlingId {
      type string;
      mandatory true;
    }
    leaf-list reservedBy {
      type string;
    }
    leaf ueConfGroupType {
      type enumeration {
        enum UE_MOBILITY_GROUP;
        enum UE_SERVICE_GROUP;
        enum UE_ADMISSION_GROUP;
      }
    }
  }
  grouping CaSCellHandlingUeCfg-attributes {
    leaf caSCellHandlingUeCfgId {
      type string;
      mandatory true;
    }
    leaf-list prefUeGroupList {
      type eytypes:int32_range_1-255;
      ordered-by user;
    }
    leaf sCellActDeactDataThres {
      type int32 {
        range "-1..5000";
      }
      default "-1";
      units "slot";
      description "range -1..5000; Default value: -1.";
    }
    leaf sCellActDeactDataThresHyst {
      type int32 {
        range "0..5000";
      }
      default "90";
      units "slot";
      description "range 0..5000; Default value: 90.";
    }
    leaf sCellActDeactUlDataThresh {
      type int32 {
        range "-1..5000";
      }
      default "100";
      units "slot";
      description "range -1..5000; Default value: 100.";
    }
    leaf sCellActDeactUlDataThreshHyst {
      type int32 {
        range "0..5000";
      }
      default "90";
      units "slot";
      description "range 0..5000; Default value: 90.";
    }
    leaf sCellActProhibitTimer {
      type eytypes:int32_range_0-5000-5;
      default "10";
      units "ms";
      description "range 0..5000; Default value: 10.";
    }
    leaf sCellDeactDelayTimer {
      type eytypes:int32_range_0-5000-5;
      default "400";
      units "ms";
      description "range 0..5000; Default value: 400.";
    }
    leaf sCellDeactProhibitTimer {
      type eytypes:int32_range_0-5000-5;
      default "500";
      units "ms";
      description "range 0..5000; Default value: 500.";
    }
    leaf-list ueConfGroupList {
      type eytypes:int32_range_1-255;
      ordered-by user;
    }
    leaf-list ueGroupList {
      type eytypes:int32_range_1-255;
      ordered-by user;
    }
    leaf userLabel {
      type string;
    }
  }
  grouping CchLoadProfile-attributes {
    leaf cchLoadProfileId {
      type string;
      mandatory true;
    }
    leaf pdcchBlockingPdschLimit {
      type eytypes:int32_range_0-100;
      default "0";
      units "percent";
      description "range 0..100; Default value: 0.";
    }
    leaf pdcchBlockingPuschLimit {
      type eytypes:int32_range_0-100;
      default "0";
      units "percent";
      description "range 0..100; Default value: 0.";
    }
    leaf-list reservedBy {
      type string;
    }
  }
  grouping CellPortionRd-attributes {
    leaf altitude {
      type int32;
      config false;
      units "m";
    }
    leaf cellPortionRdId {
      type ietfinet:port-number;
      mandatory true;
    }
    leaf fieldReplaceableUnitRef {
      type string;
      config false;
    }
    list floorInformation {
      config false;
      container attributes {
      leaf floorNumber {
        type int32 {
          range "-101..1000";
        }
        description "range -101..1000.";
      }
      leaf heightOfDot {
        type int32 {
          range "-1..500";
        }
        units "m";
        description "range -1..500.";
      }
      }
    }
    leaf latitude {
      type int32;
      config false;
      units "degree";
    }
    leaf longitude {
      type int32;
      config false;
      units "degree";
    }
    leaf nrppaCellPortionId {
      type ietfinet:port-number;
      config false;
    }
    list radioDotCoverage {
      config false;
      container attributes {
      leaf bearing {
        type eytypes:int32_range_0-3599;
        units "degree";
        description "range 0..3599.";
      }
      leaf openingAngle {
        type eytypes:int32_range_0-3599;
        units "degree";
        description "range 0..3599.";
      }
      leaf radius {
        type eytypes:int32_range_1-100000;
        units "m";
        description "range 1..100000.";
      }
      }
    }
  }
  grouping CellPriorityShift-attributes {
    leaf cellDlDrbPriorityLimitBase {
      type eytypes:int32_range_1-100-4;
      default "100";
      description "range 1..100; Default value: 100.";
    }
    leaf cellDlElevationTime {
      type int32 {
        range "10..45";
      }
      default "20";
      units "ms";
      description "range 10..45; Default value: 20.";
    }
    leaf cellDlMaxWaitingTime {
      type int32 {
        range "0 | 200 | 210 | 220 | 230 | 240 | 250 | 260 | 270 | 280 | 290 | 300 | 310 | 320 | 330 | 340 | 350 | 360 | 370 | 380 | 390 | 400 | 410 | 420 | 430 | 440 | 450 | 460 | 470 | 480 | 490 | 500 | 510 | 520 | 530 | 540 | 550 | 560 | 570 | 580 | 590 | 600 | 610 | 620 | 630 | 640 | 650 | 660 | 670 | 680 | 690 | 700 | 710 | 720 | 730 | 740 | 750 | 760 | 770 | 780 | 790 | 800 | 810 | 820 | 830 | 840 | 850 | 860 | 870 | 880 | 890 | 900 | 910 | 920 | 930 | 940 | 950 | 960 | 970 | 980 | 990 | 1000";
      }
      default "0";
      units "ms";
      description "Default value: 0.";
    }
    leaf cellMwtDlElevatedPriority {
      type enumeration {
        enum LOW;
        enum HIGH;
      }
    }
    leaf cellMwtUlElevatedPriority {
      type enumeration {
        enum LOW;
        enum HIGH;
      }
    }
    leaf cellPriorityShiftId {
      type string;
      mandatory true;
    }
    leaf cellUlDrbPriorityLimitBase {
      type eytypes:int32_range_1-100-4;
      default "100";
      description "range 1..100; Default value: 100.";
    }
    leaf cellUlElevationTime {
      type int32 {
        range "10..45";
      }
      default "20";
      units "ms";
      description "range 10..45; Default value: 20.";
    }
    leaf cellUlMaxWaitingTime {
      type int32 {
        range "0 | 200 | 210 | 220 | 230 | 240 | 250 | 260 | 270 | 280 | 290 | 300 | 310 | 320 | 330 | 340 | 350 | 360 | 370 | 380 | 390 | 400 | 410 | 420 | 430 | 440 | 450 | 460 | 470 | 480 | 490 | 500 | 510 | 520 | 530 | 540 | 550 | 560 | 570 | 580 | 590 | 600 | 610 | 620 | 630 | 640 | 650 | 660 | 670 | 680 | 690 | 700 | 710 | 720 | 730 | 740 | 750 | 760 | 770 | 780 | 790 | 800 | 810 | 820 | 830 | 840 | 850 | 860 | 870 | 880 | 890 | 900 | 910 | 920 | 930 | 940 | 950 | 960 | 970 | 980 | 990 | 1000";
      }
      default "0";
      units "ms";
      description "Default value: 0.";
    }
    leaf-list reservedBy {
      type string;
    }
  }
  grouping CellResourceMapping-attributes {
    leaf cellResourceMappingId {
      type string;
      mandatory true;
    }
    leaf-list priorityPartition5qiList {
      type eytypes:int32_range_1-255;
      ordered-by user;
    }
    leaf-list reservedBy {
      type string;
    }
    leaf shareInheritance {
      type enumeration {
        enum NONE;
        enum HIERARCHICAL;
      }
    }
    leaf userLabel {
      type string;
    }
  }
  grouping CgSwitch-attributes {
    leaf cgSwitchId {
      type string;
      mandatory true;
    }
    leaf-list reservedBy {
      type string;
    }
    leaf ueConfGroupType {
      type enumeration {
        enum UE_MOBILITY_GROUP;
        enum UE_SERVICE_GROUP;
        enum UE_ADMISSION_GROUP;
      }
    }
    leaf userLabel {
      type string;
    }
  }
  grouping CgSwitchCfg-attributes {
    leaf cgSwitchCfgId {
      type string;
      mandatory true;
    }
    leaf dlCgSwitchMode {
      type enumeration {
        enum DISABLED;
        enum ENABLED;
      }
    }
    leaf dlScgLowQualHyst {
      type int32 {
        range "0..600";
      }
      default "50";
      units "dB";
      description "range 0..600; Default value: 50.";
    }
    leaf dlScgLowQualThresh {
      type eytypes:int32_range_-400-400;
      default "50";
      units "dB";
      description "range -400..400; Default value: 50.";
    }
    leaf dlScgNoDataAcsiPeriodicity {
      type ietfinet:ip-address;
      units "ms";
      description "range 100..2600; Default value: 300.";
    }
    leaf-list reservedBy {
      type string;
    }
    leaf ulCgSwitchMode {
      type enumeration {
        enum DISABLED;
        enum ENABLED;
      }
    }
    leaf ulScgCritQualHyst {
      type eytypes:int32_range_5-600;
      units "dB";
      description "range 5..600.";
    }
    leaf ulScgCritQualThresh {
      type eytypes:int32_range_-400-1450;
      units "dB";
      description "range -400..1450.";
    }
    leaf ulScgLowQualHyst {
      type eytypes:int32_range_5-600;
      units "dB";
      description "range 5..600.";
    }
    leaf ulScgLowQualThresh {
      type eytypes:int32_range_-400-1450;
      units "dB";
      description "range -400..1450.";
    }
    leaf userLabel {
      type string;
    }
  }
  grouping CgSwitchUeCfg-attributes {
    leaf cgSwitchCfgRef {
      type string;
    }
    leaf cgSwitchUeCfgId {
      type string;
      mandatory true;
    }
    leaf-list prefUeGroupList {
      type eytypes:int32_range_1-255;
      ordered-by user;
    }
    leaf-list ueConfGroupList {
      type eytypes:int32_range_1-255;
      ordered-by user;
    }
    leaf-list ueGroupList {
      type eytypes:int32_range_1-255;
      ordered-by user;
    }
    leaf userLabel {
      type string;
    }
  }
  grouping CommonBeamforming-attributes {
    leaf azimuthCoverageWidth {
      type int32 {
        range "50..1800";
      }
      units "degree";
      description "range 50..1800.";
    }
    leaf cbfMacroTaperType {
      type ietfyang:mac-address;
    }
    leaf commonBeamformingId {
      type string;
      mandatory true;
    }
    leaf coverageShape {
      type enumeration {
        enum PRODUCT_DEFAULT;
        enum MACRO_1;
        enum HIGHRISE_1;
        enum HOTSPOT_1;
        enum MACRO_120_20;
        enum HOTSPOT_120_30;
        enum MACRO_120_15;
        enum STREET_COVERAGE_1;
        enum STREET_HOTSPOT_1;
        enum STREET_HOTSPOT_WIDE_1;
        enum FLEXIBLE_COVERAGE_1;
        enum MACRO_WIDE_1;
      }
    }
    list customComBfwWideBeam {
      key "id";
      leaf id {
        type uint32;
        description "Synthetic key for struct sequence entry.";
      }
      ordered-by user;
      container attributes {
      leaf amplitude {
        type eytypes:int32_range_0-100-3;
        description "range 0..100.";
      }
      leaf antennaNo {
        type eytypes:int32_range_0-63;
        description "range 0..63.";
      }
      leaf phase {
        type int32 {
          range "0..359";
        }
        units "degree";
        description "range 0..359.";
      }
      }
    }
    leaf digitalPan {
      type eytypes:int32_range_-900-900;
      units "degree";
      description "range -900..900.";
    }
    leaf digitalTilt {
      type eytypes:int32_range_-900-900;
      units "degree";
      description "range -900..900.";
    }
    leaf elevationCoverageWidth {
      type int32 {
        range "20..1800";
      }
      units "degree";
      description "range 20..1800.";
    }
    leaf ssbBeams {
      type enumeration {
        enum PRODUCT_DEFAULT;
        enum SSB_BEAMS_12;
        enum SSB_BEAMS_24;
        enum SSB_BEAMS_4;
        enum SSB_BEAMS_6;
        enum SSB_BEAMS_8;
      }
    }
    leaf-list supportedCbfMacroTaperTypes {
      type ietfinet:port-number;
    }
    list supportedCoverageOptions {
      config false;
      container attributes {
      leaf azimuthCoverageWidth {
        type int32 {
          range "50..1800";
        }
        units "degree";
        description "range 50..1800.";
      }
      leaf elevationCbfTaperTypes {
        type string {
          length "1..100";
        }
        description "length 1..100.";
      }
      leaf elevationCoverageWidth {
        type int32 {
          range "20..1800";
        }
        units "degree";
        description "range 20..1800.";
      }
      leaf panRange {
        type string {
          length "1..100";
        }
        description "length 1..100.";
      }
      leaf tiltRange {
        type string {
          length "1..100";
        }
        description "length 1..100.";
      }
      }
    }
    leaf-list supportedCoverageShapes {
      type ietfinet:port-number;
    }
    leaf supportedPanRange {
      type ietfinet:port-number;
      config false;
    }
    leaf supportedTiltRange {
      type ietfinet:port-number;
      config false;
    }
    leaf usedAzimuthCoverageWidth {
      type int32 {
        range "50..1800";
      }
      config false;
      units "degree";
      description "range 50..1800.";
    }
    leaf usedCbfMacroTaperType {
      type ietfyang:mac-address;
      config false;
    }
    leaf usedCoverageShape {
      type enumeration {
        enum PRODUCT_DEFAULT;
        enum MACRO_1;
        enum HIGHRISE_1;
        enum HOTSPOT_1;
        enum MACRO_120_20;
        enum HOTSPOT_120_30;
        enum MACRO_120_15;
        enum STREET_COVERAGE_1;
        enum STREET_HOTSPOT_1;
        enum STREET_HOTSPOT_WIDE_1;
        enum FLEXIBLE_COVERAGE_1;
        enum MACRO_WIDE_1;
      }
      config false;
    }
    leaf usedDigitalPan {
      type int32;
      config false;
    }
    leaf usedDigitalTilt {
      type int32;
      config false;
    }
    leaf usedElevationCoverageWidth {
      type int32 {
        range "20..1800";
      }
      config false;
      units "degree";
      description "range 20..1800.";
    }
    leaf usedSsbBeams {
      type enumeration {
        enum PRODUCT_DEFAULT;
        enum SSB_BEAMS_12;
        enum SSB_BEAMS_24;
        enum SSB_BEAMS_4;
        enum SSB_BEAMS_6;
        enum SSB_BEAMS_8;
      }
      config false;
    }
    leaf userLabel {
      type string;
    }
  }
  grouping ConfiguredGrant-attributes {
    leaf configuredGrantId {
      type string;
      mandatory true;
    }
  }
  grouping ConfiguredGrantUeCfg-attributes {
    leaf configuredGrantDataSize {
      type int32 {
        range "0..10000";
      }
      default "0";
      units "byte";
      description "range 0..10000; Default value: 0.";
    }
    leaf configuredGrantMode {
      type enumeration {
        enum DEACTIVATED;
        enum SINGLE;
      }
    }
    leaf configuredGrantPeriodicity {
      type int32 {
        range "5 | 10 | 20 | 40 | 80 | 160 | 320 | 640 | 1280";
      }
      status deprecated;
      default "10";
      description "Default value: 10; Takes effect: New connection; Status info: Since 25.Q3. Replaced by ulConfiguredGrantPeriodicity. Planned to be removed..";
      reference "Takes effect: New connection.";
    }
    leaf configuredGrantSrbConfig {
      type enumeration {
        enum UNRESTRICTED;
        enum NOT_ALLOWED;
      }
    }
    leaf configuredGrantUeCfgId {
      type string;
      mandatory true;
    }
    leaf-list notAllowed5qiList {
      type eytypes:int32_range_1-255;
      ordered-by user;
    }
    leaf-list reservedBy {
      type string;
    }
    leaf ulConfiguredGrantPeriodicity {
      type int32 {
        range "5 | 10 | 20 | 40 | 80 | 160 | 320";
      }
      default "10";
      description "Default value: 10.";
    }
    leaf userLabel {
      type string;
    }
  }
  grouping ContentionControl-attributes {
    leaf contentionControlId {
      type string;
      mandatory true;
    }
  }
  grouping CsiProfile-attributes {
    leaf csiProfileId {
      type ietfinet:ip-address;
      mandatory true;
    }
  }
  grouping CsiProfileUeCfg-attributes {
    leaf csiBufferThresh {
      type enumeration {
        enum OFF;
        enum LOW;
        enum MEDIUM;
        enum HIGH;
      }
    }
    leaf csiPollRetransmitEnabled {
      type ietfinet:ip-address;
      description "Default value: false.";
    }
    leaf csiProfileUeCfgId {
      type ietfinet:ip-address;
      mandatory true;
    }
    leaf csiRptPeriodAdd {
      type enumeration {
        enum OFF;
        enum LOW;
        enum HIGH;
      }
    }
    leaf-list reservedBy {
      type string;
    }
  }
  grouping DataRadioBearer-attributes {
    leaf dataRadioBearerId {
      type string;
      mandatory true;
    }
    leaf dlMaxRetxThreshold {
      type int32 {
        range "1..4 | 6 | 8 | 16 | 32";
      }
    }
    leaf dlPollPdu {
      type int32 {
        range "4 | 8 | 16 | 32 | 64 | 128 | 256 | 512 | 1024 | 2048 | 4096 | 6144 | 8192 | 12288 | 16384 | 20480 | 24576 | 28672 | 32768 | 40960 | 49152 | 57344 | 65536";
      }
    }
    leaf tPollRetransmitDl {
      type int32 {
        range "5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 2000 | 4000";
      }
      units "ms";
    }
    leaf tPollRetransmitUl {
      type int32 {
        range "5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 2000 | 4000";
      }
      units "ms";
    }
    leaf tStatusProhibitDl {
      type int32 {
        range "0 | 5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 1200 | 1600 | 2000 | 2400";
      }
      units "ms";
    }
    leaf tStatusProhibitUl {
      type int32 {
        range "0 | 5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 1200 | 1600 | 2000 | 2400";
      }
      units "ms";
    }
    leaf ulMaxRetxThreshold {
      type int32 {
        range "1..4 | 6 | 8 | 16 | 32";
      }
    }
    leaf ulPollPdu {
      type int32 {
        range "4 | 8 | 16 | 32 | 64 | 128 | 256 | 512 | 1024 | 2048 | 4096 | 6144 | 8192 | 12288 | 16384 | 20480 | 24576 | 28672 | 32768 | 40960 | 49152 | 57344 | 65536";
      }
    }
  }
  grouping DlBeamOptProfile-attributes {
    leaf dlBeamOptProfileId {
      type string;
      mandatory true;
    }
  }
  grouping DlBeamOptProfileUeCfg-attributes {
    leaf dlBeamOptProfileUeCfgId {
      type string;
      mandatory true;
    }
    leaf pdcchBeamOptMode {
      type enumeration {
        enum OFF;
        enum SLOW;
        enum NORMAL;
        enum FAST;
      }
    }
    leaf-list reservedBy {
      type string;
    }
  }
  grouping DlDelayBasedPriority-attributes {
    leaf dlDelayBasedPriorityId {
      type string;
      mandatory true;
    }
    leaf dlDemotedPriority {
      type enumeration {
        enum LOW;
        enum HIGH;
      }
    }
  }
  grouping DlLatencyBasedPriority-attributes {
    leaf dlDemotedPriority {
      type enumeration {
        enum LOW;
        enum HIGH;
      }
    }
    leaf dlLatencyBasedPriorityId {
      type string;
      mandatory true;
    }
    leaf dlPriorityScaler {
      type eytypes:int32_range_1-8;
      default "1";
      description "range 1..8; Default value: 1.";
    }
    leaf dlPriorityShiftMargin {
      type int32 {
        range "-231..280";
      }
      default "0";
      units "ms";
      description "range -231..280; Default value: 0.";
    }
    leaf dlResourceControlLevel {
      type enumeration {
        enum LEVEL_0;
        enum LEVEL_1;
        enum LEVEL_2;
        enum LEVEL_3;
        enum LEVEL_4;
        enum LEVEL_5;
      }
    }
    leaf dlWeightOffset {
      type enumeration {
        enum ZERO;
        enum LOW;
        enum MEDIUM;
        enum HIGH;
      }
    }
  }
  grouping DlLinkAdaptation-attributes {
    leaf dlBlerTarget {
      type int32 {
        range "1..3000";
      }
      default "1000";
      units "percent";
      description "range 1..3000; Default value: 1000.";
    }
    leaf dlBlerTargetExtended {
      type int32 {
        range "-1 | 1..100";
      }
      default "-1";
      units "percent";
      description "Default value: -1.";
    }
    leaf dlDownStep {
      type eytypes:int32_range_0-100-6;
      default "0";
      units "dB";
      description "range 0..100; Default value: 0.";
    }
    leaf dlLinkAdaptationId {
      type string;
      mandatory true;
    }
    leaf dlMaxMcsIndex {
      type eytypes:int32_range_0-28;
      default "27";
      description "range 0..28; Default value: 27.";
    }
    leaf dlMaxTbs {
      type int32 {
        range "0..65535";
      }
      default "0";
      units "bit";
      description "range 0..65535; Default value: 0.";
    }
    leaf dlSinrBackoff {
      type eytypes:int32_range_0-100-6;
      default "0";
      units "dB";
      description "range 0..100; Default value: 0.";
    }
  }
  grouping DlMimo-attributes {
    leaf dlMimoId {
      type string;
      mandatory true;
    }
  }
  grouping DlMimoUeCfg-attributes {
    leaf dlMimoUeCfgId {
      type string;
      mandatory true;
    }
    leaf-list reservedBy {
      type string;
    }
    leaf srsImpactHandling {
      type enumeration {
        enum DISABLED;
        enum ENABLED;
      }
    }
  }
  grouping DlOuterLoop-attributes {
    leaf dlOuterLoopId {
      type string;
      mandatory true;
    }
    leaf dualOuterLoopEnabled {
      type boolean;
      default "false";
      description "Default value: false.";
    }
    leaf initValMixIpn {
      type ietfinet:ip-address;
      units "dB";
      description "range -400..400; Default value: 0.";
    }
    leaf initValNonMixIpn {
      type ietfinet:ip-address;
      units "dB";
      description "range -400..400; Default value: 0.";
    }
    leaf largeStepMixIpn {
      type ietfinet:ip-address;
      units "dB";
      description "range 0..50; Default value: 10.";
    }
    leaf largeStepNonMixIpn {
      type ietfinet:ip-address;
      units "dB";
      description "range 0..50; Default value: 3.";
    }
    leaf smallDownStep {
      type eytypes:int32_range_0-30;
      default "1";
      units "dB";
      description "range 0..30; Default value: 1.";
    }
  }
  grouping DlRateBasedPriority-attributes {
    leaf dlDemotedPriority {
      type enumeration {
        enum LOW;
        enum HIGH;
      }
    }
    leaf dlDemotedRelativePriority {
      type boolean;
      default "false";
      description "Default value: false.";
    }
    leaf dlDrbOverloadHandling {
      type enumeration {
        enum BASIC;
        enum REJECT;
      }
    }
    leaf dlPrioritizedRate {
      type int32 {
        range "1..10 | 20 | 30 | 40 | 50 | 60 | 70 | 80 | 90 | 100 | 200 | 300 | 400 | 500 | 600 | 700 | 800 | 900 | 1000 | 2000 | 3000 | 4000 | 5000 | 6000 | 7000 | 8000 | 9000 | 10000 | 20000 | 30000 | 40000 | 50000 | 60000 | 70000 | 80000 | 90000 | 100000 | 200000 | 300000 | 400000 | 500000 | 600000 | 700000 | 800000 | 900000 | 1000000";
      }
      default "1";
      units "kbps";
      description "Default value: 1.";
    }
    leaf dlRateBasedPriorityId {
      type string;
      mandatory true;
    }
  }
  grouping DlResourceBasedPriority-attributes {
    leaf dlDrbPriorityLimit {
      type eytypes:int32_range_1-100-4;
      default "100";
      description "range 1..100; Default value: 100.";
    }
    leaf dlResourceBasedPriorityId {
      type string;
      mandatory true;
    }
    leaf dlResourceLimitMode {
      type enumeration {
        enum NO_LIMIT;
        enum LIMITED;
        enum LIMITED_TO_CELL_LIMIT;
      }
    }
  }
  grouping DrbRlc-attributes {
    leaf drbRlcId {
      type string;
      mandatory true;
    }
    leaf-list reservedBy {
      type string;
    }
    leaf ueConfGroupType {
      type enumeration {
        enum UE_MOBILITY_GROUP;
        enum UE_SERVICE_GROUP;
        enum UE_ADMISSION_GROUP;
      }
    }
    leaf userLabel {
      type string;
    }
  }
  grouping DrbRlcUeCfg-attributes {
    leaf dlHighRateTimerSwitchEnabled {
      type boolean;
      default "false";
      description "Default value: false.";
    }
    leaf dlMaxRetxThreshold {
      type int32 {
        range "1..4 | 6 | 8 | 16 | 32";
      }
      default "16";
      description "Default value: 16.";
    }
    leaf dlPollPdu {
      type int32 {
        range "4 | 8 | 16 | 32 | 64 | 128 | 256 | 512 | 1024 | 2048 | 4096 | 6144 | 8192 | 12288 | 16384 | 20480 | 24576 | 28672 | 32768 | 40960 | 49152 | 57344 | 65536";
      }
      default "32";
      description "Default value: 32.";
    }
    leaf drbRlcUeCfgId {
      type string;
      mandatory true;
    }
    leaf-list prefUeGroupList {
      type eytypes:int32_range_1-255;
      ordered-by user;
    }
    leaf rlcAckPduDelayMode {
      type enumeration {
        enum NO_DELAY;
        enum VERY_LOW;
        enum LOW;
        enum BALANCED;
        enum HIGH;
      }
    }
    leaf rlcSNLength {
      type int32 {
        range "6 | 12 | 18";
      }
      default "18";
      units "bit";
      description "Default value: 18.";
    }
    leaf tPollRetransmitDl {
      type int32 {
        range "5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 2000 | 4000";
      }
      default "40";
      units "ms";
      description "Default value: 40.";
    }
    leaf tPollRetransmitUl {
      type int32 {
        range "5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 2000 | 4000";
      }
      default "40";
      units "ms";
      description "Default value: 40.";
    }
    leaf tReassemblyDl {
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200";
      }
      default "25";
      units "ms";
      description "Default value: 25.";
    }
    leaf tReassemblyDlHighRate {
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200";
      }
      default "10";
      units "ms";
      description "Default value: 10.";
    }
    leaf tReassemblyUl {
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200";
      }
      default "25";
      units "ms";
      description "Default value: 25.";
    }
    leaf tStatusProhibitDl {
      type int32 {
        range "0 | 5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 1200 | 1600 | 2000 | 2400";
      }
      default "10";
      units "ms";
      description "Default value: 10.";
    }
    leaf tStatusProhibitDlHighRate {
      type int32 {
        range "0 | 5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 1200 | 1600 | 2000 | 2400";
      }
      default "5";
      units "ms";
      description "Default value: 5.";
    }
    leaf tStatusProhibitUl {
      type int32 {
        range "0 | 5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 1200 | 1600 | 2000 | 2400";
      }
      default "10";
      units "ms";
      description "Default value: 10.";
    }
    leaf-list ueConfGroupList {
      type eytypes:int32_range_1-255;
      ordered-by user;
    }
    leaf-list ueGroupList {
      type eytypes:int32_range_1-255;
      ordered-by user;
    }
    leaf ulMaxRetxThreshold {
      type int32 {
        range "1..4 | 6 | 8 | 16 | 32";
      }
      default "32";
      description "Default value: 32.";
    }
    leaf ulPollPdu {
      type int32 {
        range "4 | 8 | 16 | 32 | 64 | 128 | 256 | 512 | 1024 | 2048 | 4096 | 6144 | 8192 | 12288 | 16384 | 20480 | 24576 | 28672 | 32768 | 40960 | 49152 | 57344 | 65536";
      }
      default "16";
      description "Default value: 16.";
    }
  }
  grouping DrbUp-attributes {
    leaf drbUpId {
      type string;
      mandatory true;
    }
    leaf-list reservedBy {
      type string;
    }
    leaf ueConfGroupType {
      type enumeration {
        enum UE_MOBILITY_GROUP;
        enum UE_SERVICE_GROUP;
        enum UE_ADMISSION_GROUP;
      }
    }
    leaf userLabel {
      type string;
    }
  }
  grouping DrbUpUeCfg-attributes {
    leaf aqmCfgRef {
      type string;
    }
    leaf drbUpUeCfgId {
      type string;
      mandatory true;
    }
    leaf-list prefUeGroupList {
      type eytypes:int32_range_1-255;
      ordered-by user;
    }
    leaf-list ueConfGroupList {
      type eytypes:int32_range_1-255;
      ordered-by user;
    }
    leaf-list ueGroupList {
      type eytypes:int32_range_1-255;
      ordered-by user;
    }
    leaf userLabel {
      type string;
    }
  }
  grouping DrxProfile-attributes {
    leaf drxProfileId {
      type string;
      mandatory true;
    }
    leaf-list reservedBy {
      type string;
    }
    leaf ueConfGroupType {
      type enumeration {
        enum UE_MOBILITY_GROUP;
        enum UE_SERVICE_GROUP;
        enum UE_ADMISSION_GROUP;
      }
    }
  }
  grouping DrxProfileUeCfg-attributes {
    leaf drxEnabled {
      type boolean;
      default "true";
      description "Default value: true.";
    }
    leaf drxInactivityTimer {
      type enumeration {
        enum INACTIVITYTIMER_0MS;
        enum INACTIVITYTIMER_1MS;
        enum INACTIVITYTIMER_2MS;
        enum INACTIVITYTIMER_3MS;
        enum INACTIVITYTIMER_4MS;
        enum INACTIVITYTIMER_5MS;
        enum INACTIVITYTIMER_6MS;
        enum INACTIVITYTIMER_8MS;
        enum INACTIVITYTIMER_10MS;
        enum INACTIVITYTIMER_20MS;
        enum INACTIVITYTIMER_30MS;
        enum INACTIVITYTIMER_40MS;
        enum INACTIVITYTIMER_50MS;
        enum INACTIVITYTIMER_60MS;
        enum INACTIVITYTIMER_80MS;
        enum INACTIVITYTIMER_100MS;
        enum INACTIVITYTIMER_200MS;
        enum INACTIVITYTIMER_300MS;
        enum INACTIVITYTIMER_500MS;
        enum INACTIVITYTIMER_750MS;
        enum INACTIVITYTIMER_1280MS;
        enum INACTIVITYTIMER_1920MS;
        enum INACTIVITYTIMER_2560MS;
      }
    }
    leaf drxLongCycle {
      type enumeration {
        enum LONGCYCLE_10MS;
        enum LONGCYCLE_20MS;
        enum LONGCYCLE_32MS;
        enum LONGCYCLE_40MS;
        enum LONGCYCLE_60MS;
        enum LONGCYCLE_64MS;
        enum LONGCYCLE_70MS;
        enum LONGCYCLE_80MS;
        enum LONGCYCLE_128MS;
        enum LONGCYCLE_160MS;
        enum LONGCYCLE_256MS;
        enum LONGCYCLE_320MS;
        enum LONGCYCLE_512MS;
        enum LONGCYCLE_640MS;
        enum LONGCYCLE_1024MS;
        enum LONGCYCLE_1280MS;
        enum LONGCYCLE_2048MS;
        enum LONGCYCLE_2560MS;
        enum LONGCYCLE_5120MS;
        enum LONGCYCLE_10240MS;
      }
    }
    leaf drxOnDurationTimer {
      type enumeration {
        enum ONDURATIONTIMER_1SUBMS;
        enum ONDURATIONTIMER_2SUBMS;
        enum ONDURATIONTIMER_3SUBMS;
        enum ONDURATIONTIMER_4SUBMS;
        enum ONDURATIONTIMER_5SUBMS;
        enum ONDURATIONTIMER_6SUBMS;
        enum ONDURATIONTIMER_7SUBMS;
        enum ONDURATIONTIMER_8SUBMS;
        enum ONDURATIONTIMER_9SUBMS;
        enum ONDURATIONTIMER_10SUBMS;
        enum ONDURATIONTIMER_11SUBMS;
        enum ONDURATIONTIMER_12SUBMS;
        enum ONDURATIONTIMER_13SUBMS;
        enum ONDURATIONTIMER_14SUBMS;
        enum ONDURATIONTIMER_15SUBMS;
        enum ONDURATIONTIMER_16SUBMS;
        enum ONDURATIONTIMER_17SUBMS;
        enum ONDURATIONTIMER_18SUBMS;
        enum ONDURATIONTIMER_19SUBMS;
        enum ONDURATIONTIMER_20SUBMS;
        enum ONDURATIONTIMER_21SUBMS;
        enum ONDURATIONTIMER_22SUBMS;
        enum ONDURATIONTIMER_23SUBMS;
        enum ONDURATIONTIMER_24SUBMS;
        enum ONDURATIONTIMER_25SUBMS;
        enum ONDURATIONTIMER_26SUBMS;
        enum ONDURATIONTIMER_27SUBMS;
        enum ONDURATIONTIMER_28SUBMS;
        enum ONDURATIONTIMER_29SUBMS;
        enum ONDURATIONTIMER_30SUBMS;
        enum ONDURATIONTIMER_31SUBMS;
        enum ONDURATIONTIMER_1MS;
        enum ONDURATIONTIMER_2MS;
        enum ONDURATIONTIMER_3MS;
        enum ONDURATIONTIMER_4MS;
        enum ONDURATIONTIMER_5MS;
        enum ONDURATIONTIMER_6MS;
        enum ONDURATIONTIMER_8MS;
        enum ONDURATIONTIMER_10MS;
        enum ONDURATIONTIMER_20MS;
        enum ONDURATIONTIMER_30MS;
        enum ONDURATIONTIMER_40MS;
        enum ONDURATIONTIMER_50MS;
        enum ONDURATIONTIMER_60MS;
        enum ONDURATIONTIMER_80MS;
        enum ONDURATIONTIMER_100MS;
        enum ONDURATIONTIMER_200MS;
        enum ONDURATIONTIMER_300MS;
        enum ONDURATIONTIMER_400MS;
        enum ONDURATIONTIMER_500MS;
        enum ONDURATIONTIMER_600MS;
        enum ONDURATIONTIMER_800MS;
        enum ONDURATIONTIMER_1000MS;
        enum ONDURATIONTIMER_1200MS;
        enum ONDURATIONTIMER_1600MS;
      }
    }
    leaf drxProfileUeCfgId {
      type string;
      mandatory true;
    }
    leaf drxRetransmissionTimerDl {
      type int32 {
        range "6 | 8 | 16";
      }
      default "8";
      units "slot";
      description "Default value: 8.";
    }
    leaf drxRetransmissionTimerUl {
      type int32 {
        range "6 | 8 | 16";
      }
      default "8";
      units "slot";
      description "Default value: 8.";
    }
    leaf drxState {
      type boolean;
    }
    leaf-list prefUeGroupList {
      type eytypes:int32_range_0-255;
      ordered-by user;
    }
    leaf-list ueConfGroupList {
      type eytypes:int32_range_1-255;
      ordered-by user;
    }
    leaf-list ueGroupList {
      type eytypes:int32_range_0-255;
      ordered-by user;
    }
    leaf userLabel {
      type string;
    }
  }
  grouping DU5qi-attributes {
    leaf aqmMode {
      type enumeration {
        enum OFF;
        enum MODE1;
        enum MODE2;
      }
      status deprecated;
      default "MODE1";
      description "Default value: MODE1; Takes effect: New connection; Status info: Since 24.Q3. Planned to be removed..";
      reference "Takes effect: New connection.";
    }
    leaf drbRlcInDu5qiEnabled {
      type boolean;
    }
    leaf drbRlcRef {
      type string;
    }
    leaf drbUpRef {
      type string;
    }
    leaf dscp {
      type eytypes:int32_range_0-63;
      default "12";
      description "range 0..63; Default value: 12.";
    }
    leaf dU5qiId {
      type string;
      mandatory true;
    }
    leaf estimatedE2ERTT {
      type eytypes:int32_range_0-1023;
      status deprecated;
      default "50";
      units "ms";
      description "range 0..1023; Default value: 50; Takes effect: New connection; Status info: Since 24.Q3. Planned to be removed..";
      reference "Takes effect: New connection.";
    }
    leaf l4sCfgRef {
      type string;
    }
    leaf logicalChannelGroupId {
      type eytypes:int32_range_1-7;
      default "5";
      description "range 1..7; Default value: 5.";
    }
    leaf logicalChannelRef {
      type string;
    }
    leaf packetDelayBudget {
      type eytypes:int32_range_0-1023;
      default "280";
      units "ms";
      description "range 0..1023; Default value: 280.";
    }
    leaf packetDelayBudgetOffset {
      type eytypes:int32_range_0-1023;
      status deprecated;
      default "0";
      units "ms";
      description "range 0..1023; Default value: 0; Takes effect: New connection; Status info: Since 24.Q3. Planned to be removed..";
      reference "Takes effect: New connection.";
    }
    leaf priorityLevel {
      type int32 {
        range "1..127";
      }
      default "80";
      description "range 1..127; Default value: 80.";
    }
    leaf profile5qi {
      type eytypes:int32_range_0-255;
      mandatory true;
      description "range 0..255.";
    }
    leaf puschRepRef {
      type string;
    }
    leaf rlcSNLength {
      type int32 {
        range "6 | 12 | 18";
      }
      units "bit";
    }
    leaf schedulingProfileRef {
      type string;
    }
    leaf srHandlingRef {
      type string;
    }
    leaf tReassemblyDl {
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200";
      }
      units "ms";
    }
    leaf tReassemblyUl {
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200";
      }
      units "ms";
    }
    leaf ulPacketDelayBudget {
      type eytypes:int32_range_0-1023;
      units "ms";
      description "range 0..1023.";
    }
    leaf userLabel {
      type string;
    }
  }
  grouping DU5qiTable-attributes {
    leaf default5qiTable {
      type boolean;
      default "false";
      description "Default value: false.";
    }
    leaf dU5qiTableId {
      type string;
      mandatory true;
    }
    leaf-list reservedBy {
      type string;
    }
  }
  grouping DUModified5qi-attributes {
    leaf dUModified5qiId {
      type string;
      mandatory true;
    }
    leaf modifiedProfile5qi {
      type eytypes:int32_range_1-255;
      mandatory true;
      description "range 1..255.";
    }
    leaf ueConfGroupType {
      type enumeration {
        enum UE_MOBILITY_GROUP;
        enum UE_SERVICE_GROUP;
        enum UE_ADMISSION_GROUP;
      }
    }
  }
  grouping DUModified5qiUeCfg-attributes {
    leaf dUModified5qiUeCfgId {
      type string;
      mandatory true;
    }
    leaf l4sCfgRef {
      type string;
    }
    leaf logicalChannelRef {
      type string;
    }
    leaf packetDelayBudget {
      type int32 {
        range "1..512";
      }
      units "ms";
      description "range 1..512.";
    }
    leaf-list prefUeGroupList {
      type eytypes:int32_range_0-255;
      ordered-by user;
    }
    leaf priorityLevel {
      type int32 {
        range "1..127";
      }
      description "range 1..127.";
    }
    leaf schedulingProfileRef {
      type string;
    }
    leaf srHandlingRef {
      type string;
    }
    leaf-list ueConfGroupList {
      type eytypes:int32_range_1-255;
      ordered-by user;
    }
    leaf-list ueGroupList {
      type eytypes:int32_range_0-255;
      ordered-by user;
    }
    leaf ulPacketDelayBudget {
      type eytypes:int32_range_0-1023;
      units "ms";
      description "range 0..1023.";
    }
    leaf userLabel {
      type string;
    }
  }
  grouping DUQos-attributes {
    leaf dUQosId {
      type string;
      mandatory true;
    }
  }
  grouping DUQosModifier-attributes {
    leaf dUQosModifierId {
      type string;
      mandatory true;
    }
  }
  grouping DynPowerOpt-attributes {
    leaf downDlThreshold {
      type eytypes:int32_range_0-2000;
      default "10";
      units "slot";
      description "range 0..2000; Default value: 10.";
    }
    leaf downUlThreshold {
      type eytypes:int32_range_0-2000;
      default "10";
      units "slot";
      description "range 0..2000; Default value: 10.";
    }
    leaf dynPowerOptId {
      type string;
      mandatory true;
    }
    leaf lowDlActivityTimer {
      type eytypes:int32_range_0-5000-5;
      default "200";
      units "ms";
      description "range 0..5000; Default value: 200.";
    }
    leaf lowUlActivityTimer {
      type eytypes:int32_range_0-5000-5;
      default "200";
      units "ms";
      description "range 0..5000; Default value: 200.";
    }
    leaf-list reservedBy {
      type string;
    }
    leaf upDlThreshold {
      type eytypes:int32_range_0-2000;
      default "30";
      units "slot";
      description "range 0..2000; Default value: 30.";
    }
    leaf upUlThreshold {
      type eytypes:int32_range_0-2000;
      default "30";
      units "slot";
      description "range 0..2000; Default value: 30.";
    }
    leaf userLabel {
      type string;
    }
  }
  grouping EndpointResource-attributes {
    leaf endpointResourceId {
      type string;
      mandatory true;
    }
    leaf-list reservedBy {
      type string;
    }
    leaf userLabel {
      type string;
    }
  }
  grouping EnergyEfficiency-attributes {
    leaf energyEfficiencyId {
      type string;
      mandatory true;
    }
  }
  grouping EnergyOptPwrAlloc-attributes {
    leaf avgRbSymThresh {
      type int32 {
        range "30..100";
      }
      default "100";
      description "range 30..100; Default value: 100.";
    }
    leaf energyOptPwrAllocCellMode {
      type enumeration {
        enum DISABLED;
        enum ENABLED;
      }
    }
    leaf energyOptPwrAllocId {
      type string;
      mandatory true;
    }
    leaf energyOptPwrAllocMode {
      type enumeration {
        enum DISABLED;
        enum ENABLED;
      }
    }
    leaf rbExpansionTarget {
      type int32 {
        range "1..200";
      }
      default "70";
      description "range 1..200; Default value: 70.";
    }
    leaf-list reservedBy {
      type string;
    }
    leaf ueConfGroupType {
      type enumeration {
        enum UE_MOBILITY_GROUP;
        enum UE_SERVICE_GROUP;
        enum UE_ADMISSION_GROUP;
      }
    }
  }
  grouping EnergyOptPwrAllocUeCfg-attributes {
    leaf energyOptPwrAllocMode {
      type enumeration {
        enum DISABLED;
        enum ENABLED;
      }
    }
    leaf energyOptPwrAllocUeCfgId {
      type string;
      mandatory true;
    }
    leaf-list prefUeGroupList {
      type eytypes:int32_range_1-255;
      ordered-by user;
    }
    leaf-list ueConfGroupList {
      type eytypes:int32_range_1-255;
      ordered-by user;
    }
    leaf-list ueGroupList {
      type eytypes:int32_range_1-255;
      ordered-by user;
    }
  }
  grouping EnergyOptSymAlloc-attributes {
    leaf energyOptSymAllocId {
      type string;
      mandatory true;
    }
    leaf energyOptSymAllocMode {
      type enumeration {
        enum DISABLED;
        enum ENABLED;
      }
    }
    leaf-list reservedBy {
      type string;
    }
  }
  grouping ExtCaPriority-attributes {
    leaf adjustedPriorityMode {
      type enumeration {
        enum STATIC_PRIO_WITHOUT_POLICING;
        enum STATIC_PRIO_WITH_POLICING;
        enum DYNAMIC_PRIO;
      }
    }
    leaf extCaPriorityId {
      type string;
      mandatory true;
    }
    leaf priorityDomainBase {
      type eytypes:int32_range_1-64;
      default "48";
      description "range 1..64; Default value: 48.";
    }
    leaf priorityDomainLimit {
      type eytypes:int32_range_1-64;
      default "1";
      description "range 1..64; Default value: 1.";
    }
    leaf relativePriorityBase {
      type eytypes:int32_range_1-256;
      default "1";
      description "range 1..256; Default value: 1.";
    }
    leaf relativePriorityLimit {
      type eytypes:int32_range_1-256;
      default "256";
      description "range 1..256; Default value: 256.";
    }
    leaf-list reservedBy {
      type string;
    }
  }
  grouping ExtENodeBPartnerFunction-attributes {
    leaf eNbId {
      type eytypes:int32_range_0-1048575;
      mandatory true;
      description "range 0..1048575.";
    }
    leaf extENodeBPartnerFunctionId {
      type string;
      mandatory true;
    }
    leaf locatedOnIntraMe {
      type boolean;
      default "false";
      description "Default value: false.";
    }
    leaf pimVlanPortRef {
      type ietfinet:port-number;
    }
  }
  grouping ExtGNBDUPartnerFunction-attributes {
    leaf caVlanPortRef {
      type ietfinet:port-number;
    }
    leaf extGNBDUPartnerFunctionId {
      type string;
      mandatory true;
    }
    leaf gNBDUId {
      type eytypes:int64_range_0-68719476735;
      mandatory true;
      description "range 0..68719476735.";
    }
    leaf gNBDUName {
      type string;
      config false;
    }
    leaf gNBId {
      type eytypes:int64_range_0-4294967295;
      mandatory true;
      description "range 0..4294967295.";
    }
    leaf gNBIdLength {
      type eytypes:int32_range_22-32;
      default "22";
      description "range 22..32; Default value: 22.";
    }
  }
  grouping FlowLimit-attributes {
    leaf-list flowLimit5qiList {
      type eytypes:int32_range_1-255;
      ordered-by user;
    }
    leaf flowLimitId {
      type string;
      mandatory true;
    }
    leaf maxNoOfFlows {
      type eytypes:int32_range_0-2147483647;
      description "range 0..2147483647.";
    }
    leaf preemptionEnabled {
      type boolean;
      default "false";
      description "Default value: false.";
    }
    leaf softAdmissionEnabled {
      type boolean;
      default "false";
      description "Default value: false.";
    }
  }
  grouping GNBDUFunction-attributes {
    leaf activeF1Link {
      type enumeration {
        enum NOT_ACTIVE;
        enum ACTIVE;
      }
      config false;
    }
    leaf altDepHMultCGPeriodEnabled {
      type boolean;
    }
    leaf altDepHServAdapUPProfEnabled {
      type boolean;
      default "false";
      description "Default value: false.";
    }
    leaf autoLockDelay {
      type uint32 {
        range "0..60";
      }
      default "0";
      units "minute";
      description "range 0..60; Default value: 0.";
    }
    leaf capacityAllocationPolicy {
      type enumeration {
        enum SYSTEM_SELECTED;
        enum CAPACITY_PRIORITIZATION;
        enum CAPACITY_PRIORITIZATION_TDD;
      }
    }
    leaf capacityAllocationStatus {
      type enumeration {
        enum SYSTEM_SELECTED;
        enum CAPACITY_PRIORITIZATION;
        enum CAPACITY_PRIORITIZATION_TDD;
      }
      config false;
    }
    leaf caVlanPortRef {
      type ietfinet:port-number;
    }
    leaf configuredGrantConfMode {
      type enumeration {
        enum CELL_CG_PERIODICITY;
        enum CG_PROFILE_CG_PERIODICITY;
      }
      status deprecated;
      default "CELL_CG_PERIODICITY";
      description "Default value: CELL_CG_PERIODICITY; Takes effect: Node restart; Status info: Since 25.Q3. Planned to be removed..";
      reference "Takes effect: Node restart.";
    }
    leaf dlBbCapacityMaxLimit {
      type eytypes:int32_range_0-65535;
      config false;
      units "Mbps";
      description "range 0..65535.";
    }
    leaf dlBbCapacityNet {
      type eytypes:int32_range_0-65535;
      config false;
      units "Mbps";
      description "range 0..65535.";
    }
    leaf dlBbCapacityTarget {
      type int32 {
        range "75..65535";
      }
      units "Mbps";
      description "range 75..65535.";
    }
    list dUpLMNId {
      config false;
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
    leaf dynTACConfigEnabled {
      type boolean;
      default "false";
      description "Default value: false.";
    }
    leaf endpointResourceRef {
      type string;
    }
    leaf gNBDUFunctionId {
      type string;
      mandatory true;
    }
    leaf gNBDUId {
      type eytypes:int64_range_0-68719476735;
      mandatory true;
      description "range 0..68719476735.";
    }
    leaf gNBDUName {
      type string {
        length "1..150";
      }
      description "length 1..150.";
    }
    leaf gNBId {
      type eytypes:int64_range_0-4294967295;
      mandatory true;
      description "range 0..4294967295.";
    }
    leaf gNBIdLength {
      type eytypes:int32_range_22-32;
      default "22";
      description "range 22..32; Default value: 22.";
    }
    leaf measGapLengthMode {
      type enumeration {
        enum OFF;
        enum EUTRAN_3MS;
        enum NR_FR1_3MS;
        enum ALL_3MS;
      }
    }
    leaf mixedSrsModeEnabled {
      type boolean;
      default "false";
      description "Default value: false.";
    }
    leaf multiTddPatternSmEnabled {
      type boolean;
      default "false";
      description "Default value: false.";
    }
    leaf noOfUsedPimAvoidEranPartners {
      type eytypes:int32_range_0-4;
      config false;
      description "range 0..4.";
    }
    leaf pimAutoDetectionEnabled {
      type boolean;
      status deprecated;
      default "false";
      description "Default value: false; Status info: Since 24.Q1. Planned to be removed..";
    }
    leaf pimCancAutoConfigEnabled {
      type boolean;
      default "false";
      description "Default value: false.";
    }
    leaf pimVlanPortRef {
      type ietfinet:port-number;
    }
    leaf pwsEtwsPrimaryInd {
      type int32 {
        range "3..16";
      }
      default "8";
      description "range 3..16; Default value: 8.";
    }
    leaf release {
      type string;
      config false;
    }
    leaf rimAggressorRSSetRef {
      type string;
    }
    leaf rimFlexSrsPositionsEnabled {
      type boolean;
    }
    leaf rimVictimRSSetRef {
      type string;
    }
    leaf servAdapUPProfDepHEnabled {
      type boolean;
      default "true";
      description "Default value: true.";
    }
    leaf servAdapUPProfUlDepHEnabled {
      type boolean;
      default "true";
      description "Default value: true.";
    }
    leaf setIdAllocation {
      type enumeration {
        enum G_NODE_B;
        enum CELL;
      }
    }
    leaf trafficDefinitionDepHEnabled {
      type boolean;
      default "true";
      description "Default value: true.";
    }
    leaf ulBbCapacityMaxLimit {
      type eytypes:int32_range_0-65535;
      config false;
      units "Mbps";
      description "range 0..65535.";
    }
    leaf ulBbCapacityNet {
      type eytypes:int32_range_0-65535;
      config false;
      units "Mbps";
      description "range 0..65535.";
    }
    leaf ulServiceDepHEnabled {
      type boolean;
      default "true";
      description "Default value: true.";
    }
    leaf userLabel {
      type string;
    }
    leaf pmFwkSampLostL2Cellpartition {
      type uint64;
      config false;
    }
    leaf pmPagF1ReceivedEdrx {
      type uint64;
      config false;
    }
    leaf pmLicDlSlotsHwacLimit {
      type uint64;
      config false;
    }
    leaf pmLic5MHzBwHwacFdd {
      type int64;
      config false;
    }
    leaf pmLicUlCapUsedSum {
      type uint64;
      config false;
    }
    leaf-list pmFwkStreamDroppedEventSocketSetupFailDistr {
      type uint64;
    }
    leaf pmFwkSampLostL2Sectorcarrier {
      type uint64;
      config false;
    }
    leaf pmRimAggressorCellDetectedMax {
      type int64;
      config false;
    }
    leaf-list pmFwkStreamDroppedEventSocketConnectionFailDistr {
      type uint64;
    }
    leaf pmLicDlCapUsedSum {
      type uint64;
      config false;
    }
    leaf pmFwkSampLostL2Rb {
      type uint64;
      config false;
    }
    leaf pmLicDlSlotsData {
      type uint64;
      config false;
    }
    leaf pmRimVictimRiDetectedMax {
      type int64;
      config false;
    }
    leaf pmLicLteNrSpectrumSharingFdd {
      type int64;
      config false;
    }
    leaf pmLic5Plus5MHzScTdd {
      type int64;
      config false;
    }
    leaf-list pmRadioPdschRimBlankSlotsMaxDistr {
      type int64;
    }
    leaf pmMacVolDl {
      type ietfyang:mac-address;
      config false;
    }
    leaf pmLicDlCapUsedSamp {
      type uint64;
      config false;
    }
    leaf pmFwkSampLostL2Ue {
      type uint64;
      config false;
    }
    leaf pmFwkSampLostL2Cell {
      type uint64;
      config false;
    }
    leaf pmLic25Plus25MHzScActual {
      type int64;
      config false;
    }
    leaf pmPagF1DiscardedEdrx {
      type uint64;
      config false;
    }
    leaf-list pmFwkStreamDroppedEventDistr {
      type uint64;
    }
    leaf pmFwkSampLostL2Cellplmn {
      type uint64;
      config false;
    }
    leaf pmRimVictimCellDetectedMax {
      type int64;
      config false;
    }
    leaf pmArcLinkDelayAboveCaSchedOptThres {
      type uint64;
      config false;
    }
    leaf pmPagF1Discarded {
      type uint64;
      config false;
    }
    leaf-list pmRadioPdschRimBlankSymbolMaxDistr {
      type int64;
    }
    leaf pmLic5MHzBwHwacTdd {
      type int64;
      config false;
    }
    leaf pmFwkSampLostL2Branch {
      type uint64;
      config false;
    }
    leaf pmLicEricssonRedCapAdvCellCapacity {
      type int64;
      config false;
    }
    leaf pmLic10MHzBwHwacTdd {
      type int64;
      config false;
    }
    leaf pmFwkSampLostL2Beam {
      type uint64;
      config false;
    }
    leaf pmLicEricssonRedCapBasCellCapacity {
      type int64;
      config false;
    }
    leaf pmMacVolUl {
      type ietfyang:mac-address;
      config false;
    }
    leaf pmLicEricssonRedCapMaxCellCapacity {
      type int64;
      config false;
    }
    leaf pmLicDlCapUsedMax {
      type int64;
      config false;
    }
    leaf pmUeConfigProfileOverwrite {
      type uint64;
      config false;
    }
    leaf pmPagF1Received {
      type uint64;
      config false;
    }
    leaf pmLic5Plus5MHzScActual {
      type int64;
      config false;
    }
    leaf-list pmFwkStreamDroppedEventSocketErrorDistr {
      type uint64;
    }
    leaf pmLicUlCapUsedMax {
      type int64;
      config false;
    }
    leaf-list pmFwkStreamProducedEventDistr {
      type uint64;
    }
    leaf pmLic5Plus5MHzScFdd {
      type int64;
      config false;
    }
    leaf pmLicUlSlotsHwacLimit {
      type uint64;
      config false;
    }
    leaf-list pmFwkStreamDroppedEventSlowStreamDistr {
      type uint64;
    }
    leaf pmLic50MHzBwHwac {
      type int64;
      config false;
    }
    leaf pmLicUlCapUsedSamp {
      type uint64;
      config false;
    }
    leaf-list pmLicDlCapDistr {
      type uint64;
    }
    leaf-list pmLicUlCapDistr {
      type uint64;
    }
    leaf-list pmFwkStreamDroppedEventLicenseUnavailableDistr {
      type uint64;
    }
    leaf pmLicUlSlotsData {
      type uint64;
      config false;
    }
    leaf pmLic10MHzBwHwacFdd {
      type int64;
      config false;
    }
    leaf pmFwkSampLostL2Qos {
      type uint64;
      config false;
    }
    leaf pmArcPartnerSuspensionLinkDelay {
      type uint64;
      config false;
    }
  }
  grouping Harq-attributes {
    leaf harqId {
      type string;
      mandatory true;
    }
  }
  grouping HarqUeCfg-attributes {
    leaf dlHarqMode {
      type enumeration {
        enum HARQ_NORMAL;
        enum HARQ_VONR;
        enum HARQ_ROBUST;
      }
    }
    leaf harqUeCfgId {
      type string;
      mandatory true;
    }
    leaf-list reservedBy {
      type string;
    }
    leaf ulHarqMode {
      type enumeration {
        enum HARQ_NORMAL;
        enum HARQ_VONR;
        enum HARQ_ROBUST;
      }
    }
  }
  grouping InterMeLink-attributes {
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf caSchedOptActive {
      type boolean;
      config false;
    }
    leaf interMeLinkId {
      type string;
      mandatory true;
    }
    leaf linkLatency15minHWM {
      type int32;
      config false;
      units "microsecond";
    }
    leaf linkLatency1minAvg {
      type int32;
      config false;
      units "microsecond";
    }
    leaf linkLatency24hrsHWM {
      type int32;
      config false;
      units "microsecond";
    }
    leaf localEndpointIdentity {
      type string;
      config false;
    }
    leaf operationalState {
      type enumeration {
        enum DISABLED;
        enum ENABLED;
      }
      config false;
    }
    leaf remoteEndpointIdentity {
      type string;
      config false;
    }
    leaf vlanId {
      type int32;
      config false;
    }
  }
  grouping L4sCfg-attributes {
    leaf l4sCfgId {
      type string;
      mandatory true;
    }
    leaf-list reservedBy {
      type string;
    }
    leaf ulL4sHighThresh {
      type int32 {
        range "5..100";
      }
      default "20";
      units "ms";
      description "range 5..100; Default value: 20.";
    }
    leaf ulL4sLowThresh {
      type int32 {
        range "1..50";
      }
      default "8";
      units "ms";
      description "range 1..50; Default value: 8.";
    }
    leaf ulL4sMode {
      type enumeration {
        enum DISABLED;
        enum QUEUE_BASED;
      }
    }
    leaf userLabel {
      type string;
    }
  }
  grouping LinkAdaptation-attributes {
    leaf linkAdaptationId {
      type string;
      mandatory true;
    }
  }
  grouping LinkAdaptationUeCfg-attributes {
    leaf dlMaxBitrate {
      type int32 {
        range "-1 | 4..32";
      }
      default "-1";
      units "Mbps";
      description "Default value: -1.";
    }
    leaf dlMcsTable {
      type enumeration {
        enum QAM64;
        enum QAM256;
        enum LOW_SE_QAM64;
      }
    }
    leaf linkAdaptationUeCfgId {
      type string;
      mandatory true;
    }
    leaf linkAdaptationUeMode {
      type enumeration {
        enum GENERAL;
        enum ROBUST_BASIC;
        enum ROBUST_HIGH;
        enum CUSTOM;
        enum ROBUST_MCS;
      }
    }
    leaf-list reservedBy {
      type string;
    }
    leaf ulMcsTable {
      type enumeration {
        enum QAM64;
        enum QAM256;
        enum LOW_SE_QAM64;
      }
    }
    leaf userLabel {
      type string;
    }
  }
  grouping LocalIpEndpoint-attributes {
    leaf-list addressRef {
      type string;
      ordered-by user;
      min-elements 1;
    }
    leaf-list interfaceList {
      type enumeration {
        enum C5;
        enum E1;
        enum E6;
        enum F1;
        enum NG;
        enum S1;
        enum XN;
        enum X2;
      }
      ordered-by user;
      min-elements 1;
    }
    leaf localIpEndpointId {
      type ietfinet:ip-address;
      mandatory true;
    }
  }
  grouping LocalSctpEndpoint-attributes {
    leaf interfaceUsed {
      type enumeration {
        enum C5;
        enum E1;
        enum E6;
        enum F1;
        enum NG;
        enum S1;
        enum XN;
        enum X2;
      }
      mandatory true;
    }
    leaf localSctpEndpointId {
      type string;
      mandatory true;
    }
    leaf sctpEndpointRef {
      type string;
      mandatory true;
    }
  }
  grouping LogicalChannel-attributes {
    leaf logicalChannelId {
      type string;
      mandatory true;
    }
    leaf-list reservedBy {
      type string;
    }
    leaf ueConfGroupType {
      type enumeration {
        enum UE_MOBILITY_GROUP;
        enum UE_SERVICE_GROUP;
        enum UE_ADMISSION_GROUP;
      }
    }
  }
  grouping LogicalChannelUeCfg-attributes {
    leaf bucketSizeDuration {
      type enumeration {
        enum MS_5;
        enum MS_10;
        enum MS_20;
        enum MS_50;
        enum MS_100;
        enum MS_150;
        enum MS_300;
        enum MS_500;
        enum MS_1000;
      }
    }
    leaf logicalChannelGroup {
      type eytypes:int32_range_1-7;
      description "range 1..7.";
    }
    leaf logicalChannelPriority {
      type int32 {
        range "4..16";
      }
      description "range 4..16.";
    }
    leaf logicalChannelSrMask {
      type boolean;
      default "false";
      description "Default value: false.";
    }
    leaf logicalChannelUeCfgId {
      type string;
      mandatory true;
    }
    leaf-list prefUeGroupList {
      type eytypes:int32_range_1-255;
      ordered-by user;
    }
    leaf prioritisedBitRate {
      type enumeration {
        enum KBPS_0;
        enum KBPS_8;
        enum KBPS_16;
        enum KBPS_32;
        enum KBPS_64;
        enum KBPS_128;
        enum KBPS_256;
        enum KBPS_512;
        enum KBPS_1024;
        enum KBPS_2048;
        enum KBPS_4096;
        enum KBPS_8192;
        enum KBPS_16384;
        enum KBPS_32768;
        enum KBPS_65536;
        enum INFINITY;
      }
    }
    leaf prioritisedBitRateFR2 {
      type enumeration {
        enum KBPS_0;
        enum KBPS_8;
        enum KBPS_16;
        enum KBPS_32;
        enum KBPS_64;
        enum KBPS_128;
        enum KBPS_256;
        enum KBPS_512;
        enum KBPS_1024;
        enum KBPS_2048;
        enum KBPS_4096;
        enum KBPS_8192;
        enum KBPS_16384;
        enum KBPS_32768;
        enum KBPS_65536;
        enum INFINITY;
      }
    }
    leaf srDelayTimerApplied {
      type boolean;
      default "false";
      description "Default value: false.";
    }
    leaf-list ueConfGroupList {
      type eytypes:int32_range_1-255;
      ordered-by user;
    }
    leaf-list ueGroupList {
      type eytypes:int32_range_1-255;
      ordered-by user;
    }
  }
  grouping LteInterMeLink-attributes {
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf linkLatency15minHWM {
      type int32;
      config false;
      units "microsecond";
    }
    leaf linkLatency1minAvg {
      type int32;
      config false;
      units "microsecond";
    }
    leaf linkLatency24hrsHWM {
      type int32;
      config false;
      units "microsecond";
    }
    leaf localEndpointIdentity {
      type string;
      config false;
    }
    leaf lteInterMeLinkId {
      type string;
      mandatory true;
    }
    leaf operationalState {
      type enumeration {
        enum DISABLED;
        enum ENABLED;
      }
      config false;
    }
    leaf remoteEndpointIdentity {
      type string;
      config false;
    }
    leaf vlanId {
      type int32;
      config false;
    }
  }
  grouping MassiveMimoSleep-attributes {
    leaf massiveMimoSleepId {
      type string;
      mandatory true;
    }
  }
  grouping MMimoSleepProfile-attributes {
    leaf mMimoSleepProfileId {
      type string;
      mandatory true;
    }
    leaf-list reservedBy {
      type string;
    }
    leaf sleepMode {
      type enumeration {
        enum TXMUTE;
        enum ECO;
      }
    }
    leaf switchDownMonitorDurTimer {
      type eytypes:int32_range_0-14400;
      default "60";
      units "s";
      description "range 0..14400; Default value: 60.";
    }
    leaf switchDownMonitorDurTimerEco {
      type eytypes:int32_range_0-14400;
      default "300";
      units "s";
      description "range 0..14400; Default value: 300.";
    }
    leaf switchDownPrbThreshDl {
      type eytypes:int32_range_0-100;
      default "20";
      units "percent";
      description "range 0..100; Default value: 20.";
    }
    leaf switchDownPrbThreshDlEco {
      type eytypes:int32_range_0-100;
      default "15";
      units "percent";
      description "range 0..100; Default value: 15.";
    }
    leaf switchDownPrbThreshUlEco {
      type eytypes:int32_range_0-100;
      default "10";
      units "percent";
      description "range 0..100; Default value: 10.";
    }
    leaf switchDownRrcConnThresh {
      type eytypes:int32_range_0-5000;
      default "30";
      description "range 0..5000; Default value: 30.";
    }
    leaf switchDownRrcConnThreshEco {
      type eytypes:int32_range_0-5000;
      default "30";
      description "range 0..5000; Default value: 30.";
    }
    leaf switchUpMonitorDurTimer {
      type eytypes:int32_range_0-14400;
      default "30";
      units "s";
      description "range 0..14400; Default value: 30.";
    }
    leaf switchUpMonitorDurTimerEco {
      type eytypes:int32_range_0-14400;
      default "120";
      units "s";
      description "range 0..14400; Default value: 120.";
    }
    leaf switchUpPrbThreshDl {
      type eytypes:int32_range_0-100;
      default "30";
      units "percent";
      description "range 0..100; Default value: 30.";
    }
    leaf switchUpPrbThreshDlEco {
      type eytypes:int32_range_0-100;
      default "30";
      units "percent";
      description "range 0..100; Default value: 30.";
    }
    leaf switchUpPrbThreshUlEco {
      type eytypes:int32_range_0-100;
      default "15";
      units "percent";
      description "range 0..100; Default value: 15.";
    }
    leaf switchUpRrcConnThresh {
      type eytypes:int32_range_0-5000;
      default "50";
      description "range 0..5000; Default value: 50.";
    }
    leaf switchUpRrcConnThreshEco {
      type eytypes:int32_range_0-5000;
      default "50";
      description "range 0..5000; Default value: 50.";
    }
  }
  grouping MMimoSleepTimeGroup-attributes {
    leaf mMimoSleepTimeGroupId {
      type string;
      mandatory true;
    }
    leaf-list reservedBy {
      type string;
    }
  }
  grouping MMimoSleepTimeWindow-attributes {
    leaf daylightTimeOffsetApplied {
      type string {
        length "0..6";
      }
      config false;
      description "length 0..6.";
    }
    leaf-list dayOfWeek {
      type enumeration {
        enum ALL;
        enum MONDAY;
        enum TUESDAY;
        enum WEDNESDAY;
        enum THURSDAY;
        enum FRIDAY;
        enum SATURDAY;
        enum SUNDAY;
      }
      ordered-by user;
    }
    leaf mMimoSleepProfileRef {
      type string;
      mandatory true;
    }
    leaf mMimoSleepTimeWindowId {
      type string;
      mandatory true;
    }
    leaf startTime {
      type string {
        length "5";
        pattern "([01][0-9]|2[0-3]):([0-5][0-9])";
      }
      default "02:00";
      description "length 5..5; Default value: 02:00.";
    }
    leaf stopTime {
      type string {
        length "5";
        pattern "([01][0-9]|2[0-3]):([0-5][0-9])";
      }
      default "05:00";
      description "length 5..5; Default value: 05:00.";
    }
  }
  grouping NRCellDU-attributes {
    leaf actualPdcchRachBoost {
      type int32;
      config false;
      units "dB";
    }
    leaf actualPdschRachBoost {
      type int32;
      config false;
      units "dB";
    }
    leaf actualSsbPowerBoost {
      type int32;
      config false;
      units "dB";
    }
    leaf additionalPucchForCaEnabled {
      type boolean;
      default "false";
      description "Default value: false.";
    }
    leaf administrativeState {
      type enumeration {
        enum LOCKED;
        enum UNLOCKED;
        enum SHUTTINGDOWN;
      }
    }
    leaf advancedDlSuMimoEnabled {
      type boolean;
      default "false";
      description "Default value: false.";
    }
    leaf advDlBfWhenAllSrsPortsUsable {
      type ietfinet:port-number;
      description "Default value: false.";
    }
    leaf ailgBeamDirectionEnabled {
      type boolean;
      default "false";
      description "Default value: false.";
    }
    leaf ailgDlPrbLoadLevel {
      type uint32 {
        range "0..100";
      }
      default "0";
      units "percent";
      description "range 0..100; Default value: 0.";
    }
    leaf ailgI11BeamDirection {
      type eytypes:int32_range_0-31-13;
      default "0";
      description "range 0..31; Default value: 0.";
    }
    leaf ailgI12BeamDirection {
      type eytypes:int32_range_0-15;
      default "0";
      description "range 0..15; Default value: 0.";
    }
    leaf ailgModType {
      type enumeration {
        enum AILG_MOD_QPSK;
        enum AILG_MOD_16QAM;
        enum AILG_MOD_64QAM;
        enum AILG_MOD_256QAM;
      }
    }
    leaf ailgPdcchBeamDirectionEnabled {
      type boolean;
      default "false";
      description "Default value: false.";
    }
    leaf ailgPdcchLoadLevel {
      type uint32 {
        range "0..100";
      }
      default "0";
      units "percent";
      description "range 0..100; Default value: 0.";
    }
    leaf aperiodicSrsEnabled {
      type boolean;
      default "false";
      description "Default value: false.";
    }
    leaf autoLockAction {
      type enumeration {
        enum NO_LOCK;
        enum IMMEDIATE_LOCK;
        enum SOFT_LOCK;
      }
    }
    leaf autoSelectedModeOffset {
      type int32 {
        range "-10..30";
      }
      default "6";
      units "dB";
      description "range -10..30; Default value: 6.";
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf-list bandList {
      type eytypes:int32_range_1-1024;
    }
    leaf-list bandListManual {
      type int32 {
        range "1..3 | 5 | 7..8 | 12..14 | 18 | 20 | 24..26 | 28..31 | 34 | 38..41 | 46 | 48 | 50..51 | 53..54 | 65..68 | 70..72 | 74..102 | 104..106 | 109..110 | 257..262";
      }
      ordered-by user;
    }
    leaf bfrEnabled {
      type boolean;
    }
    leaf-list bWPRef {
      type string;
      ordered-by user;
    }
    leaf bWPSetRef {
      type string;
    }
    leaf caBufferSplitThresh {
      type uint16 {
        range "1..3000";
      }
      default "3";
      units "byte";
      description "range 1..3000; Default value: 3.";
    }
    leaf caPerCcFairnessWeightEnabled {
      type boolean;
      default "true";
      description "Default value: true.";
    }
    leaf caPerCcFairnessWeightUlEnabled {
      type boolean;
      default "false";
      description "Default value: false.";
    }
    leaf caSCellHandlingRef {
      type string;
    }
    leaf cbrsCellBandwidthPreferred {
      type int32 {
        range "10000..100000";
      }
      default "20000";
      units "kHz";
      description "range 10000..100000; Default value: 20000.";
    }
    leaf cbrsCellPriority {
      type enumeration {
        enum NORMAL;
        enum HIGH;
      }
    }
    leaf cbrsCellPriorityRank {
      type eytypes:int32_range_1-10;
      default "1";
      description "range 1..10; Default value: 1.";
    }
    leaf cbrsCellSsbControlEnabled {
      type boolean;
      default "false";
      description "Default value: false.";
    }
    leaf cchLoadProfileRef {
      type string;
    }
    leaf cellBarred {
      type enumeration {
        enum BARRED;
        enum NOT_BARRED;
      }
    }
    leaf cellBarredReason {
      type enumeration {
        enum MANUAL;
        enum CELL_SOFT_LOCK;
        enum BOOSTER_CARRIER_SLEEP;
      }
      config false;
    }
    leaf cellBarredStatus {
      type enumeration {
        enum BARRED;
        enum NOT_BARRED;
      }
      config false;
    }
    leaf cellLocalId {
      type eytypes:int32_range_0-16383;
      mandatory true;
      description "range 0..16383.";
    }
    leaf cellPriorityShiftRef {
      type string;
    }
    leaf cellRange {
      type eytypes:int32_range_1-100000;
      units "m";
      description "range 1..100000.";
    }
    leaf cellReservedForOperator {
      type enumeration {
        enum RESERVED;
        enum NOT_RESERVED;
      }
    }
    leaf cellResourceMappingRef {
      type string;
    }
    leaf cellSelectionWeightFactor {
      type uint32 {
        range "0..100";
      }
      default "100";
      description "range 0..100; Default value: 100.";
    }
    leaf cellState {
      type enumeration {
        enum IDLE;
        enum INACTIVE;
        enum ACTIVE;
      }
      config false;
    }
    leaf cfraEnabled {
      type boolean;
      default "false";
      description "Default value: false.";
    }
    leaf configuredEpsTAC {
      type eytypes:int32_range_0-65535-10;
      description "range 0..65535.";
    }
    leaf configuredGrantPeriodicity {
      type int32 {
        range "5 | 10 | 20 | 40 | 80 | 160 | 320 | 640 | 1280";
      }
      status deprecated;
      default "10";
      description "Default value: 10; Takes effect: Next cell unlock; Status info: Since 25.Q3. Planned to be removed..";
      reference "Takes effect: Next cell unlock.";
    }
    leaf covOptUlSchedFr2Enabled {
      type boolean;
      default "false";
      description "Default value: false.";
    }
    leaf csiReportFormat {
      type ietfinet:port-number;
    }
    leaf-list csiRsActivePortConfig {
      type ietfinet:port-number;
    }
    list csiRsConfig16P {
      key "id";
      leaf id {
        type uint32;
        description "Synthetic key for struct entry.";
      }
      container attributes {
      leaf csiRsControl16Ports {
        type ietfinet:port-number;
      }
      leaf i11Restriction {
        type string {
          length "0..8";
          pattern "[0-9A-F]*";
        }
        description "length 0..8.";
      }
      leaf i12Restriction {
        type string {
          length "0..2";
          pattern "[0-9A-F]*";
        }
        description "length 0..2.";
      }
      }
    }
    list csiRsConfig2P {
      key "id";
      leaf id {
        type uint32;
        description "Synthetic key for struct entry.";
      }
      container attributes {
      leaf aRestriction {
        type string {
          length "0..2";
          pattern "([0-3][0-9A-F])?";
        }
        default "3F";
        description "length 0..2; Default value: 3F.";
      }
      leaf csiRsControl2Ports {
        type ietfinet:port-number;
      }
      }
    }
    list csiRsConfig32P {
      key "id";
      leaf id {
        type uint32;
        description "Synthetic key for struct entry.";
      }
      container attributes {
      leaf csiRsControl32Ports {
        type ietfinet:port-number;
      }
      leaf i11Restriction {
        type string {
          length "0..8";
          pattern "[0-9A-F]*";
        }
        description "length 0..8.";
      }
      leaf i12Restriction {
        type string {
          length "0..4";
          pattern "[0-9A-F]*";
        }
        description "length 0..4.";
      }
      }
    }
    list csiRsConfig4P {
      key "id";
      leaf id {
        type uint32;
        description "Synthetic key for struct entry.";
      }
      container attributes {
      leaf csiRsControl4Ports {
        type ietfinet:port-number;
      }
      leaf i11Restriction {
        type string {
          length "0..2";
          pattern "[0-9A-F]*";
        }
        default "FF";
        description "length 0..2; Default value: FF.";
      }
      }
    }
    list csiRsConfig8P {
      key "id";
      leaf id {
        type uint32;
        description "Synthetic key for struct entry.";
      }
      container attributes {
      leaf csiRsControl8Ports {
        type ietfinet:port-number;
      }
      leaf i11Restriction {
        type string {
          length "0..4";
          pattern "[0-9A-F]*";
        }
        default "FFFF";
        description "length 0..4; Default value: FFFF.";
      }
      leaf i12Restriction {
        type string {
          length "0..2";
          pattern "[0-9A-F]*";
        }
        description "length 0..2.";
      }
      }
    }
    leaf csiRsPeriodicity {
      type int32 {
        range "10 | 20 | 40 | 80 | 160 | 320 | 640";
      }
      default "40";
      units "slot";
      description "Default value: 40.";
    }
    leaf csiRsShiftingPrimary {
      type enumeration {
        enum DEACTIVATED;
        enum ACTIVATED_AUTOMATIC;
      }
    }
    leaf csiRsShiftingSecondary {
      type enumeration {
        enum DEACTIVATED;
        enum ACTIVATED_AUTOMATIC;
      }
    }
    leaf dftSOfdmMsg3Enabled {
      type boolean;
      default "false";
      description "Default value: false.";
    }
    leaf dftSOfdmPuschEnabled {
      type boolean;
      default "false";
      description "Default value: false.";
    }
    leaf dftSOfdmPuschStartRsrpThresh {
      type eytypes:int32_range_-156--29;
      default "-104";
      units "dBm";
      description "range -156..-29; Default value: -104.";
    }
    leaf dl256QamEnabled {
      type boolean;
      default "true";
      description "Default value: true.";
    }
    leaf dlAvailableCrbs {
      type eytypes:uint32_range_0-272;
      description "range 0..272.";
    }
    leaf dlChannelScramblingIdentity {
      type enumeration {
        enum PCI;
        enum GENERATED;
      }
    }
    leaf dlDmrsMuxSinrThresh {
      type int32 {
        range "-10..30";
      }
      default "-10";
      units "dB";
      description "range -10..30; Default value: -10.";
    }
    leaf dlMaxMuMimoLayers {
      type int32 {
        range "0 | 2 | 4 | 6 | 8 | 10 | 12 | 14 | 16";
      }
      default "0";
      description "Default value: 0.";
    }
    leaf dlMaxSupportedModOrder {
      type ietfinet:port-number;
      config false;
    }
    leaf dlRobustLaEnabled {
      type boolean;
      status deprecated;
      default "false";
      description "Default value: false; Takes effect: Next cell unlock; Status info: Since 25.Q2. Planned to be removed..";
      reference "Takes effect: Next cell unlock.";
    }
    leaf dlScSpillover {
      type int32 {
        range "0..11";
      }
      default "0";
      units "subcarrier";
      description "range 0..11; Default value: 0.";
    }
    leaf dlSmallDataRobustness {
      type enumeration {
        enum OFF;
        enum ON;
      }
    }
    leaf dlStartCrb {
      type eytypes:uint32_range_0-272;
      default "0";
      description "range 0..272; Default value: 0.";
    }
    leaf drxEnable {
      type boolean;
    }
    leaf drxInactivityTimer {
      type enumeration {
        enum INACTIVITYTIMER_0MS;
        enum INACTIVITYTIMER_1MS;
        enum INACTIVITYTIMER_2MS;
        enum INACTIVITYTIMER_3MS;
        enum INACTIVITYTIMER_4MS;
        enum INACTIVITYTIMER_5MS;
        enum INACTIVITYTIMER_6MS;
        enum INACTIVITYTIMER_8MS;
        enum INACTIVITYTIMER_10MS;
        enum INACTIVITYTIMER_20MS;
        enum INACTIVITYTIMER_30MS;
        enum INACTIVITYTIMER_40MS;
        enum INACTIVITYTIMER_50MS;
        enum INACTIVITYTIMER_60MS;
        enum INACTIVITYTIMER_80MS;
        enum INACTIVITYTIMER_100MS;
        enum INACTIVITYTIMER_200MS;
        enum INACTIVITYTIMER_300MS;
        enum INACTIVITYTIMER_500MS;
        enum INACTIVITYTIMER_750MS;
        enum INACTIVITYTIMER_1280MS;
        enum INACTIVITYTIMER_1920MS;
        enum INACTIVITYTIMER_2560MS;
      }
    }
    leaf drxLongCycle {
      type enumeration {
        enum LONGCYCLE_10MS;
        enum LONGCYCLE_20MS;
        enum LONGCYCLE_32MS;
        enum LONGCYCLE_40MS;
        enum LONGCYCLE_60MS;
        enum LONGCYCLE_64MS;
        enum LONGCYCLE_70MS;
        enum LONGCYCLE_80MS;
        enum LONGCYCLE_128MS;
        enum LONGCYCLE_160MS;
        enum LONGCYCLE_256MS;
        enum LONGCYCLE_320MS;
        enum LONGCYCLE_512MS;
        enum LONGCYCLE_640MS;
        enum LONGCYCLE_1024MS;
        enum LONGCYCLE_1280MS;
        enum LONGCYCLE_2048MS;
        enum LONGCYCLE_2560MS;
        enum LONGCYCLE_5120MS;
        enum LONGCYCLE_10240MS;
      }
    }
    leaf drxOnDurationTimer {
      type enumeration {
        enum ONDURATIONTIMER_1SUBMS;
        enum ONDURATIONTIMER_2SUBMS;
        enum ONDURATIONTIMER_3SUBMS;
        enum ONDURATIONTIMER_4SUBMS;
        enum ONDURATIONTIMER_5SUBMS;
        enum ONDURATIONTIMER_6SUBMS;
        enum ONDURATIONTIMER_7SUBMS;
        enum ONDURATIONTIMER_8SUBMS;
        enum ONDURATIONTIMER_9SUBMS;
        enum ONDURATIONTIMER_10SUBMS;
        enum ONDURATIONTIMER_11SUBMS;
        enum ONDURATIONTIMER_12SUBMS;
        enum ONDURATIONTIMER_13SUBMS;
        enum ONDURATIONTIMER_14SUBMS;
        enum ONDURATIONTIMER_15SUBMS;
        enum ONDURATIONTIMER_16SUBMS;
        enum ONDURATIONTIMER_17SUBMS;
        enum ONDURATIONTIMER_18SUBMS;
        enum ONDURATIONTIMER_19SUBMS;
        enum ONDURATIONTIMER_20SUBMS;
        enum ONDURATIONTIMER_21SUBMS;
        enum ONDURATIONTIMER_22SUBMS;
        enum ONDURATIONTIMER_23SUBMS;
        enum ONDURATIONTIMER_24SUBMS;
        enum ONDURATIONTIMER_25SUBMS;
        enum ONDURATIONTIMER_26SUBMS;
        enum ONDURATIONTIMER_27SUBMS;
        enum ONDURATIONTIMER_28SUBMS;
        enum ONDURATIONTIMER_29SUBMS;
        enum ONDURATIONTIMER_30SUBMS;
        enum ONDURATIONTIMER_31SUBMS;
        enum ONDURATIONTIMER_1MS;
        enum ONDURATIONTIMER_2MS;
        enum ONDURATIONTIMER_3MS;
        enum ONDURATIONTIMER_4MS;
        enum ONDURATIONTIMER_5MS;
        enum ONDURATIONTIMER_6MS;
        enum ONDURATIONTIMER_8MS;
        enum ONDURATIONTIMER_10MS;
        enum ONDURATIONTIMER_20MS;
        enum ONDURATIONTIMER_30MS;
        enum ONDURATIONTIMER_40MS;
        enum ONDURATIONTIMER_50MS;
        enum ONDURATIONTIMER_60MS;
        enum ONDURATIONTIMER_80MS;
        enum ONDURATIONTIMER_100MS;
        enum ONDURATIONTIMER_200MS;
        enum ONDURATIONTIMER_300MS;
        enum ONDURATIONTIMER_400MS;
        enum ONDURATIONTIMER_500MS;
        enum ONDURATIONTIMER_600MS;
        enum ONDURATIONTIMER_800MS;
        enum ONDURATIONTIMER_1000MS;
        enum ONDURATIONTIMER_1200MS;
        enum ONDURATIONTIMER_1600MS;
      }
    }
    leaf drxProfileEnabled {
      type boolean;
    }
    leaf drxProfileRef {
      type string;
    }
    leaf eDrxMode {
      type enumeration {
        enum DISABLED;
        enum IDLE;
      }
    }
    leaf endcCgSwitchRef {
      type string;
    }
    leaf endcDlLegSwitchEnabled {
      type boolean;
      status deprecated;
      default "true";
      description "Default value: true; Takes effect: Next cell unlock; Status info: Since 24.Q1. Replaced by CgSwitchCfg::dlCgSwitchMode. Planned to be removed..";
      reference "Takes effect: Next cell unlock.";
    }
    leaf endcDlNrLowQualThresh {
      type eytypes:int32_range_-40-40;
      status deprecated;
      default "5";
      units "dB";
      description "range -40..40; Default value: 5; Takes effect: Next cell unlock; Status info: Since 24.Q1. Replaced by CgSwitchCfg::dlScgLowQualThresh. Planned to be removed..";
      reference "Takes effect: Next cell unlock.";
    }
    leaf endcDlNrQualHyst {
      type eytypes:int32_range_0-60;
      status deprecated;
      default "5";
      units "dB";
      description "range 0..60; Default value: 5; Takes effect: Next cell unlock; Status info: Since 24.Q1. Replaced by CgSwitchCfg::dlScgLowQualHyst. Planned to be removed..";
      reference "Takes effect: Next cell unlock.";
    }
    leaf endcUlCgSwitchRef {
      type string;
    }
    leaf endcUlLegSwitchEnabled {
      type boolean;
      status deprecated;
      default "false";
      description "Default value: false; Takes effect: Next cell unlock; Status info: Since 24.Q4. Replaced by UlCgSwitchCfg::ulCgSwitchMode. Planned to be removed..";
      reference "Takes effect: Next cell unlock.";
    }
    leaf endcUlNrLowQualThresh {
      type int32 {
        range "-40..145";
      }
      status deprecated;
      default "17";
      units "dB";
      description "range -40..145; Default value: 17; Takes effect: Next cell unlock; Status info: Since 24.Q4. Replaced by UlCgSwitchCfg::ulScgLowQualThresh. Planned to be removed..";
      reference "Takes effect: Next cell unlock.";
    }
    leaf endcUlNrQualHyst {
      type int32 {
        range "1..60";
      }
      status deprecated;
      default "6";
      units "dB";
      description "range 1..60; Default value: 6; Takes effect: Next cell unlock; Status info: Since 24.Q4. Replaced by UlCgSwitchCfg::ulScgLowQualHyst. Planned to be removed..";
      reference "Takes effect: Next cell unlock.";
    }
    leaf energyOptPwrAllocRef {
      type string;
    }
    leaf energyOptSymAllocRef {
      type string;
    }
    leaf essMbsfnConfiguredSubframes {
      type uint32;
      config false;
    }
    leaf essMbsfnSubframeConfig {
      type uint32 {
        range "9440512 | 9441024 | 12584960";
      }
    }
    leaf essMbsfnSubframeVariant {
      type enumeration {
        enum NSA_BASIC;
        enum SA_BASIC;
        enum SA_SIB_ROBUST_15_PERCENT;
        enum NSA_25_PERCENT;
        enum SA_25_PERCENT;
        enum NSA_SA_35_PERCENT;
        enum NSA_SA_45_PERCENT;
        enum NSA_SA_55_PERCENT;
      }
    }
    leaf essPdschEarlyStartConfig {
      type enumeration {
        enum NO_PDSCH_EARLY_START;
        enum ADAPT_MIN_SECOND;
      }
    }
    leaf extCaPriorityRef {
      type string;
    }
    leaf extendedBandN77TwoBwpEnabled {
      type boolean;
      default "false";
      description "Default value: false.";
    }
    leaf externalConnectDelay {
      type int32 {
        range "0 | 100..250";
      }
      default "0";
      units "microsecond";
      description "Default value: 0.";
    }
    leaf fixWideBeamsForPeriodicSr {
      type enumeration {
        enum FIX_WB_FOR_PERIODIC_SR_NONE;
        enum FIX_WB_FOR_PERIODIC_SR_LOW;
        enum FIX_WB_FOR_PERIODIC_SR_MEDIUM;
        enum FIX_WB_FOR_PERIODIC_SR_HIGH;
      }
    }
    leaf improvedUlInSparseBwp {
      type boolean;
      default "true";
      description "Default value: true.";
    }
    leaf improvedUlLinkAdaptation {
      type boolean;
      default "true";
      description "Default value: true.";
    }
    leaf imsEmSupportEnabled {
      type ietfinet:port-number;
      description "Default value: false.";
    }
    leaf interferenceSensingEnabled {
      type boolean;
      default "false";
      description "Default value: false.";
    }
    leaf intMitigationDlSched {
      type enumeration {
        enum DEACTIVATED;
        enum PM_ONLY;
        enum ACTIVATED;
      }
    }
    leaf limitUlQualMonSinrMaxFilterEnabled {
      type boolean;
      default "true";
      description "Default value: true.";
    }
    leaf maxNoOfAdvancedDlMuMimoLayers {
      type int32 {
        range "0 | 2 | 4 | 6 | 8 | 10 | 12 | 14 | 16";
      }
      default "0";
      description "Default value: 0.";
    }
    leaf maxNoOfUeInSparseBwp {
      type eytypes:int32_range_0-5000;
      default "900";
      description "range 0..5000; Default value: 900.";
    }
    leaf maxNoOfUeInSparseSssg {
      type eytypes:int32_range_0-5000;
      default "900";
      description "range 0..5000; Default value: 900.";
    }
    leaf maxOffloadDurationShutDown {
      type int32 {
        range "-1 | 10..1500";
      }
      default "90";
      units "s";
      description "Default value: 90.";
    }
    leaf maxPf3Resources {
      type eytypes:int32_range_1-8;
      default "2";
      description "range 1..8; Default value: 2.";
    }
    leaf maxUeSpeed {
      type enumeration {
        enum UP_TO_10KMPH;
        enum UP_TO_50KMPH;
        enum UP_TO_100KMPH;
        enum UP_TO_200KMPH;
        enum UP_TO_350KMPH;
        enum UP_TO_500KMPH;
      }
    }
    leaf maxUsersRachSchedPusch {
      type eytypes:int32_range_0-100-3;
      default "100";
      description "range 0..100; Default value: 100.";
    }
    leaf msg3MaxHarqTx {
      type uint32 {
        range "1..8";
      }
      default "4";
      description "range 1..8; Default value: 4.";
    }
    leaf nbIotCellDeployed {
      type boolean;
      default "false";
      description "Default value: false.";
    }
    leaf nCI {
      type int64;
      config false;
    }
    leaf networkSignalValue {
      type int32 {
        range "0..100 | 300 | 500 | 4300";
      }
      default "0";
      description "Default value: 0.";
    }
    leaf noOfCbraPreambles {
      type int32 {
        range "16..64";
      }
      default "16";
      description "range 16..64; Default value: 16.";
    }
    leaf nRCellDUId {
      type string;
      mandatory true;
    }
    leaf nrdcCgSwitchRef {
      type string;
    }
    leaf nrdcUlCgSwitchRef {
      type string;
    }
    leaf nrLteCoexistence {
      type boolean;
      default "false";
      description "Default value: false.";
    }
    leaf nRPCI {
      type int32 {
        range "0..1007";
      }
      mandatory true;
      description "range 0..1007.";
    }
    leaf nrRrpEnabled {
      type boolean;
      default "false";
      description "Default value: false.";
    }
    leaf-list nRSectorCarrierRef {
      type string;
      ordered-by user;
    }
    leaf nrSrsDlBufferVolThr {
      type eytypes:int32_range_0-30000;
      default "0";
      units "kB";
      description "range 0..30000; Default value: 0.";
    }
    leaf nrSrsDlPacketAgeThr {
      type eytypes:int32_range_0-1000;
      default "0";
      units "ms";
      description "range 0..1000; Default value: 0.";
    }
    leaf nRTAC {
      type eytypes:int32_range_0-16777215;
      mandatory true;
      description "range 0..16777215.";
    }
    leaf nRTACInSib1Enabled {
      type boolean;
    }
    leaf operationalState {
      type enumeration {
        enum DISABLED;
        enum ENABLED;
      }
      config false;
    }
    leaf-list pairwiseSrsCorrelationThresh {
      type uint32 {
        range "0..1000";
      }
      ordered-by user;
    }
    leaf pCellDlDataOffload {
      type boolean;
      default "false";
      description "Default value: false.";
    }
    leaf pdcchCapacityBoostEnabled {
      type boolean;
      default "false";
      description "Default value: false.";
    }
    leaf pdcchLaBfGainFraction {
      type eytypes:int32_range_0-100-3;
      default "100";
      description "range 0..100; Default value: 100.";
    }
    leaf pdcchLaSinrOffset {
      type eytypes:int32_range_-30-30;
      default "-15";
      units "dB";
      description "range -30..30; Default value: -15.";
    }
    leaf pdcchOlaSelection {
      type enumeration {
        enum NO_OLA;
        enum PDSCH_OLA;
      }
    }
    leaf pdcchRachBoost {
      type eytypes:int32_range_0-6;
      default "0";
      units "dB";
      description "range 0..6; Default value: 0.";
    }
    leaf pdcchReuseForPdschRef {
      type string;
    }
    leaf pdcchSymbConfig {
      type enumeration {
        enum MINIMUM;
        enum STATIC_2;
        enum ADAPT_MAX_2;
        enum ADAPT_MAX_3;
        enum STATIC_3;
      }
    }
    leaf pdschAllowedInDmrsSym {
      type boolean;
      default "false";
      description "Default value: false.";
    }
    leaf pdschRachBoost {
      type eytypes:int32_range_0-12;
      default "0";
      units "dB";
      description "range 0..12; Default value: 0.";
    }
    leaf pdschStartPrbStrategy {
      type enumeration {
        enum START_LOWER_EDGE;
        enum START_HIGHER_EDGE;
        enum RANDOM_START_LOWER_OR_HIGHER;
        enum RANDOM_START_WITHIN_BAND;
      }
    }
    leaf pimaVictimCellId {
      type eytypes:int32_range_0-255;
      config false;
      description "range 0..255.";
    }
    leaf pimaVictimENodeBId {
      type eytypes:int32_range_0-1048575;
      config false;
      description "range 0..1048575.";
    }
    leaf pimAvoidanceControllerEnabled {
      type boolean;
      default "false";
      description "Default value: false.";
    }
    leaf pimAvoidanceModeStatus {
      type enumeration {
        enum AGGRESSOR;
        enum VICTIM;
        enum AGGRESSOR_VICTIM;
      }
      config false;
    }
    leaf pimAvoidPeriodicPause {
      type boolean;
      default "false";
      description "Default value: false.";
    }
    leaf pimMinCrbReservedProportion {
      type ietfinet:port-number;
      default "10";
      units "percent";
      description "range 10..100; Default value: 10.";
    }
    leaf pimRunningVictimCellId {
      type eytypes:int32_range_0-255;
      config false;
      description "range 0..255.";
    }
    leaf pimRunningVictimENBId {
      type eytypes:int32_range_0-1048575;
      config false;
      description "range 0..1048575.";
    }
    list pLMNIdList {
      key "id";
      leaf id {
        type uint32;
        description "Synthetic key for struct sequence entry.";
      }
      ordered-by user;
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
    leaf pMax {
      type int32 {
        range "-30..33 | 1000";
      }
      default "23";
      units "dBm";
      description "Default value: 23.";
    }
    leaf pMaxCa {
      type int32 {
        range "-30..33 | 1000";
      }
      default "1000";
      units "dBm";
      description "Default value: 1000.";
    }
    leaf pointAArfcnDlFdd {
      type int32;
      config false;
    }
    leaf pointAArfcnTdd {
      type eytypes:int32_range_0-3279165;
      config false;
      description "range 0..3279165.";
    }
    leaf pointAArfcnUlFdd {
      type int32;
      config false;
    }
    leaf pointAFrequencyDlFdd {
      type int32;
      config false;
      units "kHz";
    }
    leaf pointAFrequencyTdd {
      type int32 {
        range "0..100000000";
      }
      config false;
      units "kHz";
      description "range 0..100000000.";
    }
    leaf pointAFrequencyUlFdd {
      type int32;
      config false;
      units "kHz";
    }
    leaf poorRadioQualDciBwpSwitchThr {
      type eytypes:int32_range_-40-40;
      default "5";
      units "dB";
      description "range -40..40; Default value: 5.";
    }
    leaf poorRadioQualSssgSwitchThresh {
      type eytypes:int32_range_-40-40;
      default "5";
      units "dB";
      description "range -40..40; Default value: 5.";
    }
    leaf prachConfigIndex {
      type int32 {
        range "155..159";
      }
      description "range 155..159.";
    }
    leaf primaryCellCapable {
      type boolean;
    }
    leaf prioBoundaryCrb {
      type int32 {
        range "0..272";
      }
      description "range 0..272.";
    }
    leaf puschAllowedInDmrsSym {
      type boolean;
      default "false";
      description "Default value: false.";
    }
    leaf puschModeOnFddSCell {
      type enumeration {
        enum LONG;
        enum SHORT_SRS_CONSEC_SL_OVERLAP;
        enum SHORT_SRS_OVERLAP;
        enum SHORT_CONSEC_SL_OVERLAP;
      }
    }
    leaf puschStartPrbStrategy {
      type enumeration {
        enum START_LOWER_EDGE;
        enum START_HIGHER_EDGE;
        enum RANDOM_START_LOWER_OR_HIGHER;
        enum RANDOM_START_WITHIN_BAND;
      }
    }
    leaf pwsBroadcastOngoing {
      type boolean;
      config false;
    }
    leaf pZeroNomPucch {
      type int32 {
        range "-202..24 | 1000";
      }
      default "-114";
      units "dBm";
      description "Default value: -114.";
    }
    leaf pZeroNomPucchAutoSelected {
      type int32;
      config false;
      units "dBm";
    }
    leaf pZeroNomPuschAutoSelected {
      type int32;
      config false;
      units "dBm";
    }
    leaf pZeroNomPuschGrant {
      type int32 {
        range "-202..24 | 1000";
      }
      default "-100";
      units "dBm";
      description "Default value: -100.";
    }
    leaf pZeroNomSrs {
      type int32 {
        range "-202..24";
      }
      default "-110";
      units "dBm";
      description "range -202..24; Default value: -110.";
    }
    leaf pZeroUePuschOffset256Qam {
      type int32 {
        range "0..15";
      }
      default "0";
      units "dB";
      description "range 0..15; Default value: 0.";
    }
    leaf qQualMin {
      type eytypes:int32_range_-43--12;
      units "dB";
      description "range -43..-12.";
    }
    leaf qQualMinOffset {
      type eytypes:int32_range_1-8-14;
      units "dB";
      description "range 1..8.";
    }
    leaf qRxLevMin {
      type eytypes:int32_range_-140--44;
      default "-140";
      units "dBm";
      description "range -140..-44; Default value: -140.";
    }
    leaf qRxLevMinOffset {
      type int32 {
        range "2..16";
      }
      units "dB";
      description "range 2..16.";
    }
    leaf qualHystDciBwpSwitch {
      type eytypes:int32_range_0-60;
      default "3";
      units "dB";
      description "range 0..60; Default value: 3.";
    }
    leaf qualHystSssgSwitch {
      type eytypes:int32_range_0-60;
      default "3";
      units "dB";
      description "range 0..60; Default value: 3.";
    }
    leaf rachPreambleDetThrFraction {
      type eytypes:int32_range_1-100-4;
      default "10";
      description "range 1..100; Default value: 10.";
    }
    leaf rachPreambleFormat {
      type enumeration {
        enum RACH_PREAMBLE_FORMAT_00;
        enum RACH_PREAMBLE_FORMAT_01;
        enum RACH_PREAMBLE_FORMAT_02;
        enum RACH_PREAMBLE_FORMAT_03;
        enum RACH_PREAMBLE_FORMAT_04;
      }
    }
    leaf rachPreambleRecTargetPower {
      type int32 {
        range "-202..-60";
      }
      default "-110";
      units "dBm";
      description "range -202..-60; Default value: -110.";
    }
    leaf rachPreambleTransMax {
      type int32 {
        range "3..8 | 10 | 20 | 50 | 100 | 200";
      }
      default "10";
      description "Default value: 10.";
    }
    leaf rachRef {
      type string;
    }
    leaf rachRestrictedSetConfig {
      type enumeration {
        enum UNRESTRICTED_SET;
        enum RESTRICTED_SET_TYPE_A;
        enum RESTRICTED_SET_TYPE_B;
      }
      config false;
    }
    leaf rachRootSequence {
      type eytypes:int32_range_0-837;
      default "1";
      description "range 0..837; Default value: 1.";
    }
    leaf radioRecIntPwrOffset {
      type int32 {
        range "0..3000";
      }
      default "0";
      units "dB";
      description "range 0..3000; Default value: 0.";
    }
    leaf raResponseWindow {
      type int32 {
        range "10 | 20";
      }
      default "10";
      description "Default value: 10.";
    }
    leaf rdsUeAdvancedPosEnabled {
      type boolean;
      default "false";
      description "Default value: false.";
    }
    leaf redCap1RxEnabled {
      type boolean;
      default "false";
      description "Default value: false.";
    }
    leaf redCap2RxEnabled {
      type boolean;
      default "false";
      description "Default value: false.";
    }
    leaf redCapUeLimit {
      type enumeration {
        enum NONE;
        enum BASIC;
        enum ADVANCED;
        enum MAXIMUM;
      }
    }
    leaf resourceAllocTypeDlRef {
      type string;
    }
    leaf rimAggressorRSSetRef {
      type string;
    }
    leaf rimBgNoiseThresh {
      type int32 {
        range "-125..-100";
      }
      default "-110";
      units "dBm";
      description "range -125..-100; Default value: -110.";
    }
    leaf rimBlank2DlSlotEnabled {
      type boolean;
      default "false";
      description "Default value: false.";
    }
    leaf rimCLPCEnabled {
      type boolean;
      default "true";
      description "Default value: true.";
    }
    leaf rimCLPCHighIpnRSThresh {
      type ietfinet:ip-address;
      units "dBm";
      description "range -120..-70; Default value: -105.";
    }
    leaf rimCLPCPowerTargetOffset {
      type eytypes:int32_range_0-300;
      default "0";
      units "dB";
      description "range 0..300; Default value: 0.";
    }
    leaf rimDetectedRS1State {
      type boolean;
      config false;
    }
    leaf rimDetectedRS2State {
      type boolean;
      config false;
    }
    leaf rimDetectedSlopeState {
      type boolean;
      config false;
    }
    leaf rimDetectionEnabled {
      type boolean;
      default "false";
      description "Default value: false.";
    }
    leaf rimDLMitChangePcThresh {
      type eytypes:int32_range_0-100;
      default "75";
      units "percent";
      description "range 0..100; Default value: 75.";
    }
    leaf rimDLMitChangeSymThresh {
      type eytypes:int32_range_0-100;
      default "60";
      units "percent";
      description "range 0..100; Default value: 60.";
    }
    leaf rimDLMitChangeTime {
      type int32 {
        range "2..10";
      }
      default "2";
      description "range 2..10; Default value: 2.";
    }
    leaf rimFlexSrsPositionsEnabled {
      type boolean;
      default "false";
      description "Default value: false.";
    }
    leaf rimHighIpnState {
      type ietfinet:ip-address;
      config false;
    }
    leaf rimHighIpnThresh {
      type ietfinet:ip-address;
      units "dBm";
      description "range -125..-80; Default value: -105.";
    }
    leaf rimLocationEnabled {
      type boolean;
      default "false";
      description "Default value: false.";
    }
    leaf rimMaxNoReportedSequences {
      type ietfinet:port-number;
      default "50";
      description "range 20..100; Default value: 50.";
    }
    leaf rimNotEnoughPortionThresh {
      type ietfinet:port-number;
      default "20";
      units "percent";
      description "range 0..100; Default value: 20.";
    }
    leaf rimOffloadEnabled {
      type boolean;
      default "false";
      description "Default value: false.";
    }
    leaf rimOffloadHighIpNThresh {
      type ietfinet:ip-address;
      units "dBm";
      description "range -125..-80; Default value: -105.";
    }
    leaf rimPdschSlotBlankDlOffset {
      type int32 {
        range "0..20";
      }
      default "0";
      units "dBm";
      description "range 0..20; Default value: 0.";
    }
    leaf rimPdschSlotBlankDlSsThresh {
      type eytypes:int32_range_-120--70;
      default "-95";
      units "dBm";
      description "range -120..-70; Default value: -95.";
    }
    leaf rimPdschSlotBlankMode {
      type enumeration {
        enum DISABLED;
        enum AUTO_MODE;
        enum SPECIAL_SLOT;
        enum SPECIAL_DL_SLOT;
        enum AUTO_RS1;
        enum AUTO_RS1_PC;
        enum SPECIAL_2DL_SLOT;
      }
    }
    leaf rimPdschSlotBlankSsThresh {
      type eytypes:int32_range_-120--70;
      default "-95";
      units "dBm";
      description "range -120..-70; Default value: -95.";
    }
    leaf rimPdschSlotBlankStopThresh {
      type eytypes:int32_range_-120--70;
      default "-101";
      units "dBm";
      description "range -120..-70; Default value: -101.";
    }
    leaf rimPdschSlotBlankTimer {
      type eytypes:int32_range_0-86400;
      default "1260";
      units "s";
      description "range 0..86400; Default value: 1260.";
    }
    leaf rimPdschSlotPcBlankThrOffset {
      type int32 {
        range "0..20";
      }
      default "6";
      units "dBm";
      description "range 0..20; Default value: 6.";
    }
    leaf rimPdschSlotPcPrbUsageThresh {
      type eytypes:int32_range_0-100;
      default "30";
      units "percent";
      description "range 0..100; Default value: 30.";
    }
    leaf rimPdschSlotPcPwrBackoffHigh {
      type int32 {
        range "0..10";
      }
      default "10";
      units "dB";
      description "range 0..10; Default value: 10.";
    }
    leaf rimPdschSlotPcPwrBackoffLow {
      type int32 {
        range "0..10";
      }
      default "6";
      units "dB";
      description "range 0..10; Default value: 6.";
    }
    leaf rimPdschSlotPcSinrThresh {
      type int32 {
        range "0..32";
      }
      default "13";
      units "dB";
      description "range 0..32; Default value: 13.";
    }
    leaf rimPdschSlotPcThreshHigh {
      type eytypes:int32_range_-120--70;
      default "-90";
      units "dBm";
      description "range -120..-70; Default value: -90.";
    }
    leaf rimPdschSlotPcThreshLow {
      type eytypes:int32_range_-120--70;
      default "-93";
      units "dBm";
      description "range -120..-70; Default value: -93.";
    }
    leaf rimPowerControlEnabled {
      type boolean;
      default "false";
      description "Default value: false.";
    }
    leaf rimQRxLevMinConstant {
      type uint32 {
        range "0..40";
      }
      default "0";
      units "dB";
      description "range 0..40; Default value: 0.";
    }
    leaf rimQRxLevMinIpNCompFactor {
      type ietfinet:ip-address;
      description "range 0..200; Default value: 100.";
    }
    leaf rimRefIpN {
      type ietfinet:ip-address;
      units "dBm";
      description "range -125..-100; Default value: -115.";
    }
    leaf rimRiTriggeredOffloadEnabled {
      type boolean;
      default "true";
      description "Default value: true.";
    }
    leaf rimRS1DetectedThresh {
      type eytypes:uint32_range_0-214748647;
      default "4";
      description "range 0..214748647; Default value: 4.";
    }
    leaf rimRS1FarThresh {
      type eytypes:int32_range_0-100;
      default "50";
      units "percent";
      description "range 0..100; Default value: 50.";
    }
    leaf rimRS1NotEnoughDetectedThresh {
      type eytypes:uint32_range_0-214748647;
      description "range 0..214748647.";
    }
    leaf rimRS1PortionStartDLMitThresh {
      type ietfinet:port-number;
      default "50";
      units "percent";
      description "range 0..100; Default value: 50.";
    }
    leaf rimRS1PortionStopDLMitThresh {
      type ietfinet:port-number;
      default "20";
      units "percent";
      description "range 0..100; Default value: 20.";
    }
    leaf rimRS2DetectedThresh {
      type eytypes:uint32_range_0-214748647;
      default "6";
      description "range 0..214748647; Default value: 6.";
    }
    leaf rimRS2TransEnabled {
      type boolean;
      default "true";
      description "Default value: true.";
    }
    leaf rimRS2TransStartThresh {
      type eytypes:int32_range_0-100;
      units "percent";
      description "range 0..100.";
    }
    leaf rimRS2TransStopThresh {
      type eytypes:int32_range_0-100;
      units "percent";
      description "range 0..100.";
    }
    leaf rimRSDetectionThresholdOffset {
      type eytypes:int32_range_1-100;
      default "10";
      units "percent";
      description "range 1..100; Default value: 10.";
    }
    leaf rimRSDetectionTime {
      type int32 {
        range "1..30";
      }
      default "3";
      description "range 1..30; Default value: 3.";
    }
    leaf rimRSReportInterval {
      type ietfinet:port-number;
      default "1000";
      units "ms";
      description "range 1000..10000; Default value: 1000.";
    }
    leaf rimSlopeDetectPeriod {
      type int32 {
        range "1..30";
      }
      default "10";
      units "minute";
      description "range 1..30; Default value: 10.";
    }
    leaf rimSlopeFrontSymIndex {
      type enumeration {
        enum SS_LAST_UL;
        enum SS_2LAST_UL;
        enum SS_3LAST_UL;
        enum SS_4LAST_UL;
        enum UL1_FRONT_DMRS;
        enum UL1_END_DMRS;
        enum UL2_FRONT_DMRS;
      }
    }
    leaf rimSlopePwrDiffThresh {
      type eytypes:int32_range_1-8-14;
      default "3";
      units "dB";
      description "range 1..8; Default value: 3.";
    }
    leaf rimTransmittedRS1State {
      type boolean;
      config false;
    }
    leaf rimTransmittedRS2State {
      type boolean;
      config false;
    }
    leaf-list rimValidFrequencyOffsets {
      type int32 {
        range "0..549";
      }
    }
    leaf rimVictimRSSetRef {
      type string;
    }
    leaf riOffloadHighIpnRSThresh {
      type ietfinet:ip-address;
      units "dBm";
      description "range -120..-70; Default value: -110.";
    }
    leaf secondaryCellOnly {
      type boolean;
      default "true";
      description "Default value: true.";
    }
    leaf serviceState {
      type enumeration {
        enum OUT_OF_SERVICE;
        enum IN_SERVICE;
      }
      config false;
    }
    leaf sfnOffset {
      type int16 {
        range "-512..511";
      }
      default "0";
      units "radio frame";
      description "range -512..511; Default value: 0.";
    }
    leaf sib9BroadcastOngoing {
      type boolean;
      config false;
    }
    list sibType2 {
      key "id";
      leaf id {
        type uint32;
        description "Synthetic key for struct entry.";
      }
      container attributes {
      leaf siBroadcastStatus {
        type enumeration {
          enum BROADCASTING;
        }
      }
      leaf siPeriodicity {
        type ietfinet:ip-address;
        units "radio frame";
        description "Default value: 64.";
      }
      }
    }
    list sibType4 {
      key "id";
      leaf id {
        type uint32;
        description "Synthetic key for struct entry.";
      }
      container attributes {
      leaf siBroadcastStatus {
        type enumeration {
          enum BROADCASTING;
        }
      }
      leaf siPeriodicity {
        type ietfinet:ip-address;
        units "radio frame";
        description "Default value: 64.";
      }
      }
    }
    list sibType5 {
      key "id";
      leaf id {
        type uint32;
        description "Synthetic key for struct entry.";
      }
      container attributes {
      leaf siBroadcastStatus {
        type enumeration {
          enum BROADCASTING;
        }
      }
      leaf siPeriodicity {
        type ietfinet:ip-address;
        units "radio frame";
        description "Default value: 64.";
      }
      }
    }
    list sibType6 {
      key "id";
      leaf id {
        type uint32;
        description "Synthetic key for struct entry.";
      }
      container attributes {
      leaf siBroadcastStatus {
        type enumeration {
          enum BROADCASTING;
        }
      }
      leaf siPeriodicity {
        type ietfinet:ip-address;
        units "radio frame";
        description "Default value: 16.";
      }
      }
    }
    list sibType7 {
      key "id";
      leaf id {
        type uint32;
        description "Synthetic key for struct entry.";
      }
      container attributes {
      leaf siBroadcastStatus {
        type enumeration {
          enum BROADCASTING;
        }
      }
      leaf siPeriodicity {
        type ietfinet:ip-address;
        units "radio frame";
        description "Default value: 64.";
      }
      }
    }
    list sibType8 {
      key "id";
      leaf id {
        type uint32;
        description "Synthetic key for struct entry.";
      }
      container attributes {
      leaf siBroadcastStatus {
        type enumeration {
          enum BROADCASTING;
        }
      }
      leaf siPeriodicity {
        type ietfinet:ip-address;
        units "radio frame";
        description "Default value: 64.";
      }
      }
    }
    list sibType9 {
      key "id";
      leaf id {
        type uint32;
        description "Synthetic key for struct entry.";
      }
      container attributes {
      leaf includeReferenceTimeInfo {
        type boolean;
        default "false";
        description "Default value: false.";
      }
      leaf siBroadcastStatus {
        type enumeration {
          enum BROADCASTING;
        }
      }
      leaf siPeriodicity {
        type ietfinet:ip-address;
        units "radio frame";
        description "Default value: 64.";
      }
      }
    }
    leaf siWindowLength {
      type int32 {
        range "5 | 10 | 20 | 40 | 80 | 160 | 320 | 640 | 1280";
      }
      default "20";
      units "slot";
      description "Default value: 20.";
    }
    list slotSpecificDlLaConfigList {
      key "id";
      leaf id {
        type uint32;
        description "Synthetic key for struct sequence entry.";
      }
      ordered-by user;
      container attributes {
      leaf modulationEnabledList {
        type string {
          length "4";
          pattern "[01]*1[01]*";
        }
        description "length 4..4.";
      }
      leaf outerLoopAdjustDisabled {
        type string;
      }
      leaf rankEnabledList {
        type string {
          length "4";
          pattern "[01]*1[01]*";
        }
        description "length 4..4.";
      }
      leaf sfnOffsetForLaConfig {
        type eytypes:int32_range_0-1023-23;
        description "range 0..1023.";
      }
      leaf sfnPeriodForLaConfig {
        type eytypes:int32_range_1-1024;
        description "range 1..1024.";
      }
      leaf sinrBackoff {
        type eytypes:int32_range_0-300;
        units "dB";
        description "range 0..300.";
      }
      leaf slotForLaConfig {
        type int32 {
          range "-1..19";
        }
        description "range -1..19.";
      }
      }
    }
    list sNSSAIList {
      key "id";
      leaf id {
        type uint32;
        description "Synthetic key for struct sequence entry.";
      }
      ordered-by user;
      container attributes {
      leaf sd {
        type eytypes:int32_range_0-16777215;
        description "range 0..16777215.";
      }
      leaf sst {
        type eytypes:int32_range_0-255;
        description "range 0..255.";
      }
      }
    }
    leaf speedAdvMuThresh {
      type int32 {
        range "0..500";
      }
      default "500";
      units "km/h";
      description "range 0..500; Default value: 500.";
    }
    leaf speedAdvSuThresh {
      type int32 {
        range "0..500";
      }
      default "500";
      units "km/h";
      description "range 0..500; Default value: 500.";
    }
    leaf srbPriorityRef {
      type string;
    }
    leaf srDetectHighEnabled {
      type boolean;
      default "false";
      description "Default value: false.";
    }
    leaf srPeriodicityPoolSetRef {
      type string;
    }
    leaf srPeriodicityRef {
      type string;
    }
    leaf srsCapacityBoostEnabled {
      type boolean;
      default "false";
      description "Default value: false.";
    }
    leaf srsHoppingBandwidth {
      type enumeration {
        enum FULL;
        enum HALF;
      }
    }
    leaf srsPeriodicity {
      type int32 {
        range "5 | 10 | 20 | 40 | 80 | 160";
      }
      default "40";
      units "slot";
      description "Default value: 40.";
    }
    leaf srsSymbolCombSelectionMode {
      type enumeration {
        enum DEFAULT;
        enum COMMON;
      }
    }
    leaf ssbDuration {
      type eytypes:int32_range_1-5;
      units "ms";
      description "range 1..5.";
    }
    leaf ssbDurationAutoSelected {
      type int32;
      config false;
      units "ms";
    }
    leaf ssbFrequency {
      type eytypes:int32_range_0-3279165;
      default "0";
      description "range 0..3279165; Default value: 0.";
    }
    leaf ssbFrequencyAutoSelected {
      type int32;
      config false;
    }
    leaf ssbGscn {
      type int32;
      config false;
    }
    leaf ssbIndex {
      type eytypes:int32_range_0-2;
      description "range 0..2.";
    }
    leaf ssbIndexAutoSelected {
      type int32;
      config false;
    }
    leaf ssbOffset {
      type eytypes:int32_range_0-159;
      units "ms";
      description "range 0..159.";
    }
    leaf ssbOffsetAutoSelected {
      type int32;
      config false;
      units "ms";
    }
    leaf ssbPeriodicity {
      type int32 {
        range "5 | 10 | 20 | 40 | 80 | 160";
      }
      default "20";
      units "ms";
      description "Default value: 20.";
    }
    leaf ssbPowerBoost {
      type eytypes:int32_range_0-12;
      default "0";
      units "dB";
      description "range 0..12; Default value: 0.";
    }
    leaf ssbPowerBoostMMimoSleep {
      type eytypes:int32_range_0-12;
      units "dB";
      description "range 0..12.";
    }
    leaf ssbSubCarrierSpacing {
      type int32 {
        range "15 | 30 | 120 | 240";
      }
      default "120";
      units "kHz";
      description "Default value: 120.";
    }
    leaf ssbTimeShiftEnabled {
      type boolean;
      default "false";
      description "Default value: false.";
    }
    leaf sssgSwitchRef {
      type string;
    }
    leaf subCarrierSpacing {
      type int32 {
        range "15 | 30 | 60 | 120";
      }
      default "120";
      units "kHz";
      description "Default value: 120.";
    }
    leaf tddBorderVersion {
      type enumeration {
        enum DISABLED;
        enum VERSION_1;
      }
    }
    leaf tddSpecialSlotPattern {
      type enumeration {
        enum TDD_SPECIAL_SLOT_PATTERN_00;
        enum TDD_SPECIAL_SLOT_PATTERN_01;
        enum TDD_SPECIAL_SLOT_PATTERN_02;
        enum TDD_SPECIAL_SLOT_PATTERN_03;
        enum TDD_SPECIAL_SLOT_PATTERN_04;
        enum TDD_SPECIAL_SLOT_PATTERN_05;
        enum TDD_SPECIAL_SLOT_PATTERN_06;
        enum TDD_SPECIAL_SLOT_PATTERN_07;
      }
    }
    leaf tddUlDlPattern {
      type enumeration {
        enum TDD_ULDL_PATTERN_00;
        enum TDD_ULDL_PATTERN_01;
        enum TDD_ULDL_PATTERN_02;
        enum TDD_ULDL_PATTERN_03;
        enum TDD_ULDL_PATTERN_04;
        enum TDD_ULDL_PATTERN_05;
        enum TDD_ULDL_PATTERN_06;
        enum TDD_ULDL_PATTERN_07;
        enum TDD_ULDL_PATTERN_08;
      }
    }
    leaf totalNoOfRaPreambles {
      type int32 {
        range "16..64";
      }
      default "17";
      description "range 16..64; Default value: 17.";
    }
    leaf trafficDefinitionRef {
      type string;
    }
    leaf trafficGroupRef {
      type string;
      status deprecated;
      description "MOM flags: isNillable=true; Status info: Since 25.Q2. Replaced by trafficDefinitionRef. Planned to be removed..";
    }
    leaf transmitPosSibEnabled {
      type boolean;
      default "false";
      description "Default value: false.";
    }
    leaf trsConfigMode {
      type enumeration {
        enum AUTO;
        enum FULL_BW;
        enum PRB_52;
        enum FULL_BW_MUTE;
      }
    }
    leaf trsModeSelected {
      type enumeration {
        enum AUTO;
        enum FULL_BW;
        enum PRB_52;
        enum FULL_BW_MUTE;
      }
      config false;
    }
    leaf trsPeriodicity {
      type int32 {
        range "10 | 20 | 40 | 80";
      }
      default "20";
      units "ms";
      description "Default value: 20.";
    }
    leaf trsPowerBoosting {
      type int32 {
        range "0..6";
      }
      default "0";
      description "range 0..6; Default value: 0.";
    }
    leaf trsResourceShifting {
      type enumeration {
        enum DEACTIVATED;
        enum ACTIVATED;
      }
    }
    leaf typeISinglePanelRiRestriction {
      type eytypes:uint8_range_1-15;
      default "15";
      description "range 1..15; Default value: 15.";
    }
    leaf ueAmbrPriorityDomainThresh {
      type eytypes:int32_range_1-64;
      description "range 1..64.";
    }
    leaf ueBbProfileRef {
      type string;
    }
    leaf ueSpecificDrxMode {
      type enumeration {
        enum ENABLED;
        enum DISABLED;
      }
    }
    leaf ul256QamEnabled {
      type boolean;
      default "false";
      description "Default value: false.";
    }
    leaf ulAvailableCrbs {
      type eytypes:uint32_range_0-272;
      description "range 0..272.";
    }
    leaf ulCaTimeAlignmentMode {
      type enumeration {
        enum N_TA_O_STANDARD;
        enum N_TA_O_39936;
      }
    }
    leaf ulMaxMuMimoLayers {
      type int32 {
        range "0 | 2 | 4 | 6 | 8";
      }
      default "0";
      description "Default value: 0.";
    }
    leaf ulQualMonitorHyst {
      type int32 {
        range "1..30";
      }
      default "6";
      units "dB";
      description "range 1..30; Default value: 6.";
    }
    leaf ulQualMonitorTime {
      type eytypes:int32_range_0-10000;
      default "1000";
      units "ms";
      description "range 0..10000; Default value: 1000.";
    }
    leaf ulRobustLaEnabled {
      type boolean;
      status deprecated;
      default "false";
      description "Default value: false; Takes effect: Next cell unlock; Status info: Since 25.Q2. Planned to be removed..";
      reference "Takes effect: Next cell unlock.";
    }
    leaf ulScSpillover {
      type int32 {
        range "0..11";
      }
      default "0";
      units "subcarrier";
      description "range 0..11; Default value: 0.";
    }
    leaf ulStartCrb {
      type eytypes:uint32_range_0-272;
      default "0";
      description "range 0..272; Default value: 0.";
    }
    leaf ulTxSwitchingEnabled {
      type boolean;
      default "false";
      description "Default value: false.";
    }
    leaf userLabel {
      type string;
    }
    leaf pmUeCtxtSetupSucc {
      type uint64;
      config false;
    }
    leaf-list pmRimPdschActionLastDlSlotDistr {
      type uint64;
    }
    leaf-list pmMacHarqDlAck256QamInitSlotDistr {
      type ietfyang:mac-address;
    }
    leaf pmMacVolUlUnresUeBsrGrant {
      type ietfyang:mac-address;
      config false;
    }
    leaf-list pmMacSchedSlotPdschSavedSymDistr {
      type ietfyang:mac-address;
    }
    leaf-list pmMacSchedSlotDlSCellActivatedDistr {
      type ietfyang:mac-address;
    }
    leaf pmMacRBSymAvailPdcch {
      type ietfyang:mac-address;
      config false;
    }
    leaf-list pmMacVolDlSCellExtBwp {
      type ietfyang:mac-address;
    }
    leaf pmDrxSleepTimeConfGrant {
      type uint64;
      config false;
    }
    leaf pmMacVolUlUnresUe {
      type ietfyang:mac-address;
      config false;
    }
    leaf pmRadioRaCfAttMsg2 {
      type uint64;
      config false;
    }
    leaf pmPuschSchedActivityDynSlotAggr {
      type uint64;
      config false;
    }
    leaf-list pmMacHarqDlNack64QamInitSlotDistr {
      type ietfyang:mac-address;
    }
    leaf pmMacHarqDlNack256QamInit {
      type ietfyang:mac-address;
      config false;
    }
    leaf-list pmMacVolDlBwp {
      type ietfyang:mac-address;
    }
    leaf-list pmMacPdcchCongestionUlExclPreschedDistr {
      type ietfyang:mac-address;
    }
    leaf pmMacRBSymUsedPdcchTypeBAggrLvl4 {
      type ietfyang:mac-address;
      config false;
    }
    leaf pmRadioRaCbAttMsg2 {
      type uint64;
      config false;
    }
    leaf-list pmRimDetectedAggressorDistanceMaxDistr {
      type int64;
    }
    leaf-list pmMacBsrLcg4Distr {
      type ietfyang:mac-address;
    }
    leaf pmPimAvoidMutedCrbSamp {
      type uint64;
      config false;
    }
    leaf pmSessionTimeUeBwpSamp {
      type uint64;
      config false;
    }
    leaf pmMacThpUlUeMax {
      type ietfyang:mac-address;
      config false;
    }
    leaf pmRadioPdschEmptySlots {
      type uint64;
      config false;
    }
    leaf-list pmMacContentionDelayDlDistr {
      type ietfyang:mac-address;
    }
    leaf pmMacVolDlDrbSingleBurst {
      type ietfyang:mac-address;
      config false;
    }
    leaf pmPuschAvailTime {
      type uint64;
      config false;
    }
    leaf pmRadioMacDftsTransUl {
      type ietfyang:mac-address;
      config false;
    }
    leaf-list pmMacVolDlDrbSingleSlotShortBurstQoS {
      type ietfyang:mac-address;
    }
    leaf pmRadioRaCfFailMsg1Ooc {
      type uint64;
      config false;
    }
    leaf pmRadioRaCfUnassignedFalse {
      type uint64;
      config false;
    }
    leaf pmMacHarqUlDtx64Qam {
      type ietfyang:mac-address;
      config false;
    }
    leaf pmMacRBSymUsedNrEfficiency {
      type ietfyang:mac-address;
      config false;
    }
    leaf pmMacVolDl {
      type ietfyang:mac-address;
      config false;
    }
    leaf pmMacHarqDlNack64Qam {
      type ietfyang:mac-address;
      config false;
    }
    leaf pmPagReceived {
      type uint64;
      config false;
    }
    leaf pmActiveUeUlSamp {
      type ietfyang:mac-address;
      config false;
    }
    leaf pmActiveUeDlTrueSamp {
      type ietfyang:mac-address;
      config false;
    }
    leaf pmBwpUeConfSamp {
      type uint64;
      config false;
    }
    leaf pmRlcDelayTimeDl {
      type uint64;
      config false;
    }
    leaf pmRlcArqUlAck {
      type uint64;
      config false;
    }
    leaf-list pmRadioUeRepCqi64QamLowSeRank1Distr {
      type uint64;
    }
    leaf pmActiveUeUlMax {
      type ietfyang:mac-address;
      config false;
    }
    leaf-list pmRadioUeRepPmiSecondaryCsiRsRank2Distr {
      type uint64;
    }
    leaf-list pmRadioRecInterferencePwrUlSlot6Distr {
      type uint64;
    }
    leaf pmMacVolDlDrb {
      type ietfyang:mac-address;
      config false;
    }
    leaf pmRadioPucchFailSr {
      type uint64;
      config false;
    }
    leaf-list pmMacBsrLcg0Distr {
      type ietfyang:mac-address;
    }
    leaf-list pmRadioServingBeamDlDistr {
      type uint64;
    }
    leaf pmPdschSchedActivityLowPrioArea {
      type uint64;
      config false;
    }
    leaf pmMacVolUlResUeLate {
      type ietfyang:mac-address;
      config false;
    }
    leaf-list pmDrbEstabSoftAdmissionQos {
      type uint64;
    }
    leaf pmMacTimeDlDrbSamp {
      type ietfyang:mac-address;
      config false;
    }
    leaf pmMacHarqUlAck16QamInit {
      type ietfyang:mac-address;
      config false;
    }
    leaf-list pmUeCtxtModAttWvfSwitchDistr {
      type uint64;
    }
    leaf-list pmMacRBSymUsedPdschAdvMimoUserDistr {
      type ietfyang:mac-address;
    }
    leaf-list pmPdcchDciSwitchBwp {
      type uint64;
    }
    leaf pmMacOverlapTimeDlDrbExtSCell {
      type ietfyang:mac-address;
      config false;
    }
    leaf-list pmMacRBSymUsedPdschAdvEisSuMimoTxRankDistr {
      type ietfyang:mac-address;
    }
    leaf-list pmMacVolUlSCellBwp {
      type ietfyang:mac-address;
    }
    leaf pmMacActiveSrsUe {
      type ietfyang:mac-address;
      config false;
    }
    leaf pmMacHarqUlAckInclPreschedNoData {
      type ietfyang:mac-address;
      config false;
    }
    leaf pmPuschSchedActivityPCellCa {
      type uint64;
      config false;
    }
    leaf pmUeCtxtAllocatedSamp {
      type uint64;
      config false;
    }
    leaf-list pmRlcDelayPktTransmitDlQos {
      type uint64;
    }
    leaf pmDuCellDownLockMan {
      type uint64;
      config false;
    }
    leaf-list pmDrbModSoftAdmissionQos {
      type uint64;
    }
    leaf-list pmMacTimeDlDrbSingleSlotShortBurstQoS {
      type ietfyang:mac-address;
    }
    leaf-list pmRadioUeRepCqi64QamRank2Distr {
      type uint64;
    }
    leaf pmRadioRaCfPreambles {
      type uint64;
      config false;
    }
    leaf-list pmMacRBSymUsedPdschMimoUserDistr {
      type ietfyang:mac-address;
    }
    leaf-list pmRadioPdschTable1MbsfnMcsDistr {
      type uint64;
    }
    leaf pmMacRBSymAvailUl {
      type ietfyang:mac-address;
      config false;
    }
    leaf pmDrxTotalTime {
      type uint64;
      config false;
    }
    leaf pmPagDiscardedEdrx {
      type uint64;
      config false;
    }
    leaf-list pmRadioSinrPuschHarqFailDistr {
      type uint64;
    }
    leaf-list pmRadioPreambleSinrMsg3SuccTx2Distr {
      type uint64;
    }
    leaf pmMacRBSymUsedPusch1Port1Layer {
      type ietfinet:port-number;
      config false;
    }
    leaf pmMacRBSymUsedPusch2Port1Layer {
      type ietfinet:port-number;
      config false;
    }
    leaf pmUeCtxtSetupAtt {
      type uint64;
      config false;
    }
    leaf pmMacRBSymUsedPdcchAilg {
      type ietfyang:mac-address;
      config false;
    }
    leaf-list pmMacTimeDlDrbLastSlotQos {
      type ietfyang:mac-address;
    }
    leaf-list pmRadioRecInterferencePwrUlSlot8Distr {
      type uint64;
    }
    leaf-list pmMacRBSymUsedPdcchTypeAAggrLvl16Bwp {
      type ietfyang:mac-address;
    }
    leaf-list pmRadioPdschRimBlankSymbolCellDistr {
      type int64;
    }
    leaf pmRadioRecInterferencePwrSlotSamp {
      type uint64;
      config false;
    }
    leaf pmMacOffloadVolDlSCellExt {
      type ietfyang:mac-address;
      config false;
    }
    leaf pmMacHarqUlDtx64QamInit {
      type ietfyang:mac-address;
      config false;
    }
    leaf-list pmRadioRaCfPreambleFailedUlCaDistr {
      type uint64;
    }
    leaf-list pmRadioMacLongPsrSinrDistr {
      type ietfyang:mac-address;
    }
    leaf-list pmRadioUeRepPmiPrimaryCsiRsRank2Distr {
      type ietfinet:ip-address;
    }
    leaf pmMacHarqUlNack16Qam {
      type ietfyang:mac-address;
      config false;
    }
    leaf-list pmRadioRecInterferencePwrSumPrbDistr {
      type uint64;
    }
    leaf pmRadioRaCfSucc {
      type uint64;
      config false;
    }
    leaf pmMacHarqDlResAllocType0Dci11 {
      type ietfyang:mac-address;
      config false;
    }
    leaf-list pmRadioUeRepRankDistr {
      type uint64;
    }
    leaf-list pmMacRBSymUsedPdcchTypeADciSwitchBwp {
      type ietfyang:mac-address;
    }
    leaf pmMacPduVolDlUeSCell {
      type ietfyang:mac-address;
      config false;
    }
    leaf pmMacHighPrioPreschedGrants {
      type ietfyang:mac-address;
      config false;
    }
    leaf pmMacOffloadVolUlSCell {
      type ietfyang:mac-address;
      config false;
    }
    leaf-list pmRadioPuschPwrSpectralDensityDistr {
      type uint64;
    }
    leaf-list pmRadioSinrPucchF0Distr {
      type uint64;
    }
    leaf-list pmRadioUeRepPmiSecondaryCsiRsRank3Distr {
      type uint64;
    }
    leaf pmMacHighPrioPreschedGrantsUsed {
      type ietfyang:mac-address;
      config false;
    }
    leaf-list pmMacUaiOhIndSCellDistr {
      type ietfyang:mac-address;
    }
    leaf pmMacRBSymUsedPdcchTypeAAggrLvl8 {
      type ietfyang:mac-address;
      config false;
    }
    leaf pmCellUptime {
      type uint64;
      config false;
    }
    leaf-list pmMeasGapDurationDistr {
      type uint64;
    }
    leaf pmBwpSwitchDciDropped {
      type ietfinet:ip-prefix;
      config false;
    }
    leaf pmMacHarqDlDtx64Qam {
      type ietfyang:mac-address;
      config false;
    }
    leaf-list pmMacRBSymUsedPdschSuMimoLayerDistr {
      type ietfyang:mac-address;
    }
    leaf pmMacVolDlCaDrb {
      type ietfyang:mac-address;
      config false;
    }
    leaf pmUeCtxtAllocatedMax {
      type int64;
      config false;
    }
    leaf pmMacHarqDlAck16Qam {
      type ietfyang:mac-address;
      config false;
    }
    leaf pmActiveUeUlSum {
      type ietfyang:mac-address;
      config false;
    }
    leaf pmMacHarqUlDtxQpsk {
      type ietfyang:mac-address;
      config false;
    }
    leaf pmMacHarqDlNack256Qam {
      type ietfyang:mac-address;
      config false;
    }
    leaf-list pmPagBundledUeDistr {
      type uint64;
    }
    leaf pmMacRBSymCsiRs {
      type ietfyang:mac-address;
      config false;
    }
    leaf-list pmMacBsrLcg3Distr {
      type ietfyang:mac-address;
    }
    leaf-list pmMacRBSymUsedPdschMimoSinrThresUserDistr {
      type ietfyang:mac-address;
    }
    leaf pmMacRBSymUsedPdschTypeA {
      type ietfyang:mac-address;
      config false;
    }
    leaf pmRadioRaCbFailMsg3Dtx {
      type uint64;
      config false;
    }
    leaf-list pmRadioMacLongPsrRsrpDistr {
      type ietfyang:mac-address;
    }
    leaf-list pmMacLatTimeDlDrxSyncSampQos {
      type ietfyang:mac-address;
    }
    leaf-list pmMacLatTimeDlNoDrxSyncQos {
      type ietfyang:mac-address;
    }
    leaf-list pmMacBsrLcg6Distr {
      type ietfyang:mac-address;
    }
    leaf-list pmMacRBSymUsedPdschAdvEisMuMimoLayerDistr {
      type ietfyang:mac-address;
    }
    leaf-list pmRadioRecInterferencePwrUlSlot2Distr {
      type uint64;
    }
    leaf pmPdschPimBlankedSlot {
      type uint64;
      config false;
    }
    leaf pmMacHarqUlDtx256Qam {
      type ietfyang:mac-address;
      config false;
    }
    leaf-list pmMacRBSymUsedPdschCbRatDistr {
      type ietfyang:mac-address;
    }
    leaf pmMacRBSymAvailPucch {
      type ietfyang:mac-address;
      config false;
    }
    leaf pmMacTimeDlCaDrbActivity {
      type ietfyang:mac-address;
      config false;
    }
    leaf-list pmRimPdschActionSpecialSlotDistr {
      type uint64;
    }
    leaf-list pmRadioPreambleSinrMsg3DtxAllTxDistr {
      type uint64;
    }
    leaf pmMacRBSymUsedPdschTypeB {
      type ietfyang:mac-address;
      config false;
    }
    leaf-list pmRadioRecInterferencePowerDistr {
      type uint64;
    }
    leaf pmMacOffloadVolUlSCellExt {
      type ietfyang:mac-address;
      config false;
    }
    leaf pmMacVolDlDrbLastSlot {
      type ietfyang:mac-address;
      config false;
    }
    leaf pmMacTimeDlDrbSingleSlotShortBurst {
      type ietfyang:mac-address;
      config false;
    }
    leaf pmMacVolUlUnresUePreemptGrant {
      type ietfyang:mac-address;
      config false;
    }
    leaf-list pmMacVolPdschMimoSinrThresUserDistr {
      type ietfyang:mac-address;
    }
    leaf-list pmMacBsrLcg5Distr {
      type ietfyang:mac-address;
    }
    leaf pmRadioMacWvfSwitchSuccUlDfts {
      type ietfyang:mac-address;
      config false;
    }
    leaf-list pmMacHarqDlAck16QamInitSlotDistr {
      type ietfyang:mac-address;
    }
    leaf-list pmRadioMacShortPsrRsrpDistr {
      type ietfyang:mac-address;
    }
    leaf-list pmMacRBSymUsedPdschAdvSuMimoLayerDistr {
      type ietfyang:mac-address;
    }
    leaf pmMacRBSymUsedPdcchTypeBAggrLvl8 {
      type ietfyang:mac-address;
      config false;
    }
    leaf pmRimDetectedVictimSetIDsMax {
      type int64;
      config false;
    }
    leaf pmMacVolDlAdvEis {
      type ietfyang:mac-address;
      config false;
    }
    leaf pmMacVolUlSCellExt {
      type ietfyang:mac-address;
      config false;
    }
    leaf pmRadioMacCpofdmTransUl {
      type ietfyang:mac-address;
      config false;
    }
    leaf pmPagReceivedEdrx {
      type uint64;
      config false;
    }
    leaf pmMacHarqDlDtx64QamInit {
      type ietfyang:mac-address;
      config false;
    }
    leaf-list pmMacRBSymUsedPdcchTypeAAggrLvl4Bwp {
      type ietfyang:mac-address;
    }
    leaf pmPdschPimBlankingReq {
      type uint64;
      config false;
    }
    leaf-list pmSssgUeConfSumDistr {
      type uint64;
    }
    leaf-list pmRadioPdschTable3McsDistr {
      type uint64;
    }
    leaf pmMacHarqDlDtxQpsk {
      type ietfyang:mac-address;
      config false;
    }
    leaf pmDrxSleepTime {
      type uint64;
      config false;
    }
    leaf pmMacVolUlUeLastSlot {
      type ietfyang:mac-address;
      config false;
    }
    leaf pmMacTimeDlCaDrb {
      type ietfyang:mac-address;
      config false;
    }
    leaf-list pmDrbEstabFailAdmissionRejQos {
      type uint64;
    }
    leaf pmRlcArqUlNack {
      type uint64;
      config false;
    }
    leaf-list pmRadioMacShortPsrSinrDistr {
      type ietfyang:mac-address;
    }
    leaf pmSssgSwitchDciDropped {
      type ietfinet:ip-prefix;
      config false;
    }
    leaf pmPdschAvailTime {
      type uint64;
      config false;
    }
    leaf-list pmBwpUeConfSumDistr {
      type uint64;
    }
    leaf-list pmRadioRecInterferencePwrUlSlot4Distr {
      type uint64;
    }
    leaf pmMassiveMimoSleepTimeTxMute {
      type uint64;
      config false;
    }
    leaf-list pmRadioPreambleSinrMsg3SuccTx3Distr {
      type uint64;
    }
    leaf pmPagReceivedRan {
      type uint64;
      config false;
    }
    leaf pmRrcAccessFailBbIntens {
      type uint64;
      config false;
    }
    leaf pmMacPdcchBlockingPuschOccasionsExclPresched {
      type ietfyang:mac-address;
      config false;
    }
    leaf-list pmMacTempAlarmSCellDistr {
      type ietfyang:mac-address;
    }
    leaf-list pmMacPucchSrPuschGrantLatDistr {
      type ietfyang:mac-address;
    }
    leaf-list pmRadioUeRepCqi64QamLowSeRank2Distr {
      type uint64;
    }
    leaf-list pmRlcDelayTimeDlQos {
      type uint64;
    }
    leaf pmMacHarqDlAck64Qam {
      type ietfyang:mac-address;
      config false;
    }
    leaf pmMacVolUl {
      type ietfyang:mac-address;
      config false;
    }
    leaf pmRadioBeamSwitchTargetNotAvailable {
      type uint64;
      config false;
    }
    leaf pmMacHarqUlAck256Qam {
      type ietfyang:mac-address;
      config false;
    }
    leaf pmMacHarqUlNackQpsk {
      type ietfyang:mac-address;
      config false;
    }
    leaf pmMacVolUlPCellCa {
      type ietfyang:mac-address;
      config false;
    }
    leaf-list pmPdcchDciSwitchSssg {
      type uint64;
    }
    leaf-list pmMacRBSymUsedPdcchTypeAAggrLvl16Sssg {
      type ietfyang:mac-address;
    }
    leaf-list pmPdschSchedActivitySssg {
      type uint64;
    }
    leaf pmMacRBSymUtilDlMax {
      type ietfyang:mac-address;
      config false;
    }
    leaf-list pmRadioRecInterferencePwrSpecialSlot3Distr {
      type uint64;
    }
    leaf-list pmMacSchedSlotUlSCellActivatedDistr {
      type ietfyang:mac-address;
    }
    leaf-list pmMacHarqDlNackQpskInitSlotDistr {
      type ietfyang:mac-address;
    }
    leaf pmCellSleepTimeEnergySaving {
      type uint64;
      config false;
    }
    leaf pmMacHarqUlAckNoData {
      type ietfyang:mac-address;
      config false;
    }
    leaf-list pmMacInitSchedDelayUlMaxQos {
      type ietfyang:mac-address;
    }
    leaf pmMacVolUlUnresUePucchSrGrant {
      type ietfyang:mac-address;
      config false;
    }
    leaf-list pmMacRBSymUsedPdschAdvMuMimoTxRankDistr {
      type ietfyang:mac-address;
    }
    leaf pmMacRBSymUtilUlMax {
      type ietfyang:mac-address;
      config false;
    }
    leaf-list pmMacRBSymPowerBackoffDistr {
      type ietfyang:mac-address;
    }
    leaf pmMacHarqUlDtx16QamInit {
      type ietfyang:mac-address;
      config false;
    }
    leaf-list pmRadioRaSuccTaRelDistr {
      type uint64;
    }
    leaf-list pmRadioPdschTable2MbsfnMcsDistr {
      type uint64;
    }
    leaf pmMacRBSymUsedPdcchTypeAAggrLvl1 {
      type ietfyang:mac-address;
      config false;
    }
    leaf-list pmMacLatTimeDlNoDrxSyncSampQos {
      type ietfyang:mac-address;
    }
    leaf-list pmMacRBSymUsedPuschMimoUserDistr {
      type ietfyang:mac-address;
    }
    leaf-list pmMacRBSymUsedPdcchTypeADciSwitchSssg {
      type ietfyang:mac-address;
    }
    leaf pmMacHarqDlAckQpskInit {
      type ietfyang:mac-address;
      config false;
    }
    leaf pmRadioBeamSwitchSuccMacCe {
      type ietfyang:mac-address;
      config false;
    }
    leaf-list pmMacServingDelayUlUeDistr {
      type ietfyang:mac-address;
    }
    leaf pmMacHarqDlNackQpskInit {
      type ietfyang:mac-address;
      config false;
    }
    leaf-list pmRadioUeRepPmiPrimaryCsiRsRank3Distr {
      type ietfinet:ip-address;
    }
    leaf pmMacVolDlDrbSingleSlotShortBurst {
      type ietfyang:mac-address;
      config false;
    }
    leaf pmUeCtxtRelAbnormalGnbDuPnr {
      type uint64;
      config false;
    }
    leaf-list pmRadioPdschTable1McsDistr {
      type uint64;
    }
    leaf-list pmRadioRecInterferencePwrUlSlot3Distr {
      type uint64;
    }
    leaf pmMacHarqDlFail {
      type ietfyang:mac-address;
      config false;
    }
    leaf-list pmRadioUeRepPmiPrimaryCsiRsRank1Distr {
      type ietfinet:ip-address;
    }
    leaf-list pmMacVolUlSssg {
      type ietfyang:mac-address;
    }
    leaf-list pmMacRBSymReservedPdcchCapacityBoostOfdmSymDistr {
      type ietfyang:mac-address;
    }
    leaf-list pmPuschSchedEntityDistr {
      type uint64;
    }
    leaf pmPduSessionEstabFailAdmissionRej {
      type uint64;
      config false;
    }
    leaf pmMacVolUlResCaUe {
      type ietfyang:mac-address;
      config false;
    }
    leaf-list pmMeasGapUeMnSumDistr {
      type uint64;
    }
    leaf pmActiveUeUlTrueSamp {
      type ietfyang:mac-address;
      config false;
    }
    leaf pmMacRBSymUsedPdcchTypeBAggrLvl16 {
      type ietfyang:mac-address;
      config false;
    }
    leaf pmActiveUeDlMax {
      type ietfyang:mac-address;
      config false;
    }
    leaf-list pmRimPdschAction2LastDlSlotDistr {
      type uint64;
    }
    leaf-list pmMacSchedSlotUlCellSchedDistr {
      type ietfyang:mac-address;
    }
    leaf-list pmRadioSinrPdschDistr {
      type uint64;
    }
    leaf pmMacRBSymUsedPdcchTypeAAggrLvl2 {
      type ietfyang:mac-address;
      config false;
    }
    leaf pmMacHarqUlAckQpsk {
      type ietfyang:mac-address;
      config false;
    }
    leaf pmMacTimeUlResCaUe {
      type ietfyang:mac-address;
      config false;
    }
    leaf pmMacRBSymUsedPdschAilg {
      type ietfyang:mac-address;
      config false;
    }
    leaf-list pmMacRBSymUtilUlDistr {
      type ietfyang:mac-address;
    }
    leaf pmRadioPdschEmptySlotsForced {
      type uint64;
      config false;
    }
    leaf pmMacHarqUlNack64QamInit {
      type ietfyang:mac-address;
      config false;
    }
    leaf-list pmMacPdcchCongestionDlDistr {
      type ietfyang:mac-address;
    }
    leaf pmMacHarqDlResAllocType1Dci11 {
      type ietfyang:mac-address;
      config false;
    }
    leaf-list pmMacRBSymUsedPdschAdvMuMimoLayersDistr {
      type ietfyang:mac-address;
    }
    leaf pmMacHarqDlAck16QamInit {
      type ietfyang:mac-address;
      config false;
    }
    leaf-list pmMacRBSymUsedPdschAdvEisSuMimoLayerDistr {
      type ietfyang:mac-address;
    }
    leaf pmMacTimeUlResUe {
      type ietfyang:mac-address;
      config false;
    }
    leaf pmDrxTotalTimeConfGrant {
      type uint64;
      config false;
    }
    leaf pmRadioMacSrPeriodicitySwitchLimitedCoverage {
      type ietfyang:mac-address;
      config false;
    }
    leaf-list pmRadioUeRepCqi256QamRank1Distr {
      type uint64;
    }
    leaf pmMacRBSymPucchSchedPusch {
      type ietfyang:mac-address;
      config false;
    }
    leaf-list pmMacRBSymUsedPdcchTypeAAggrLvl2Bwp {
      type ietfyang:mac-address;
    }
    leaf-list pmPuschSchedActivitySssg {
      type uint64;
    }
    leaf pmRadioMacTransUl1LayerSinrDelta {
      type ietfyang:mac-address;
      config false;
    }
    leaf-list pmMacContentionDelayUlDistr {
      type ietfyang:mac-address;
    }
    leaf-list pmMacRBSymUtilDlDistr {
      type ietfyang:mac-address;
    }
    leaf pmMacHarqUlNack16QamInit {
      type ietfyang:mac-address;
      config false;
    }
    leaf-list pmRadioRaAttTaDistr {
      type uint64;
    }
    leaf pmRadioRaCbFailMsg1Ooc {
      type uint64;
      config false;
    }
    leaf pmRadioSrsResUsedAntSwitching {
      type uint64;
      config false;
    }
    leaf pmMacRBSymReservedPdcchCapacityBoost {
      type ietfyang:mac-address;
      config false;
    }
    leaf-list pmMacRBSymUsedPdschAdvMuMimoLayerDistr {
      type ietfyang:mac-address;
      description "MOM flags: noNotification.";
    }
    leaf pmMacTimeDlDrbLastSlot {
      type ietfyang:mac-address;
      config false;
    }
    leaf-list pmMacVolDlSCellBwp {
      type ietfyang:mac-address;
    }
    leaf pmMassiveMimoSleepTimeEcoPending {
      type uint64;
      config false;
    }
    leaf-list pmRadioRecInterferenceNoOfEventsPrbDistr {
      type uint64;
    }
    leaf pmRlcArqDlNack {
      type uint64;
      config false;
    }
    leaf-list pmDrbModFailAdmissionRejQos {
      type uint64;
    }
    leaf pmRlcDelayPktTransmitDl {
      type uint64;
      config false;
    }
    leaf-list pmMacBsrLcg2Distr {
      type ietfyang:mac-address;
    }
    leaf pmRimDetectedAggressorSetIDsMax {
      type int64;
      config false;
    }
    leaf pmMassiveMimoSleepOppTimeEco {
      type uint64;
      config false;
    }
    leaf-list pmMeasGapUeMaxDistr {
      type int64;
    }
    leaf-list pmMacRBSymUsedPdcchTypeAAggrLvl1Sssg {
      type ietfyang:mac-address;
    }
    leaf-list pmRadioSinrPuschNackDistr {
      type uint64;
    }
    leaf-list pmRadioRecEffectiveIpNPwrDistr {
      type ietfinet:ip-address;
    }
    leaf-list pmMacBsrLcg1Distr {
      type ietfyang:mac-address;
    }
    leaf pmPimAvoidMutedCrbSum {
      type uint64;
      config false;
    }
    leaf pmMeasGapUeSamp {
      type uint64;
      config false;
    }
    leaf-list pmRimDetectedVictimDistanceMaxDistr {
      type int64;
    }
    leaf pmMacVolUlSCell {
      type ietfyang:mac-address;
      config false;
    }
    leaf-list pmMacHarqDlAck64QamInitSlotDistr {
      type ietfyang:mac-address;
    }
    leaf pmRadioMacWvfSwitchAttUlCpofdm {
      type ietfyang:mac-address;
      config false;
    }
    leaf pmRadioMacTransUl1Layer {
      type ietfyang:mac-address;
      config false;
    }
    leaf-list pmRadioUeRepCqi64QamLowSeRank4Distr {
      type uint64;
    }
    leaf pmMacHarqDlDtx16QamInit {
      type ietfyang:mac-address;
      config false;
    }
    leaf pmMacVolDlSCellExt {
      type ietfyang:mac-address;
      config false;
    }
    leaf-list pmRadioPreambleSinrMsg3NackDistr {
      type uint64;
    }
    leaf pmRadioRaCbFailMsg3Crc {
      type uint64;
      config false;
    }
    leaf-list pmMacVolUlBwp {
      type ietfyang:mac-address;
    }
    leaf-list pmMacSchedSlotDlCellSchedDistr {
      type ietfyang:mac-address;
    }
    leaf pmMacRBSymUsedPdcchTypeAAggrLvl4 {
      type ietfyang:mac-address;
      config false;
    }
    leaf-list pmMacSchedSlotUlTempAlarmSCellDistr {
      type ietfyang:mac-address;
    }
    leaf-list pmRadioPdschTable2McsDistr {
      type uint64;
    }
    leaf pmPagDiscardedRan {
      type uint64;
      config false;
    }
    leaf-list pmMacSymUsedPdcchDistr {
      type ietfyang:mac-address;
    }
    leaf pmMacVolUlResUe {
      type ietfyang:mac-address;
      config false;
    }
    leaf-list pmRadioMaxDeltaIpNDistr {
      type ietfinet:ip-address;
    }
    leaf-list pmMacHarqDlNack256QamInitSlotDistr {
      type ietfyang:mac-address;
    }
    leaf-list pmRadioUeRepPmiSecondaryCsiRsRank4Distr {
      type uint64;
    }
    leaf pmMacRBSymUsedPusch2Port2Layer {
      type ietfinet:port-number;
      config false;
    }
    leaf pmRadioRaCbPreambles {
      type uint64;
      config false;
    }
    leaf pmMacHarqDlDtx256QamInit {
      type ietfyang:mac-address;
      config false;
    }
    leaf-list pmRadioSchedUlSuMimoRankDistr {
      type uint64;
    }
    leaf pmRadioMacWvfSwitchSuccUlCpofdm {
      type ietfyang:mac-address;
      config false;
    }
    leaf-list pmPimAvoidMutedCrbDistr {
      type uint64;
    }
    leaf pmRadioMacWvfSwitchAttUlDfts {
      type ietfyang:mac-address;
      config false;
    }
    leaf pmMacVolDlPCellCa {
      type ietfyang:mac-address;
      config false;
    }
    leaf-list pmRadioRaSuccTaAbsDistr {
      type uint64;
    }
    leaf-list pmMacTimeDlDrbSampQos {
      type ietfyang:mac-address;
    }
    leaf-list pmMacRBSymUsedPdcchTypeAAggrLvl8Sssg {
      type ietfyang:mac-address;
    }
    leaf-list pmRadioRaCfPreambleFailedDistr {
      type uint64;
      description "MOM flags: noNotification.";
    }
    leaf pmMacHarqDlNack16QamInit {
      type ietfyang:mac-address;
      config false;
    }
    leaf pmMacPdcchBlockingPdschOccasions {
      type ietfyang:mac-address;
      config false;
    }
    leaf-list pmRadioUeRepCqi256QamRank4Distr {
      type uint64;
    }
    leaf pmCellTimeSamp {
      type uint64;
      config false;
    }
    leaf-list pmSessionTimeUeBwpSumDistr {
      type uint64;
    }
    leaf pmMacTimeDlDrb {
      type ietfyang:mac-address;
      config false;
    }
    leaf pmPuschAvailSlot {
      type uint64;
      config false;
    }
    leaf pmMacHarqUlFail {
      type ietfyang:mac-address;
      config false;
    }
    leaf-list pmUeCtxtModSuccWvfSwitchDistr {
      type uint64;
    }
    leaf pmCellDowntimeAuto {
      type uint64;
      config false;
    }
    leaf-list pmMacPdcchCongestionUlDistr {
      type ietfyang:mac-address;
    }
    leaf pmMacVolDlDrbSingleBurstSamp {
      type ietfyang:mac-address;
      config false;
    }
    leaf-list pmMacVolDlDrbSingleBurstSampQos {
      type ietfyang:mac-address;
    }
    leaf-list pmRadioPdschRimBlankSlotsCellDistr {
      type int64;
    }
    leaf pmRadioRaCbFailMsg3Crnti {
      type uint64;
      config false;
    }
    leaf pmMacThpDlDrbMax {
      type ietfyang:mac-address;
      config false;
    }
    leaf-list pmRadioPuschTable2McsDistr {
      type uint64;
    }
    leaf pmMacPduVolDlUePCell {
      type ietfyang:mac-address;
      config false;
    }
    leaf-list pmMeasGapUeMnMaxDistr {
      type int64;
    }
    leaf pmPdschAvailSlot {
      type uint64;
      config false;
    }
    leaf pmMacRBSymEstimatedPdschTypeA {
      type ietfyang:mac-address;
      config false;
    }
    leaf-list pmMacRBSymUsedPdschAdvMimoSinrThresUserDistr {
      type ietfyang:mac-address;
    }
    leaf-list pmRadioRaCfPreambleUnusedDistr {
      type uint64;
    }
    leaf pmMassiveMimoSleepTimeEco {
      type uint64;
      config false;
    }
    leaf-list pmRadioRaCfPreambleFailedHoDistr {
      type uint64;
    }
    leaf-list pmRadioPdschTable3MbsfnMcsDistr {
      type uint64;
    }
    leaf-list pmMacVolDlDrbLastSlotQos {
      type ietfyang:mac-address;
    }
    leaf-list pmMacVolDlSssg {
      type ietfyang:mac-address;
    }
    leaf-list pmMacRBSymUsedPdcchTypeAAggrLvl4Sssg {
      type ietfyang:mac-address;
    }
    leaf pmMacHarqDlNack64QamInit {
      type ietfyang:mac-address;
      config false;
    }
    leaf pmRimVictimRiDetectedCell {
      type int64;
      config false;
    }
    leaf pmRadioBeamSwitchSucc {
      type uint64;
      config false;
    }
    leaf-list pmRadioUeRepCqi64QamRank1Distr {
      type uint64;
    }
    leaf pmMacThpDlMax {
      type ietfyang:mac-address;
      config false;
    }
    leaf pmPuschSchedActivity {
      type uint64;
      config false;
    }
    leaf-list pmRadioNarrowBeamAcqTimeDistr {
      type ietfyang:mac-address;
    }
    leaf-list pmRadioRecInterferencePwrSpecialSlot4Distr {
      type uint64;
    }
    leaf pmMacHarqUlNack256Qam {
      type ietfyang:mac-address;
      config false;
    }
    leaf pmMacVolDlSCell {
      type ietfyang:mac-address;
      config false;
    }
    leaf pmMacHarqDlAckQpsk {
      type ietfyang:mac-address;
      config false;
    }
    leaf-list pmMacLatTimeDlDrxSyncQos {
      type ietfyang:mac-address;
    }
    leaf pmMacHarqDlDtx16Qam {
      type ietfyang:mac-address;
      config false;
    }
    leaf-list pmMacHarqDlNack16QamInitSlotDistr {
      type ietfyang:mac-address;
    }
    leaf pmCellDowntimeMan {
      type uint64;
      config false;
    }
    leaf-list pmRadioPreambleSinrMsg3SuccTx4Distr {
      type uint64;
    }
    leaf pmMacHarqDlDtx256Qam {
      type ietfyang:mac-address;
      config false;
    }
    leaf pmRadioRaCfFailMsg1DiscSched {
      type uint64;
      config false;
    }
    leaf-list pmRadioUeRepCqi64QamRank3Distr {
      type uint64;
    }
    leaf pmMacRBSymUsedPdcchTypeA {
      type ietfyang:mac-address;
      config false;
    }
    leaf pmRlcArqDlAck {
      type uint64;
      config false;
    }
    leaf-list pmRadioPuschTable1McsDistr {
      type uint64;
    }
    leaf pmMacHarqDlAck256QamInit {
      type ietfyang:mac-address;
      config false;
    }
    leaf pmPdschSchedActivity {
      type uint64;
      config false;
    }
    leaf-list pmRadioPreambleSinrMsg3SuccTx1Distr {
      type uint64;
    }
    leaf pmActiveUeDlSum {
      type ietfyang:mac-address;
      config false;
    }
    leaf-list pmMacVolDlDrbSingleBurstQos {
      type ietfyang:mac-address;
    }
    leaf pmMacHarqUlAck64QamInit {
      type ietfyang:mac-address;
      config false;
    }
    leaf-list pmMeasGapUeSumDistr {
      type uint64;
    }
    leaf-list pmMacRBSymUsedPdschMuMimoLayerDistr {
      type ietfyang:mac-address;
    }
    leaf-list pmRadioSinrPucchF2Distr {
      type uint64;
    }
    leaf pmMacOffloadVolDlSCell {
      type ietfyang:mac-address;
      config false;
    }
    leaf pmMacRBSymUsedPdschTypeABroadcasting {
      type ietfyang:mac-address;
      config false;
    }
    leaf pmMacHarqUlNack64Qam {
      type ietfyang:mac-address;
      config false;
    }
    leaf-list pmPuschSchedEntityInclPreschedDistr {
      type uint64;
    }
    leaf pmMacHarqUlAck64Qam {
      type ietfyang:mac-address;
      config false;
    }
    leaf pmEeAllResBlockUsed {
      type uint64;
      config false;
    }
    leaf pmMacHarqDlNack16Qam {
      type ietfyang:mac-address;
      config false;
    }
    leaf pmMacRBSymUsedPdcchTypeAAggrLvl16 {
      type ietfyang:mac-address;
      config false;
    }
    leaf pmRadioSsbBeamSwitch {
      type uint32;
      config false;
    }
    leaf pmMacHarqDlAck256Qam {
      type ietfyang:mac-address;
      config false;
    }
    leaf-list pmMacRBSymUsedPdcchTypeAAggrLvl1Bwp {
      type ietfyang:mac-address;
    }
    leaf-list pmRadioUeRepCqi64QamRank4Distr {
      type uint64;
    }
    leaf-list pmMacVolUlSCellExtBwp {
      type ietfyang:mac-address;
    }
    leaf-list pmRadioUeRepCqi256QamRank3Distr {
      type uint64;
    }
    leaf pmRimRS1EnoughNotEnoughRatioMax {
      type int64;
      config false;
    }
    leaf-list pmRadioPreambleSinrMsg3SuccBeyondTx4Distr {
      type uint64;
    }
    leaf pmMassiveMimoSleepOppTimeTxMute {
      type uint64;
      config false;
    }
    leaf pmRadioRaCbSuccMsg3 {
      type uint64;
      config false;
    }
    leaf-list pmRadioUeRepPmiSecondaryCsiRsRank1Distr {
      type uint64;
    }
    leaf pmMacThpUlMax {
      type ietfyang:mac-address;
      config false;
    }
    leaf-list pmMacVolDlDrbOverlapLastSlotQoS {
      type ietfyang:mac-address;
    }
    leaf-list pmPagBundledUeSampDistr {
      type uint64;
    }
    leaf-list pmRadioPucchSrResourcesRestoredDistr {
      type uint32;
    }
    leaf pmRadioMacSrPeriodicitySwitchGoodCoverage {
      type ietfyang:mac-address;
      config false;
    }
    leaf-list pmMacRBSymUsedPdschAdvSuMimoTxRankDistr {
      type ietfyang:mac-address;
    }
    leaf pmPagDiscarded {
      type uint64;
      config false;
    }
    leaf-list pmMacRBSymUsedPdschAdvEisMuMimoTxRankDistr {
      type ietfyang:mac-address;
    }
    leaf pmMacRBSymRachSchedPusch {
      type ietfyang:mac-address;
      config false;
    }
    leaf-list pmMacRBSymUsedPuschMimoLayerDistr {
      type ietfyang:mac-address;
    }
    leaf-list pmMacSrsPdschAgeDistr {
      type ietfyang:mac-address;
    }
    leaf-list pmMacVolDlDrbQos {
      type ietfyang:mac-address;
    }
    leaf pmMacRBSymUsedPdcchTypeB {
      type ietfyang:mac-address;
      config false;
    }
    leaf-list pmRadioSymbolDeltaIpnDistr {
      type ietfinet:ip-address;
    }
    leaf-list pmMacContentionDelayDlMaxQos {
      type ietfyang:mac-address;
    }
    leaf pmCellDowntimeManCbrs {
      type uint64;
      config false;
    }
    leaf-list pmRimCumulatedRSPowerDistr {
      type int64;
    }
    leaf pmDuCellDownUnlockMan {
      type uint64;
      config false;
    }
    leaf pmMacHarqDlDtxQpskInit {
      type ietfyang:mac-address;
      config false;
    }
    leaf pmMacTimeDlDrbLastSlotSamp {
      type ietfyang:mac-address;
      config false;
    }
    leaf-list pmUeEffDopplerSpeedDistr {
      type uint64;
    }
    leaf pmMacPdcchBlockingPuschOccasions {
      type ietfyang:mac-address;
      config false;
    }
    leaf pmMacRBSymUsedPdcchTypeBAggrLvl2 {
      type ietfyang:mac-address;
      config false;
    }
    leaf pmRrcAccessFailMpLoad {
      type uint64;
      config false;
    }
    leaf pmMacVolUlOffloadSCell {
      type ietfyang:mac-address;
      config false;
      status deprecated;
      description "MOM flags: noNotification.";
    }
    leaf pmMacTimeDlCaConfigDrbActivity {
      type ietfyang:mac-address;
      config false;
    }
    leaf-list pmMacTimeUlResDrbMaxQos {
      type ietfyang:mac-address;
    }
    leaf-list pmMacTimeDlDrbLastSlotSampQos {
      type ietfyang:mac-address;
    }
    leaf pmRadioMacTransUl2Layers {
      type ietfyang:mac-address;
      config false;
    }
    leaf-list pmMacVolPdschAdvMimoSinrThresUserDistr {
      type ietfyang:mac-address;
    }
    leaf pmMacHarqUlAck256QamInit {
      type ietfyang:mac-address;
      config false;
    }
    leaf pmMacHarqUlAck16Qam {
      type ietfyang:mac-address;
      config false;
    }
    leaf-list pmRadioPuschPhrDistr {
      type uint64;
    }
    leaf-list pmMacSchedSlotDlTempAlarmSCellDistr {
      type ietfyang:mac-address;
    }
    leaf-list pmSessionTimeUeSssgSumDistr {
      type uint64;
    }
    leaf pmMacHarqDlNackQpsk {
      type ietfyang:mac-address;
      config false;
    }
    leaf pmMacHarqUlAckQpskInit {
      type ietfyang:mac-address;
      config false;
    }
    leaf-list pmRadioSinrPuschDtxDistr {
      type uint64;
    }
    leaf pmMacHarqUlNackQpskInit {
      type ietfyang:mac-address;
      config false;
    }
    leaf-list pmPdschSchedActivityBwp {
      type uint64;
    }
    leaf-list pmMacRBSymUsedPdcchOfdmSymDistr {
      type ietfyang:mac-address;
    }
    leaf pmMacHarqUlDtx256QamInit {
      type ietfyang:mac-address;
      config false;
    }
    leaf pmMacVolDlDrbOverlapLastSlot {
      type ietfyang:mac-address;
      config false;
    }
    leaf-list pmMacRBSymUsedPdschMimoLayerDistr {
      type ietfyang:mac-address;
    }
    leaf-list pmRadioRecInterferencePwrSpecialSlot1Distr {
      type uint64;
    }
    leaf-list pmRadioPreambleSinrMsg3AckDistr {
      type uint64;
    }
    leaf-list pmPimAvoidPowerExcessDistr {
      type uint64;
    }
    leaf pmMacRBSymUsedPdcchCss {
      type ietfyang:mac-address;
      config false;
    }
    leaf-list pmMacTimeDlDrbQos {
      type ietfyang:mac-address;
    }
    leaf-list pmMacRBSymUsedPdcchTypeAAggrLvl8Bwp {
      type ietfyang:mac-address;
    }
    leaf pmRadioRaCfFailMsg2Disc {
      type uint64;
      config false;
    }
    leaf-list pmMacRBSymUsedPdcchTypeAAggrLvl2Sssg {
      type ietfyang:mac-address;
    }
    leaf pmMacVolDlRat {
      type ietfyang:mac-address;
      config false;
    }
    leaf pmDuCellDownLockAuto {
      type uint64;
      config false;
    }
    leaf pmMacRBSymUsedPuschTypeA {
      type ietfyang:mac-address;
      config false;
    }
    leaf pmMacRBSymUsedPuschTypeAExclPresched {
      type ietfyang:mac-address;
      config false;
    }
    leaf-list pmRadioUeRepPmiPrimaryCsiRsRank4Distr {
      type ietfinet:ip-address;
    }
    leaf pmMacRBSymAvailRach {
      type ietfyang:mac-address;
      config false;
    }
    leaf pmMacHarqUlDtx16Qam {
      type ietfyang:mac-address;
      config false;
    }
    leaf pmMacRBSymUsedPuschTypeB {
      type ietfyang:mac-address;
      config false;
    }
    leaf pmMacHarqUlNack256QamInit {
      type ietfyang:mac-address;
      config false;
    }
    leaf pmActiveUeDlSamp {
      type ietfyang:mac-address;
      config false;
    }
    leaf-list pmDrbAdmissionPreemptQos {
      type uint64;
    }
    leaf pmMacHarqUlDtxQpskInit {
      type ietfyang:mac-address;
      config false;
    }
    leaf-list pmRadioRecInterferencePwrUlSlot7Distr {
      type uint64;
    }
    leaf-list pmRadioPreambleSinrMsg3HarqFailDistr {
      type uint64;
    }
    leaf pmRadioSrsResAvailAntSwitching {
      type uint64;
      config false;
    }
    leaf pmMacHarqDlAck64QamInit {
      type ietfyang:mac-address;
      config false;
    }
    leaf pmSssgUeConfSamp {
      type uint64;
      config false;
    }
    leaf-list pmMacHarqDlAckQpskInitSlotDistr {
      type ietfyang:mac-address;
    }
    leaf-list pmRadioUeRepCqi64QamLowSeRank3Distr {
      type uint64;
    }
    leaf-list pmPimAvoidPowerExcessReportMissDistr {
      type ietfinet:port-number;
    }
    leaf pmSessionTimeUeSssgSamp {
      type uint64;
      config false;
    }
    leaf-list pmPdschSchedEntityDistr {
      type uint64;
    }
    leaf-list pmMacBsrLcg7Distr {
      type ietfyang:mac-address;
    }
    leaf pmMacRBSymAvailDl {
      type ietfyang:mac-address;
      config false;
    }
    leaf-list pmRadioRecInterferencePwrSpecialSlot2Distr {
      type uint64;
    }
    leaf-list pmPuschSchedActivityBwp {
      type uint64;
    }
    leaf-list pmRadioRecInterferencePwrUlSlot5Distr {
      type uint64;
    }
    leaf-list pmRadioPreambleSinrMsg3DtxDistr {
      type uint64;
    }
    leaf-list pmRadioPuschTable3McsDistr {
      type uint64;
    }
    leaf pmMacVolUlResUeLastSlot {
      type ietfyang:mac-address;
      config false;
      status deprecated;
      description "MOM flags: noNotification.";
    }
    leaf-list pmMacRBSymUsedPdschAdvEisMimoUserDistr {
      type ietfyang:mac-address;
    }
    leaf pmMacRBSymUsedPdcchTypeBAggrLvl1 {
      type ietfyang:mac-address;
      config false;
    }
    leaf pmRadioRaCbFailMsg1MaxMsg3Sched {
      type uint64;
      config false;
    }
    leaf-list pmRadioRecInterferencePwrUlSlot1Distr {
      type uint64;
    }
    leaf-list pmRadioPathlossUlDistr {
      type uint64;
    }
    leaf pmUeCtxtAllocatedSum {
      type uint64;
      config false;
    }
    leaf-list pmRadioUeRepCqi256QamRank2Distr {
      type uint64;
    }
    leaf-list pmRadioSinrPuschDistr {
      type uint64;
    }
    leaf-list pmRadioSinrPucchDistr {
      type uint64;
    }
    leaf-list pmMacOverlapTimeDlDrbExtSCellQoS {
      type ietfyang:mac-address;
    }
    leaf-list pmRadioSinrPuschAckDistr {
      type uint64;
    }
    leaf pmRadioRaCbFailMsg2Disc {
      type uint64;
      config false;
    }
  }
  grouping NRPimCancellationConfig-attributes {
    leaf createdBy {
      type enumeration {
        enum SYSTEM;
        enum OPERATOR;
      }
      config false;
    }
    leaf dlPimCandidate {
      type boolean;
      default "false";
      description "Default value: false.";
    }
    leaf nRPimCancellationConfigId {
      type string;
      mandatory true;
    }
    leaf pimCancellationFunctionRef {
      type string;
      mandatory true;
    }
    leaf ulPimCancellationMode {
      type enumeration {
        enum EXCLUDED;
        enum DEACTIVATED;
        enum ACTIVATED;
      }
    }
  }
  grouping NRSectorCarrier-attributes {
    leaf administrativeState {
      type enumeration {
        enum LOCKED;
        enum UNLOCKED;
        enum SHUTTINGDOWN;
      }
    }
    leaf altitude {
      type int32 {
        range "-32768..32767";
      }
      units "m";
      description "range -32768..32767.";
    }
    leaf arfcnDL {
      type eytypes:int32_range_0-3279165;
      mandatory true;
      description "range 0..3279165.";
    }
    leaf arfcnUL {
      type eytypes:int32_range_0-3279165;
      mandatory true;
      description "range 0..3279165.";
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    list azimuthNull {
      key "id";
      leaf id {
        type uint32;
        description "Synthetic key for struct sequence entry.";
      }
      ordered-by user;
      container attributes {
      leaf frequency {
        type int32 {
          range "0..6000000";
        }
        default "0";
        units "kHz";
        description "range 0..6000000; Default value: 0.";
      }
      leaf horizontalAngle {
        type int32 {
          range "-90..90";
        }
        units "degree";
        description "range -90..90.";
      }
      leaf nullWidth {
        type enumeration {
          enum NARROW;
          enum MEDIUM;
          enum WIDE;
        }
      }
      leaf verticalAngle {
        type int32 {
          range "-15..15";
        }
        default "0";
        units "degree";
        description "range -15..15; Default value: 0.";
      }
      }
    }
    leaf bbOnlyBackoffAllowed {
      type boolean;
      default "false";
      description "Default value: false.";
    }
    leaf bSChannelBwDL {
      type int32 {
        range "5 | 10 | 15 | 20 | 25 | 30 | 35 | 40 | 50 | 60 | 70 | 80 | 90 | 100 | 200";
      }
      mandatory true;
      units "MHz";
    }
    leaf bSChannelBwUL {
      type int32 {
        range "5 | 10 | 15 | 20 | 25 | 30 | 35 | 40 | 50 | 60 | 70 | 80 | 90 | 100 | 200";
      }
      mandatory true;
      units "MHz";
    }
    leaf cbrsEnabled {
      type boolean;
      default "false";
      description "Default value: false.";
    }
    leaf cbrsTxExpireTime {
      type string;
      config false;
    }
    leaf configuredMaxTxPower {
      type eytypes:int32_range_0-10000000;
      default "20000";
      units "mW";
      description "range 0..10000000; Default value: 20000.";
    }
    list coverage {
      key "id";
      leaf id {
        type uint32;
        description "Synthetic key for struct entry.";
      }
      container attributes {
      leaf bearing {
        type eytypes:int32_range_0-3599;
        units "degree";
        description "range 0..3599.";
      }
      leaf openingAngle {
        type eytypes:int32_range_0-3599;
        units "degree";
        description "range 0..3599.";
      }
      leaf radius {
        type eytypes:int32_range_1-100000;
        units "m";
        description "range 1..100000.";
      }
      }
    }
    list dlCalibrationData {
      config false;
      description "MOM flags: isNillable=true; Status info: Since 25.Q2. Planned to be removed..";
      container attributes {
      leaf dlCalibrationActiveMethod {
        type enumeration {
          enum NONE;
          enum INTERNAL;
        }
      }
      leaf dlCalibrationStatus {
        type enumeration {
          enum INACTIVE;
          enum CONVERGING;
          enum CALIBRATED;
          enum FAILED;
        }
      }
      leaf dlCalibrationSupportedMethods {
        type ietfinet:port-number;
      }
      }
    }
    leaf dlCalibrationEnabled {
      type boolean;
      status deprecated;
      default "true";
      description "Default value: true; Takes effect: Next MO unlock; Status info: Since 25.Q2. Planned to be removed..";
      reference "Takes effect: Next MO unlock.";
    }
    list elevationNull {
      key "id";
      leaf id {
        type uint32;
        description "Synthetic key for struct sequence entry.";
      }
      ordered-by user;
      container attributes {
      leaf frequency {
        type int32 {
          range "0..6000000";
        }
        default "0";
        units "kHz";
        description "range 0..6000000; Default value: 0.";
      }
      leaf nullWidth {
        type enumeration {
          enum NARROW;
          enum MEDIUM;
          enum WIDE;
        }
      }
      leaf verticalAngle {
        type int32 {
          range "-15..15";
        }
        units "degree";
        description "range -15..15.";
      }
      }
    }
    leaf essScLocalId {
      type int32 {
        range "1..99999";
      }
      description "range 1..99999.";
    }
    leaf essScPairId {
      type int64 {
        range "1..9223372036854775807";
      }
      description "range 1..9223372036854775807.";
    }
    leaf frameStartOffset {
      type uint32 {
        range "0..19660799";
      }
      default "0";
      units "Tc";
      description "range 0..19660799; Default value: 0.";
    }
    leaf frequencyDL {
      type int32;
      config false;
      units "kHz";
    }
    leaf frequencyUL {
      type int32;
      config false;
      units "kHz";
    }
    leaf ipnMeasurementBranchRef {
      type ietfinet:ip-address;
    }
    leaf ipnMeasurementStatus {
      type ietfinet:ip-address;
      config false;
    }
    leaf latitude {
      type int32 {
        range "-90000000..90000000";
      }
      units "degree";
      description "range -90000000..90000000.";
    }
    list lcsToGcsTranslation {
      key "id";
      leaf id {
        type uint32;
        description "Synthetic key for struct entry.";
      }
      container attributes {
      leaf alpha {
        type eytypes:int32_range_0-3599;
        units "degree";
        description "range 0..3599.";
      }
      leaf beta {
        type eytypes:int32_range_0-3599;
        units "degree";
        description "range 0..3599.";
      }
      leaf gamma {
        type eytypes:int32_range_0-3599;
        units "degree";
        description "range 0..3599.";
      }
      }
    }
    leaf longitude {
      type int32 {
        range "-180000000..180000000";
      }
      units "degree";
      description "range -180000000..180000000.";
    }
    leaf massiveMimoSleepEnabled {
      type enumeration {
        enum DISABLED;
        enum ENABLED;
        enum DETECTION;
      }
    }
    leaf massiveMimoSleepState {
      type enumeration {
        enum DEACTIVATED;
        enum TXMUTE;
        enum ECO;
        enum ECO_PENDING;
      }
      config false;
    }
    leaf maxAllowedEirpPsd {
      type int32 {
        range "-1 | 1..10000";
      }
      default "-1";
      units "dBm/MHz";
      description "Default value: -1.";
    }
    leaf maxEirpPsdThresh {
      type int32 {
        range "1..1000";
      }
      units "dBm/MHz";
      description "range 1..1000.";
    }
    leaf maxRegPowerLimit {
      type int32 {
        range "-1..10000000";
      }
      default "-1";
      units "mW";
      description "range -1..10000000; Default value: -1.";
    }
    leaf maxTransmissionPower {
      type int32;
      config false;
      units "mW";
    }
    leaf mMimoSleepTimeGroupRef {
      type string;
    }
    leaf muEirpPmiDistBasedThreshold {
      type eytypes:int32_range_0-31-13;
      default "4";
      description "range 0..31; Default value: 4.";
    }
    leaf noOfRxAntennas {
      type int32 {
        range "0..2 | 4 | 8";
      }
      default "0";
      description "Default value: 0.";
    }
    leaf noOfTxAntennas {
      type int32 {
        range "0..2 | 4 | 8 | 16";
      }
      default "0";
      description "Default value: 0.";
    }
    leaf noOfUsedRxAntennas {
      type int32;
      config false;
    }
    leaf noOfUsedTxAntennas {
      type int32;
      config false;
    }
    leaf noTxPowerAction {
      type enumeration {
        enum NO_ACTION;
        enum SC_AND_CELL_RESTART;
      }
    }
    leaf nRMicroSleepTxEnabled {
      type boolean;
      default "true";
      description "Default value: true.";
    }
    leaf nrppaCellPortionId {
      type ietfinet:port-number;
      config false;
      description "range 0..4095.";
    }
    leaf nRSectorCarrierId {
      type string;
      mandatory true;
    }
    leaf nullSteeringMode {
      type enumeration {
        enum ALL;
        enum COMMON_BEAMFORMING;
        enum CSI_RS_MAPPING;
      }
    }
    leaf operationalState {
      type enumeration {
        enum DISABLED;
        enum ENABLED;
      }
      config false;
    }
    leaf pimAvoidDlMutingPeriod {
      type int32 {
        range "1..15";
      }
      default "8";
      units "slot";
      description "range 1..15; Default value: 8.";
    }
    leaf pimAvoidLevel {
      type enumeration {
        enum DISABLED;
        enum LOW;
        enum MEDIUM;
        enum HIGH;
      }
    }
    leaf pimAvoidStatus {
      type boolean;
      config false;
    }
    leaf pimDetected {
      type boolean;
      config false;
      status deprecated;
      description "MOM flags: noNotification, isNillable=true; Status info: Since 24.Q1. Planned to be removed..";
    }
    leaf pimDetectionEnabled {
      type boolean;
      status deprecated;
      default "false";
      description "Default value: false; Status info: Since 24.Q1. Planned to be removed..";
    }
    list polygon {
      key "id";
      leaf id {
        type uint32;
        description "Synthetic key for struct sequence entry.";
      }
      ordered-by user;
      container attributes {
      leaf latitude {
        type int32 {
          range "-90000000..90000000";
        }
        units "degree";
        description "range -90000000..90000000.";
      }
      leaf longitude {
        type int32 {
          range "-180000000..180000000";
        }
        units "degree";
        description "range -180000000..180000000.";
      }
      }
    }
    leaf powerBackoffMode {
      type enumeration {
        enum AUTO;
        enum OFF;
        enum STATIC;
      }
    }
    leaf powerBackoffOffset {
      type int32 {
        range "-20..20";
      }
      default "0";
      units "dB";
      description "range -20..20; Default value: 0.";
    }
    leaf powerMeasAvgTime {
      type uint32 {
        range "30..1800";
      }
      units "s";
      description "range 30..1800.";
    }
    leaf radioReportControlled {
      type ietfinet:port-number;
      description "Default value: true.";
    }
    leaf radioTransmitPerfMode {
      type enumeration {
        enum COVERAGE;
        enum CAPACITY;
        enum COVERAGE_GREEN;
        enum CAPACITY_GREEN;
      }
    }
    leaf-list reservedBy {
      type string;
    }
    leaf-list rfBranchRxRef {
      type string;
      ordered-by user;
    }
    leaf-list rfBranchTxRef {
      type string;
      ordered-by user;
    }
    leaf scaledTransmissionPower {
      type int32;
      config false;
      units "mW";
    }
    leaf sectorEquipmentFunctionRef {
      type ietfinet:ip-address;
      mandatory true;
    }
    leaf txDirection {
      type enumeration {
        enum DL_AND_UL;
        enum DL;
      }
    }
    leaf txPowerChangeRate {
      type int32 {
        range "1..10";
      }
      default "1";
      units "%/s";
      description "range 1..10; Default value: 1.";
    }
    leaf txPowerPersistentLock {
      type boolean;
      default "false";
      description "Default value: false.";
    }
    leaf txPowerRatio {
      type eytypes:int32_range_10-100;
      default "100";
      units "percent";
      description "range 10..100; Default value: 100.";
    }
    leaf txPowerState {
      type enumeration {
        enum INVALID;
        enum STABLE;
        enum CHANGING;
      }
      config false;
    }
    leaf ueAssistedPrecodingOptEnabled {
      type boolean;
      default "false";
      description "Default value: false.";
    }
    leaf ueAssistedPrecodingOptStatus {
      type enumeration {
        enum INACTIVE;
        enum ACTIVE_NO_UPDATE;
        enum ACTIVE_FAILED;
        enum ACTIVE_CALIBRATED;
        enum ACTIVE_CALIBRATED_UPDATING;
      }
      config false;
    }
    leaf ueAssistedPrecodingOptTimeGap {
      type int32 {
        range "0..43198";
      }
      default "300";
      units "s";
      description "range 0..43198; Default value: 300.";
    }
    list ulCalibrationData {
      config false;
      description "MOM flags: isNillable=true; Status info: Since 25.Q2. Planned to be removed..";
      container attributes {
      leaf ulCalibrationActiveMethod {
        type enumeration {
          enum NONE;
          enum INTERNAL;
        }
      }
      leaf ulCalibrationStatus {
        type enumeration {
          enum INACTIVE;
          enum CONVERGING;
          enum CALIBRATED;
          enum FAILED;
        }
      }
      leaf ulCalibrationSupportedMethods {
        type ietfinet:port-number;
      }
      }
    }
    leaf ulGainScalingDelta {
      type eytypes:int32_range_-30-30;
      default "0";
      units "dB";
      description "range -30..30; Default value: 0.";
    }
    leaf ulGainScalingEnabled {
      type boolean;
      default "false";
      description "Default value: false.";
    }
    leaf pmEmfResourceAllowedDir {
      type uint64;
      config false;
      status deprecated;
      description "MOM flags: noNotification.";
    }
    leaf-list pmEmfPwrBackoffStepPwrDir1Distr {
      type uint64;
    }
    leaf-list pmEmfPwrBackoffPwrDir6Distr {
      type uint64;
    }
    leaf-list pmEmfPwrBackoffPwrDir1Distr {
      type uint64;
    }
    leaf pmSectorCarrierDowntimeMan {
      type uint64;
      config false;
    }
    leaf-list pmEmfPwrBackoffStepPwrDir4Distr {
      type uint64;
    }
    leaf pmSectorCarrierDowntimeAutoCbrs {
      type uint64;
      config false;
    }
    leaf-list pmEmfPwrBackoffStepPwrDir3Distr {
      type uint64;
    }
    leaf pmUeAssistedPrecodingOptCalibratedUpdating {
      type uint64;
      config false;
    }
    leaf-list pmEmfPwrBackoffPwrDir8Distr {
      type uint64;
    }
    leaf-list pmEmfPwrBackoffPwrDistr {
      type uint32;
    }
    leaf-list pmEmfPwrBackoffStepPwrDir6Distr {
      type uint64;
    }
    leaf-list pmRadioBranchDeltaSinr0Distr {
      type uint64;
    }
    leaf-list pmEmfPrbSclPowerDeboostPdschDirDistr {
      type uint64;
    }
    leaf-list pmEmfPwrBackoffPwrDir7Distr {
      type uint64;
    }
    leaf pmEmfPwrBackoffHardLimit {
      type uint32;
      config false;
    }
    leaf pmActiveUeUlSum {
      type ietfyang:mac-address;
      config false;
    }
    leaf-list pmEmfPwrBackoffStepPwrDir8Distr {
      type uint64;
    }
    leaf-list pmEmfPwrBackoffDynResThrDir2Distr {
      type uint64;
    }
    leaf-list pmEmfPwrBackoffDynResThrDistr {
      type uint32;
    }
    leaf-list pmRadioBranchDeltaSinr2Distr {
      type uint64;
    }
    leaf pmSectorCarrierTimeSamp {
      type uint64;
      config false;
    }
    leaf-list pmEmfPwrBackoffDynResThrDir7Distr {
      type uint64;
    }
    leaf-list pmEmfPwrBackoffPwrDir3Distr {
      type uint64;
    }
    leaf pmEmfPwrBackoffSamp {
      type uint32;
      config false;
    }
    leaf-list pmEmfPwrBackoffPwrDir2Distr {
      type uint64;
    }
    leaf pmActiveUeUlSamp {
      type ietfyang:mac-address;
      config false;
    }
    leaf-list pmEmfPwrBackoffPwrDir5Distr {
      type uint64;
    }
    leaf-list pmRadioBranchDeltaSinr5Distr {
      type uint64;
    }
    leaf-list pmEmfPwrBackoffCtrlStepPwrDistr {
      type uint64;
    }
    leaf-list pmEmfPwrBackoffStepPwrDir2Distr {
      type uint64;
    }
    leaf-list pmRadioPowerDlDistr {
      type uint64;
    }
    leaf-list pmEmfPwrBackoffStepPwrDir7Distr {
      type uint64;
    }
    leaf pmRadioScaledTxPowerMax {
      type int64;
      config false;
    }
    leaf-list pmEmfPwrBackoffDynResThrDirDistr {
      type uint64;
    }
    leaf-list pmEmfPwrBackoffDynResThrDir6Distr {
      type uint64;
    }
    leaf-list pmEmfPwrBackoffPwrDir4Distr {
      type uint64;
    }
    leaf pmMicroTxSleepTime {
      type uint64;
      config false;
    }
    leaf-list pmRadioBranchDeltaSinr1Distr {
      type uint64;
    }
    leaf-list pmEmfPwrBackoffDynResThrDir1Distr {
      type uint64;
    }
    leaf pmSectorCarrierDowntime {
      type uint64;
      config false;
    }
    leaf-list pmRadioBranchDeltaSinr4Distr {
      type uint64;
    }
    leaf pmSectorCarrierDowntimeManCbrs {
      type uint64;
      config false;
    }
    leaf-list pmEmfPwrBackoffDynResThrDir3Distr {
      type uint64;
    }
    leaf-list pmRadioBranchDeltaSinr3Distr {
      type uint64;
    }
    leaf-list pmEmfPwrBackoffDynResThrDir5Distr {
      type uint64;
    }
    leaf-list pmRadioBranchDeltaSinr6Distr {
      type uint64;
    }
    leaf pmSectorCarrierDowntimeAuto {
      type uint64;
      config false;
    }
    leaf-list pmEmfPwrBackoffStepPwrDirDistr {
      type uint64;
    }
    leaf-list pmEmfPwrBackoffDynResThrDir8Distr {
      type uint64;
    }
    leaf pmEmfPwrBackoffSampDir {
      type uint64;
      config false;
    }
    leaf-list pmEmfPwrBackoffPwrDirDistr {
      type uint64;
    }
    leaf pmUeAssistedPrecodingOptNoUpdate {
      type uint64;
      config false;
    }
    leaf pmSectorCarrierUptime {
      type uint64;
      config false;
    }
    leaf-list pmEmfPwrBackoffDynResThrDir4Distr {
      type uint64;
    }
    leaf-list pmBwAssignedDistr {
      type uint64;
    }
    leaf-list pmEmfPwrBackoffStepPwrDir5Distr {
      type uint64;
    }
    leaf pmActiveUeUlMax {
      type ietfyang:mac-address;
      config false;
    }
    leaf pmEmfResourceAllowedNormalizedDir {
      type uint64;
      config false;
    }
    leaf pmUeAssistedPrecodingOptCalibrated {
      type uint64;
      config false;
    }
    leaf-list pmEmfPwrBackoffScaledPwrDistr {
      type uint64;
    }
  }
  grouping NRSynchronization-attributes {
    leaf nRSynchronizationId {
      type string;
      mandatory true;
    }
  }
  grouping OutOfCov-attributes {
    leaf outOfCovId {
      type string;
      mandatory true;
    }
  }
  grouping OutOfCovUeCfg-attributes {
    leaf dlOutOfCovPCellReleaseThresh {
      type int16 {
        range "-1 | 10 | 20 | 30 | 40 | 50 | 60 | 70 | 80 | 90 | 100 | 110 | 120 | 130 | 140 | 150 | 160 | 170 | 180 | 190 | 200";
      }
      default "-1";
      description "Default value: -1.";
    }
    leaf outOfCovUeCfgId {
      type string;
      mandatory true;
    }
    leaf-list reservedBy {
      type string;
    }
    leaf ulOutOfCovPCellReleaseThresh {
      type int16 {
        range "-1 | 10 | 20 | 30 | 40 | 50 | 60 | 70 | 80 | 90 | 100 | 110 | 120 | 130 | 140 | 150 | 160 | 170 | 180 | 190 | 200";
      }
      default "-1";
      description "Default value: -1.";
    }
  }
  grouping Paging-attributes {
    leaf defaultPagingCycle {
      type int32 {
        range "32 | 64 | 128 | 256";
      }
      default "128";
      description "Default value: 128.";
    }
    leaf n {
      type enumeration {
        enum T;
        enum T1_2;
        enum T1_4;
        enum T1_8;
        enum T1_16;
      }
    }
    leaf nS {
      type int32 {
        range "1..2 | 4";
      }
      default "1";
      description "Default value: 1.";
    }
    leaf pagingDiscardTimer {
      type eytypes:int32_range_1-15;
      default "3";
      units "s";
      description "range 1..15; Default value: 3.";
    }
    leaf pagingDiscardTimerEdrx {
      type eytypes:int32_range_1-20;
      default "10";
      units "s";
      description "range 1..20; Default value: 10.";
    }
    leaf pagingId {
      type string;
      mandatory true;
    }
  }
  grouping PartitionMapping-attributes {
    leaf caPartition {
      type boolean;
      default "false";
      description "Default value: false.";
    }
    leaf-list listResourcePartitionRef {
      type string;
      ordered-by user;
    }
    leaf networkId {
      type int32 {
        range "1..6";
      }
      description "range 1..6.";
    }
    leaf partitionId {
      type int32 {
        range "1..13";
      }
      mandatory true;
      description "range 1..13.";
    }
    leaf partitionMappingId {
      type string;
      mandatory true;
    }
    leaf partitionMappingName {
      type string {
        length "1..255";
      }
      description "length 1..255.";
    }
    leaf-list priorityPartition5qiList {
      type eytypes:int32_range_1-255;
      ordered-by user;
    }
    leaf resourceAllocationPolicyRef {
      type string;
    }
    leaf resourcePartitionRef {
      type string;
      status deprecated;
      description "Takes effect: New connection; MOM flags: isNillable=true; Status info: Since 23.Q2. Replaced by listResourcePartitionRef. Planned to be removed..";
      reference "Takes effect: New connection.";
    }
    leaf userLabel {
      type string;
    }
  }
  grouping PdcchLinkAdaptation-attributes {
    leaf pdcchLaSinrUeOffset {
      type eytypes:int32_range_-10-10;
      default "0";
      units "dB";
      description "range -10..10; Default value: 0.";
    }
    leaf pdcchLinkAdaptationId {
      type string;
      mandatory true;
    }
  }
  grouping PdcchReuseForPdsch-attributes {
    leaf pdcchReuseForPdschId {
      type string;
      mandatory true;
    }
    leaf-list reservedBy {
      type string;
    }
    leaf ueConfGroupType {
      type enumeration {
        enum UE_MOBILITY_GROUP;
        enum UE_SERVICE_GROUP;
        enum UE_ADMISSION_GROUP;
      }
    }
    leaf userLabel {
      type string;
    }
  }
  grouping PdcchReuseForPdschUeCfg-attributes {
    leaf pdcchReuseForPdschEnabled {
      type boolean;
      default "false";
      description "Default value: false.";
    }
    leaf pdcchReuseForPdschUeCfgId {
      type string;
      mandatory true;
    }
    leaf-list prefUeGroupList {
      type eytypes:int32_range_1-255;
      ordered-by user;
    }
    leaf-list ueConfGroupList {
      type eytypes:int32_range_1-255;
      ordered-by user;
    }
    leaf-list ueGroupList {
      type eytypes:int32_range_1-255;
      ordered-by user;
    }
    leaf userLabel {
      type string;
    }
  }
  grouping PowerBackoff-attributes {
    leaf powerBackoffAvgTime {
      type eytypes:int32_range_30-1800;
      mandatory true;
      units "s";
      description "range 30..1800.";
    }
    leaf powerBackoffEnabled {
      type boolean;
      mandatory true;
    }
    leaf powerBackoffEnhanced {
      type boolean;
      default "false";
      description "Default value: false.";
    }
    leaf powerBackoffId {
      type string;
      mandatory true;
    }
    leaf powerBackoffThresh {
      type eytypes:int32_range_0-1000-2;
      mandatory true;
      description "range 0..1000.";
    }
  }
  grouping PowerBackoffDir-attributes {
    leaf powerBackoffDirAvgTime {
      type eytypes:int32_range_30-1800;
      mandatory true;
      units "s";
      description "range 30..1800.";
    }
    leaf powerBackoffDirEnabled {
      type boolean;
      mandatory true;
    }
    leaf powerBackoffDirId {
      type string;
      mandatory true;
    }
    list powerBackoffDirThresh {
      key "id";
      leaf id {
        type uint32;
        description "Synthetic key for struct entry.";
      }
      container attributes {
      leaf powerBackoffDirThresh1 {
        type eytypes:int32_range_0-1000-2;
        description "range 0..1000.";
      }
      leaf powerBackoffDirThresh2 {
        type eytypes:int32_range_0-1000-2;
        description "range 0..1000.";
      }
      leaf powerBackoffDirThresh3 {
        type eytypes:int32_range_0-1000-2;
        description "range 0..1000.";
      }
      leaf powerBackoffDirThresh4 {
        type eytypes:int32_range_0-1000-2;
        description "range 0..1000.";
      }
      leaf powerBackoffDirThresh5 {
        type eytypes:int32_range_0-1000-2;
        description "range 0..1000.";
      }
      leaf powerBackoffDirThresh6 {
        type eytypes:int32_range_0-1000-2;
        description "range 0..1000.";
      }
      leaf powerBackoffDirThresh7 {
        type eytypes:int32_range_0-1000-2;
        description "range 0..1000.";
      }
      leaf powerBackoffDirThresh8 {
        type eytypes:int32_range_0-1000-2;
        description "range 0..1000.";
      }
      }
    }
  }
  grouping PowerControl-attributes {
    leaf powerControlId {
      type string;
      mandatory true;
    }
  }
  grouping PowerControlUeCfg-attributes {
    leaf powerControlUeCfgId {
      type string;
      mandatory true;
    }
    leaf puschPowerControlModeFr1 {
      type enumeration {
        enum OLPC;
        enum POWER_BASED_CLPC;
      }
    }
    leaf puschPowerControlModeFr2 {
      type enumeration {
        enum OLPC;
        enum POWER_BASED_CLPC;
      }
    }
    leaf pZeroNomPuschOffset {
      type int32 {
        range "-16..15";
      }
      default "0";
      units "dB";
      description "range -16..15; Default value: 0.";
    }
    leaf-list reservedBy {
      type string;
    }
    leaf userLabel {
      type string;
    }
  }
  grouping Prescheduling-attributes {
    leaf preschedulingId {
      type string;
      mandatory true;
    }
  }
  grouping PreschedulingUeCfg-attributes {
    leaf highPrioPreschedDuration {
      type uint32 {
        range "10..1000";
      }
      default "100";
      units "ms";
      description "range 10..1000; Default value: 100.";
    }
    leaf highPrioPreschedPauseDuration {
      type uint32 {
        range "1..100";
      }
      default "4";
      units "ms";
      description "range 1..100; Default value: 4.";
    }
    leaf highPrioPreschedSinrBackoff {
      type int32 {
        range "0..100 | 1000";
      }
      default "0";
      units "dB";
      description "Default value: 0.";
    }
    leaf preschedulingDataSize {
      type uint32 {
        range "1..5000";
      }
      default "86";
      units "byte";
      description "range 1..5000; Default value: 86.";
    }
    leaf preschedulingDuration {
      type uint32 {
        range "5..30000";
      }
      default "100";
      units "ms";
      description "range 5..30000; Default value: 100.";
    }
    leaf preschedulingGrantInterval {
      type eytypes:int32_range_1-20-15;
      default "5";
      units "ms";
      description "range 1..20; Default value: 5.";
    }
    leaf preschedulingPathlossThresh {
      type int32 {
        range "50..170";
      }
      default "125";
      units "dB";
      description "range 50..170; Default value: 125.";
    }
    leaf preschedulingUeCfgId {
      type string;
      mandatory true;
    }
    leaf preschedulingUeMode {
      type enumeration {
        enum DISABLE;
        enum BASIC;
        enum HIGH_PRIORITY;
        enum DEFAULT;
      }
    }
    leaf-list reservedBy {
      type string;
    }
    leaf userLabel {
      type string;
    }
  }
  grouping PriorityDomainMapping-attributes {
    leaf priorityDomain {
      type eytypes:int32_range_1-64;
      default "48";
      description "range 1..64; Default value: 48.";
    }
    leaf priorityDomainMappingId {
      type string;
      mandatory true;
    }
    leaf-list priorityLevelsList {
      type uint32 {
        range "1..127";
      }
      ordered-by user;
    }
  }
  grouping PuschRep-attributes {
    leaf puschRepId {
      type string;
      mandatory true;
    }
    leaf-list reservedBy {
      type string;
    }
    leaf ueConfGroupType {
      type enumeration {
        enum UE_MOBILITY_GROUP;
        enum UE_SERVICE_GROUP;
        enum UE_ADMISSION_GROUP;
      }
    }
  }
  grouping PuschRepRel16Drx-attributes {
    leaf puschRepDrxInactTimer {
      type enumeration {
        enum INACTIVITYTIMER_0MS;
        enum INACTIVITYTIMER_1MS;
        enum INACTIVITYTIMER_2MS;
        enum INACTIVITYTIMER_3MS;
        enum INACTIVITYTIMER_4MS;
        enum INACTIVITYTIMER_5MS;
        enum INACTIVITYTIMER_6MS;
        enum INACTIVITYTIMER_8MS;
        enum INACTIVITYTIMER_10MS;
        enum INACTIVITYTIMER_20MS;
        enum INACTIVITYTIMER_30MS;
        enum INACTIVITYTIMER_40MS;
        enum INACTIVITYTIMER_50MS;
        enum INACTIVITYTIMER_60MS;
        enum INACTIVITYTIMER_80MS;
        enum INACTIVITYTIMER_100MS;
        enum INACTIVITYTIMER_200MS;
        enum INACTIVITYTIMER_300MS;
        enum INACTIVITYTIMER_500MS;
        enum INACTIVITYTIMER_750MS;
        enum INACTIVITYTIMER_1280MS;
        enum INACTIVITYTIMER_1920MS;
        enum INACTIVITYTIMER_2560MS;
      }
    }
    leaf puschRepDrxMode {
      type enumeration {
        enum ACTIVE;
        enum FORCED;
      }
    }
    leaf puschRepDrxRetxTimerUl {
      type int32 {
        range "6 | 8 | 16 | 24 | 33 | 40";
      }
      units "slot";
    }
    leaf puschRepRel16DrxId {
      type string;
      mandatory true;
    }
    leaf userLabel {
      type string;
    }
  }
  grouping PuschRepUeCfg-attributes {
    leaf-list prefUeGroupList {
      type eytypes:int32_range_1-255;
      ordered-by user;
    }
    leaf puschRepMode {
      type enumeration {
        enum NOT_ALLOWED;
        enum DYNAMIC;
      }
    }
    leaf puschRepUeCfgId {
      type string;
      mandatory true;
    }
    leaf-list ueConfGroupList {
      type eytypes:int32_range_1-255;
      ordered-by user;
    }
    leaf-list ueGroupList {
      type eytypes:int32_range_1-255;
      ordered-by user;
    }
    leaf userLabel {
      type string;
    }
  }
  grouping QosPriorityMapping-attributes {
    leaf defaultDomain {
      type uint32 {
        range "48";
      }
      config false;
      description "range 48..48.";
    }
    leaf qosPriorityMappingId {
      type string;
      mandatory true;
    }
  }
  grouping QosPriorityShift-attributes {
    leaf qosPriorityShiftId {
      type string;
      mandatory true;
    }
  }
  grouping Rach-attributes {
    leaf rachId {
      type string;
      mandatory true;
    }
    leaf-list reservedBy {
      type string;
    }
    leaf ueConfGroupType {
      type enumeration {
        enum UE_MOBILITY_GROUP;
        enum UE_SERVICE_GROUP;
        enum UE_ADMISSION_GROUP;
      }
    }
    leaf userLabel {
      type string;
    }
  }
  grouping RachUeCfg-attributes {
    leaf cfraEnabled {
      type boolean;
      default "false";
      description "Default value: false.";
    }
    leaf-list prefUeGroupList {
      type eytypes:int32_range_1-255;
      ordered-by user;
    }
    leaf rachUeCfgId {
      type string;
      mandatory true;
    }
    leaf-list ueConfGroupList {
      type eytypes:int32_range_1-255;
      ordered-by user;
    }
    leaf-list ueGroupList {
      type eytypes:int32_range_1-255;
      ordered-by user;
    }
    leaf userLabel {
      type string;
    }
  }
  grouping RadioBearerTable-attributes {
    leaf radioBearerTableId {
      type string;
      mandatory true;
    }
  }
  grouping RadioLinkControl-attributes {
    leaf radioLinkControlId {
      type string;
      mandatory true;
    }
  }
  grouping ResourceAllocationPolicies-attributes {
    leaf resourceAllocationPoliciesId {
      type string;
      mandatory true;
    }
    leaf userLabel {
      type string;
    }
  }
  grouping ResourceAllocationPolicy-attributes {
    leaf demotedRrpSchedulingPriority {
      type enumeration {
        enum DEMOTED_NORMAL;
        enum DEMOTED_LOW;
      }
    }
    leaf overAllocationAllowed {
      type boolean;
      default "true";
      description "Default value: true.";
    }
    leaf-list reservedBy {
      type string;
    }
    leaf resourceAllocationPolicyId {
      type string;
      mandatory true;
    }
    leaf resourceShareLimitRef {
      type string;
    }
    leaf rrpControllerRef {
      type string;
    }
    leaf rrpOperationModeDl {
      type enumeration {
        enum BALANCED;
        enum FAIRNESS_FAVORED;
      }
    }
    leaf rrpOperationModeUl {
      type enumeration {
        enum BALANCED;
        enum FAIRNESS_FAVORED;
      }
    }
    leaf shareAdjustmentModeDl {
      type enumeration {
        enum ABSOLUTE;
        enum GENERAL_COMPENSATION;
      }
    }
    leaf shareAdjustmentModeUl {
      type enumeration {
        enum ABSOLUTE;
        enum GENERAL_COMPENSATION;
      }
    }
    leaf spectrumShareDl {
      type eytypes:int32_range_0-100;
      mandatory true;
      units "percent";
      description "range 0..100.";
    }
    leaf spectrumShareUl {
      type eytypes:int32_range_0-100;
      mandatory true;
      units "percent";
      description "range 0..100.";
    }
    leaf userLabel {
      type string;
    }
  }
  grouping ResourceAllocTypeDl-attributes {
    leaf-list reservedBy {
      type string;
    }
    leaf resourceAllocTypeDlId {
      type string;
      mandatory true;
    }
    leaf ueConfGroupType {
      type enumeration {
        enum UE_MOBILITY_GROUP;
        enum UE_SERVICE_GROUP;
        enum UE_ADMISSION_GROUP;
      }
    }
  }
  grouping ResourceAllocTypeDlUeCfg-attributes {
    leaf-list prefUeGroupList {
      type eytypes:int32_range_1-255;
      ordered-by user;
    }
    leaf prefUeResourceAllocDlTypeFr1 {
      type enumeration {
        enum RESOURCE_ALLOCATION_TYPE_0;
        enum DYNAMIC_SWITCH_FB_TYPE_0;
        enum RESOURCE_ALLOCATION_TYPE_1;
        enum DYNAMIC_SWITCH_FB_TYPE_1;
      }
    }
    leaf resourceAllocTypeDlUeCfgId {
      type string;
      mandatory true;
    }
    leaf-list ueConfGroupList {
      type eytypes:int32_range_1-255;
      ordered-by user;
    }
    leaf-list ueGroupList {
      type eytypes:int32_range_1-255;
      ordered-by user;
    }
    leaf userLabel {
      type string;
    }
  }
  grouping ResourcePartition-attributes {
    leaf related5qiTableRef {
      type string;
    }
    leaf-list reservedBy {
      type string;
    }
    leaf resourcePartitionId {
      type string;
      mandatory true;
    }
    leaf resourcePartitionName {
      type string {
        length "1..255";
      }
      description "length 1..255.";
    }
  }
  grouping ResourcePartitionMember-attributes {
    leaf-list cellIdList {
      type eytypes:int32_range_0-16383;
      ordered-by user;
    }
    leaf endpointResourceRef {
      type string;
    }
    list pLMNIdList {
      key "id";
      leaf id {
        type uint32;
        description "Synthetic key for struct sequence entry.";
      }
      ordered-by user;
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
    leaf resourcePartitionMemberId {
      type string;
      mandatory true;
    }
    list sNSSAIList {
      key "id";
      leaf id {
        type uint32;
        description "Synthetic key for struct sequence entry.";
      }
      ordered-by user;
      container attributes {
      leaf sd {
        type eytypes:int32_range_0-16777215;
        description "range 0..16777215.";
      }
      leaf sst {
        type eytypes:int32_range_0-255;
        description "range 0..255.";
      }
      }
    }
    leaf-list spidRfspList {
      type eytypes:int32_range_0-256;
      ordered-by user;
    }
    leaf trafficCategory {
      type enumeration {
        enum SA;
        enum ENDC;
      }
    }
  }
  grouping ResourcePartitions-attributes {
    leaf resourcePartitionsId {
      type string;
      mandatory true;
    }
  }
  grouping ResourceShareLimit-attributes {
    leaf-list reservedBy {
      type string;
    }
    leaf resourceShareLimitId {
      type string;
      mandatory true;
    }
    leaf spectrumShareDlLowerLimit {
      type eytypes:int32_range_0-100;
      default "10";
      units "percent";
      description "range 0..100; Default value: 10.";
    }
    leaf spectrumShareDlUpperLimit {
      type eytypes:int32_range_1-100;
      default "90";
      units "percent";
      description "range 1..100; Default value: 90.";
    }
    leaf spectrumShareUlLowerLimit {
      type eytypes:int32_range_0-100;
      default "10";
      units "percent";
      description "range 0..100; Default value: 10.";
    }
    leaf spectrumShareUlUpperLimit {
      type eytypes:int32_range_1-100;
      default "90";
      units "percent";
      description "range 1..100; Default value: 90.";
    }
    leaf userLabel {
      type string;
    }
  }
  grouping RimOffload-attributes {
    leaf rimOffloadId {
      type string;
      mandatory true;
    }
  }
  grouping RimOffloadUeCfg-attributes {
    leaf-list reservedBy {
      type string;
    }
    leaf rimOffloadUeCfgId {
      type string;
      mandatory true;
    }
    leaf rimUlCriticalQualThresh {
      type eytypes:int32_range_-150-450;
      default "-50";
      units "dB";
      description "range -150..450; Default value: -50.";
    }
  }
  grouping RimRSGlobal-attributes {
    list frequencyDomainPara {
      key "id";
      leaf id {
        type uint32;
        description "Synthetic key for struct entry.";
      }
      container attributes {
      leaf rimRSBandwidth {
        type int32;
        default "48";
        units "PRB";
        description "Default value: 48.";
      }
      leaf rimRSCommonCarrierRefPoint {
        type int32 {
          range "-1..7125000";
        }
        default "-1";
        units "kHz";
        description "range -1..7125000; Default value: -1.";
      }
      leaf rimRSStartingFreqOffsetIdList {
        type string;
      }
      }
    }
    leaf rimRSGlobalId {
      type string;
      mandatory true;
    }
    list sequenceDomainPara {
      key "id";
      leaf id {
        type uint32;
        description "Synthetic key for struct entry.";
      }
      container attributes {
      leaf enableEnoughNotEnoughIndication {
        type enumeration {
          enum DISABLED;
          enum ENABLED;
        }
      }
      leaf rimRSScrambleIdListofRS1 {
        type string;
      }
      leaf rimRSScrambleIdListofRS2 {
        type string;
      }
      leaf rimRSScrambleTimerMultiplier {
        type ietfinet:ip-address;
        description "range 0..2147483647; Default value: 1.";
      }
      leaf rimRSScrambleTimerOffset {
        type eytypes:int32_range_0-2147483647;
        default "0";
        description "range 0..2147483647; Default value: 0.";
      }
      }
    }
    list timeDomainPara {
      key "id";
      leaf id {
        type uint32;
        description "Synthetic key for struct entry.";
      }
      container attributes {
      leaf dlUlSwitchingPeriod1 {
        type enumeration {
          enum MS0P5;
          enum MS0P625;
          enum MS1;
          enum MS1P25;
          enum MS2;
          enum MS2P5;
          enum MS3;
          enum MS4;
          enum MS5;
          enum MS10;
          enum MS20;
        }
      }
      leaf dlUlSwitchingPeriod2 {
        type enumeration {
          enum MS0P5;
          enum MS0P625;
          enum MS1;
          enum MS1P25;
          enum MS2;
          enum MS2P5;
          enum MS3;
          enum MS4;
          enum MS5;
          enum MS10;
          enum MS20;
        }
      }
      leaf enablenearfarIndicationRS1 {
        type enumeration {
          enum DISABLED;
          enum ENABLED;
        }
      }
      leaf enablenearfarIndicationRS2 {
        type enumeration {
          enum DISABLED;
          enum ENABLED;
        }
      }
      leaf farSymbolOffsetRS1 {
        type int32 {
          range "26..28";
        }
        default "26";
        description "range 26..28; Default value: 26.";
      }
      leaf farSymbolOffsetRS2 {
        type int32 {
          range "26..28";
        }
        default "26";
        description "range 26..28; Default value: 26.";
      }
      leaf nearOrOnlySymbolOffsetRS1 {
        type int32;
        default "6";
        description "Default value: 6.";
      }
      leaf nearOrOnlySymbolOffsetRS2 {
        type int32;
        default "6";
        description "Default value: 6.";
      }
      leaf nrofConsecutiveRIMRS1 {
        type int32;
        default "2";
        description "Default value: 2.";
      }
      leaf nrofConsecutiveRIMRS2 {
        type int32;
        default "2";
        description "Default value: 2.";
      }
      leaf symbolOffsetOfReferencePoint1 {
        type int32;
        default "52";
        description "Default value: 52.";
      }
      leaf symbolOffsetOfReferencePoint2 {
        type int32 {
          range "109..110";
        }
        default "110";
        description "range 109..110; Default value: 110.";
      }
      leaf totalNrOfSetIdOfRS1 {
        type uint32;
        default "524288";
        description "Default value: 524288.";
      }
      leaf totalNrOfSetIdOfRS2 {
        type uint32;
        default "524288";
        description "Default value: 524288.";
      }
      }
    }
  }
  grouping RimRSSet-attributes {
    leaf-list reservedBy {
      type string;
    }
    leaf rimRSSetId {
      type string;
      mandatory true;
    }
    leaf setId {
      type int32 {
        range "0..4194303";
      }
      mandatory true;
      description "range 0..4194303.";
    }
    leaf setType {
      type enumeration {
        enum RS_1;
        enum RS_2;
      }
    }
  }
  grouping Rrc-attributes {
    leaf n310 {
      type int32 {
        range "1..4 | 6 | 8 | 10 | 20";
      }
      default "20";
      description "Default value: 20.";
    }
    leaf n311 {
      type int32 {
        range "1..6 | 8 | 10";
      }
      default "1";
      description "Default value: 1.";
    }
    leaf rrcId {
      type string;
      mandatory true;
    }
    leaf t300 {
      type int32 {
        range "100 | 200 | 300 | 400 | 600 | 1000 | 1500 | 2000";
      }
      default "1000";
      units "ms";
      description "Default value: 1000.";
    }
    leaf t301 {
      type int32 {
        range "100 | 200 | 300 | 400 | 600 | 1000 | 1500 | 2000";
      }
      default "400";
      units "ms";
      description "Default value: 400.";
    }
    leaf t304 {
      type int32 {
        range "50 | 100 | 150 | 200 | 500 | 1000 | 2000 | 10000";
      }
      default "1000";
      units "ms";
      description "Default value: 1000.";
    }
    leaf t310 {
      type int32 {
        range "0 | 50 | 100 | 200 | 500 | 1000 | 2000 | 4000 | 6000";
      }
      default "2000";
      units "ms";
      description "Default value: 2000.";
    }
    leaf t311 {
      type int32 {
        range "1000 | 3000 | 5000 | 10000 | 15000 | 20000 | 30000";
      }
      default "3000";
      units "ms";
      description "Default value: 3000.";
    }
    leaf t319 {
      type int32 {
        range "100 | 200 | 300 | 400 | 600 | 1000 | 1500 | 2000";
      }
      default "400";
      units "ms";
      description "Default value: 400.";
    }
  }
  grouping RrpController-attributes {
    leaf-list reservedBy {
      type string;
    }
    leaf rrpControllerId {
      type string;
      mandatory true;
    }
    leaf rrpControllerMode {
      type enumeration {
        enum NO_AUTO_CONTROL;
        enum AUTO_CONTROL_1;
        enum AUTO_CONTROL_2;
      }
    }
    list slopeInfoDl {
      key "id";
      leaf id {
        type uint32;
        description "Synthetic key for struct sequence entry.";
      }
      ordered-by user;
      container attributes {
      leaf slope {
        type eytypes:int32_range_0-1000-11;
        units "percent";
        description "range 0..1000.";
      }
      leaf startOfRange {
        type int32 {
          range "0..10000";
        }
        description "range 0..10000.";
      }
      }
    }
    list slopeInfoUl {
      key "id";
      leaf id {
        type uint32;
        description "Synthetic key for struct sequence entry.";
      }
      ordered-by user;
      container attributes {
      leaf slope {
        type eytypes:int32_range_0-1000-11;
        units "percent";
        description "range 0..1000.";
      }
      leaf startOfRange {
        type int32 {
          range "0..10000";
        }
        description "range 0..10000.";
      }
      }
    }
    leaf spectrumShareDlDownStepLimit {
      type eytypes:int32_range_1-100;
      default "5";
      units "percent";
      description "range 1..100; Default value: 5.";
    }
    leaf spectrumShareDlUpStepLimit {
      type eytypes:int32_range_1-100;
      default "5";
      units "percent";
      description "range 1..100; Default value: 5.";
    }
    leaf spectrumShareUlDownStepLimit {
      type eytypes:int32_range_1-100;
      default "5";
      units "percent";
      description "range 1..100; Default value: 5.";
    }
    leaf spectrumShareUlUpStepLimit {
      type eytypes:int32_range_1-100;
      default "5";
      units "percent";
      description "range 1..100; Default value: 5.";
    }
    leaf targetThpDl {
      type eytypes:int32_range_0-1000000;
      default "0";
      units "kbps";
      description "range 0..1000000; Default value: 0.";
    }
    leaf targetThpUl {
      type eytypes:int32_range_0-1000000;
      default "0";
      units "kbps";
      description "range 0..1000000; Default value: 0.";
    }
    leaf userLabel {
      type string;
    }
  }
  grouping SchedulingProfile-attributes {
    leaf dlCaSchedulingMode {
      type enumeration {
        enum UNLIMITED;
        enum PCELL_ONLY;
      }
    }
    leaf essResourceAllocationMode {
      type enumeration {
        enum SCHED_POLICY;
        enum DEMAND_WEIGHTED_RP;
      }
    }
    leaf relativePriority {
      type eytypes:int32_range_1-256;
      default "1";
      description "range 1..256; Default value: 1.";
    }
    leaf relativePriorityMode {
      type enumeration {
        enum RP_ONLY;
        enum PDB_ONLY;
        enum RP_AND_PDB;
      }
    }
    leaf-list reservedBy {
      type string;
    }
    leaf schedulingAlgorithm {
      type enumeration {
        enum RESOURCE_FAIR;
        enum PRIORITIZED_RATE;
        enum SOFT_RATE_THROTTLING;
        enum ELEVATION_TIME;
        enum LATENCY_PRIORITIZED;
        enum LATENCY_PRIORITIZED_TCC;
      }
    }
    leaf schedulingProfileId {
      type string;
      mandatory true;
    }
    leaf ulRelativePriority {
      type eytypes:int32_range_1-256;
      description "range 1..256.";
    }
    leaf ulSchedulingAlgorithm {
      type enumeration {
        enum RESOURCE_FAIR;
        enum PRIORITIZED_RATE;
        enum SOFT_RATE_THROTTLING;
        enum ELEVATION_TIME;
        enum LATENCY_PRIORITIZED;
        enum LATENCY_PRIORITIZED_TCC;
      }
    }
    leaf userLabel {
      type string;
    }
  }
  grouping ServicePolicy-attributes {
    leaf demotedRrpSchedulingPriority {
      type enumeration {
        enum DEMOTED_NORMAL;
        enum DEMOTED_LOW;
      }
    }
    leaf resourceShareLimitRef {
      type string;
    }
    leaf rrpControllerRef {
      type string;
    }
    leaf rrpOperationModeDl {
      type enumeration {
        enum BALANCED;
        enum FAIRNESS_FAVORED;
      }
    }
    leaf rrpOperationModeUl {
      type enumeration {
        enum BALANCED;
        enum FAIRNESS_FAVORED;
      }
    }
    leaf serviceId {
      type eytypes:int32_range_1-2;
      mandatory true;
      description "range 1..2.";
    }
    leaf-list servicePolicy5qiList {
      type eytypes:int32_range_1-255;
      ordered-by user;
    }
    leaf servicePolicyId {
      type string;
      mandatory true;
    }
    leaf servicePolicyName {
      type string {
        length "1..255";
      }
      description "length 1..255.";
    }
    leaf spectrumShareDl {
      type eytypes:int32_range_0-100;
      mandatory true;
      units "percent";
      description "range 0..100.";
    }
    leaf spectrumShareUl {
      type eytypes:int32_range_0-100;
      mandatory true;
      units "percent";
      description "range 0..100.";
    }
    leaf userLabel {
      type string;
    }
  }
  grouping SessionLimit-attributes {
    leaf maxNoOfSessions {
      type eytypes:int32_range_0-2147483647;
      description "range 0..2147483647.";
    }
    leaf-list reservedBy {
      type string;
    }
    leaf sessionLimitId {
      type string;
      mandatory true;
    }
  }
  grouping SignalingRadioBearer-attributes {
    leaf dlMaxRetxThreshold {
      type int32 {
        range "1..4 | 6 | 8 | 16 | 32";
      }
      default "8";
      description "Default value: 8.";
    }
    leaf rlcAckPduDelayMode {
      type enumeration {
        enum NO_DELAY;
        enum VERY_LOW;
        enum LOW;
        enum BALANCED;
        enum HIGH;
      }
    }
    leaf signalingRadioBearerId {
      type string;
      mandatory true;
    }
    leaf tPollRetransmitDl {
      type int32 {
        range "5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 2000 | 4000";
      }
      default "45";
      units "ms";
      description "Default value: 45.";
    }
    leaf tPollRetransmitUl {
      type int32 {
        range "5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 2000 | 4000";
      }
      default "45";
      units "ms";
      description "Default value: 45.";
    }
    leaf tReassemblyDl {
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200";
      }
      default "35";
      units "ms";
      description "Default value: 35.";
    }
    leaf tReassemblyUl {
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200";
      }
      default "35";
      units "ms";
      description "Default value: 35.";
    }
    leaf ulMaxRetxThreshold {
      type int32 {
        range "1..4 | 6 | 8 | 16 | 32";
      }
      default "8";
      description "Default value: 8.";
    }
  }
  grouping SoftAcAssist-attributes {
    leaf softAcAssistId {
      type string;
      mandatory true;
    }
    leaf ueConfGroupType {
      type enumeration {
        enum UE_MOBILITY_GROUP;
        enum UE_SERVICE_GROUP;
        enum UE_ADMISSION_GROUP;
      }
    }
  }
  grouping SoftAcAssistUeCfg-attributes {
    leaf-list prefUeGroupList {
      type eytypes:int32_range_1-255;
      ordered-by user;
    }
    leaf-list reservedBy {
      type string;
    }
    leaf softAcAssistEnabled {
      type boolean;
      default "true";
      description "Default value: true.";
    }
    leaf softAcAssistUeCfgId {
      type string;
      mandatory true;
    }
    leaf-list ueConfGroupList {
      type eytypes:int32_range_1-255;
      ordered-by user;
    }
    leaf-list ueGroupList {
      type eytypes:int32_range_1-255;
      ordered-by user;
    }
  }
  grouping SrbPriority-attributes {
    leaf-list reservedBy {
      type string;
    }
    leaf srbPriorityId {
      type string;
      mandatory true;
    }
    leaf ueConfGroupType {
      type enumeration {
        enum UE_MOBILITY_GROUP;
        enum UE_SERVICE_GROUP;
        enum UE_ADMISSION_GROUP;
      }
    }
  }
  grouping SrbPriorityUeCfg-attributes {
    leaf-list prefUeGroupList {
      type eytypes:int32_range_1-255;
      ordered-by user;
    }
    leaf srbPriority {
      type eytypes:int32_range_1-16;
      default "1";
      description "range 1..16; Default value: 1.";
    }
    leaf srbPriorityUeCfgId {
      type string;
      mandatory true;
    }
    leaf-list ueConfGroupList {
      type eytypes:int32_range_1-255;
      ordered-by user;
    }
    leaf-list ueGroupList {
      type eytypes:int32_range_1-255;
      ordered-by user;
    }
  }
  grouping SrHandling-attributes {
    leaf-list reservedBy {
      type string;
    }
    leaf srHandlingId {
      type string;
      mandatory true;
    }
    leaf ueConfGroupType {
      type enumeration {
        enum UE_MOBILITY_GROUP;
        enum UE_SERVICE_GROUP;
        enum UE_ADMISSION_GROUP;
      }
    }
    leaf userLabel {
      type string;
    }
  }
  grouping SrHandlingUeCfg-attributes {
    leaf-list conditional5qi {
      type eytypes:int32_range_0-255;
      ordered-by user;
    }
    leaf-list prefUeGroupList {
      type eytypes:int32_range_1-255;
      ordered-by user;
    }
    leaf srHandlingMode {
      type enumeration {
        enum DISABLED;
        enum SR_PRIO_5QI;
      }
    }
    leaf srHandlingUeCfgId {
      type string;
      mandatory true;
    }
    leaf-list ueConfGroupList {
      type eytypes:int32_range_1-255;
      ordered-by user;
    }
    leaf-list ueGroupList {
      type eytypes:int32_range_1-255;
      ordered-by user;
    }
  }
  grouping SrPeriodicity-attributes {
    leaf-list reservedBy {
      type string;
    }
    leaf srPeriodicityId {
      type string;
      mandatory true;
    }
    leaf ueConfGroupType {
      type enumeration {
        enum UE_MOBILITY_GROUP;
        enum UE_SERVICE_GROUP;
        enum UE_ADMISSION_GROUP;
      }
    }
  }
  grouping SrPeriodicityCovAdaptUeCfg-attributes {
    leaf covAdaptSrPEnabled {
      type boolean;
      default "false";
      description "Default value: false.";
    }
    leaf covAdaptSrPNrLowQualThresh {
      type int32 {
        range "-40..145";
      }
      default "20";
      units "dB";
      description "range -40..145; Default value: 20.";
    }
    leaf covAdaptSrPNrQualHyst {
      type eytypes:int32_range_0-60;
      default "5";
      units "dB";
      description "range 0..60; Default value: 5.";
    }
    leaf covAdaptSrPStartRsrpThresh {
      type eytypes:int32_range_-156--29;
      default "-107";
      units "dBm";
      description "range -156..-29; Default value: -107.";
    }
    leaf-list prefUeGroupList {
      type eytypes:int32_range_1-255;
      ordered-by user;
    }
    leaf srPeriodicityCovAdaptUeCfgId {
      type string;
      mandatory true;
    }
    leaf-list ueConfGroupList {
      type eytypes:int32_range_1-255;
      ordered-by user;
    }
    leaf-list ueGroupList {
      type eytypes:int32_range_1-255;
      ordered-by user;
    }
  }
  grouping SrPeriodicityPoolSet-attributes {
    leaf fddTddUlDlPattern {
      type enumeration {
        enum TDD_ULDL_PATTERN_00;
        enum TDD_ULDL_PATTERN_01;
        enum TDD_ULDL_PATTERN_02;
        enum TDD_ULDL_PATTERN_03;
        enum TDD_ULDL_PATTERN_04;
        enum TDD_ULDL_PATTERN_05;
        enum TDD_ULDL_PATTERN_06;
        enum TDD_ULDL_PATTERN_07;
        enum TDD_ULDL_PATTERN_08;
        enum FDD;
      }
      mandatory true;
    }
    leaf noOfSrResourcesHsPool1 {
      type eytypes:int32_range_0-32;
      default "32";
      description "range 0..32; Default value: 32.";
    }
    leaf noOfSrResourcesHsPool2 {
      type eytypes:int32_range_0-32;
      default "0";
      description "range 0..32; Default value: 0.";
    }
    leaf noOfSrResourcesHsPool3 {
      type eytypes:int32_range_0-32;
      default "0";
      description "range 0..32; Default value: 0.";
    }
    leaf noOfSrResourcesHsPool4 {
      type eytypes:int32_range_0-32;
      default "0";
      description "range 0..32; Default value: 0.";
    }
    leaf noOfSrResourcesHsPool5 {
      type eytypes:int32_range_0-32;
      default "0";
      description "range 0..32; Default value: 0.";
    }
    leaf noOfSrResourcesPool1 {
      type eytypes:int32_range_0-240;
      default "56";
      description "range 0..240; Default value: 56.";
    }
    leaf noOfSrResourcesPool2 {
      type eytypes:int32_range_0-240;
      default "0";
      description "range 0..240; Default value: 0.";
    }
    leaf noOfSrResourcesPool3 {
      type eytypes:int32_range_0-240;
      default "0";
      description "range 0..240; Default value: 0.";
    }
    leaf noOfSrResourcesPool4 {
      type eytypes:int32_range_0-240;
      default "0";
      description "range 0..240; Default value: 0.";
    }
    leaf noOfSrResourcesPool5 {
      type eytypes:int32_range_0-240;
      default "0";
      description "range 0..240; Default value: 0.";
    }
    leaf-list reservedBy {
      type string;
    }
    leaf srPeriodicityPool1 {
      type enumeration {
        enum SR_PERIODICITY_SYM2;
        enum SR_PERIODICITY_SYM6_OR_7;
        enum SR_PERIODICITY_SL1;
        enum SR_PERIODICITY_SL2;
        enum SR_PERIODICITY_SL4;
        enum SR_PERIODICITY_SL5;
        enum SR_PERIODICITY_SL8;
        enum SR_PERIODICITY_SL10;
        enum SR_PERIODICITY_SL16;
        enum SR_PERIODICITY_SL20;
        enum SR_PERIODICITY_SL40;
        enum SR_PERIODICITY_SL80;
        enum SR_PERIODICITY_SL160;
        enum SR_PERIODICITY_SL320;
        enum SR_PERIODICITY_SL640;
      }
    }
    leaf srPeriodicityPool2 {
      type enumeration {
        enum SR_PERIODICITY_SYM2;
        enum SR_PERIODICITY_SYM6_OR_7;
        enum SR_PERIODICITY_SL1;
        enum SR_PERIODICITY_SL2;
        enum SR_PERIODICITY_SL4;
        enum SR_PERIODICITY_SL5;
        enum SR_PERIODICITY_SL8;
        enum SR_PERIODICITY_SL10;
        enum SR_PERIODICITY_SL16;
        enum SR_PERIODICITY_SL20;
        enum SR_PERIODICITY_SL40;
        enum SR_PERIODICITY_SL80;
        enum SR_PERIODICITY_SL160;
        enum SR_PERIODICITY_SL320;
        enum SR_PERIODICITY_SL640;
      }
    }
    leaf srPeriodicityPool3 {
      type enumeration {
        enum SR_PERIODICITY_SYM2;
        enum SR_PERIODICITY_SYM6_OR_7;
        enum SR_PERIODICITY_SL1;
        enum SR_PERIODICITY_SL2;
        enum SR_PERIODICITY_SL4;
        enum SR_PERIODICITY_SL5;
        enum SR_PERIODICITY_SL8;
        enum SR_PERIODICITY_SL10;
        enum SR_PERIODICITY_SL16;
        enum SR_PERIODICITY_SL20;
        enum SR_PERIODICITY_SL40;
        enum SR_PERIODICITY_SL80;
        enum SR_PERIODICITY_SL160;
        enum SR_PERIODICITY_SL320;
        enum SR_PERIODICITY_SL640;
      }
    }
    leaf srPeriodicityPool4 {
      type enumeration {
        enum SR_PERIODICITY_SYM2;
        enum SR_PERIODICITY_SYM6_OR_7;
        enum SR_PERIODICITY_SL1;
        enum SR_PERIODICITY_SL2;
        enum SR_PERIODICITY_SL4;
        enum SR_PERIODICITY_SL5;
        enum SR_PERIODICITY_SL8;
        enum SR_PERIODICITY_SL10;
        enum SR_PERIODICITY_SL16;
        enum SR_PERIODICITY_SL20;
        enum SR_PERIODICITY_SL40;
        enum SR_PERIODICITY_SL80;
        enum SR_PERIODICITY_SL160;
        enum SR_PERIODICITY_SL320;
        enum SR_PERIODICITY_SL640;
      }
    }
    leaf srPeriodicityPool5 {
      type enumeration {
        enum SR_PERIODICITY_SYM2;
        enum SR_PERIODICITY_SYM6_OR_7;
        enum SR_PERIODICITY_SL1;
        enum SR_PERIODICITY_SL2;
        enum SR_PERIODICITY_SL4;
        enum SR_PERIODICITY_SL5;
        enum SR_PERIODICITY_SL8;
        enum SR_PERIODICITY_SL10;
        enum SR_PERIODICITY_SL16;
        enum SR_PERIODICITY_SL20;
        enum SR_PERIODICITY_SL40;
        enum SR_PERIODICITY_SL80;
        enum SR_PERIODICITY_SL160;
        enum SR_PERIODICITY_SL320;
        enum SR_PERIODICITY_SL640;
      }
    }
    leaf srPeriodicityPoolSetId {
      type string;
      mandatory true;
    }
    leaf subCarrierSpacing {
      type int32 {
        range "15 | 30 | 120";
      }
      default "120";
      units "kHz";
      description "Default value: 120.";
    }
  }
  grouping SrPeriodicityUeCfg-attributes {
    leaf-list prefUeGroupList {
      type eytypes:int32_range_1-255;
      ordered-by user;
    }
    leaf prefUeSrPeriodicityPool {
      type enumeration {
        enum SR_PERIODICITY_POOL_1;
        enum SR_PERIODICITY_POOL_2;
        enum SR_PERIODICITY_POOL_3;
        enum SR_PERIODICITY_POOL_4;
        enum SR_PERIODICITY_POOL_5;
      }
    }
    leaf prefUeSrPeriodicityPoolFr2 {
      type enumeration {
        enum SR_PERIODICITY_POOL_1;
        enum SR_PERIODICITY_POOL_2;
        enum SR_PERIODICITY_POOL_3;
        enum SR_PERIODICITY_POOL_4;
        enum SR_PERIODICITY_POOL_5;
      }
    }
    leaf srPeriodicityUeCfgId {
      type string;
      mandatory true;
    }
    leaf-list ueConfGroupList {
      type eytypes:int32_range_1-255;
      ordered-by user;
    }
    leaf-list ueGroupList {
      type eytypes:int32_range_1-255;
      ordered-by user;
    }
    leaf userLabel {
      type string;
    }
  }
  grouping SssgSwitch-attributes {
    leaf-list reservedBy {
      type string;
    }
    leaf sssgSwitchId {
      type string;
      mandatory true;
    }
    leaf ueConfGroupType {
      type enumeration {
        enum UE_MOBILITY_GROUP;
        enum UE_SERVICE_GROUP;
        enum UE_ADMISSION_GROUP;
      }
    }
    leaf userLabel {
      type string;
    }
  }
  grouping SssgSwitchPwrOpt-attributes {
    leaf downDlThreshold {
      type eytypes:int32_range_0-2000;
      default "10";
      units "slot";
      description "range 0..2000; Default value: 10.";
    }
    leaf downUlThreshold {
      type eytypes:int32_range_0-2000;
      default "10";
      units "slot";
      description "range 0..2000; Default value: 10.";
    }
    leaf lowDlActivityTimer {
      type eytypes:int32_range_0-5000-5;
      default "200";
      units "ms";
      description "range 0..5000; Default value: 200.";
    }
    leaf lowUlActivityTimer {
      type eytypes:int32_range_0-5000-5;
      default "200";
      units "ms";
      description "range 0..5000; Default value: 200.";
    }
    leaf-list reservedBy {
      type string;
    }
    leaf sssgSwitchPwrOptId {
      type string;
      mandatory true;
    }
    leaf upDlThreshold {
      type eytypes:int32_range_0-2000;
      default "100";
      units "slot";
      description "range 0..2000; Default value: 100.";
    }
    leaf upUlThreshold {
      type eytypes:int32_range_0-2000;
      default "100";
      units "slot";
      description "range 0..2000; Default value: 100.";
    }
    leaf userLabel {
      type string;
    }
  }
  grouping SssgSwitchUeCfg-attributes {
    leaf-list prefUeGroupList {
      type eytypes:int32_range_1-255;
      ordered-by user;
    }
    leaf sssgSwitchPmIdentity {
      type eytypes:int32_range_1-8;
      config false;
      description "range 1..8.";
    }
    leaf sssgSwitchPwrOptRef {
      type string;
    }
    leaf sssgSwitchUeCfgId {
      type string;
      mandatory true;
    }
    leaf-list ueConfGroupList {
      type eytypes:int32_range_1-255;
      ordered-by user;
    }
    leaf-list ueGroupList {
      type eytypes:int32_range_1-255;
      ordered-by user;
    }
    leaf userLabel {
      type string;
    }
  }
  grouping TermPointToGNBCUCP-attributes {
    leaf administrativeState {
      type enumeration {
        enum LOCKED;
        enum UNLOCKED;
        enum SHUTTINGDOWN;
      }
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf gNBCUName {
      type string {
        length "1..150";
      }
      config false;
      description "length 1..150.";
    }
    leaf ipv4Address {
      type ietfinet:ipv4-address;
      default "0.0.0.0";
      description "length 7..15; Default value: 0.0.0.0.";
    }
    leaf ipv6Address {
      type ietfinet:ipv6-address;
      default "::";
      description "length 2..39; Default value: ::.";
    }
    leaf operationalState {
      type enumeration {
        enum DISABLED;
        enum ENABLED;
      }
      config false;
    }
    leaf termPointToGNBCUCPId {
      type string;
      mandatory true;
    }
    leaf usedIpAddress {
      type ietfinet:ip-address;
      config false;
    }
  }
  grouping TrafficDefinition-attributes {
    leaf-list reservedBy {
      type string;
    }
    leaf trafficDefinitionId {
      type string;
      mandatory true;
    }
  }
  grouping TrafficDefinitions-attributes {
    leaf trafficDefinitionsId {
      type string;
      mandatory true;
    }
  }
  grouping TrafficGroup-attributes {
    leaf-list reservedBy {
      type string;
      description "Status info: Since 25.Q2. Planned to be removed..";
    }
    leaf trafficGroupId {
      type string;
      mandatory true;
      status deprecated;
      description "MOM flags: restricted, noNotification; Status info: Since 25.Q2. Planned to be removed..";
    }
  }
  grouping TrafficGroupMember-attributes {
    list pLMNIdList {
      key "id";
      leaf id {
        type uint32;
        description "Synthetic key for struct sequence entry.";
      }
      ordered-by user;
      description "Status info: Since 25.Q2. Replaced by TrafficSetMember::pLMNIdList. Planned to be removed..";
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
    leaf sessionLimitRef {
      type string;
      status deprecated;
      description "MOM flags: isNillable=true; Status info: Since 25.Q2. Replaced by TrafficSet::sessionLimitRef. Planned to be removed..";
    }
    list sNSSAIList {
      key "id";
      leaf id {
        type uint32;
        description "Synthetic key for struct sequence entry.";
      }
      ordered-by user;
      description "Status info: Since 25.Q2. Replaced by TrafficSetMember::sNSSAIList. Planned to be removed.; Specification: 3GPP TS 28.541.";
      container attributes {
      leaf sd {
        type eytypes:int32_range_0-16777215;
        description "range 0..16777215.";
      }
      leaf sst {
        type eytypes:int32_range_0-255;
        description "range 0..255.";
      }
      }
    }
    leaf-list spidRfspList {
      type eytypes:int32_range_0-256;
      ordered-by user;
      description "Status info: Since 25.Q2. Replaced by TrafficSetMember::spidRfspList. Planned to be removed..";
    }
    leaf trafficCategory {
      type enumeration {
        enum SA;
        enum ENDC;
      }
      status deprecated;
      default "SA";
      description "Default value: SA; Status info: Since 25.Q2. Replaced by TrafficSetMember::trafficCategory. Planned to be removed..";
    }
    leaf trafficGroupMemberId {
      type string;
      mandatory true;
      status deprecated;
      description "MOM flags: restricted, noNotification; Status info: Since 25.Q2. Planned to be removed..";
    }
  }
  grouping TrafficGroups-attributes {
    leaf trafficGroupsId {
      type string;
      mandatory true;
      status deprecated;
      description "MOM flags: restricted, noNotification; Status info: Since 25.Q2. Planned to be removed..";
    }
  }
  grouping TrafficSet-attributes {
    leaf sessionLimitRef {
      type string;
    }
    leaf trafficSetId {
      type string;
      mandatory true;
    }
  }
  grouping TrafficSetMember-attributes {
    list pLMNIdList {
      key "id";
      leaf id {
        type uint32;
        description "Synthetic key for struct sequence entry.";
      }
      ordered-by user;
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
    list sNSSAIList {
      key "id";
      leaf id {
        type uint32;
        description "Synthetic key for struct sequence entry.";
      }
      ordered-by user;
      container attributes {
      leaf sd {
        type eytypes:int32_range_0-16777215;
        description "range 0..16777215.";
      }
      leaf sst {
        type eytypes:int32_range_0-255;
        description "range 0..255.";
      }
      }
    }
    leaf-list spidRfspList {
      type eytypes:int32_range_0-256;
      ordered-by user;
    }
    leaf trafficCategory {
      type enumeration {
        enum SA;
        enum ENDC;
      }
    }
    leaf trafficSetMemberId {
      type string;
      mandatory true;
    }
  }
  grouping UeAdaptiveRlc-attributes {
    leaf ueAdaptiveRlcId {
      type string;
      mandatory true;
    }
    leaf ueConfGroupType {
      type enumeration {
        enum UE_MOBILITY_GROUP;
        enum UE_SERVICE_GROUP;
        enum UE_ADMISSION_GROUP;
      }
    }
  }
  grouping UeAdaptiveRlcUeCfg-attributes {
    leaf-list prefUeGroupList {
      type eytypes:int32_range_1-255;
      ordered-by user;
    }
    leaf ueAdaptiveRlcRetxMode {
      type enumeration {
        enum ENABLED;
        enum DISABLED;
      }
    }
    leaf ueAdaptiveRlcUeCfgId {
      type string;
      mandatory true;
    }
    leaf-list ueConfGroupList {
      type eytypes:int32_range_1-255;
      ordered-by user;
    }
    leaf-list ueGroupList {
      type eytypes:int32_range_1-255;
      ordered-by user;
    }
  }
  grouping UeBb-attributes {
    leaf ueBbId {
      type string;
      mandatory true;
    }
  }
  grouping UeBbProfile-attributes {
    leaf-list reservedBy {
      type string;
    }
    leaf ueBbProfileId {
      type string;
      mandatory true;
    }
    leaf ueConfGroupType {
      type enumeration {
        enum UE_MOBILITY_GROUP;
        enum UE_SERVICE_GROUP;
        enum UE_ADMISSION_GROUP;
      }
    }
    leaf userLabel {
      type string;
    }
  }
  grouping UeBbProfileUeCfg-attributes {
    leaf bsrUeCfgRef {
      type string;
    }
    leaf configuredGrantUeCfgRef {
      type string;
    }
    leaf csiProfileUeCfgRef {
      type ietfinet:ip-address;
    }
    leaf dlBeamOptProfileUeCfgRef {
      type string;
    }
    leaf dlMimoUeCfgRef {
      type string;
    }
    leaf harqUeCfgRef {
      type string;
    }
    leaf linkAdaptationUeCfgRef {
      type string;
    }
    leaf outOfCovUeCfgRef {
      type string;
    }
    leaf powerControlUeCfgRef {
      type string;
    }
    leaf-list prefUeGroupList {
      type eytypes:int32_range_0-255;
      ordered-by user;
    }
    leaf preschedulingUeCfgRef {
      type string;
    }
    leaf rimOffloadUeCfgRef {
      type string;
    }
    leaf ueBbProfileUeCfgId {
      type string;
      mandatory true;
    }
    leaf-list ueConfGroupList {
      type eytypes:int32_range_1-255;
      ordered-by user;
    }
    leaf-list ueGroupList {
      type eytypes:int32_range_0-255;
      ordered-by user;
    }
    leaf ulServiceDefinitionUeCfgRef {
      type string;
    }
    leaf ulWfPortSwitchUeCfgRef {
      type ietfinet:port-number;
    }
    leaf userLabel {
      type string;
    }
  }
  grouping UeCA-attributes {
    leaf ueCAId {
      type string;
      mandatory true;
    }
  }
  grouping UeCC-attributes {
    leaf ueCCId {
      type string;
      mandatory true;
    }
  }
  grouping UlBranchInterference-attributes {
    leaf rfBranchRef {
      type string;
      config false;
    }
    leaf ulBranchInterferenceId {
      type string;
      mandatory true;
    }
    leaf-list pmRadioRecInterferencePwrPrbDistr {
      type uint64;
    }
  }
  grouping UlCgSwitch-attributes {
    leaf-list reservedBy {
      type string;
    }
    leaf ueConfGroupType {
      type enumeration {
        enum UE_MOBILITY_GROUP;
        enum UE_SERVICE_GROUP;
        enum UE_ADMISSION_GROUP;
      }
    }
    leaf ulCgSwitchId {
      type string;
      mandatory true;
    }
    leaf userLabel {
      type string;
    }
  }
  grouping UlCgSwitchCfg-attributes {
    leaf-list reservedBy {
      type string;
    }
    leaf ulCgSwitchCfgId {
      type string;
      mandatory true;
    }
    leaf ulCgSwitchMode {
      type enumeration {
        enum DISABLED;
        enum ENABLED;
      }
    }
    leaf ulScgLowQualHyst {
      type eytypes:int32_range_5-600;
      default "60";
      units "dB";
      description "range 5..600; Default value: 60.";
    }
    leaf ulScgLowQualThresh {
      type eytypes:int32_range_-400-1450;
      default "170";
      units "dB";
      description "range -400..1450; Default value: 170.";
    }
    leaf userLabel {
      type string;
    }
  }
  grouping UlCgSwitchUeCfg-attributes {
    leaf-list prefUeGroupList {
      type eytypes:int32_range_1-255;
      ordered-by user;
    }
    leaf-list ueConfGroupList {
      type eytypes:int32_range_1-255;
      ordered-by user;
    }
    leaf-list ueGroupList {
      type eytypes:int32_range_1-255;
      ordered-by user;
    }
    leaf ulCgSwitchCfgRef {
      type string;
    }
    leaf ulCgSwitchUeCfgId {
      type string;
      mandatory true;
    }
    leaf userLabel {
      type string;
    }
  }
  grouping UlDelayBasedPriority-attributes {
    leaf ulDelayBasedPriorityId {
      type string;
      mandatory true;
    }
    leaf ulDemotedPriority {
      type enumeration {
        enum LOW;
        enum HIGH;
      }
    }
  }
  grouping UlLatencyBasedPriority-attributes {
    leaf ulDemotedPriority {
      type enumeration {
        enum LOW;
        enum HIGH;
      }
    }
    leaf ulLatencyBasedPriorityId {
      type string;
      mandatory true;
    }
    leaf ulPriorityScaler {
      type eytypes:int32_range_1-8;
      default "1";
      description "range 1..8; Default value: 1.";
    }
    leaf ulPriorityShiftMargin {
      type int32 {
        range "-231..280";
      }
      default "0";
      units "ms";
      description "range -231..280; Default value: 0.";
    }
    leaf ulResourceControlLevel {
      type enumeration {
        enum LEVEL_0;
        enum LEVEL_1;
        enum LEVEL_2;
        enum LEVEL_3;
        enum LEVEL_4;
        enum LEVEL_5;
      }
    }
    leaf ulWeightOffset {
      type enumeration {
        enum ZERO;
        enum LOW;
        enum MEDIUM;
        enum HIGH;
      }
    }
  }
  grouping UlLinkAdaptation-attributes {
    leaf ulBlerTarget {
      type int32 {
        range "1..3000";
      }
      default "1000";
      units "percent";
      description "range 1..3000; Default value: 1000.";
    }
    leaf ulBlerTargetExtended {
      type int32 {
        range "-1 | 1..100";
      }
      default "-1";
      units "percent";
      description "Default value: -1.";
    }
    leaf ulDownStep {
      type eytypes:int32_range_0-100-6;
      default "0";
      units "dB";
      description "range 0..100; Default value: 0.";
    }
    leaf ulLinkAdaptationId {
      type string;
      mandatory true;
    }
    leaf ulMaxMcsIndex {
      type eytypes:int32_range_0-28;
      default "27";
      description "range 0..28; Default value: 27.";
    }
    leaf ulMinTbs {
      type int32 {
        range "-1 | 96..1023";
      }
      default "96";
      units "bit";
      description "Default value: 96.";
    }
    leaf ulServicePacketInterval {
      type int32 {
        range "-1 | 10..100";
      }
      status deprecated;
      default "-1";
      units "ms";
      description "Default value: -1; Takes effect: New connection; Status info: Since 24.Q3. Replaced by UlService::ulServicePacketInterval. Planned to be removed..";
      reference "Takes effect: New connection.";
    }
    leaf ulServicePacketSize {
      type int32 {
        range "-1 | 30..120";
      }
      status deprecated;
      default "-1";
      units "byte";
      description "Default value: -1; Takes effect: New connection; Status info: Since 24.Q3. Replaced by UlService::ulServicePacketSize. Planned to be removed..";
      reference "Takes effect: New connection.";
    }
    leaf ulSinrBackoff {
      type eytypes:int32_range_0-100-6;
      default "0";
      units "dB";
      description "range 0..100; Default value: 0.";
    }
  }
  grouping UlRateBasedPriority-attributes {
    leaf ulDemotedPriority {
      type enumeration {
        enum LOW;
        enum HIGH;
      }
    }
    leaf ulDemotedRelativePriority {
      type boolean;
      default "false";
      description "Default value: false.";
    }
    leaf ulDrbOverloadHandling {
      type enumeration {
        enum BASIC;
        enum REJECT;
      }
    }
    leaf ulPrioritizedRate {
      type int32 {
        range "1..10 | 20 | 30 | 40 | 50 | 60 | 70 | 80 | 90 | 100 | 200 | 300 | 400 | 500 | 600 | 700 | 800 | 900 | 1000 | 2000 | 3000 | 4000 | 5000 | 6000 | 7000 | 8000 | 9000 | 10000 | 20000 | 30000 | 40000 | 50000 | 60000 | 70000 | 80000 | 90000 | 100000 | 200000 | 300000 | 400000 | 500000 | 600000 | 700000 | 800000 | 900000 | 1000000";
      }
      default "1";
      units "kbps";
      description "Default value: 1.";
    }
    leaf ulRateBasedPriorityId {
      type string;
      mandatory true;
    }
  }
  grouping UlResourceBasedPriority-attributes {
    leaf ulDrbPriorityLimit {
      type eytypes:int32_range_1-100-4;
      default "100";
      description "range 1..100; Default value: 100.";
    }
    leaf ulResourceBasedPriorityId {
      type string;
      mandatory true;
    }
    leaf ulResourceLimitMode {
      type enumeration {
        enum NO_LIMIT;
        enum LIMITED;
        enum LIMITED_TO_CELL_LIMIT;
      }
    }
  }
  grouping UlService-attributes {
    leaf ulPacketPredictionMode {
      type enumeration {
        enum DEACTIVATED;
        enum BASIC;
      }
    }
    leaf ulService5qi {
      type eytypes:int32_range_1-255;
      description "range 1..255.";
    }
    leaf ulServiceId {
      type string;
      mandatory true;
    }
    leaf ulServicePacketInterval {
      type int32 {
        range "-1 | 10..160";
      }
      default "-1";
      units "ms";
      description "Default value: -1.";
    }
    leaf ulServicePacketSize {
      type int32 {
        range "-1 | 30..200";
      }
      default "-1";
      units "byte";
      description "Default value: -1.";
    }
  }
  grouping UlServiceDefinition-attributes {
    leaf ulServiceDefinitionId {
      type string;
      mandatory true;
    }
  }
  grouping UlServiceDefinitionUeCfg-attributes {
    leaf-list reservedBy {
      type string;
    }
    leaf ulServiceDefinitionUeCfgId {
      type string;
      mandatory true;
    }
  }
  grouping UlWfPortSwitch-attributes {
    leaf ulWfPortSwitchId {
      type ietfinet:port-number;
      mandatory true;
    }
  }
  grouping UlWfPortSwitchUeCfg-attributes {
    leaf-list reservedBy {
      type string;
    }
    leaf ulLayerSwitchMetric {
      type enumeration {
        enum UL_WB_SINR;
        enum UL_SINR_MAX;
        enum UL_SINR_MIN;
      }
    }
    leaf ulLayerSwitchQualHyst {
      type eytypes:int32_range_0-100-6;
      default "50";
      units "dB";
      description "range 0..100; Default value: 50.";
    }
    leaf ulLayerSwitchQualThresh {
      type int32 {
        range "-10000 | -400..1150 | 10000";
      }
      default "50";
      units "dB";
      description "Default value: 50.";
    }
    leaf ulPortSwitchFr1Mode {
      type ietfinet:port-number;
    }
    leaf ulPortSwitchMetric {
      type ietfinet:port-number;
    }
    leaf ulPortSwitchQualHyst {
      type ietfinet:port-number;
      default "50";
      units "dB";
      description "range 0..100; Default value: 50.";
    }
    leaf ulPortSwitchQualThresh {
      type ietfinet:port-number;
      default "50";
      units "dB";
      description "Default value: 50.";
    }
    leaf ulPortSwitchTimeToTrigger {
      type ietfinet:port-number;
      default "4000";
      units "ms";
      description "range 0..4000; Default value: 4000.";
    }
    leaf ulWfPortSwitchUeCfgId {
      type ietfinet:port-number;
      mandatory true;
    }
    leaf ulWfPuschStartFr1RsrpThresh {
      type eytypes:int32_range_-156--29;
      default "-104";
      units "dBm";
      description "range -156..-29; Default value: -104.";
    }
    leaf ulWfSwitchFr1CpRetProhibTimer {
      type eytypes:int32_range_0-10000;
      default "1000";
      units "ms";
      description "range 0..10000; Default value: 1000.";
    }
    leaf ulWfSwitchFr1Mode {
      type enumeration {
        enum CP_OFDM_NOSWITCH;
        enum DFTS_OFDM_NOSWITCH;
        enum WAVEFORM_SWITCH;
      }
    }
    leaf ulWfSwitchFr1QualHyst {
      type int32 {
        range "1..300";
      }
      default "100";
      units "dB";
      description "range 1..300; Default value: 100.";
    }
    leaf ulWfSwitchFr1QualThresh {
      type int32 {
        range "-400..1150";
      }
      default "-400";
      units "dB";
      description "range -400..1150; Default value: -400.";
    }
    leaf userLabel {
      type string;
    }
  }
}
