module ericsson-rcspmeventm-radio {
  yang-version 1.1;
  namespace "urn:com:ericsson:ecim:RcsPMEventM";
  prefix rcspmeve;
  import ietf-inet-types {
    prefix ietfinet;
  }
  import ericsson-managed-element {
    prefix emael;
  }
  description "Auto-generated from Ericsson ECIM (MOM XML).";
  revision 2026-02-13 {
    description "Initial auto-generated revision. Generated at 2026-02-13 20:11.";
  }

  augment "/emael:ManagedElement/emael:SystemFunctions" {
    list PmEventM {
      description "Additional definitions from MOM:min/max-elements:1/1;root;systemCreated; The Performance Management (PM) Event Management fragment. It is used to manage the event jobs on the Managed Element. Once an event job is activated the events can be collected and sent via streaming and/or file transfer.";
      key "pmEventMId";
      leaf pmEventMId {
        type leafref {
          path "../attributes/pmEventMId";
        }
      }
      container attributes {
        uses PmEventM-attributes;
      }
    }
  }

  augment "/emael:ManagedElement/emael:SystemFunctions/PmEventM/EventProducer/EventGroup" {
    list EventType {
      description "Additional definitions from MOM:min/max-elements:0/unbounded;systemCreated; Defines the event type that can be generated by the Managed Element.";
      key "eventTypeId";
      leaf eventTypeId {
        type leafref {
          path "../attributes/eventTypeId";
        }
      }
      container attributes {
        uses EventType-attributes;
      }
    }
  }

  augment "/emael:ManagedElement/emael:SystemFunctions/PmEventM/EventProducer" {
    list FilePullCapabilities {
      description "Additional definitions from MOM:min/max-elements:0/1;systemCreated; Event capabilities specific to file pull.";
      key "filePullCapabilitiesId";
      leaf filePullCapabilitiesId {
        type leafref {
          path "../attributes/filePullCapabilitiesId";
        }
      }
      container attributes {
        uses FilePullCapabilities-attributes;
      }
    }
  }

  augment "/emael:ManagedElement/emael:SystemFunctions/PmEventM/EventProducer" {
    list EventCapabilities {
      description "Additional definitions from MOM:min/max-elements:1/1;systemCreated; Event capabilities.";
      key "eventCapabilitiesId";
      leaf eventCapabilitiesId {
        type leafref {
          path "../attributes/eventCapabilitiesId";
        }
      }
      container attributes {
        uses EventCapabilities-attributes;
      }
    }
  }

  augment "/emael:ManagedElement/emael:SystemFunctions/PmEventM/EventProducer" {
    list StreamingCapabilities {
      description "Additional definitions from MOM:min/max-elements:0/1;systemCreated; Streaming capabilities.";
      key "streamCapabilitiesId";
      leaf streamCapabilitiesId {
        type leafref {
          path "../attributes/streamCapabilitiesId";
        }
      }
      container attributes {
        uses StreamingCapabilities-attributes;
      }
    }
  }

  augment "/emael:ManagedElement/emael:SystemFunctions/PmEventM/EventProducer" {
    list EventGroup {
      description "Additional definitions from MOM:min/max-elements:0/unbounded;systemCreated; Represents a group of related Event Types.";
      key "eventGroupId";
      leaf eventGroupId {
        type leafref {
          path "../attributes/eventGroupId";
        }
      }
      container attributes {
        uses EventGroup-attributes;
      }
    }
  }

  augment "/emael:ManagedElement/emael:SystemFunctions/PmEventM/EventProducer" {
    list EventFilterType {
      description "Additional definitions from MOM:min/max-elements:0/unbounded;systemCreated; Describes the available Event Filter Type definitions.";
      key "eventFilterTypeId";
      leaf eventFilterTypeId {
        type leafref {
          path "../attributes/eventFilterTypeId";
        }
      }
      container attributes {
        uses EventFilterType-attributes;
      }
    }
  }

  augment "/emael:ManagedElement/emael:SystemFunctions/PmEventM/EventProducer" {
    list EventJob {
      description "Additional definitions from MOM:min/max-elements:0/unbounded; Defines the information to be used to activate and configure an event job on the Managed Element.";
      key "eventJobId";
      leaf eventJobId {
        type leafref {
          path "../attributes/eventJobId";
        }
      }
      container attributes {
        uses EventJob-attributes;
      }
    }
  }

  augment "/emael:ManagedElement/emael:SystemFunctions/PmEventM/EventProducer" {
    list FileTypes {
      description "Additional definitions from MOM:min/max-elements:1/1;systemCreated; Configuration specified for each FileType. Usage is defined for each node type.";
      key "fileTypesId";
      leaf fileTypesId {
        type leafref {
          path "../attributes/fileTypesId";
        }
      }
      container attributes {
        uses FileTypes-attributes;
      }
    }
  }

  augment "/emael:ManagedElement/emael:SystemFunctions/PmEventM/EventProducer/FileTypes" {
    list FileType {
      description "Additional definitions from MOM:min/max-elements:0/unbounded;systemCreated; Describes the file type collected by PM Event Producer.";
      key "fileTypeId";
      leaf fileTypeId {
        type leafref {
          path "../attributes/fileTypeId";
        }
      }
      container attributes {
        uses FileType-attributes;
      }
    }
  }

  augment "/emael:ManagedElement/emael:SystemFunctions/PmEventM" {
    list EventProducer {
      description "Additional definitions from MOM:min/max-elements:0/unbounded;systemCreated; Event Producer. Allows for multiple types of Event Producer within an Application describing distinct Event functions and capabilities.";
      key "eventProducerId";
      leaf eventProducerId {
        type leafref {
          path "../attributes/eventProducerId";
        }
      }
      container attributes {
        uses EventProducer-attributes;
      }
    }
  }
  typedef CompressionTypes {
    type enumeration {
      enum GZIP;
    }
  }
  typedef DnsLookupSupport {
    type enumeration {
      enum DNS_LOOKUP_SUPPORTED;
      enum DNS_LOOKUP_NOT_SUPPORTED;
    }
  }
  typedef EventStatus {
    type enumeration {
      enum PRELIMINARY;
      enum USED;
      enum DEPRECATED;
    }
  }
  typedef FilterMethod {
    type enumeration {
      enum SINGLE_SELECT;
      enum MULTI_SELECT;
      enum INTERVAL;
      enum DISTINGUISHED_NAMES;
      enum REGEXP;
    }
  }
  typedef JobControl {
    type enumeration {
      enum FULL;
      enum STARTSTOP;
      enum VIEWONLY;
    }
  }
  typedef JobState {
    type enumeration {
      enum ACTIVE;
      enum STOPPED;
    }
  }
  typedef SessionState {
    type enumeration {
      enum ACTIVATING;
      enum ACTIVE;
      enum DEACTIVATING;
      enum STOPPED;
      enum FAILED;
    }
  }
  typedef TimePeriod {
    type enumeration {
      enum ONE_MIN;
      enum FIVE_MIN;
      enum FIFTEEN_MIN;
      enum THIRTY_MIN;
      enum ONE_HOUR;
      enum TWELVE_HOUR;
      enum ONE_DAY;
      enum TEN_SECONDS;
      enum THIRTY_SECONDS;
    }
  }
  grouping EventCapabilities-attributes {
    leaf eventCapabilitiesId {
      type string;
      mandatory true;
    }
    leaf maxNoOfJobs {
      type uint16;
      config false;
    }
    leaf fileLocation {
      type string;
    }
    leaf fileName {
      type string;
    }
    leaf fileVersion {
      type string;
    }
  }
  grouping EventFilterType-attributes {
    leaf eventFilterTypeId {
      type string;
      mandatory true;
    }
    leaf description {
      type ietfinet:ip-address;
      config false;
    }
    leaf filterMethod {
      type enumeration {
        enum SINGLE_SELECT;
        enum MULTI_SELECT;
        enum INTERVAL;
        enum DISTINGUISHED_NAMES;
        enum REGEXP;
      }
      config false;
    }
    leaf valueSpec {
      type string;
      config false;
    }
    leaf defaultValue {
      type string;
      config false;
    }
  }
  grouping EventGroup-attributes {
    leaf eventGroupId {
      type string;
      mandatory true;
    }
    leaf description {
      type ietfinet:ip-address;
      config false;
    }
    list moClass {
      config false;
      container attributes {
      leaf moClassName {
        type string;
      }
      leaf mimName {
        type string;
      }
      }
    }
    leaf eventGroupVersion {
      type string;
      config false;
    }
    leaf-list validFilters {
      type string;
    }
    leaf generation {
      type string;
      config false;
    }
  }
  grouping EventJob-attributes {
    leaf eventJobId {
      type string;
      mandatory true;
    }
    leaf description {
      type ietfinet:ip-address;
    }
    list eventFilter {
      key "id";
      leaf id {
        type uint32;
        description "Synthetic key for struct sequence entry.";
      }
      container attributes {
      leaf filterName {
        type string;
      }
      leaf filterValue {
        type string;
      }
      }
    }
    leaf requestedJobState {
      type enumeration {
        enum ACTIVE;
        enum STOPPED;
      }
    }
    leaf currentJobState {
      type enumeration {
        enum ACTIVATING;
        enum ACTIVE;
        enum DEACTIVATING;
        enum STOPPED;
        enum FAILED;
      }
      config false;
    }
    leaf fileOutputEnabled {
      type boolean;
      mandatory true;
    }
    leaf streamDestinationIpAddress {
      type ietfinet:ip-address;
    }
    leaf streamDestinationPort {
      type ietfinet:port-number;
    }
    leaf reportingPeriod {
      type ietfinet:port-number;
    }
    leaf streamOutputEnabled {
      type boolean;
      mandatory true;
    }
    leaf jobControl {
      type enumeration {
        enum FULL;
        enum STARTSTOP;
        enum VIEWONLY;
      }
      config false;
    }
    leaf-list eventGroupRef {
      type string;
    }
    leaf-list eventTypeRef {
      type string;
    }
    leaf fileCompressionType {
      type enumeration {
        enum GZIP;
      }
    }
    leaf streamCompressionType {
      type enumeration {
        enum GZIP;
      }
    }
    leaf jobGroup {
      type string;
    }
    leaf streamDestination {
      type string;
    }
  }
  grouping EventProducer-attributes {
    leaf eventProducerId {
      type string;
      mandatory true;
    }
    leaf eventProducerName {
      type string;
      config false;
    }
    leaf generation {
      type string;
      config false;
    }
    leaf associatedFunction {
      type string;
      config false;
    }
  }
  grouping EventType-attributes {
    leaf eventTypeId {
      type string;
      mandatory true;
    }
    leaf triggerDescription {
      type ietfinet:ip-address;
      config false;
    }
    leaf eventStatus {
      type enumeration {
        enum PRELIMINARY;
        enum USED;
        enum DEPRECATED;
      }
      config false;
    }
    leaf periodicity {
      type uint64;
      config false;
    }
  }
  grouping FilePullCapabilities-attributes {
    leaf filePullCapabilitiesId {
      type string;
      mandatory true;
    }
    leaf-list supportedReportingPeriods {
      type ietfinet:port-number;
    }
    leaf outputDirectory {
      type string;
      config false;
    }
    leaf maxNoOfEventFiles {
      type uint16;
      config false;
    }
    leaf alignedReportingPeriod {
      type ietfinet:port-number;
      config false;
      description "Default value: true.";
    }
    leaf-list supportedCompressionTypes {
      type ietfinet:port-number;
    }
    leaf finalROP {
      type boolean;
      config false;
      default "false";
      description "Default value: false.";
    }
  }
  grouping FileType-attributes {
    leaf fileTypeId {
      type string;
      mandatory true;
    }
    leaf description {
      type ietfinet:ip-address;
      config false;
    }
    leaf fileSizeMax {
      type string;
      config false;
    }
    leaf fileSizePercent {
      type string;
      mandatory true;
    }
  }
  grouping FileTypes-attributes {
    leaf fileTypesId {
      type string;
      mandatory true;
    }
    leaf userLabel {
      type string;
    }
  }
  grouping PmEventM-attributes {
    leaf pmEventMId {
      type string;
      mandatory true;
    }
  }
  grouping StreamingCapabilities-attributes {
    leaf streamCapabilitiesId {
      type string;
      mandatory true;
    }
    leaf-list supportedCompressionTypes {
      type ietfinet:port-number;
    }
    leaf dnsLookupSupport {
      type ietfinet:port-number;
      config false;
    }
  }
}
