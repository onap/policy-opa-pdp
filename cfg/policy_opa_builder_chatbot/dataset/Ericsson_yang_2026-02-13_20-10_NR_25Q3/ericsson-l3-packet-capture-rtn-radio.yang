module ericsson-l3-packet-capture-rtn-radio {
  yang-version 1.1;
  namespace "urn:com:ericsson:ecim:RtnL3PacketCapture";
  prefix l3pktcaprdo;
  import ericsson-managed-element {
    prefix emael;
  }
  description "Auto-generated from Ericsson ECIM (MOM XML).";
  revision 2026-02-13 {
    description "Initial auto-generated revision. Generated at 2026-02-13 20:11.";
  }

  augment "/emael:ManagedElement/emael:Transport" {
    list PacketCapture {
      description "Additional definitions from MOM:min/max-elements:0/1;root; Packet Capture";
      key "packetCaptureId";
      leaf packetCaptureId {
        type leafref {
          path "../attributes/packetCaptureId";
        }
      }
      container attributes {
        uses PacketCapture-attributes;
      }
    }
  }
  typedef PacketCaptureDirection {
    type enumeration {
      enum BOTH;
      enum EGRESS;
      enum INGRESS;
    }
  }
  grouping PacketCapture-attributes {
    leaf packetCaptureId {
      type string;
      mandatory true;
    }
    leaf userLabel {
      type string {
        length "1..128";
      }
      description "length 1..128.";
    }
  }
}
