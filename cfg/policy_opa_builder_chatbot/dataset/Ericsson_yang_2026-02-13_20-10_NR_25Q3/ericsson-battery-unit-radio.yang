module ericsson-battery-unit-radio {
  yang-version 1.1;
  namespace "urn:com:ericsson:ecim:ReqBatteryUnit";
  prefix bturdo;
  import ericsson-managed-element {
    prefix emael;
  }
  import ericsson-yang-types {
    prefix eytypes;
  }
  import ericsson-equip-radio {
    prefix equiprdo;
  }
  description "Auto-generated from Ericsson ECIM (MOM XML).";
  revision 2026-02-13 {
    description "Initial auto-generated revision. Generated at 2026-02-13 20:11.";
  }

  augment "/emael:ManagedElement/equiprdo:Equipment" {
    list BatteryUnit {
      description "Additional definitions from MOM:min/max-elements:0/32;root;systemCreated; This MO represents a battery unit connected to the system. The battery unit can be of lithium-ion type or lead-acid type. This MO is created automatically. MO can only be deleted by action delete(). To prevent the system from recreating the BatteryUnit MO, battery hardware must be disconnected. RDNs of these MOs are BatteryUnit=1, BatteryUnit=2 and so on.";
      key "batteryUnitId";
      leaf batteryUnitId {
        type leafref {
          path "../attributes/batteryUnitId";
        }
      }
      container attributes {
        uses BatteryUnit-attributes;
      }
    }
  }
  typedef AvailStatus {
    type enumeration {
      enum IN_TEST;
      enum FAILED;
      enum POWER_OFF;
      enum OFF_LINE;
      enum OFF_DUTY;
      enum DEPENDENCY;
      enum DEGRADED;
      enum NOT_INSTALLED;
      enum LOG_FULL;
      enum DEPENDENCY_LOCKED;
      enum DEPENDENCY_FAILED;
      enum DEPENDENCY_SHUTTINGDOWN;
      enum DEPENDENCY_RECOVERY;
      enum DEPENDENCY_HOLDING;
    }
  }
  typedef OperState {
    type enumeration {
      enum DISABLED;
      enum ENABLED;
    }
  }
  grouping BatteryUnit-attributes {
    leaf batteryUnitId {
      type string;
      mandatory true;
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf fullyChargedCapacity {
      type eytypes:int32_range_-1-999999;
      config false;
      units "Ah";
      description "range -1..999999.";
    }
    leaf nominalCapacity {
      type eytypes:int32_range_-1-999999;
      config false;
      units "Ah";
      description "range -1..999999.";
    }
    leaf operationalState {
      type enumeration {
        enum DISABLED;
        enum ENABLED;
      }
      config false;
    }
    list productData {
      config false;
      container attributes {
      leaf productionDate {
        type string {
          length "5..8";
        }
        description "length 5..8.";
      }
      leaf productName {
        type string {
          length "1..32";
        }
        description "length 1..32.";
      }
      leaf productNumber {
        type string {
          length "1..24";
        }
        description "length 1..24.";
      }
      leaf productRevision {
        type string {
          length "1..7";
        }
        description "length 1..7.";
      }
      leaf serialNumber {
        type string {
          length "1..13";
        }
        description "length 1..13.";
      }
      }
    }
    leaf stateOfHealth {
      type eytypes:int32_range_-1-100;
      config false;
      units "percent";
      description "range -1..100.";
    }
    leaf batteryBackupRef {
      type string;
      config false;
    }
    leaf batteryFuseUnitRef {
      type string;
      config false;
    }
    leaf batteryProtocolAdapterRef {
      type string;
      config false;
    }
    leaf installationDate {
      type string {
        length "8";
      }
      default "00000000";
      description "length 8..8; Default value: 00000000.";
    }
    leaf userLabel {
      type string {
        length "0..128";
      }
      description "length 0..128.";
    }
    leaf-list pmBatteryCellVoltageMin {
      type uint32;
    }
    leaf-list pmBatteryCellVoltageDelta {
      type uint32;
    }
    leaf-list pmBatteryUnitTemp {
      type uint32;
    }
    leaf pmUnderTempAlarms {
      type uint32;
      config false;
    }
    leaf-list pmBatteryCellVoltageMax {
      type uint32;
    }
    leaf pmOverTempAlarms {
      type uint32;
      config false;
    }
    leaf pmDisconnectsAtCharge {
      type uint32;
      config false;
    }
  }
}
