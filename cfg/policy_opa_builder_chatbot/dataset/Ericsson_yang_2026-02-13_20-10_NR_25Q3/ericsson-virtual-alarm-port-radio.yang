module ericsson-virtual-alarm-port-radio {
  yang-version 1.1;
  namespace "urn:com:ericsson:ecim:ReqVirtualAlarmPort";
  prefix valprtrdo;
  import ietf-inet-types {
    prefix ietfinet;
  }
  import ericsson-cabinet-radio {
    prefix cabrdo;
  }
  import ericsson-managed-element {
    prefix emael;
  }
  import ericsson-equip-radio {
    prefix equiprdo;
  }
  description "Auto-generated from Ericsson ECIM (MOM XML).";
  revision 2026-02-13 {
    description "Initial auto-generated revision. Generated at 2026-02-13 20:11.";
  }

  augment "/emael:ManagedElement/equiprdo:Equipment/cabrdo:Cabinet" {
    list VirtualAlarmPort {
      description "Additional definitions from MOM:min/max-elements:0/unbounded;root;systemCreated; This MO is in secondary node. It mirrors an AlarmPort MO which is in primary node. MO is created by the system when the mirrored AlarmPort MO has a raised alarm. MO is deleted when the alarm is ceased. The RDN of this MO is described in attribute virtualAlarmPortId. Dependencies: Can only exist in the node when the attribute supportSystemControl on MO EquipmentSupportFunction is set to false.";
      key "virtualAlarmPortId";
      leaf virtualAlarmPortId {
        type leafref {
          path "../attributes/virtualAlarmPortId";
        }
      }
      container attributes {
        uses VirtualAlarmPort-attributes;
      }
    }
  }
  typedef ApcPerceivedSeverity {
    type enumeration {
      enum CRITICAL;
      enum MAJOR;
      enum MINOR;
      enum WARNING;
    }
  }
  grouping VirtualAlarmPort-attributes {
    leaf virtualAlarmPortId {
      type ietfinet:port-number;
      mandatory true;
    }
    leaf alarmSlogan {
      type string {
        length "1..63";
      }
      config false;
      description "length 1..63.";
    }
    leaf perceivedSeverity {
      type enumeration {
        enum CRITICAL;
        enum MAJOR;
        enum MINOR;
        enum WARNING;
      }
      config false;
    }
  }
}
