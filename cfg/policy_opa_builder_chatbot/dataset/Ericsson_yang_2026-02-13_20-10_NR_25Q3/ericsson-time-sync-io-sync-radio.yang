module ericsson-time-sync-io-sync-radio {
  yang-version 1.1;
  namespace "urn:com:ericsson:ecim:RsyncTimeSyncIO";
  prefix tsynciordo;
  import ietf-inet-types {
    prefix ietfinet;
  }
  import ericsson-synchronization-sync-radio {
    prefix syncrdo;
  }
  import ericsson-managed-element {
    prefix emael;
  }
  description "Auto-generated from Ericsson ECIM (MOM XML).";
  revision 2026-02-13 {
    description "Initial auto-generated revision. Generated at 2026-02-13 20:11.";
  }

  augment "/emael:ManagedElement/emael:Transport/syncrdo:Synchronization" {
    list TimeSyncIO {
      description "Additional definitions from MOM:min/max-elements:0/8;root; The TimeSyncIO is used to indicate that a physical synchronization port is used for time synchronization.";
      key "timeSyncIOId";
      leaf timeSyncIOId {
        type leafref {
          path "../attributes/timeSyncIOId";
        }
      }
      container attributes {
        uses TimeSyncIO-attributes;
      }
    }
  }
  typedef AvailStatus {
    type enumeration {
      enum IN_TEST;
      enum FAILED;
      enum POWER_OFF;
      enum OFF_LINE;
      enum OFF_DUTY;
      enum DEPENDENCY;
      enum DEGRADED;
      enum NOT_INSTALLED;
      enum LOG_FULL;
      enum DEPENDENCY_LOCKED;
      enum DEPENDENCY_FAILED;
      enum DEPENDENCY_SHUTTINGDOWN;
    }
  }
  typedef OperState {
    type enumeration {
      enum DISABLED;
      enum ENABLED;
    }
  }
  typedef PortDirection {
    type enumeration {
      enum INPUT_ONLY;
      enum OUTPUT_ONLY;
    }
  }
  typedef TimeSyncIOStatus {
    type enumeration {
      enum NO_FAULT;
      enum LOSS_OF_SIGNAL;
      enum HW_FAULT;
      enum NO_MESSAGES;
      enum PROTOCOL_NOT_RECOGNIZED;
      enum LOSS_OF_1PPS_SIGNAL;
      enum NO_SYNC_TO_SATELLITES;
      enum DEGRADED;
    }
  }
  grouping TimeSyncIO-attributes {
    leaf adminPortDirection {
      type ietfinet:port-number;
      status deprecated;
      description "Default value: INPUT_ONLY.";
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
      }
    }
    leaf compensationDelay {
      type uint16 {
        range "0..65535";
      }
      default "0";
      units "ns";
      description "range 0..65535; Default value: 0.";
    }
    leaf encapsulation {
      type string;
      mandatory true;
    }
    leaf filterTime {
      type uint16 {
        range "1..12";
      }
      default "12";
      units "min";
      description "range 1..12; Default value: 12.";
    }
    leaf operationalState {
      type enumeration {
        enum DISABLED;
        enum ENABLED;
      }
      config false;
    }
    leaf-list reservedBy {
      type string;
    }
    leaf timeSyncIOId {
      type string;
      mandatory true;
    }
    leaf timeSyncIOStatus {
      type enumeration {
        enum NO_FAULT;
        enum LOSS_OF_SIGNAL;
        enum HW_FAULT;
        enum NO_MESSAGES;
        enum PROTOCOL_NOT_RECOGNIZED;
        enum LOSS_OF_1PPS_SIGNAL;
        enum NO_SYNC_TO_SATELLITES;
        enum DEGRADED;
      }
      config false;
    }
    leaf-list phaseJump {
      type uint64;
    }
    leaf gnssTimeOffsetActiveReference {
      type int64;
      config false;
    }
    leaf gnssTimeOffsetMax {
      type int64;
      config false;
    }
    leaf gnssTimeOffsetStDev {
      type int64;
      config false;
    }
    leaf gnssTimeOffsetMin {
      type int64;
      config false;
    }
    leaf gnssTimeOffsetAvg {
      type int64;
      config false;
    }
  }
}
