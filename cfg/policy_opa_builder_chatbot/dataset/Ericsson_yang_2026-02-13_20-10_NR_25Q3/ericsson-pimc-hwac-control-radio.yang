module ericsson-pimc-hwac-control-radio {
  yang-version 1.1;
  namespace "urn:com:ericsson:ecim:ReqPimcHwacControl";
  prefix phctrlrdo;
  import ericsson-field-replaceable-unit-radio {
    prefix frurdo;
  }
  import ericsson-managed-element {
    prefix emael;
  }
  import ericsson-equip-radio {
    prefix equiprdo;
  }
  description "Auto-generated from Ericsson ECIM (MOM XML).";
  revision 2026-02-13 {
    description "Initial auto-generated revision. Generated at 2026-02-13 20:11.";
  }

  augment "/emael:ManagedElement/equiprdo:Equipment/frurdo:FieldReplaceableUnit" {
    list PimcHwacControl {
      description "Additional definitions from MOM:min/max-elements:0/1;root; Represents Passive Inter-Modulation Cancellation (PIMC) function configured on a radio unit. Created manually for enabling PIMC on current radio unit.";
      key "pimcHwacControlId";
      leaf pimcHwacControlId {
        type leafref {
          path "../attributes/pimcHwacControlId";
        }
      }
      container attributes {
        uses PimcHwacControl-attributes;
      }
    }
  }
  grouping PimcHwacControl-attributes {
    leaf pimcHwacControlId {
      type string;
      mandatory true;
    }
    leaf pimcEnabled {
      type boolean;
      default "false";
      description "Default value: false.";
    }
    leaf pimcHwacAllocated {
      type boolean;
      config false;
    }
  }
}
