module ericsson-rtnpeeripsecprofile-radio {
  yang-version 1.1;
  namespace "urn:com:ericsson:ecim:RtnPeerIpsecProfile";
  prefix rtnpeeri;
  import ietf-inet-types {
    prefix ietfinet;
  }
  import ericsson-l3-router-rtn-radio {
    prefix l3rtrdo;
  }
  import ericsson-managed-element {
    prefix emael;
  }
  description "Auto-generated from Ericsson ECIM (MOM XML).";
  revision 2026-02-13 {
    description "Initial auto-generated revision. Generated at 2026-02-13 20:11.";
  }

  augment "/emael:ManagedElement/emael:Transport/l3rtrdo:Router" {
    list PeerIpsecProfile {
      description "Additional definitions from MOM:min/max-elements:0/1;root; Enables node to automatically setup direct IPsec VPN connections to other RBS based on X2 or Xn neighbor information in node. Information for IKE and Child SA negotiation for direct IPsec VPN connections by referring to Ikev2PolicyProfile MO and IpsecProposalProfile MO. PeerIpsecProfile MO must be configured in Router MO where AddressIPv4 MO or AddressIPv6 MO used for X2 or Xn is configured.";
      key "peerIpsecProfileId";
      leaf peerIpsecProfileId {
        type leafref {
          path "../attributes/peerIpsecProfileId";
        }
      }
      container attributes {
        uses PeerIpsecProfile-attributes;
      }
    }
  }
  grouping PeerIpsecProfile-attributes {
    leaf antiReplayProtection {
      type boolean;
      default "true";
      description "Default value: true.";
    }
    leaf ikev2PolicyProfile {
      type string;
      mandatory true;
    }
    leaf ipsecProposalProfile {
      type ietfinet:ip-address;
      mandatory true;
    }
    leaf peerIpsecProfileId {
      type ietfinet:ip-address;
      mandatory true;
    }
    leaf userLabel {
      type string {
        length "1..128";
      }
      description "length 1..128.";
    }
  }
}
