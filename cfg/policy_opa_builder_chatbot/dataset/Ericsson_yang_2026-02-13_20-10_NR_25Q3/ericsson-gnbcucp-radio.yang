module ericsson-gnbcucp-radio {
  yang-version 1.1;
  namespace "urn:com:ericsson:ecim:GNBCUCP";
  prefix gnbcucp;
  import ietf-inet-types {
    prefix ietfinet;
  }
  import ericsson-managed-element {
    prefix emael;
  }
  import ericsson-yang-types {
    prefix eytypes;
  }
  description "Auto-generated from Ericsson ECIM (MOM XML).";
  revision 2026-02-13 {
    description "Initial auto-generated revision. Generated at 2026-02-13 20:11.";
  }

  augment "/emael:ManagedElement" {
    list GNBCUCPFunction {
      description "Additional definitions from MOM:min/max-elements:0/unbounded;root; Represents the logical node gNodeB-CU-CP.";
      key "gNBCUCPFunctionId";
      leaf gNBCUCPFunctionId {
        type leafref {
          path "../attributes/gNBCUCPFunctionId";
        }
      }
      container attributes {
        uses GNBCUCPFunction-attributes;
      }
    }
  }

  augment "/emael:ManagedElement/GNBCUCPFunction/AdmissionControl" {
    list AdmissionLimit {
      description "Additional definitions from MOM:min/max-elements:0/unbounded; Configured capacity used by Priority-Based Admission Control. Applies to UEs that use the cell as PCell or PSCell. Attributes are used on cell level. Instance AdmissionLimit=Default is created automatically when parent MO instance is created, unless created manually in same transaction. NRCellCU::admissionLimitRef is automatically set to AdmissionLimit=Default instance, unless manually set to refer to another MO instance. Precondition: Instance AdmissionLimit=Default can only be created in same transaction as parent MO instance and cannot be deleted unless parent MO instance is deleted. Other instances can be created and deleted at any time.";
      key "admissionLimitId";
      leaf admissionLimitId {
        type leafref {
          path "../attributes/admissionLimitId";
        }
      }
      container attributes {
        uses AdmissionLimit-attributes;
      }
    }
  }

  augment "/emael:ManagedElement/GNBCUCPFunction/AdmissionControl" {
    list AdmissionPriority {
      description "Additional definitions from MOM:min/max-elements:0/unbounded; UE priorities definition used by Priority-Based Admission Control. Instance AdmissionPriority=Default is created automatically when parent MO instance is created, unless created manually in same transaction. NRCellCU::admissionPriorityRef is automatically set to AdmissionPriority=Default instance, unless manually set to refer to another MO instance. Precondition: Instance AdmissionPriority=Default can only be created in same transaction as parent MO instance and cannot be deleted unless parent MO instance is deleted. Other instances can be created and deleted at any time.";
      key "admissionPriorityId";
      leaf admissionPriorityId {
        type leafref {
          path "../attributes/admissionPriorityId";
        }
      }
      container attributes {
        uses AdmissionPriority-attributes;
      }
    }
  }

  augment "/emael:ManagedElement/GNBCUCPFunction/AdmissionControl" {
    list Uac {
      description "Additional definitions from MOM:min/max-elements:0/1; Container class for NR Unified Access Control. Container class with underlying classes that contain attributes for configuration of unified access control function. Instance Uac=1 is created automatically when parent MO instance is created, unless created manually in same transaction. The RDN of this MO must be Uac=1. Precondition: Instance Uac=1 can only be created in same transaction as parent MO instance and cannot be deleted unless parent MO instance is deleted.";
      key "uacId";
      leaf uacId {
        type leafref {
          path "../attributes/uacId";
        }
      }
      container attributes {
        uses Uac-attributes;
      }
    }
  }

  augment "/emael:ManagedElement/GNBCUCPFunction/AdmissionControl/AdmissionPriority" {
    list AdmissionPriorityUeCfg {
      description "Additional definitions from MOM:min/max-elements:0/32; Admission Priority, UE configuration group. Applies to UEs that use cell as PCell or PSCell. Attributes are used on cell level. Instance AdmissionPriorityUeCfg=Base is created automatically when parent MO instance is created, unless created manually in same transaction. Attributes prefUeGroupList, ueGroupList and ueConfGroupList must be empty in instance AdmissionPriorityUeCfg=Base but cannot all be empty in any other instance of AdmissionPriorityUeCfg under same parent AdmissionPriority instance. Precondition: Instance AdmissionPriorityUeCfg=Base can only be created in same transaction as parent MO instance and cannot be deleted unless parent MO instance is deleted. Other instances can be created and deleted at any time. Maximum 31 AdmissionPriorityUeCfg instances, with RDN different from Base, can be created under parent MO instance.";
      key "admissionPriorityUeCfgId";
      leaf admissionPriorityUeCfgId {
        type leafref {
          path "../attributes/admissionPriorityUeCfgId";
        }
      }
      container attributes {
        uses AdmissionPriorityUeCfg-attributes;
      }
    }
  }

  augment "/emael:ManagedElement/GNBCUCPFunction/AnrFunction" {
    list AnrFunctionEUtran {
      description "Additional definitions from MOM:min/max-elements:0/1; E-UTRAN ANR functions. The RDN of this MO must be AnrFunctionEUtran=1.";
      key "anrFunctionEUtranId";
      leaf anrFunctionEUtranId {
        type leafref {
          path "../attributes/anrFunctionEUtranId";
        }
      }
      container attributes {
        uses AnrFunctionEUtran-attributes;
      }
    }
  }

  augment "/emael:ManagedElement/GNBCUCPFunction/AnrFunction" {
    list AnrFunctionNR {
      description "Additional definitions from MOM:min/max-elements:0/1; NR Automated Neighbor Relation (ANR) functions. The RDN of this MO must be AnrFunctionNR=1.";
      key "anrFunctionNRId";
      leaf anrFunctionNRId {
        type leafref {
          path "../attributes/anrFunctionNRId";
        }
      }
      container attributes {
        uses AnrFunctionNR-attributes;
      }
    }
  }

  augment "/emael:ManagedElement/GNBCUCPFunction/AnrFunction/AnrFunctionEUtran" {
    list AnrFunctionEUtranUeCfg {
      description "Additional definitions from MOM:min/max-elements:0/1; UE configuration of E-UTRAN ANR functions. Instance AnrFunctionEUtranUeCfg=Base is created automatically when parent MO instance is created, unless created manually in same transaction. Precondition: Instance AnrFunctionEUtranUeCfg=Base can only be created in same transaction as parent MO instance and cannot be deleted unless parent MO instance is deleted.";
      key "anrFunctionEUtranUeCfgId";
      leaf anrFunctionEUtranUeCfgId {
        type leafref {
          path "../attributes/anrFunctionEUtranUeCfgId";
        }
      }
      container attributes {
        uses AnrFunctionEUtranUeCfg-attributes;
      }
    }
  }

  augment "/emael:ManagedElement/GNBCUCPFunction/AnrFunction/AnrFunctionNR" {
    list AnrFunctionNRUeCfg {
      description "Additional definitions from MOM:min/max-elements:0/1; UE configuration of NR ANR functions. Instance AnrFunctionNRUeCfg=Base is created automatically when parent MO instance is created, unless created manually in same transaction. Precondition: Instance AnrFunctionNRUeCfg=Base can only be created in same transaction as parent MO instance and cannot be deleted unless parent MO instance is deleted.";
      key "anrFunctionNRUeCfgId";
      leaf anrFunctionNRUeCfgId {
        type leafref {
          path "../attributes/anrFunctionNRUeCfgId";
        }
      }
      container attributes {
        uses AnrFunctionNRUeCfg-attributes;
      }
    }
  }

  augment "/emael:ManagedElement/GNBCUCPFunction/AnrFunction/AnrFunctionNR" {
    list AnrPLMNTable {
      description "Additional definitions from MOM:min/max-elements:0/11; A table of ANR support for gNBId length for each PLMN. Each AnrPLMNTable instance contains a gNBId length that is supported for a list of PLMNs. ANR supports the gNBId length for a PLMN when target gNodeB belongs to a PLMN that is listed for that gNBId length. If a PLMN is not configured within AnrPLMNTable instances, ANR uses GNBCUCPFunction::gNBIdLength of its own node as gNBId length for node of newly found cell.";
      key "anrPLMNTableId";
      leaf anrPLMNTableId {
        type leafref {
          path "../attributes/anrPLMNTableId";
        }
      }
      container attributes {
        uses AnrPLMNTable-attributes;
      }
    }
  }

  augment "/emael:ManagedElement/GNBCUCPFunction/CUCP5qiTable" {
    list CUCP5qi {
      description "Additional definitions from MOM:min/max-elements:1/29; QoS configuration for each 5QI profile. Each profile can be present once in each table.";
      key "cUCP5qiId";
      leaf cUCP5qiId {
        type leafref {
          path "../attributes/cUCP5qiId";
        }
      }
      container attributes {
        uses CUCP5qi-attributes;
      }
    }
  }

  augment "/emael:ManagedElement/GNBCUCPFunction/CarrierAggregation/CaCellMeasProfile" {
    list CaCellMeasProfileUeCfg {
      description "Additional definitions from MOM:min/max-elements:0/32; Carrier Aggregation cell measurement configuration profile, UE configuration group. Applies to UEs that use cell as SpCell. Attributes are used on cell level. Instance CaCellMeasProfileUeCfg=Base is created automatically when parent MO instance is created, unless created manually in same transaction. Attributes prefUeGroupList, ueGroupList and ueConfGroupList must be empty in instance CaCellMeasProfileUeCfg=Base but cannot all be empty in other instances of CaCellMeasProfileUeCfg under same parent CaCellMeasProfile. Precondition: Instance CaCellMeasProfileUeCfg=Base can only be created in same transaction as parent MO instance and cannot be deleted unless parent MO instance is deleted. Other instances can be created and deleted at any time. Maximum 31 CaCellMeasProfileUeCfg instances, with RDN different from Base, can be created under parent MO instance.";
      key "caCellMeasProfileUeCfgId";
      leaf caCellMeasProfileUeCfgId {
        type leafref {
          path "../attributes/caCellMeasProfileUeCfgId";
        }
      }
      container attributes {
        uses CaCellMeasProfileUeCfg-attributes;
      }
    }
  }

  augment "/emael:ManagedElement/GNBCUCPFunction/CarrierAggregation/CaCellProfile" {
    list CaCellProfileUeCfg {
      description "Additional definitions from MOM:min/max-elements:0/32; Carrier Aggregation cell configuration profile, UE configuration group. Applies to UEs that use cell as SpCell. Attributes are used on cell level. Instance CaCellProfileUeCfg=Base is created automatically when parent MO instance is created, unless created manually in same transaction. Attributes prefUeGroupList, ueGroupList and ueConfGroupList must be empty in instance CaCellProfileUeCfg=Base but cannot all be empty in any other instance of CaCellProfileUeCfg under same parent CaCellProfile instance. Precondition: Instance CaCellProfileUeCfg=Base can only be created in same transaction as parent MO instance and cannot be deleted unless parent MO instance is deleted. Other instances can be created and deleted at any time. To be able to create an instance, the total number of instances, including all auto created instances, must be less than the total allowed number of instances under a GNBCUCPFunction instance that is 32.";
      key "caCellProfileUeCfgId";
      leaf caCellProfileUeCfgId {
        type leafref {
          path "../attributes/caCellProfileUeCfgId";
        }
      }
      container attributes {
        uses CaCellProfileUeCfg-attributes;
      }
    }
  }

  augment "/emael:ManagedElement/GNBCUCPFunction/CarrierAggregation/CaFreqRelMeasProfile" {
    list CaFreqRelMeasProfileUeCfg {
      description "Additional definitions from MOM:min/max-elements:0/32; Carrier Aggregation frequency measurement configuration profile, UE configuration group. Applies to UEs that use cell as SpCell. Attributes are used on NR frequency relation level. Instance CaFreqRelMeasProfileUeCfg=Base is created automatically when parent MO instance is created, unless created manually in same transaction. Attributes prefUeGroupList, ueGroupList and ueConfGroupList must be empty in instance CaFreqRelMeasProfileUeCfg=Base but cannot all be empty in other instances of CaFreqRelMeasProfileUeCfg under same parent CaFreqRelMeasProfile. Precondition: Instance CaFreqRelMeasProfileUeCfg=Base can only be created in same transaction as parent MO instance and cannot be deleted unless parent MO instance is deleted. Other instances can be created and deleted at any time. Maximum 31 CaFreqRelMeasProfileUeCfg instances, with RDN different from Base, can be created under parent MO instance.";
      key "caFreqRelMeasProfileUeCfgId";
      leaf caFreqRelMeasProfileUeCfgId {
        type leafref {
          path "../attributes/caFreqRelMeasProfileUeCfgId";
        }
      }
      container attributes {
        uses CaFreqRelMeasProfileUeCfg-attributes;
      }
    }
  }

  augment "/emael:ManagedElement/GNBCUCPFunction/UeCC/CapabilityHandling" {
    list CapabilityHandlingUeCfg {
      description "Additional definitions from MOM:min/max-elements:0/8; Configuration of CapabilityHandling for UE groups. Instance CapabilityHandlingUeCfg=Base is created automatically when parent MO instance is created, unless created manually in same transaction. Attributes prefUeGroupList, ueGroupList and ueConfGroupList must be empty in instance CapabilityHandlingUeCfg=Base but cannot all be empty in any other instance of CapabilityHandlingUeCfg under same parent CapabilityHandling instance. Precondition: Instance CapabilityHandlingUeCfg=Base can only be created in same transaction as parent MO instance and cannot be deleted unless parent MO instance is deleted. Other instances can be created and deleted at any time. Maximum 7 CapabilityHandlingUeCfg instances, with RDN different from Base, can be created under parent MO instance.";
      key "capabilityHandlingUeCfgId";
      leaf capabilityHandlingUeCfgId {
        type leafref {
          path "../attributes/capabilityHandlingUeCfgId";
        }
      }
      container attributes {
        uses CapabilityHandlingUeCfg-attributes;
      }
    }
  }

  augment "/emael:ManagedElement/GNBCUCPFunction/CarrierAggregation" {
    list CaCellMeasProfile {
      description "Additional definitions from MOM:min/max-elements:0/unbounded; Carrier Aggregation cell measurement configuration profile. Applies to UEs that use cell as SpCell. Attributes are used on cell level. Instance CaCellMeasProfile=Default is created automatically when parent MO instance is created, unless created manually in same transaction. NRCellCU::caCellMeasProfileRef is automatically set to CaCellMeasProfile=Default instance, unless manually set to refer to another MO instance. Precondition: Instance CaCellMeasProfile=Default can only be created in same transaction as parent MO instance and cannot be deleted unless parent MO instance is deleted. Other instances can be created and deleted at any time.";
      key "caCellMeasProfileId";
      leaf caCellMeasProfileId {
        type leafref {
          path "../attributes/caCellMeasProfileId";
        }
      }
      container attributes {
        uses CaCellMeasProfile-attributes;
      }
    }
  }

  augment "/emael:ManagedElement/GNBCUCPFunction/CarrierAggregation" {
    list CaCellProfile {
      description "Additional definitions from MOM:min/max-elements:0/32; Carrier Aggregation cell configuration profile. Applies to UEs that use cell as SpCell. Attributes are used on cell level. Instance CaCellProfile=Default is created automatically when parent MO instance is created, unless created manually in same transaction. NRCellCU::caCellProfileRef is automatically set to CaCellProfile=Default instance, unless manually set to refer to another MO instance. Precondition: Instance CaCellProfile=Default can only be created in same transaction as parent MO instance and cannot be deleted unless parent MO instance is deleted. Other instances can be created and deleted at any time. Maximum 31 CaCellProfile instances, with RDN different from Default, can be created. When creating an instance there must be possible to create a child CaCellProfileUeCfg=Base among total allowed instances of that MO class that is 32.";
      key "caCellProfileId";
      leaf caCellProfileId {
        type leafref {
          path "../attributes/caCellProfileId";
        }
      }
      container attributes {
        uses CaCellProfile-attributes;
      }
    }
  }

  augment "/emael:ManagedElement/GNBCUCPFunction/CarrierAggregation" {
    list CaFreqRelMeasProfile {
      description "Additional definitions from MOM:min/max-elements:0/unbounded; Carrier Aggregation frequency measurement configuration profile. Applies to UEs that use cell as SpCell. Attributes are used on NR frequency relation level. Instance CaFreqRelMeasProfile=Default is created automatically when parent MO instance is created, unless created manually in same transaction. NRFreqRelation::caFreqRelMeasProfileRef is automatically set to CaFreqRelMeasProfile=Default instance, unless manually set to refer to another MO instance. Precondition: Instance CaFreqRelMeasProfile=Default can only be created in same transaction as parent MO instance and cannot be deleted unless parent MO instance is deleted. Other instances can be created and deleted at any time.";
      key "caFreqRelMeasProfileId";
      leaf caFreqRelMeasProfileId {
        type leafref {
          path "../attributes/caFreqRelMeasProfileId";
        }
      }
      container attributes {
        uses CaFreqRelMeasProfile-attributes;
      }
    }
  }

  augment "/emael:ManagedElement/GNBCUCPFunction/UeCC/DrbData" {
    list DrbDataUeCfg {
      description "Additional definitions from MOM:min/max-elements:0/4; Configuration of data radio bearer user plane UE profile for UE groups. Instance DrbDataUeCfg=Base is created automatically when parent MO instance is created, unless created manually in same transaction. Each UE configuration group identifier can only be defined in one ueConfGroupList among DrbDataUeCfg instances contained under parent DrbData instance. Any combination of one UE group identifier in ueGroupList and one preference UE group identifier in prefUeGroupList must be unique among DrbDataUeCfg instances contained under parent DrbData instance. Attributes prefUeGroupList, ueGroupList and ueConfGroupList must be empty in instance DrbDataUeCfg=Base but cannot all be empty in any other instance of DrbDataUeCfg under same parent DrbData instance. Precondition: Instance DrbDataUeCfg=Base can only be created in same transaction as parent MO instance and cannot be deleted unless parent MO instance is deleted. Other instances can be created and deleted at any time. Maximum 3 DrbDataUeCfg instances, with RDN different from Base, can be created under parent MO instance.";
      key "drbDataUeCfgId";
      leaf drbDataUeCfgId {
        type leafref {
          path "../attributes/drbDataUeCfgId";
        }
      }
      container attributes {
        uses DrbDataUeCfg-attributes;
      }
    }
  }

  augment "/emael:ManagedElement/GNBCUCPFunction/EUtraNetwork" {
    list EUtranFrequency {
      description "Additional definitions from MOM:min/max-elements:0/32; Container for information of a specific E-UTRAN frequency. The RDNs of these MOs are EUtranFrequency=<number>, for example EUtranFrequency=2586. RDN must match arfcnValueEUtranDl.";
      key "eUtranFrequencyId";
      leaf eUtranFrequencyId {
        type leafref {
          path "../attributes/eUtranFrequencyId";
        }
      }
      container attributes {
        uses EUtranFrequency-attributes;
      }
    }
  }

  augment "/emael:ManagedElement/GNBCUCPFunction/EUtraNetwork" {
    list ExternalENodeBFunction {
      description "Additional definitions from MOM:min/max-elements:0/256; Representation of an eNodeB. Created automatically when X2 interface is set up, unless it already exists. Deleted automatically. Can also be created and deleted manually. When created automatically, the RDN of this MO is ExternalENodeBFunction=auto<mcc>_<mnc>_<mncLength>_<eNodeBId>. Length of RDN value is up to 21 characters for automatically created instance. Instance can be created without a preceding user-initiated transaction.";
      key "externalENodeBFunctionId";
      leaf externalENodeBFunctionId {
        type leafref {
          path "../attributes/externalENodeBFunctionId";
        }
      }
      container attributes {
        uses ExternalENodeBFunction-attributes;
      }
    }
  }

  augment "/emael:ManagedElement/GNBCUCPFunction/EndpointResource" {
    list LocalDnsEndpoint {
      description "Additional definitions from MOM:min/max-elements:0/1; Local transport network endpoint for DNS interface. If no instance exists, DNS interface configured in the OAM network is used.";
      key "localDnsEndpointId";
      leaf localDnsEndpointId {
        type leafref {
          path "../attributes/localDnsEndpointId";
        }
      }
      container attributes {
        uses LocalDnsEndpoint-attributes;
      }
    }
  }

  augment "/emael:ManagedElement/GNBCUCPFunction/EndpointResource" {
    list LocalIpEndpoint {
      description "Additional definitions from MOM:min/max-elements:0/unbounded; Local transport network endpoint for user plane interface. E1 control plane uses TCP, hence this interface is also configured by this class.";
      key "localIpEndpointId";
      leaf localIpEndpointId {
        type leafref {
          path "../attributes/localIpEndpointId";
        }
      }
      container attributes {
        uses LocalIpEndpoint-attributes;
      }
    }
  }

  augment "/emael:ManagedElement/GNBCUCPFunction/EndpointResource" {
    list LocalSctpEndpoint {
      description "Additional definitions from MOM:min/max-elements:0/unbounded; Local transport network endpoint for control plane interface. E1 control plane uses TCP, hence this interface is configured in MO class LocalIpEndpoint.";
      key "localSctpEndpointId";
      leaf localSctpEndpointId {
        type leafref {
          path "../attributes/localSctpEndpointId";
        }
      }
      container attributes {
        uses LocalSctpEndpoint-attributes;
      }
    }
  }

  augment "/emael:ManagedElement/GNBCUCPFunction/EnergyPerformance" {
    list EpBoCS {
      description "Additional definitions from MOM:min/max-elements:0/1; Configuration and supervision support for Booster Carrier Sleep function. Instance EpBoCS=1 is created automatically when parent MO instance is created, unless created manually in same transaction. The RDN of this MO must be EpBoCS=1. Precondition: Instance EpBoCS=1 can only be created in same transaction as parent MO instance and cannot be deleted unless parent MO instance is deleted.";
      key "epBoCSId";
      leaf epBoCSId {
        type leafref {
          path "../attributes/epBoCSId";
        }
      }
      container attributes {
        uses EpBoCS-attributes;
      }
    }
  }

  augment "/emael:ManagedElement/GNBCUCPFunction/EnergyPerformance/EpBoCS" {
    list EpBoosterAdvCfg {
      description "Additional definitions from MOM:min/max-elements:0/50; Booster Carrier Sleep advanced profile settings. Instance EpBoosterAdvCfg=Default is created automatically when parent MO instance is created, unless created manually in same transaction. EpBoosterCellProfile::epBoosterAdvCfgRef is automatically set to EpBoosterAdvCfg=Default instance, unless manually set to refer to another MO instance. Precondition: Instance EpBoosterAdvCfg=Default can only be created in same transaction as parent MO instance and cannot be deleted unless parent MO instance is deleted. Maximum 49 EpBoosterAdvCfg instances, with RDN different from Default, can be created under parent MO instance. Other instances can be created and deleted at any time.";
      key "epBoosterAdvCfgId";
      leaf epBoosterAdvCfgId {
        type leafref {
          path "../attributes/epBoosterAdvCfgId";
        }
      }
      container attributes {
        uses EpBoosterAdvCfg-attributes;
      }
    }
  }

  augment "/emael:ManagedElement/GNBCUCPFunction/EnergyPerformance/EpBoCS" {
    list EpBoosterCellProfile {
      description "Additional definitions from MOM:min/max-elements:0/50; Booster Carrier Sleep profile. Instance EpBoosterCellProfile=Default is created automatically when parent MO instance is created, unless created manually in same transaction. Precondition: Instance EpBoosterCellProfile=Default can only be created in same transaction as parent MO instance and cannot be deleted unless parent MO instance is deleted. Maximum 49 EpBoosterCellProfile instances, with RDN different from Default, can be created under parent MO instance. Other instances can be created and deleted at any time.";
      key "epBoosterCellProfileId";
      leaf epBoosterCellProfileId {
        type leafref {
          path "../attributes/epBoosterCellProfileId";
        }
      }
      container attributes {
        uses EpBoosterCellProfile-attributes;
      }
    }
  }

  augment "/emael:ManagedElement/GNBCUCPFunction/EUtraNetwork/ExternalENodeBFunction" {
    list ExternalEUtranCell {
      description "Additional definitions from MOM:min/max-elements:0/48; External E-UTRAN cell. Contains parameters that are specific for this cell. Can be created by action promoteLwEUtranCellRelation in NRCellCU instance. RDN is the same as for automatically created instance. When created automatically, the RDN of this MO is ExternalEUtranCell=auto<ECI>, where ECI = <eNBid>*256 + <cellLocalId>. Length of RDN value is up to 13 characters for automatically created instance. Instance can be created without a preceding user-initiated transaction.";
      key "externalEUtranCellId";
      leaf externalEUtranCellId {
        type leafref {
          path "../attributes/externalEUtranCellId";
        }
      }
      container attributes {
        uses ExternalEUtranCell-attributes;
      }
    }
  }

  augment "/emael:ManagedElement/GNBCUCPFunction/EUtraNetwork/ExternalENodeBFunction" {
    list TermPointToENodeB {
      description "Additional definitions from MOM:min/max-elements:0/1; Local eNodeB termination point of X2 link between gNodeB and eNodeB. Created automatically when X2 interface is set up, unless it already exists. Deleted automatically. Can also be created and deleted manually. When created automatically, the RDN of this MO is TermPointToENodeB=auto1. Length of RDN value is 5 characters for automatically created instance. Instance can be created without a preceding user-initiated transaction.";
      key "termPointToENodeBId";
      leaf termPointToENodeBId {
        type leafref {
          path "../attributes/termPointToENodeBId";
        }
      }
      container attributes {
        uses TermPointToENodeB-attributes;
      }
    }
  }

  augment "/emael:ManagedElement/GNBCUCPFunction/NRNetwork/ExternalGNBCUCPFunction" {
    list ExternalNRCellCU {
      description "Additional definitions from MOM:min/max-elements:0/256; Representation of an external NRCellCU. Created automatically when Xn message is received, unless it already exists. Deleted automatically. Can also be created and deleted manually. Can be created by action promoteLwNRCellRelation in NRCellCU instance. RDN is the same as for automatically created instance. When created automatically, the RDN of this MO is ExternalNRCellCU=auto<NCI>, where NCI = <gNBId>*2^(36-<gNBIdLength>) + <cellLocalId>. Length of RDN value is up to 15 characters for automatically created instance. Instance can be created without a preceding user-initiated transaction.";
      key "externalNRCellCUId";
      leaf externalNRCellCUId {
        type leafref {
          path "../attributes/externalNRCellCUId";
        }
      }
      container attributes {
        uses ExternalNRCellCU-attributes;
      }
    }
  }

  augment "/emael:ManagedElement/GNBCUCPFunction/NRNetwork/ExternalGNBCUCPFunction" {
    list TermPointToGNodeB {
      description "Additional definitions from MOM:min/max-elements:0/1; Local gNodeB termination point of Xn link between gNodeB and neighbor gNodeB. Created automatically when Xn interface is set up, unless it already exists. Deleted automatically. Can also be created and deleted manually. When created automatically, the RDN of this MO is TermPointToGNodeB=auto1. Length of RDN value is 5 characters for automatically created instance. Instance can be created without a preceding user-initiated transaction. Precondition: Manual creation of TermPointToGNodeB instances, to gNodeBs listed in GNBCUCPFunction::blockedGNodeBList, is blocked.";
      key "termPointToGNodeBId";
      leaf termPointToGNodeBId {
        type leafref {
          path "../attributes/termPointToGNodeBId";
        }
      }
      container attributes {
        uses TermPointToGNodeB-attributes;
      }
    }
  }

  augment "/emael:ManagedElement/GNBCUCPFunction/NRNetwork/ExternalGNBCUCPFunction/ExternalNRCellCU" {
    list ExternalBroadcastPLMNInfo {
      description "Additional definitions from MOM:min/max-elements:0/12; PLMN-related information that is served by external NR cell. Created automatically when Xn message is received, unless it already exists. Deleted automatically. Can also be created and deleted manually. Can be created by action promoteLwNRCellRelation in NRCellCU instance. RDN is the same as for automatically created instance. When created automatically, the RDNs of these MOs are ExternalBroadcastPLMNInfo=1 to ExternalBroadcastPLMNInfo=12. RDN value is assigned based on order received over Xn. Length of RDN value is up to 2 characters for automatically created instance. Instance can be created without a preceding user-initiated transaction. Precondition: MO can be created and deleted manually, only if TermPointToGNodeB has administrativeState LOCKED.";
      key "externalBroadcastPLMNInfoId";
      leaf externalBroadcastPLMNInfoId {
        type leafref {
          path "../attributes/externalBroadcastPLMNInfoId";
        }
      }
      container attributes {
        uses ExternalBroadcastPLMNInfo-attributes;
      }
    }
  }

  augment "/emael:ManagedElement/GNBCUCPFunction" {
    list AdmissionControl {
      description "Additional definitions from MOM:min/max-elements:0/1; Container class for admission limits, admission priority and unified access control. Instance AdmissionControl=1 is created automatically when parent MO instance is created, unless created manually in same transaction. The RDN of this MO must be AdmissionControl=1. Precondition: Instance AdmissionControl=1 can only be created in same transaction as parent MO instance and cannot be deleted unless parent MO instance is deleted.";
      key "admissionControlId";
      leaf admissionControlId {
        type leafref {
          path "../attributes/admissionControlId";
        }
      }
      container attributes {
        uses AdmissionControl-attributes;
      }
    }
  }

  augment "/emael:ManagedElement/GNBCUCPFunction" {
    list AnrFunction {
      description "Additional definitions from MOM:min/max-elements:0/1; Parameters and constraints for ANR functions. The RDN of this MO must be AnrFunction=1.";
      key "anrFunctionId";
      leaf anrFunctionId {
        type leafref {
          path "../attributes/anrFunctionId";
        }
      }
      container attributes {
        uses AnrFunction-attributes;
      }
    }
  }

  augment "/emael:ManagedElement/GNBCUCPFunction" {
    list BlockedGNodeB {
      description "Additional definitions from MOM:min/max-elements:0/512; Configuration of blocked neighbor gNodeBs. When gNodeB is blocked, Xn setup to it is blocked.";
      key "blockedGNodeBId";
      leaf blockedGNodeBId {
        type leafref {
          path "../attributes/blockedGNodeBId";
        }
      }
      container attributes {
        uses BlockedGNodeB-attributes;
      }
    }
  }

  augment "/emael:ManagedElement/GNBCUCPFunction" {
    list CardinalityLimits {
      description "Additional definitions from MOM:min/max-elements:0/1; Cardinality limits for current deployment. Listed cardinality limits is maximum number of MO instances that can be created. Instance CardinalityLimits=1 is created automatically when parent MO instance is created, unless created manually in same transaction. The RDN of this MO must be CardinalityLimits=1. Precondition: Instance CardinalityLimits=1 can only be created in same transaction as parent MO instance and cannot be deleted unless parent MO instance is deleted.";
      key "cardinalityLimitsId";
      leaf cardinalityLimitsId {
        type leafref {
          path "../attributes/cardinalityLimitsId";
        }
      }
      container attributes {
        uses CardinalityLimits-attributes;
      }
    }
  }

  augment "/emael:ManagedElement/GNBCUCPFunction" {
    list CarrierAggregation {
      description "Additional definitions from MOM:min/max-elements:0/1; Container class for Carrier Aggregation control attributes and profile classes. Instance CarrierAggregation=1 is created automatically when parent MO instance is created, unless created manually in same transaction. The RDN of this MO must be CarrierAggregation=1. Precondition: Instance CarrierAggregation=1 can only be created in same transaction as parent MO instance and cannot be deleted unless parent MO instance is deleted.";
      key "carrierAggregationId";
      leaf carrierAggregationId {
        type leafref {
          path "../attributes/carrierAggregationId";
        }
      }
      container attributes {
        uses CarrierAggregation-attributes;
      }
    }
  }

  augment "/emael:ManagedElement/GNBCUCPFunction" {
    list CellGroupCategoryDefinition {
      description "Additional definitions from MOM:min/max-elements:0/8; Cell group category definition.";
      key "cellGroupCategoryDefinitionId";
      leaf cellGroupCategoryDefinitionId {
        type leafref {
          path "../attributes/cellGroupCategoryDefinitionId";
        }
      }
      container attributes {
        uses CellGroupCategoryDefinition-attributes;
      }
    }
  }

  augment "/emael:ManagedElement/GNBCUCPFunction" {
    list CUCP5qiTable {
      description "Additional definitions from MOM:min/max-elements:0/36; Mapping from 5G QoS Identifier to parameters that have impact on QoS. At least one CUCP5qi instance must be created in same transaction when a CUCP5qiTable is created.";
      key "cUCP5qiTableId";
      leaf cUCP5qiTableId {
        type leafref {
          path "../attributes/cUCP5qiTableId";
        }
      }
      container attributes {
        uses CUCP5qiTable-attributes;
      }
    }
  }

  augment "/emael:ManagedElement/GNBCUCPFunction" {
    list EmCall {
      description "Additional definitions from MOM:min/max-elements:0/12; Emergency call configuration for NRCellCU instances.";
      key "emCallId";
      leaf emCallId {
        type leafref {
          path "../attributes/emCallId";
        }
      }
      container attributes {
        uses EmCall-attributes;
      }
    }
  }

  augment "/emael:ManagedElement/GNBCUCPFunction" {
    list EndpointResource {
      description "Additional definitions from MOM:min/max-elements:0/unbounded; Transport network endpoints for RAN interfaces. Configuration is valid for an entity that refers to an instance of this MO.";
      key "endpointResourceId";
      leaf endpointResourceId {
        type leafref {
          path "../attributes/endpointResourceId";
        }
      }
      container attributes {
        uses EndpointResource-attributes;
      }
    }
  }

  augment "/emael:ManagedElement/GNBCUCPFunction" {
    list EnergyPerformance {
      description "Additional definitions from MOM:min/max-elements:0/1; Configuration and supervision support for functions related to energy performance. Instance EnergyPerformance=1 is created automatically when parent MO instance is created, unless created manually in same transaction. The RDN of this MO must be EnergyPerformance=1. Precondition: Instance EnergyPerformance=1 can only be created in same transaction as parent MO instance and cannot be deleted unless parent MO instance is deleted.";
      key "energyPerformanceId";
      leaf energyPerformanceId {
        type leafref {
          path "../attributes/energyPerformanceId";
        }
      }
      container attributes {
        uses EnergyPerformance-attributes;
      }
    }
  }

  augment "/emael:ManagedElement/GNBCUCPFunction" {
    list EUtraNetwork {
      description "Additional definitions from MOM:min/max-elements:0/1; Container for MOs related to E-UTRA networks. Created automatically when X2 message is received, unless it already exists. Can also be created and deleted manually. When created automatically, the RDN of this MO is EUtraNetwork=1. Length of RDN value is 1 character for automatically created instance. Instance can be created without a preceding user-initiated transaction.";
      key "eUtraNetworkId";
      leaf eUtraNetworkId {
        type leafref {
          path "../attributes/eUtraNetworkId";
        }
      }
      container attributes {
        uses EUtraNetwork-attributes;
      }
    }
  }

  augment "/emael:ManagedElement/GNBCUCPFunction" {
    list IntraFreqMC {
      description "Additional definitions from MOM:min/max-elements:0/1; This is a container for Intra-frequency mobility control profiles. Instance IntraFreqMC=1 is created automatically when parent MO instance is created, unless created manually in same transaction. The RDN of this MO must be IntraFreqMC=1. Precondition: Instance IntraFreqMC=1 can only be created in same transaction as parent MO instance and cannot be deleted unless parent MO instance is deleted.";
      key "intraFreqMCId";
      leaf intraFreqMCId {
        type leafref {
          path "../attributes/intraFreqMCId";
        }
      }
      container attributes {
        uses IntraFreqMC-attributes;
      }
    }
  }

  augment "/emael:ManagedElement/GNBCUCPFunction" {
    list Mcfb {
      description "Additional definitions from MOM:min/max-elements:0/1; Container class for mobility control fallback attributes and profile classes. Instance Mcfb=1 is created automatically when parent MO instance is created, unless created manually in same transaction. The RDN of this MO is Mcfb=1. Precondition: Instance Mcfb=1 can only be created in same transaction as parent MO instance and cannot be deleted unless parent MO instance is deleted.";
      key "mcfbId";
      leaf mcfbId {
        type leafref {
          path "../attributes/mcfbId";
        }
      }
      container attributes {
        uses Mcfb-attributes;
      }
    }
  }

  augment "/emael:ManagedElement/GNBCUCPFunction" {
    list Mcpc {
      description "Additional definitions from MOM:min/max-elements:0/1; Configuration of Mobility Control at Poor Coverage function and container for MCPC profiles. Instance Mcpc=1 is created automatically when parent MO instance is created, unless created manually in same transaction. The RDN of this MO must be Mcpc=1. Precondition: Instance Mcpc=1 can only be created in same transaction as parent MO instance and cannot be deleted unless parent MO instance is deleted.";
      key "mcpcId";
      leaf mcpcId {
        type leafref {
          path "../attributes/mcpcId";
        }
      }
      container attributes {
        uses Mcpc-attributes;
      }
    }
  }

  augment "/emael:ManagedElement/GNBCUCPFunction" {
    list Mdt {
      description "Additional definitions from MOM:min/max-elements:0/1; Container class for MDT profile classes. Instance Mdt=1 is created automatically when parent MO instance is created, unless created manually in same transaction. The RDN of this MO must be Mdt=1. Precondition: Instance Mdt=1 can only be created in same transaction as parent MO instance and cannot be deleted unless parent MO instance is deleted.";
      key "mdtId";
      leaf mdtId {
        type leafref {
          path "../attributes/mdtId";
        }
      }
      container attributes {
        uses Mdt-attributes;
      }
    }
  }

  augment "/emael:ManagedElement/GNBCUCPFunction" {
    list Nccm {
      description "Additional definitions from MOM:min/max-elements:0/1; Container class for neighbor cell coverage measurement configuration classes. Instance Nccm=1 is created automatically when parent MO instance is created, unless created manually in same transaction. Only applicable to Low-Band and Mid-Band cells. The RDN of this MO must be Nccm=1. Precondition: Instance Nccm=1 can only be created in same transaction as parent MO instance and cannot be deleted unless parent MO instance is deleted.";
      key "nccmId";
      leaf nccmId {
        type leafref {
          path "../attributes/nccmId";
        }
      }
      container attributes {
        uses Nccm-attributes;
      }
    }
  }

  augment "/emael:ManagedElement/GNBCUCPFunction" {
    list NRCellCU {
      description "Additional definitions from MOM:min/max-elements:0/unbounded; Representation of an NR cell in gNodeB-CU. Manages inter-cell mobility and neighbor relations through NR Automated Neighbor Relations feature. Created automatically when a configuration message over F1 interface is received if no NRCellCU instance with same NCI already exists. Can also be created and deleted manually. When created automatically, RDN of this MO is NRCellCU=<NCI>, where NCI = <gNBId>*2^(36-<gNBIdLength>) + <cellLocalId>. Length of RDN value is up to 11 characters for automatically created instance. Instance can be created without a preceding user-initiated transaction. Precondition: Can be deleted only when NRCellDU instance with matching cellLocalId does not exist or has administrativeState LOCKED.";
      key "nRCellCUId";
      leaf nRCellCUId {
        type leafref {
          path "../attributes/nRCellCUId";
        }
      }
      container attributes {
        uses NRCellCU-attributes;
      }
    }
  }

  augment "/emael:ManagedElement/GNBCUCPFunction" {
    list NrdcControl {
      description "Additional definitions from MOM:min/max-elements:0/1; Configuration of NR-NR Dual Connectivity in Master Node and container for NR-DC profiles. Instance NrdcControl=1 is created automatically when parent MO instance is created, unless created manually in same transaction. The RDN of this MO must be NrdcControl=1. Precondition: Instance NrdcControl=1 can only be created in same transaction as parent MO instance and cannot be deleted unless parent MO instance is deleted.";
      key "nrdcControlId";
      leaf nrdcControlId {
        type leafref {
          path "../attributes/nrdcControlId";
        }
      }
      container attributes {
        uses NrdcControl-attributes;
      }
    }
  }

  augment "/emael:ManagedElement/GNBCUCPFunction" {
    list NrdcSnTermination {
      description "Additional definitions from MOM:min/max-elements:0/30; Profile for Secondary Node termination. Instance NrdcSnTermination=SnTerminationProhibited is created automatically when parent MO instance is created, unless created manually in same transaction. Attribute defaultNrdcSnTerm must be false in NrdcSnTermination=SnTerminationProhibited instance. Precondition: Instance NrdcSnTermination=SnTerminationProhibited can only be created in same transaction as parent MO instance and cannot be deleted unless parent MO instance is deleted. Other instances can be created and deleted at any time. Maximum 29 NrdcSnTermination instances, with RDN different from SnTerminationProhibited, can be created under parent MO instance.";
      key "nrdcSnTerminationId";
      leaf nrdcSnTerminationId {
        type leafref {
          path "../attributes/nrdcSnTerminationId";
        }
      }
      container attributes {
        uses NrdcSnTermination-attributes;
      }
    }
  }

  augment "/emael:ManagedElement/GNBCUCPFunction" {
    list NRNetwork {
      description "Additional definitions from MOM:min/max-elements:0/1; Container for MOs related to NR networks. Created automatically when Xn message is received, unless it already exists. Can also be created and deleted manually. When created automatically, the RDN of this MO is NRNetwork=1. Length of RDN value is 1 character for automatically created instance. Instance can be created without a preceding user-initiated transaction.";
      key "nRNetworkId";
      leaf nRNetworkId {
        type leafref {
          path "../attributes/nRNetworkId";
        }
      }
      container attributes {
        uses NRNetwork-attributes;
      }
    }
  }

  augment "/emael:ManagedElement/GNBCUCPFunction" {
    list PciHandling {
      description "Additional definitions from MOM:min/max-elements:0/1; Parameters and constraints for PCI handling functions. Instance PciHandling=1 is created automatically when parent MO instance is created, unless created manually in same transaction. The RDN of this MO must be PciHandling=1. Precondition: Instance PciHandling=1 can only be created in same transaction as parent MO instance and cannot be deleted unless parent MO instance is deleted.";
      key "pciHandlingId";
      leaf pciHandlingId {
        type leafref {
          path "../attributes/pciHandlingId";
        }
      }
      container attributes {
        uses PciHandling-attributes;
      }
    }
  }

  augment "/emael:ManagedElement/GNBCUCPFunction" {
    list PeriodicUeMeas {
      description "Additional definitions from MOM:min/max-elements:0/1; Container class for periodic UE measurement profiles. Instance PeriodicUeMeas=1 is created automatically when parent MO instance is created, unless created manually in same transaction. The RDN of this MO must be PeriodicUeMeas=1. Precondition: Instance PeriodicUeMeas=1 can only be created in same transaction as parent MO instance and cannot be deleted unless parent MO instance is deleted.";
      key "periodicUeMeasId";
      leaf periodicUeMeasId {
        type leafref {
          path "../attributes/periodicUeMeasId";
        }
      }
      container attributes {
        uses PeriodicUeMeas-attributes;
      }
    }
  }

  augment "/emael:ManagedElement/GNBCUCPFunction" {
    list PmUeMeas {
      description "Additional definitions from MOM:min/max-elements:0/1; Container class for PM UE measurement profile classes. Instance PmUeMeas=1 is created automatically when parent MO instance is created, unless created manually in same transaction. The RDN of this MO must be PmUeMeas=1. Precondition: Instance PmUeMeas=1 can only be created in same transaction as parent MO instance and cannot be deleted unless parent MO instance is deleted.";
      key "pmUeMeasId";
      leaf pmUeMeasId {
        type leafref {
          path "../attributes/pmUeMeasId";
        }
      }
      container attributes {
        uses PmUeMeas-attributes;
      }
    }
  }

  augment "/emael:ManagedElement/GNBCUCPFunction" {
    list PriorityService {
      description "Additional definitions from MOM:min/max-elements:0/12; Priority service configuration for NRCellCU instances.";
      key "priorityServiceId";
      leaf priorityServiceId {
        type leafref {
          path "../attributes/priorityServiceId";
        }
      }
      container attributes {
        uses PriorityService-attributes;
      }
    }
  }

  augment "/emael:ManagedElement/GNBCUCPFunction" {
    list QciProfileEndcConfigExt {
      description "Additional definitions from MOM:min/max-elements:1/1;systemCreated; Managing QoS-related parameters for Data Radio Bearers in EN-DC and NR-DC. The RDN of this MO is QciProfileEndcConfigExt=1.";
      key "qciProfileEndcConfigExtId";
      status deprecated;
      leaf qciProfileEndcConfigExtId {
        type leafref {
          path "../attributes/qciProfileEndcConfigExtId";
        }
        status deprecated;
      }
      container attributes {
        uses QciProfileEndcConfigExt-attributes;
      }
    }
  }

  augment "/emael:ManagedElement/GNBCUCPFunction" {
    list RelaxedRrmMeas {
      description "Additional definitions from MOM:min/max-elements:0/1; Container class for relaxed RRM measurement cell profiles.";
      key "relaxedRrmMeasId";
      leaf relaxedRrmMeasId {
        type leafref {
          path "../attributes/relaxedRrmMeasId";
        }
      }
      container attributes {
        uses RelaxedRrmMeas-attributes;
      }
    }
  }

  augment "/emael:ManagedElement/GNBCUCPFunction" {
    list ResourcePartitions {
      description "Additional definitions from MOM:min/max-elements:0/1; Set of resource partitions.";
      key "resourcePartitionsId";
      leaf resourcePartitionsId {
        type leafref {
          path "../attributes/resourcePartitionsId";
        }
      }
      container attributes {
        uses ResourcePartitions-attributes;
      }
    }
  }

  augment "/emael:ManagedElement/GNBCUCPFunction" {
    list SecurityHandling {
      description "Additional definitions from MOM:min/max-elements:1/1;systemCreated; Manageable characteristics of security handling except during Xn handover and NG handover. The RDN of this MO is SecurityHandling=1.";
      key "securityHandlingId";
      leaf securityHandlingId {
        type leafref {
          path "../attributes/securityHandlingId";
        }
      }
      container attributes {
        uses SecurityHandling-attributes;
      }
    }
  }

  augment "/emael:ManagedElement/GNBCUCPFunction" {
    list TermPointToAmf {
      description "Additional definitions from MOM:min/max-elements:0/64; Models an NG link AMF termination point. Created and deleted automatically by DNS lookup on 5GS TAI if GNBCUCPFunction::dnsLookupOn5GsTai is true. Can also be created and deleted manually. When created automatically, the RDNs of these MOs are TermPointToAmf=<MCC>-<MNC>-<AMF Region Id>-<AMF Set Id>-<AMF Pointer>. Length of RDN value is up to 19 characters for automatically created instance. Instance can be created without a preceding user-initiated transaction.";
      key "termPointToAmfId";
      leaf termPointToAmfId {
        type leafref {
          path "../attributes/termPointToAmfId";
        }
      }
      container attributes {
        uses TermPointToAmf-attributes;
      }
    }
  }

  augment "/emael:ManagedElement/GNBCUCPFunction" {
    list TermPointToGNBCUUP {
      description "Additional definitions from MOM:min/max-elements:0/unbounded;systemCreated; Models an E1 link to a gNodeB-CU-UP. Created when E1 link is set up. Deleted at node restart. The RDN of this MO is TermPointToGNBCUUP=[Local Ip Address]_[Remote Ip Address]. Length of RDN value is up to 79 characters. Instance can be created without a preceding user-initiated transaction.";
      key "termPointToGNBCUUPId";
      leaf termPointToGNBCUUPId {
        type leafref {
          path "../attributes/termPointToGNBCUUPId";
        }
      }
      container attributes {
        uses TermPointToGNBCUUP-attributes;
      }
    }
  }

  augment "/emael:ManagedElement/GNBCUCPFunction" {
    list TermPointToGNBDU {
      description "Additional definitions from MOM:min/max-elements:0/unbounded;systemCreated; Models an F1-C link to a gNodeB-DU. Created when F1-C link is set up. Deleted at node restart. The RDN of this MO is TermPointToGNBDU=[gNBDUId]. Length of RDN value is up to 11 characters. Instance can be created without a preceding user-initiated transaction.";
      key "termPointToGNBDUId";
      leaf termPointToGNBDUId {
        type leafref {
          path "../attributes/termPointToGNBDUId";
        }
      }
      container attributes {
        uses TermPointToGNBDU-attributes;
      }
    }
  }

  augment "/emael:ManagedElement/GNBCUCPFunction" {
    list TimeSchedulingGroup {
      description "Additional definitions from MOM:min/max-elements:0/96; A collection of TimeSchedulingWindow.";
      key "timeSchedulingGroupId";
      leaf timeSchedulingGroupId {
        type leafref {
          path "../attributes/timeSchedulingGroupId";
        }
      }
      container attributes {
        uses TimeSchedulingGroup-attributes;
      }
    }
  }

  augment "/emael:ManagedElement/GNBCUCPFunction" {
    list TrafficOffload {
      description "Additional definitions from MOM:min/max-elements:0/1; Container for traffic offload profiles. Instance TrafficOffload=1 is created automatically when parent MO instance is created, unless created manually in same transaction. The RDN of this MO must be TrafficOffload=1. Precondition: Instance TrafficOffload=1 can only be created in same transaction as parent MO instance and cannot be deleted unless parent MO instance is deleted.";
      key "trafficOffloadId";
      leaf trafficOffloadId {
        type leafref {
          path "../attributes/trafficOffloadId";
        }
      }
      container attributes {
        uses TrafficOffload-attributes;
      }
    }
  }

  augment "/emael:ManagedElement/GNBCUCPFunction" {
    list TrafficSteering {
      description "Additional definitions from MOM:min/max-elements:0/1; Configuration of Traffic Steering (TrSt) and container for TrSt profiles. Instance TrafficSteering=1 is created automatically when parent MO instance is created, unless created manually in same transaction. The RDN of this MO must be TrafficSteering=1. Precondition: Instance TrafficSteering=1 can only be created in same transaction as parent MO instance and cannot be deleted unless parent MO instance is deleted.";
      key "trafficSteeringId";
      leaf trafficSteeringId {
        type leafref {
          path "../attributes/trafficSteeringId";
        }
      }
      container attributes {
        uses TrafficSteering-attributes;
      }
    }
  }

  augment "/emael:ManagedElement/GNBCUCPFunction" {
    list UeCC {
      description "Additional definitions from MOM:min/max-elements:0/1; Container class for UE connection control attributes and profile classes. Instance UeCC=1 is created automatically when parent MO instance is created, unless created manually in same transaction. The RDN of this MO must be UeCC=1. Precondition: Instance UeCC=1 can only be created in same transaction as parent MO instance and cannot be deleted unless parent MO instance is deleted.";
      key "ueCCId";
      leaf ueCCId {
        type leafref {
          path "../attributes/ueCCId";
        }
      }
      container attributes {
        uses UeCC-attributes;
      }
    }
  }

  augment "/emael:ManagedElement/GNBCUCPFunction" {
    list UeCovMeas {
      description "Additional definitions from MOM:min/max-elements:0/1; Container class for UE coverage measurement configuration classes. Instance UeCovMeas=1 is created automatically when parent MO instance is created, unless created manually in same transaction. The RDN of this MO must be UeCovMeas=1. Precondition: Instance UeCovMeas=1 can only be created in same transaction as parent MO instance and cannot be deleted unless parent MO instance is deleted.";
      key "ueCovMeasId";
      leaf ueCovMeasId {
        type leafref {
          path "../attributes/ueCovMeasId";
        }
      }
      container attributes {
        uses UeCovMeas-attributes;
      }
    }
  }

  augment "/emael:ManagedElement/GNBCUCPFunction" {
    list UeGroupSelection {
      description "Additional definitions from MOM:min/max-elements:0/1; Container class for MO classes defining different UE group types. The RDN of this MO must be UeGroupSelection=1.";
      key "ueGroupSelectionId";
      leaf ueGroupSelectionId {
        type leafref {
          path "../attributes/ueGroupSelectionId";
        }
      }
      container attributes {
        uses UeGroupSelection-attributes;
      }
    }
  }

  augment "/emael:ManagedElement/GNBCUCPFunction" {
    list UeMC {
      description "Additional definitions from MOM:min/max-elements:0/1; Container class for UE mobility control attributes and UeMC profile classes. Instance UeMC=1 is created automatically when parent MO instance is created, unless created manually in same transaction. The RDN of this MO must be UeMC=1. Precondition: Instance UeMC=1 can only be created in same transaction as parent MO instance and cannot be deleted unless parent MO instance is deleted.";
      key "ueMCId";
      leaf ueMCId {
        type leafref {
          path "../attributes/ueMCId";
        }
      }
      container attributes {
        uses UeMC-attributes;
      }
    }
  }

  augment "/emael:ManagedElement/GNBCUCPFunction" {
    list UeNoDrb {
      description "Additional definitions from MOM:min/max-elements:0/1; Configuration of UE context without DRBs. Instance UeNoDrb=1 is created automatically when parent MO instance is created, unless created manually in same transaction. The RDN of this MO must be UeNoDrb=1. Precondition: Instance UeNoDrb=1 can only be created in same transaction as parent MO instance and cannot be deleted unless parent MO instance is deleted.";
      key "ueNoDrbId";
      leaf ueNoDrbId {
        type leafref {
          path "../attributes/ueNoDrbId";
        }
      }
      container attributes {
        uses UeNoDrb-attributes;
      }
    }
  }

  augment "/emael:ManagedElement/GNBCUCPFunction" {
    list UeUlResMon {
      description "Additional definitions from MOM:min/max-elements:0/1; Container class for UE uplink resource monitoring attributes and configuration classes. Instance UeUlResMon=1 is created automatically when parent MO instance is created, unless created manually in same transaction. The RDN of this MO must be UeUlResMon=1. Precondition: Instance UeUlResMon=1 can only be created in same transaction as parent MO instance and cannot be deleted unless parent MO instance is deleted.";
      key "ueUlResMonId";
      leaf ueUlResMonId {
        type leafref {
          path "../attributes/ueUlResMonId";
        }
      }
      container attributes {
        uses UeUlResMon-attributes;
      }
    }
  }

  augment "/emael:ManagedElement/GNBCUCPFunction/UeGroupSelection/ImeiSvGroups" {
    list ImeiSvGroup {
      description "Additional definitions from MOM:min/max-elements:0/512; A set of IMEISVs used to define a subset of all UEs.";
      key "imeiSvGroupId";
      leaf imeiSvGroupId {
        type leafref {
          path "../attributes/imeiSvGroupId";
        }
      }
      container attributes {
        uses ImeiSvGroup-attributes;
      }
    }
  }

  augment "/emael:ManagedElement/GNBCUCPFunction/UeCC/InactivityProfile" {
    list InactivityProfileUeCfg {
      description "Additional definitions from MOM:min/max-elements:0/8; Configuration of inactivity timer profile for UE groups. Instance InactivityProfileUeCfg=Base is created automatically when parent MO instance is created, unless created manually in same transaction. Attributes prefUeGroupList, ueGroupList and ueConfGroupList must be empty in instance InactivityProfileUeCfg=Base but cannot all be empty in any other instance of InactivityProfileUeCfg under same parent InactivityProfile instance. Value 0 is no longer allowed and is planned to be removed from the valid range of prefUeGroupList and ueGroupList. Precondition: Instance InactivityProfileUeCfg=Base can only be created in same transaction as parent MO instance and cannot be deleted unless parent MO instance is deleted. Other instances can be created and deleted at any time. Maximum 7 InactivityProfileUeCfg instances, with RDN different from Base, can be created under parent MO instance.";
      key "inactivityProfileUeCfgId";
      leaf inactivityProfileUeCfgId {
        type leafref {
          path "../attributes/inactivityProfileUeCfgId";
        }
      }
      container attributes {
        uses InactivityProfileUeCfg-attributes;
      }
    }
  }

  augment "/emael:ManagedElement/GNBCUCPFunction/UeCC/InitialCg" {
    list InitialCgUeCfg {
      description "Additional definitions from MOM:min/max-elements:0/8; Initial cell group UE configuration group. Instance InitialCgUeCfg=Base is created automatically when parent MO instance is created, unless created manually in same transaction. Each UE configuration group identifier can only be defined in one ueConfGroupList among InitialCgUeCfg instances contained under parent InitialCg instance. Any combination of one UE group identifier in ueGroupList and one preference UE group identifier in prefUeGroupList must be unique among InitialCgUeCfg instances contained under parent InitialCg instance. Attributes prefUeGroupList, ueGroupList and ueConfGroupList must be empty in instance InitialCgUeCfg=Base but cannot all be empty in any other instance of InitialCgUeCfg under same parent InitialCg instance. Precondition: Instance InitialCgUeCfg=Base can only be created in same transaction as parent MO instance and cannot be deleted unless parent MO instance is deleted. Other instances can be created and deleted at any time. Maximum 7 InitialCgUeCfg instances, with RDN different from Base, can be created under parent MO instance.";
      key "initialCgUeCfgId";
      leaf initialCgUeCfgId {
        type leafref {
          path "../attributes/initialCgUeCfgId";
        }
      }
      container attributes {
        uses InitialCgUeCfg-attributes;
      }
    }
  }

  augment "/emael:ManagedElement/GNBCUCPFunction/IntraFreqMC" {
    list IntraFreqMCCellProfile {
      description "Additional definitions from MOM:min/max-elements:0/unbounded; Intra-frequency mobility control, cell configuration profile. Applies to UEs that use cell as SpCell. Attributes are used on cell level. Instance IntraFreqMCCellProfile=Default is created automatically when parent MO instance is created, unless created manually in same transaction. NRCellCU::intraFreqMCCellProfileRef is automatically set to IntraFreqMCCellProfile=Default instance, unless manually set to refer to another MO instance. Precondition: Instance IntraFreqMCCellProfile=Default can only be created in same transaction as parent MO instance and cannot be deleted unless parent MO instance is deleted. Other instances can be created and deleted at any time.";
      key "intraFreqMCCellProfileId";
      leaf intraFreqMCCellProfileId {
        type leafref {
          path "../attributes/intraFreqMCCellProfileId";
        }
      }
      container attributes {
        uses IntraFreqMCCellProfile-attributes;
      }
    }
  }

  augment "/emael:ManagedElement/GNBCUCPFunction/IntraFreqMC" {
    list IntraFreqMCFreqRelProfile {
      description "Additional definitions from MOM:min/max-elements:0/unbounded; Intra-frequency mobility control cell configuration profile. Applies to UEs that use cell as SpCell. Attributes are used on NR frequency relation level. Instance IntraFreqMCFreqRelProfile=Default is created automatically when parent MO instance is created, unless created manually in same transaction. NRFreqRelation::intraFreqMCFreqRelProfileRef is automatically set to IntraFreqMCFreqRelProfile=Default instance, unless manually set to refer to another MO instance. Precondition: Instance IntraFreqMCFreqRelProfile=Default can only be created in same transaction as parent MO instance and cannot be deleted unless parent MO instance is deleted. Other instances can be created and deleted at any time.";
      key "intraFreqMCFreqRelProfileId";
      status deprecated;
      leaf intraFreqMCFreqRelProfileId {
        type leafref {
          path "../attributes/intraFreqMCFreqRelProfileId";
        }
        status deprecated;
      }
      container attributes {
        uses IntraFreqMCFreqRelProfile-attributes;
      }
    }
  }

  augment "/emael:ManagedElement/GNBCUCPFunction/IntraFreqMC/IntraFreqMCCellProfile" {
    list IntraFreqMCCellProfileUeCfg {
      description "Additional definitions from MOM:min/max-elements:0/32; Intra-frequency mobility control cell configuration profile, UE configuration group. Applies to UEs that use cell as SpCell. Attributes are used on cell level. Instance IntraFreqMCCellProfileUeCfg=Base is created automatically when parent MO instance is created, unless created manually in same transaction. Attributes prefUeGroupList, ueGroupList and ueConfGroupList must be empty in instance IntraFreqMCCellProfileUeCfg=Base but cannot all be empty in any other instance of IntraFreqMCCellProfileUeCfg under same parent IntraFreqMCCellProfile instance. Precondition: Instance IntraFreqMCCellProfileUeCfg=Base can only be created in same transaction as parent MO instance and cannot be deleted unless parent MO instance is deleted. Other instances can be created and deleted at any time. Maximum 31 IntraFreqMCCellProfileUeCfg instances, with RDN different from Base, can be created under parent MO instance.";
      key "intraFreqMCCellProfileUeCfgId";
      leaf intraFreqMCCellProfileUeCfgId {
        type leafref {
          path "../attributes/intraFreqMCCellProfileUeCfgId";
        }
      }
      container attributes {
        uses IntraFreqMCCellProfileUeCfg-attributes;
      }
    }
  }

  augment "/emael:ManagedElement/GNBCUCPFunction/IntraFreqMC/IntraFreqMCFreqRelProfile" {
    list IntraFreqMCFreqRelProfileUeCfg {
      description "Additional definitions from MOM:min/max-elements:0/32; Intra-frequency mobility control cell configuration profile for UE configuration group. Applies to UEs that use cell as SpCell. Attributes are used on NR frequency relation level. Instance IntraFreqMCFreqRelProfileUeCfg=Base is created automatically when parent MO instance is created, unless created manually in same transaction. Attributes prefUeGroupList, ueGroupList and ueConfGroupList must be empty in instance IntraFreqMCFreqRelProfileUeCfg=Base but cannot all be empty in any other instance of IntraFreqMCFreqRelProfileUeCfg under same parent IntraFreqMCFreqRelProfile instance. Precondition: Instance IntraFreqMCFreqRelProfileUeCfg=Base can only be created in same transaction as parent MO instance and cannot be deleted unless parent MO instance is deleted. Other instances can be created and deleted at any time. Maximum 31 IntraFreqMCFreqRelProfileUeCfg instances, with RDN different from Base, can be created under parent MO instance.";
      key "intraFreqMCFreqRelProfileUeCfgId";
      status deprecated;
      leaf intraFreqMCFreqRelProfileUeCfgId {
        type leafref {
          path "../attributes/intraFreqMCFreqRelProfileUeCfgId";
        }
        status deprecated;
      }
      container attributes {
        uses IntraFreqMCFreqRelProfileUeCfg-attributes;
      }
    }
  }

  augment "/emael:ManagedElement/GNBCUCPFunction/Mcfb" {
    list McfbCellProfile {
      description "Additional definitions from MOM:min/max-elements:0/unbounded; Profile of mobility control fallback for cell. Applies to UEs that use the cell as PCell. Attributes are used on cell level. Instance McfbCellProfile=Default is created automatically when parent MO instance is created, unless created manually in same transaction. NRCellCU::mcfbCellProfileRef is automatically set to McfbCellProfile=Default instance, unless manually set to refer to another MO instance. Precondition: Instance McfbCellProfile=Default can only be created in same transaction as parent MO instance and cannot be deleted unless parent MO instance is deleted.";
      key "mcfbCellProfileId";
      leaf mcfbCellProfileId {
        type leafref {
          path "../attributes/mcfbCellProfileId";
        }
      }
      container attributes {
        uses McfbCellProfile-attributes;
      }
    }
  }

  augment "/emael:ManagedElement/GNBCUCPFunction/Mcfb/McfbCellProfile" {
    list McfbCellProfileUeCfg {
      description "Additional definitions from MOM:min/max-elements:0/32; Mobility Control Fallback Cell Profile, UE configuration group. Applies to UEs that use cell as PCell. Attributes are used on cell level. Instance McfbCellProfileUeCfg=Base is created automatically when parent MO instance is created, unless created manually in same transaction. Attributes prefUeGroupList, ueGroupList and ueConfGroupList must be empty in instance McfbCellProfileUeCfg=Base but cannot all be empty in any other instance of McfbCellProfileUeCfg under same parent McfbCellProfile instance. Precondition: Instance McfbCellProfileUeCfg=Base can only be created in same transaction as parent MO instance and cannot be deleted unless parent MO instance is deleted. Other instances can be created and deleted at any time. Maximum 31 McfbCellProfileUeCfg instances, with RDN different from Base, can be created under parent MO instance.";
      key "mcfbCellProfileUeCfgId";
      leaf mcfbCellProfileUeCfgId {
        type leafref {
          path "../attributes/mcfbCellProfileUeCfgId";
        }
      }
      container attributes {
        uses McfbCellProfileUeCfg-attributes;
      }
    }
  }

  augment "/emael:ManagedElement/GNBCUCPFunction/Mcpc" {
    list McpcNrdcPSCellProfile {
      description "Additional definitions from MOM:min/max-elements:0/unbounded; Mobility Control at Poor Coverage (MCPC) function for PSCell in NR-DC configuration. Applies to UEs that use cell as PSCell in NR-DC. Attributes are used on cell level. Instance McpcNrdcPSCellProfile=Default is created automatically when parent MO instance is created, unless created manually in same transaction. NRCellCU::mcpcNrdcPSCellProfileRef is automatically set to McpcNrdcPSCellProfile=Default instance, unless manually set to refer to another MO instance. Precondition: Instance McpcNrdcPSCellProfile=Default can only be created in same transaction as parent MO instance and cannot be deleted unless parent MO instance is deleted. Other instances can be created and deleted at any time.";
      key "mcpcNrdcPSCellProfileId";
      leaf mcpcNrdcPSCellProfileId {
        type leafref {
          path "../attributes/mcpcNrdcPSCellProfileId";
        }
      }
      container attributes {
        uses McpcNrdcPSCellProfile-attributes;
      }
    }
  }

  augment "/emael:ManagedElement/GNBCUCPFunction/Mcpc" {
    list McpcPCellEUtranFreqRelProfile {
      description "Additional definitions from MOM:min/max-elements:0/unbounded; Mobility Control at Poor Coverage (MCPC) for PCell. Applies to UEs that use the cell as PCell. Attributes are used on E-UTRAN frequency relation level. Instance McpcPCellEUtranFreqRelProfile=Default is created automatically when parent MO instance is created, unless created manually in same transaction. MCPC for PCell is enabled for each NRCellCU instance by setting NRCellCU::mcpcPCellEnabled. EUtranFreqRelation::mcpcPCellEUtranFreqRelProfileRef is automatically set to McpcPCellEUtranFreqRelProfile=Default instance, unless manually set to refer to another MO instance. Precondition: Instance McpcPCellEUtranFreqRelProfile=Default can only be created in same transaction as parent MO instance and cannot be deleted unless parent MO instance is deleted. Other instances can be created and deleted at any time.";
      key "mcpcPCellEUtranFreqRelProfileId";
      leaf mcpcPCellEUtranFreqRelProfileId {
        type leafref {
          path "../attributes/mcpcPCellEUtranFreqRelProfileId";
        }
      }
      container attributes {
        uses McpcPCellEUtranFreqRelProfile-attributes;
      }
    }
  }

  augment "/emael:ManagedElement/GNBCUCPFunction/Mcpc" {
    list McpcPCellNrFreqRelProfile {
      description "Additional definitions from MOM:min/max-elements:0/unbounded; Mobility Control at Poor Coverage (MCPC) for PCell. Applies to UEs that use the cell as PCell. Attributes are used on NR frequency relation level. Instance McpcPCellNrFreqRelProfile=Default is created automatically when parent MO instance is created, unless created manually in same transaction. MCPC for PCell is enabled per NRCellCU instance by setting NRCellCU::mcpcPCellEnabled. NRFreqRelation::mcpcPCellNrFreqRelProfileRef is automatically set to McpcPCellNrFreqRelProfile=Default instance, unless manually set to refer to another MO instance. Precondition: Instance McpcPCellNrFreqRelProfile=Default can only be created in same transaction as parent MO instance and cannot be deleted unless parent MO instance is deleted. Other instances can be created and deleted at any time.";
      key "mcpcPCellNrFreqRelProfileId";
      leaf mcpcPCellNrFreqRelProfileId {
        type leafref {
          path "../attributes/mcpcPCellNrFreqRelProfileId";
        }
      }
      container attributes {
        uses McpcPCellNrFreqRelProfile-attributes;
      }
    }
  }

  augment "/emael:ManagedElement/GNBCUCPFunction/Mcpc" {
    list McpcPCellProfile {
      description "Additional definitions from MOM:min/max-elements:0/unbounded; Mobility Control at Poor Coverage (MCPC) for PCell. Applies to UEs that use the cell as PCell. Attributes are used on cell level. Instance McpcPCellProfile=Default is created automatically when parent MO instance is created, unless created manually in same transaction. MCPC for PCell is enabled per NRCellCU instance by setting NRCellCU::mcpcPCellEnabled. NRCellCU::mcpcPCellProfileRef is automatically set to McpcPCellProfile=Default instance, unless manually set to refer to another MO instance. Precondition: Instance McpcPCellProfile=Default can only be created in same transaction as parent MO instance and cannot be deleted unless parent MO instance is deleted. Other instances can be created and deleted at any time.";
      key "mcpcPCellProfileId";
      leaf mcpcPCellProfileId {
        type leafref {
          path "../attributes/mcpcPCellProfileId";
        }
      }
      container attributes {
        uses McpcPCellProfile-attributes;
      }
    }
  }

  augment "/emael:ManagedElement/GNBCUCPFunction/Mcpc" {
    list McpcPSCellNrFreqRelProfile {
      description "Additional definitions from MOM:min/max-elements:0/unbounded; Mobility Control at Poor Coverage function for PSCell in EN-DC. Applies to UEs that use this cell as PSCell in EN-DC. Attributes are used on NR frequency relation level. This function for PSCell in EN-DC can be enabled for each NRCellCU instance with NRCellCU::mcpcPSCellEnabled. Instance McpcPSCellNrFreqRelProfile=Default is created automatically when parent MO instance is created, unless created manually in same transaction. NRFreqRelation::mcpcPSCellNrFreqRelProfileRef is automatically set to McpcPSCellNrFreqRelProfile=Default instance, unless manually set to refer to another MO instance. Precondition: Instance McpcPSCellNrFreqRelProfile=Default can only be created in same transaction as parent MO instance and cannot be deleted unless parent MO instance is deleted. Other instances can be created and deleted at any time.";
      key "mcpcPSCellNrFreqRelProfileId";
      leaf mcpcPSCellNrFreqRelProfileId {
        type leafref {
          path "../attributes/mcpcPSCellNrFreqRelProfileId";
        }
      }
      container attributes {
        uses McpcPSCellNrFreqRelProfile-attributes;
      }
    }
  }

  augment "/emael:ManagedElement/GNBCUCPFunction/Mcpc" {
    list McpcPSCellProfile {
      description "Additional definitions from MOM:min/max-elements:0/unbounded; Mobility Control at Poor Coverage function for PSCell in EN-DC. Applies to UEs that use this cell as PSCell in EN-DC. Attributes are used on cell level. This function for PSCell in EN-DC can be enabled for each NRCellCU instance with NRCellCU::mcpcPSCellEnabled. Instance McpcPSCellProfile=Default is created automatically when parent MO instance is created, unless created manually in same transaction. NRCellCU::mcpcPSCellProfileRef is automatically set to McpcPSCellProfile=Default instance, unless manually set to refer to another MO instance. Precondition: Instance McpcPSCellProfile=Default can only be created in same transaction as parent MO instance and cannot be deleted unless parent MO instance is deleted. Other instances can be created and deleted at any time.";
      key "mcpcPSCellProfileId";
      leaf mcpcPSCellProfileId {
        type leafref {
          path "../attributes/mcpcPSCellProfileId";
        }
      }
      container attributes {
        uses McpcPSCellProfile-attributes;
      }
    }
  }

  augment "/emael:ManagedElement/GNBCUCPFunction/Mcpc/McpcNrdcPSCellProfile" {
    list McpcNrdcPSCellProfileUeCfg {
      description "Additional definitions from MOM:min/max-elements:0/32; Mobility Control at Poor Coverage function for PSCell in NR-DC, UE configuration group. Applies to UEs that use cell as PSCell in NR-DC. Attributes are used on cell level. Instance McpcNrdcPSCellProfileUeCfg=Base is created automatically when parent MO instance is created, unless created manually in same transaction. Attributes prefUeGroupList, ueGroupList and ueConfGroupList must be empty in instance McpcNrdcPSCellProfileUeCfg=Base but cannot all be empty in any other instance of McpcNrdcPSCellProfileUeCfg under same parent McpcNrdcPSCellProfile instance. Precondition: Instance McpcNrdcPSCellProfileUeCfg=Base can only be created in same transaction as parent MO instance and cannot be deleted unless parent MO instance is deleted. Other instances can be created and deleted at any time. Maximum 31 McpcNrdcPSCellProfileUeCfg instances, with RDN different from Base, can be created under parent MO instance.";
      key "mcpcNrdcPSCellProfileUeCfgId";
      leaf mcpcNrdcPSCellProfileUeCfgId {
        type leafref {
          path "../attributes/mcpcNrdcPSCellProfileUeCfgId";
        }
      }
      container attributes {
        uses McpcNrdcPSCellProfileUeCfg-attributes;
      }
    }
  }

  augment "/emael:ManagedElement/GNBCUCPFunction/Mcpc/McpcPCellEUtranFreqRelProfile" {
    list McpcPCellEUtranFreqRelProfileUeCfg {
      description "Additional definitions from MOM:min/max-elements:0/32; Mobility Control at Poor Coverage (MCPC) for PCell, UE configuration group. Applies to UEs that use the cell as PCell. Attributes are used on E-UTRAN frequency relation level. Instance McpcPCellEUtranFreqRelProfileUeCfg=Base is created automatically when parent MO instance is created, unless created manually in same transaction. Attributes prefUeGroupList, ueGroupList and ueConfGroupList must be empty in instance McpcPCellEUtranFreqRelProfileUeCfg=Base but cannot all be empty in any other instance of McpcPCellEUtranFreqRelProfileUeCfg under same parent McpcPCellEUtranFreqRelProfile instance. Precondition: Instance McpcPCellEUtranFreqRelProfileUeCfg=Base can only be created in same transaction as parent MO instance and cannot be deleted unless parent MO instance is deleted. Other instances can be created and deleted at any time. Maximum 31 McpcPCellEUtranFreqRelProfileUeCfg instances, with RDN different from Base, can be created under parent MO instance.";
      key "mcpcPCellEUtranFreqRelProfileUeCfgId";
      leaf mcpcPCellEUtranFreqRelProfileUeCfgId {
        type leafref {
          path "../attributes/mcpcPCellEUtranFreqRelProfileUeCfgId";
        }
      }
      container attributes {
        uses McpcPCellEUtranFreqRelProfileUeCfg-attributes;
      }
    }
  }

  augment "/emael:ManagedElement/GNBCUCPFunction/Mcpc/McpcPCellNrFreqRelProfile" {
    list McpcPCellNrFreqRelProfileUeCfg {
      description "Additional definitions from MOM:min/max-elements:0/32; Mobility Control at Poor Coverage (MCPC) for PCell, UE configuration group. Applies to UEs that use the cell as PCell. Attributes are used on NR frequency relation level. Instance McpcPCellNrFreqRelProfileUeCfg=Base is created automatically when parent MO instance is created, unless created manually in same transaction. Attributes prefUeGroupList, ueGroupList and ueConfGroupList must be empty in instance McpcPCellNrFreqRelProfileUeCfg=Base but cannot all be empty in any other instance of McpcPCellNrFreqRelProfileUeCfg under same parent McpcPCellNrFreqRelProfile instance. Precondition: Instance McpcPCellNrFreqRelProfileUeCfg=Base can only be created in same transaction as parent MO instance and cannot be deleted unless parent MO instance is deleted. Other instances can be created and deleted at any time. Maximum 31 McpcPCellNrFreqRelProfileUeCfg instances, with RDN different from Base, can be created under parent MO instance.";
      key "mcpcPCellNrFreqRelProfileUeCfgId";
      leaf mcpcPCellNrFreqRelProfileUeCfgId {
        type leafref {
          path "../attributes/mcpcPCellNrFreqRelProfileUeCfgId";
        }
      }
      container attributes {
        uses McpcPCellNrFreqRelProfileUeCfg-attributes;
      }
    }
  }

  augment "/emael:ManagedElement/GNBCUCPFunction/Mcpc/McpcPCellProfile" {
    list McpcPCellProfileUeCfg {
      description "Additional definitions from MOM:min/max-elements:0/32; Mobility Control at Poor Coverage (MCPC) for PCell, UE configuration group. Applies to UEs that use cell as PCell. Attributes are used on cell level. Instance McpcPCellProfileUeCfg=Base is created automatically when parent MO instance is created, unless created manually in same transaction. Attributes prefUeGroupList, ueGroupList and ueConfGroupList must be empty in instance McpcPCellProfileUeCfg=Base but cannot all be empty in any other instance of McpcPCellProfileUeCfg under same parent McpcPCellProfile instance. Precondition: Instance McpcPCellProfileUeCfg=Base can only be created in same transaction as parent MO instance and cannot be deleted unless parent MO instance is deleted. Other instances can be created and deleted at any time. Maximum 31 McpcPCellProfileUeCfg instances, with RDN different from Base, can be created under parent MO instance.";
      key "mcpcPCellProfileUeCfgId";
      leaf mcpcPCellProfileUeCfgId {
        type leafref {
          path "../attributes/mcpcPCellProfileUeCfgId";
        }
      }
      container attributes {
        uses McpcPCellProfileUeCfg-attributes;
      }
    }
  }

  augment "/emael:ManagedElement/GNBCUCPFunction/Mcpc/McpcPSCellNrFreqRelProfile" {
    list McpcPSCellNrFreqRelProfileUeCfg {
      description "Additional definitions from MOM:min/max-elements:0/32; Mobility Control at Poor Coverage function for PSCell in EN-DC, UE configuration group. Applies to UEs that use this cell as PSCell in EN-DC. Attributes are used on NR frequency relation level. Instance McpcPSCellNrFreqRelProfileUeCfg=Base is created automatically when parent MO instance is created, unless created manually in same transaction. Attributes prefUeGroupList, ueGroupList and ueConfGroupList must be empty in instance McpcPSCellNrFreqRelProfileUeCfg=Base but cannot all be empty in any other instance of McpcPSCellNrFreqRelProfileUeCfg under same parent McpcPSCellNrFreqRelProfile instance. Precondition: Instance McpcPSCellNrFreqRelProfileUeCfg=Base can only be created in same transaction as parent MO instance and cannot be deleted unless parent MO instance is deleted. Other instances can be created and deleted at any time. Maximum 31 McpcPSCellNrFreqRelProfileUeCfg instances, with RDN different from Base, can be created under parent MO instance.";
      key "mcpcPSCellNrFreqRelProfileUeCfgId";
      leaf mcpcPSCellNrFreqRelProfileUeCfgId {
        type leafref {
          path "../attributes/mcpcPSCellNrFreqRelProfileUeCfgId";
        }
      }
      container attributes {
        uses McpcPSCellNrFreqRelProfileUeCfg-attributes;
      }
    }
  }

  augment "/emael:ManagedElement/GNBCUCPFunction/Mcpc/McpcPSCellProfile" {
    list McpcPSCellProfileUeCfg {
      description "Additional definitions from MOM:min/max-elements:0/32; Mobility Control at Poor Coverage function for PSCell in EN-DC, UE configuration group. Applies to UEs that use this cell as PSCell in EN-DC. Attributes are used on cell level. Instance McpcPSCellProfileUeCfg=Base is created automatically when parent MO instance is created, unless created manually in same transaction. Attributes prefUeGroupList, ueGroupList and ueConfGroupList must be empty in instance McpcPSCellProfileUeCfg=Base but cannot all be empty in any other instance of McpcPSCellProfileUeCfg under same parent McpcPSCellProfile instance. Precondition: Instance McpcPSCellProfileUeCfg=Base can only be created in same transaction as parent MO instance and cannot be deleted unless parent MO instance is deleted. Other instances can be created and deleted at any time. Maximum 31 McpcPSCellProfileUeCfg instances, with RDN different from Base, can be created under parent MO instance.";
      key "mcpcPSCellProfileUeCfgId";
      leaf mcpcPSCellProfileUeCfgId {
        type leafref {
          path "../attributes/mcpcPSCellProfileUeCfgId";
        }
      }
      container attributes {
        uses McpcPSCellProfileUeCfg-attributes;
      }
    }
  }

  augment "/emael:ManagedElement/GNBCUCPFunction/Mdt" {
    list MdtCellProfile {
      description "Additional definitions from MOM:min/max-elements:0/unbounded; MDT profile for cell level. Instance MdtCellProfile=Default is created automatically when parent MO instance is created, unless created manually in same transaction. NRCellCU::mdtCellProfileRef is automatically set to MdtCellProfile=Default instance, unless manually set to refer to another MO instance. Precondition: Instance MdtCellProfile=Default can only be created in same transaction as parent MO instance and cannot be deleted unless parent MO instance is deleted. Other instances can be created and deleted at any time.";
      key "mdtCellProfileId";
      leaf mdtCellProfileId {
        type leafref {
          path "../attributes/mdtCellProfileId";
        }
      }
      container attributes {
        uses MdtCellProfile-attributes;
      }
    }
  }

  augment "/emael:ManagedElement/GNBCUCPFunction/Mdt/MdtCellProfile" {
    list MdtCellProfileUeCfg {
      description "Additional definitions from MOM:min/max-elements:0/32; MDT profile for UE configuration group. Applies to UEs configured for MDT. Instance MdtCellProfileUeCfg=Base is created automatically when parent MO instance is created, unless created manually in same transaction. Precondition: Instance MdtCellProfileUeCfg=Base can only be created in same transaction as parent MO instance and cannot be deleted unless parent MO instance is deleted. Other instances can be created and deleted at any time. Maximum 31 MdtCellProfileUeCfg instances, with RDN different from Base, can be created under parent MO instance.";
      key "mdtCellProfileUeCfgId";
      leaf mdtCellProfileUeCfgId {
        type leafref {
          path "../attributes/mdtCellProfileUeCfgId";
        }
      }
      container attributes {
        uses MdtCellProfileUeCfg-attributes;
      }
    }
  }

  augment "/emael:ManagedElement/GNBCUCPFunction/NRCellCU" {
    list AdditionalPLMNInfo {
      description "Additional definitions from MOM:min/max-elements:0/11;systemCreated; PLMN-related Information that can be additionally served by NR cell. Created when F1 interface is set up or configuration is updated by GNBDUFunction. Deleted when configuration is updated by GNBDUFunction. The RDNs of these MOs are AdditionalPLMNInfo=1 to AdditionalPLMNInfo=11. Length of RDN value is up to 2 characters. Instance can be created without a preceding user-initiated transaction.";
      key "additionalPLMNInfoId";
      leaf additionalPLMNInfoId {
        type leafref {
          path "../attributes/additionalPLMNInfoId";
        }
      }
      container attributes {
        uses AdditionalPLMNInfo-attributes;
      }
    }
  }

  augment "/emael:ManagedElement/GNBCUCPFunction/NRCellCU" {
    list DESManagementFunction {
      description "Additional definitions from MOM:min/max-elements:0/1; Distributed SON energy saving settings for cell. Instance DESManagementFunction=1 is created automatically when parent MO instance is created, unless created manually in same transaction. The RDN of this MO must be DESManagementFunction=1. Precondition: Instance DESManagementFunction=1 can only be created in same transaction as parent MO instance and cannot be deleted unless parent MO instance is deleted.";
      key "dESManagementFunctionId";
      leaf dESManagementFunctionId {
        type leafref {
          path "../attributes/dESManagementFunctionId";
        }
      }
      container attributes {
        uses DESManagementFunction-attributes;
      }
    }
  }

  augment "/emael:ManagedElement/GNBCUCPFunction/NRCellCU" {
    list EUtranCellRelation {
      description "Additional definitions from MOM:min/max-elements:0/128; Handover relationship between NR cell and a neighboring E-UTRAN cell. Can be created by action promoteLwEUtranCellRelation in NRCellCU instance. RDN is the same as for automatically created instance. When created automatically, the RDN of this MO is EUtranCellRelation=auto<ECI>, where ECI = <eNBid>*256 + <cellLocalId>. Length of RDN value is up to 13 characters for automatically created instance. Instance can be created without a preceding user-initiated transaction.";
      key "eUtranCellRelationId";
      leaf eUtranCellRelationId {
        type leafref {
          path "../attributes/eUtranCellRelationId";
        }
      }
      container attributes {
        uses EUtranCellRelation-attributes;
      }
    }
  }

  augment "/emael:ManagedElement/GNBCUCPFunction/NRCellCU" {
    list EUtranFreqRelation {
      description "Additional definitions from MOM:min/max-elements:0/16; Mobility relation between NR cell and an E-UTRAN frequency.";
      key "eUtranFreqRelationId";
      leaf eUtranFreqRelationId {
        type leafref {
          path "../attributes/eUtranFreqRelationId";
        }
      }
      container attributes {
        uses EUtranFreqRelation-attributes;
      }
    }
  }

  augment "/emael:ManagedElement/GNBCUCPFunction/NRCellCU" {
    list NRCellRelation {
      description "Additional definitions from MOM:min/max-elements:0/512; Handover relationship between NR cell and a neighboring NR cell. This MO is updated or deleted automatically when configuration message over F1, Xn or X2 interface is received, with changed frequency of neighbor cell. If matching NRFreqRelation instance exists, then nRFreqRelationRef is updated. Otherwise, NRCellRelation instance is deleted. See dependencies of nRFreqRelationRef. Can be created by action promoteLwNRCellRelation in NRCellCU instance. RDN is the same as for automatically created instance. When created automatically, the RDN of this MO is NRCellRelation=auto<NCI>, where NCI = <gNBId>*2^(36-<gNBIdLength>) + <cellLocalId>. Length of RDN value is up to 15 characters for automatically created instance. Instance can be created without a preceding user-initiated transaction.";
      key "nRCellRelationId";
      leaf nRCellRelationId {
        type leafref {
          path "../attributes/nRCellRelationId";
        }
      }
      container attributes {
        uses NRCellRelation-attributes;
      }
    }
  }

  augment "/emael:ManagedElement/GNBCUCPFunction/NRCellCU" {
    list NRFreqRelation {
      description "Additional definitions from MOM:min/max-elements:0/16; Mobility relation between NR cell and an NR frequency. Must use an NRFrequency on the Global Synchronization Channel Raster (indicated in NRFrequency::gscn) for Standalone operation. Frequency relation not on the GSCN are not included in SIB4, nor used for PCell mobility. Created automatically when F1, Xn or X2 message is received. Can also be created and deleted manually. When created automatically, the RDN of this MO is NRFreqRelation=auto<arfcn>_<scs>. Length of RDN value is up to 15 characters for automatically created instance. Instance can be created without a preceding user-initiated transaction.";
      key "nRFreqRelationId";
      leaf nRFreqRelationId {
        type leafref {
          path "../attributes/nRFreqRelationId";
        }
      }
      container attributes {
        uses NRFreqRelation-attributes;
      }
    }
  }

  augment "/emael:ManagedElement/GNBCUCPFunction/NRCellCU" {
    list NRFreqRelationTemplate {
      description "Additional definitions from MOM:min/max-elements:0/4; Frequency range of automatically created or deleted NRFreqRelation instances. Can be used, for example, for CBRS. Contains reference to default NRFreqRelation instance used as template for automatically created NRFreqRelation instances within this range. Note: Only NRFreqRelation instances within this range are automatically deleted. Changing the range or deleting an NRFreqRelationTemplate instance may require manual deletion of NRFreqRelation instances. NRFreqRelationTemplate instances cannot have overlapping nRFrequencyRange values under same NRCellCU instance.";
      key "nRFreqRelationTemplateId";
      leaf nRFreqRelationTemplateId {
        type leafref {
          path "../attributes/nRFreqRelationTemplateId";
        }
      }
      container attributes {
        uses NRFreqRelationTemplate-attributes;
      }
    }
  }

  augment "/emael:ManagedElement/GNBCUCPFunction/NRCellCU" {
    list RibTmRelation {
      description "Additional definitions from MOM:min/max-elements:0/unbounded; Radio interface-based time monitoring relation between a monitoring and an assisting NR cell. Created automatically when GNBCUCPFunction::ribTmAutoMax is higher than 0, a suitable NRCellRelation instance exists and there is enough capacity. Runs periodically every 5 minutes. Deleted automatically when GNBCUCPFunction::ribTmAutoMax is set to 0 or number of automatically created RibTmRelation instances exceeded GNBCUCPFunction::ribTmAutoMax limit (after setting new GNBCUCPFunction::ribTmAutoMax). Runs periodically every 5 minutes. Can also be created and deleted manually. When created automatically, the RDN of this MO is RibTmRelation=auto<NCI>, where remote NCI = <gNBId>*2^(36-<gNBIdLength>) + <cellLocalId>. Length of RDN value is up to 15 characters for automatically created instance. Instance can be created without a preceding user-initiated transaction.";
      key "ribTmRelationId";
      leaf ribTmRelationId {
        type leafref {
          path "../attributes/ribTmRelationId";
        }
      }
      container attributes {
        uses RibTmRelation-attributes;
      }
    }
  }

  augment "/emael:ManagedElement/GNBCUCPFunction/NRNetwork/NRFrequency" {
    list NRFrequencyUeCfg {
      description "Additional definitions from MOM:min/max-elements:0/32; NRFrequency parameters for UE groups. Instance NRFrequencyUeCfg=Base is created automatically when parent MO instance is created, unless created manually in same transaction. Attributes prefUeGroupList, ueGroupList and ueConfGroupList must be empty in instance NRFrequencyUeCfg=Base but cannot all be empty in any other instance of NRFrequencyUeCfg under same parent NRFrequency instance. Precondition: Instance NRFrequencyUeCfg=Base can only be created in same transaction as parent MO instance and cannot be deleted unless parent MO instance is deleted. Other instances can be created and deleted at any time. Maximum 31 NRFrequencyUeCfg instances, with RDN different from Base, can be created under parent MO instance.";
      key "nRFrequencyUeCfgId";
      leaf nRFrequencyUeCfgId {
        type leafref {
          path "../attributes/nRFrequencyUeCfgId";
        }
      }
      container attributes {
        uses NRFrequencyUeCfg-attributes;
      }
    }
  }

  augment "/emael:ManagedElement/GNBCUCPFunction/NRNetwork" {
    list ExternalGNBCUCPFunction {
      description "Additional definitions from MOM:min/max-elements:0/512; Representation of external gNodeB-CU-CP function. Created automatically when Xn interface is set up, unless it already exists. Deleted automatically. Can also be created and deleted manually. When created automatically, the RDN of this MO is ExternalGNBCUCPFunction=auto<mcc>_<mnc>_<mncLength>_<gNodeBId>. Length of RDN value is up to 24 characters for automatically created instance. Instance can be created without a preceding user-initiated transaction.";
      key "externalGNBCUCPFunctionId";
      leaf externalGNBCUCPFunctionId {
        type leafref {
          path "../attributes/externalGNBCUCPFunctionId";
        }
      }
      container attributes {
        uses ExternalGNBCUCPFunction-attributes;
      }
    }
  }

  augment "/emael:ManagedElement/GNBCUCPFunction/NRNetwork" {
    list NRFrequency {
      description "Additional definitions from MOM:min/max-elements:0/64; NRFrequency and related measurement parameters. Created automatically when X2, Xn, or F1 message is received, unless it already exists. Can also be created and deleted manually. The RDN of this MO must be NRFrequency=<arfcnValueNRDl>-<smtcScs>. Length of RDN value is up to 11 characters. Instance can be created without a preceding user-initiated transaction. Example: NRFrequency=630000-30";
      key "nRFrequencyId";
      leaf nRFrequencyId {
        type leafref {
          path "../attributes/nRFrequencyId";
        }
      }
      container attributes {
        uses NRFrequency-attributes;
      }
    }
  }

  augment "/emael:ManagedElement/GNBCUCPFunction/Nccm" {
    list NccmUeCfg {
      description "Additional definitions from MOM:min/max-elements:0/32; Neighbor Cell Coverage Measurement UE configuration group. Instance NccmUeCfg=Base is created automatically when parent MO instance is created, unless created manually in same transaction. Each UE configuration group identifier can only be defined in one ueConfGroupList among NccmUeCfg instances under parent Nccm instance. Any combination of one UE group identifier in ueGroupList and one preference UE group identifier in prefUeGroupList must be unique among NccmUeCfg instances under parent Nccm instance. Attributes prefUeGroupList, ueGroupList, and ueConfGroupList must be empty in instance NccmUeCfg=Base but cannot all be empty in any other instance of NccmUeCfg. Only applicable to inter-frequency periodic measurements. Precondition: Instance NccmUeCfg=Base can only be created in same transaction as parent MO instance and cannot be deleted unless parent MO instance is deleted. Other instances can be created and deleted at any time. Maximum 31 NccmUeCfg instances, with RDN different from Base, can be created under parent MO instance.";
      key "nccmUeCfgId";
      leaf nccmUeCfgId {
        type leafref {
          path "../attributes/nccmUeCfgId";
        }
      }
      container attributes {
        uses NccmUeCfg-attributes;
      }
    }
  }

  augment "/emael:ManagedElement/GNBCUCPFunction/NrdcControl" {
    list NrdcMnCellProfile {
      description "Additional definitions from MOM:min/max-elements:0/unbounded; NR-NR Dual Connectivity control for PCell in Master Node. Applies to UEs that use the cell as PCell in Master Node. Attributes are used on cell level. Instance NrdcMnCellProfile=Default is created automatically when parent MO instance is created, unless created manually in same transaction. NRCellCU::nrdcMnCellProfileRef is automatically set to NrdcMnCellProfile=Default instance, unless manually set to refer to another MO instance. Precondition: Instance NrdcMnCellProfile=Default can only be created in same transaction as parent MO instance and cannot be deleted unless parent MO instance is deleted. Other instances can be created and deleted at any time.";
      key "nrdcMnCellProfileId";
      leaf nrdcMnCellProfileId {
        type leafref {
          path "../attributes/nrdcMnCellProfileId";
        }
      }
      container attributes {
        uses NrdcMnCellProfile-attributes;
      }
    }
  }

  augment "/emael:ManagedElement/GNBCUCPFunction/NrdcControl/NrdcMnCellProfile" {
    list NrdcMnCellProfileUeCfg {
      description "Additional definitions from MOM:min/max-elements:0/8; NR-NR Dual Connectivity control for PCell in Master Node, UE configuration group. Applies to UEs that use the cell as PCell in Master Node. Attributes are used on cell level. Instance NrdcMnCellProfileUeCfg=Base is created automatically when parent MO instance is created, unless created manually in same transaction. Attributes prefUeGroupList, ueGroupList, and ueConfGroupList must be empty in instance NrdcMnCellProfileUeCfg=Base but cannot all be empty in any other instance of NrdcMnCellProfileUeCfg under same parent NrdcMnCellProfile instance. Only applicable to Low-Band and Mid-Band cells. Precondition: Instance NrdcMnCellProfileUeCfg=Base can only be created in same transaction as parent MO instance and cannot be deleted unless parent MO instance is deleted. Other instances can be created and deleted at any time. Maximum 7 NrdcMnCellProfileUeCfg instances, with RDN different from Base, can be created under parent MO instance.";
      key "nrdcMnCellProfileUeCfgId";
      leaf nrdcMnCellProfileUeCfgId {
        type leafref {
          path "../attributes/nrdcMnCellProfileUeCfgId";
        }
      }
      container attributes {
        uses NrdcMnCellProfileUeCfg-attributes;
      }
    }
  }

  augment "/emael:ManagedElement/GNBCUCPFunction/NrdcSnTermination" {
    list NrdcSnTerminationUeCfg {
      description "Additional definitions from MOM:min/max-elements:0/32; UE configuration of Secondary Node termination for NR-DC. Instance NrdcSnTerminationUeCfg=Base is created automatically when parent MO instance is created, unless created manually in same transaction. Attributes prefUeGroupList, ueGroupList and ueConfGroupList must be empty in instance NrdcSnTerminationUeCfg=Base but cannot all be empty in any other instance of NrdcSnTerminationUeCfg under same parent NrdcSnTermination instance. Precondition: Instance NrdcSnTerminationUeCfg=Base can only be created in same transaction as parent MO instance and cannot be deleted unless parent MO instance is deleted. Other instances can be created and deleted at any time. Maximum 31 NrdcSnTerminationUeCfg instances, with RDN different from Base, can be created under parent MO instance.";
      key "nrdcSnTerminationUeCfgId";
      leaf nrdcSnTerminationUeCfgId {
        type leafref {
          path "../attributes/nrdcSnTerminationUeCfgId";
        }
      }
      container attributes {
        uses NrdcSnTerminationUeCfg-attributes;
      }
    }
  }

  augment "/emael:ManagedElement/GNBCUCPFunction/TrafficOffload/OffloadCellProfile" {
    list OffloadCellProfileUeCfg {
      description "Additional definitions from MOM:min/max-elements:0/32; Traffic offload profile, UE configuration group. Attributes are used on cell level. Instance OffloadCellProfileUeCfg=Base is created automatically when parent MO instance is created, unless created manually in same transaction. Attributes prefUeGroupList, ueGroupList and ueConfGroupList must be empty in instance OffloadCellProfileUeCfg=Base but cannot all be empty in any other instance of OffloadCellProfileUeCfg under same parent OffloadCellProfile instance. Precondition: Instance OffloadCellProfileUeCfg=Base can only be created in same transaction as parent MO instance and cannot be deleted unless parent MO instance is deleted. Other instances can be created and deleted at any time. Maximum 31 OffloadCellProfileUeCfg instances, with RDN different from Base, can be created under parent MO instance.";
      key "offloadCellProfileUeCfgId";
      leaf offloadCellProfileUeCfgId {
        type leafref {
          path "../attributes/offloadCellProfileUeCfgId";
        }
      }
      container attributes {
        uses OffloadCellProfileUeCfg-attributes;
      }
    }
  }

  augment "/emael:ManagedElement/GNBCUCPFunction/TrafficOffload/OffloadEUtranFreqRelProfile" {
    list OffloadEUtranFreqRelProfileUeCfg {
      description "Additional definitions from MOM:min/max-elements:0/32; Traffic offload profile, UE configuration group. Attributes are used on NR frequency relation level. Instance OffloadEUtranFreqRelProfileUeCfg=Base is created automatically when parent MO instance is created, unless created manually in same transaction. Attributes prefUeGroupList, ueGroupList and ueConfGroupList must be empty in instance OffloadEUtranFreqRelProfileUeCfg=Base but cannot all be empty in any other instance of OffloadEUtranFreqRelProfileUeCfg under same parent OffloadEUtranFreqRelProfile instance. Precondition: Instance OffloadEUtranFreqRelProfileUeCfg=Base can only be created in same transaction as parent MO instance and cannot be deleted unless parent MO instance is deleted. Other instances can be created and deleted at any time. Maximum 31 OffloadEUtranFreqRelProfileUeCfg instances, with RDN different from Base, can be created under parent MO instance.";
      key "offloadEUtranFreqRelProfileUeCfgId";
      leaf offloadEUtranFreqRelProfileUeCfgId {
        type leafref {
          path "../attributes/offloadEUtranFreqRelProfileUeCfgId";
        }
      }
      container attributes {
        uses OffloadEUtranFreqRelProfileUeCfg-attributes;
      }
    }
  }

  augment "/emael:ManagedElement/GNBCUCPFunction/TrafficOffload/OffloadNrFreqRelProfile" {
    list OffloadNrFreqRelProfileUeCfg {
      description "Additional definitions from MOM:min/max-elements:0/32; Traffic offload profile, UE configuration group. Attributes are used on NR frequency relation level. Instance OffloadNrFreqRelProfileUeCfg=Base is created automatically when parent MO instance is created, unless created manually in same transaction. Attributes prefUeGroupList, ueGroupList and ueConfGroupList must be empty in instance OffloadNrFreqRelProfileUeCfg=Base but cannot all be empty in any other instance of OffloadNrFreqRelProfileUeCfg under same parent OffloadNrFreqRelProfile instance. Precondition: Instance OffloadNrFreqRelProfileUeCfg=Base can only be created in same transaction as parent MO instance and cannot be deleted unless parent MO instance is deleted. Other instances can be created and deleted at any time. Maximum 31 OffloadNrFreqRelProfileUeCfg instances, with RDN different from Base, can be created under parent MO instance.";
      key "offloadNrFreqRelProfileUeCfgId";
      leaf offloadNrFreqRelProfileUeCfgId {
        type leafref {
          path "../attributes/offloadNrFreqRelProfileUeCfgId";
        }
      }
      container attributes {
        uses OffloadNrFreqRelProfileUeCfg-attributes;
      }
    }
  }

  augment "/emael:ManagedElement/GNBCUCPFunction/PciHandling/PciConflictEUtran" {
    list PciConflictEUtranUeCfg {
      description "Additional definitions from MOM:min/max-elements:0/32; UE configuration of E-UTRAN PCI conflict handling functions. Instance PciConflictEUtranUeCfg=Base is created automatically when parent MO instance is created, unless created manually in same transaction. Attributes prefUeGroupList, ueGroupList and ueConfGroupList must be empty in instance PciConflictEUtranUeCfg=Base but cannot all be empty in any other instance of PciConflictEUtranUeCfg under same parent PciConflictEUtran instance. Precondition: Instance PciConflictEUtranUeCfg=Base can only be created in same transaction as parent MO instance and cannot be deleted unless parent MO instance is deleted. Other instances can be created and deleted at any time. Maximum 31 PciConflictEUtranUeCfg instances, with RDN different from Base, can be created under parent MO instance.";
      key "pciConflictEUtranUeCfgId";
      leaf pciConflictEUtranUeCfgId {
        type leafref {
          path "../attributes/pciConflictEUtranUeCfgId";
        }
      }
      container attributes {
        uses PciConflictEUtranUeCfg-attributes;
      }
    }
  }

  augment "/emael:ManagedElement/GNBCUCPFunction/PciHandling/PciConflictNR" {
    list PciConflictNRUeCfg {
      description "Additional definitions from MOM:min/max-elements:0/32; UE configuration of NR PCI conflict handling functions. Instance PciConflictNRUeCfg=Base is created automatically when parent MO instance is created, unless created manually in same transaction. Attributes prefUeGroupList, ueGroupList and ueConfGroupList must be empty in instance PciConflictNRUeCfg=Base but cannot all be empty in any other instance of PciConflictNRUeCfg under same parent PciConflictNR instance. Precondition: Instance PciConflictNRUeCfg=Base can only be created in same transaction as parent MO instance and cannot be deleted unless parent MO instance is deleted. Other instances can be created and deleted at any time. Maximum 31 PciConflictNRUeCfg instances, with RDN different from Base, can be created under parent MO instance.";
      key "pciConflictNRUeCfgId";
      leaf pciConflictNRUeCfgId {
        type leafref {
          path "../attributes/pciConflictNRUeCfgId";
        }
      }
      container attributes {
        uses PciConflictNRUeCfg-attributes;
      }
    }
  }

  augment "/emael:ManagedElement/GNBCUCPFunction/PciHandling" {
    list PciConflictEUtran {
      description "Additional definitions from MOM:min/max-elements:0/1; Configuration for finding cells suspicious of PCI conflict and creation of cell relation object. Instance PciConflictEUtran=1 is created automatically when parent MO instance is created, unless created manually in same transaction. The RDN of this MO must be PciConflictEUtran=1. Precondition: Instance PciConflictEUtran=1 can only be created in same transaction as parent MO instance and cannot be deleted unless parent MO instance is deleted.";
      key "pciConflictEUtranId";
      leaf pciConflictEUtranId {
        type leafref {
          path "../attributes/pciConflictEUtranId";
        }
      }
      container attributes {
        uses PciConflictEUtran-attributes;
      }
    }
  }

  augment "/emael:ManagedElement/GNBCUCPFunction/PciHandling" {
    list PciConflictNR {
      description "Additional definitions from MOM:min/max-elements:0/1; Configuration for finding cells suspicious of PCI conflict and creation of cell relation object. Instance PciConflictNR=1 is created automatically when parent MO instance is created, unless created manually in same transaction. The RDN of this MO must be PciConflictNR=1. Precondition: Instance PciConflictNR=1 can only be created in same transaction as parent MO instance and cannot be deleted unless parent MO instance is deleted.";
      key "pciConflictNRId";
      leaf pciConflictNRId {
        type leafref {
          path "../attributes/pciConflictNRId";
        }
      }
      container attributes {
        uses PciConflictNR-attributes;
      }
    }
  }

  augment "/emael:ManagedElement/GNBCUCPFunction/PeriodicUeMeas" {
    list PuemCellProfile {
      description "Additional definitions from MOM:min/max-elements:0/unbounded; Periodic UE measurement profile for cell level. Instance PuemCellProfile=Default is created automatically when parent MO instance is created, unless created manually in same transaction. NRCellCU::puemCellProfileRef is automatically set to PuemCellProfile=Default instance, unless manually set to refer to another MO instance. Precondition: Instance PuemCellProfile=Default can only be created in same transaction as parent MO instance and cannot be deleted unless parent MO instance is deleted. Other instances can be created and deleted at any time.";
      key "puemCellProfileId";
      leaf puemCellProfileId {
        type leafref {
          path "../attributes/puemCellProfileId";
        }
      }
      container attributes {
        uses PuemCellProfile-attributes;
      }
    }
  }

  augment "/emael:ManagedElement/GNBCUCPFunction/PmUeMeas" {
    list PmUeIntraFreqCellProfile {
      description "Additional definitions from MOM:min/max-elements:0/11; Profile for PM intra-frequency UE measurements. Instance PmUeIntraFreqCellProfile=Default is created automatically when parent MO instance is created, unless created manually in same transaction. NRCellCU::pmUeIntraFreqCellProfileRef is automatically set to PmUeIntraFreqCellProfile=Default instance, unless manually set to refer to another MO instance. Precondition: Instance PmUeIntraFreqCellProfile=Default can only be created in same transaction as parent MO instance and cannot be deleted unless parent MO instance is deleted. Other instances can be created and deleted at any time. Maximum 10 PmUeIntraFreqCellProfile instances, with RDN different from Default, can be created under parent MO instance.";
      key "pmUeIntraFreqCellProfileId";
      leaf pmUeIntraFreqCellProfileId {
        type leafref {
          path "../attributes/pmUeIntraFreqCellProfileId";
        }
      }
      container attributes {
        uses PmUeIntraFreqCellProfile-attributes;
      }
    }
  }

  augment "/emael:ManagedElement/GNBCUCPFunction/PeriodicUeMeas/PuemCellProfile" {
    list PuemCellProfileUeCfg {
      description "Additional definitions from MOM:min/max-elements:0/32; Periodic UE measurement profile for UE configuration group. Applies to UEs configured for periodic UE measurement. Instance PuemCellProfileUeCfg=Base is created automatically when parent MO instance is created, unless created manually in same transaction. Attributes prefUeGroupList, ueGroupList and ueConfGroupList must be empty in instance PuemCellProfileUeCfg=Base but cannot all be empty in any other instance of PuemCellProfileUeCfg under same parent PuemCellProfile instance. Precondition: Instance PuemCellProfileUeCfg=Base can only be created in same transaction as parent MO instance and cannot be deleted unless parent MO instance is deleted. Other instances can be created and deleted at any time. Maximum 31 PuemCellProfileUeCfg instances, with RDN different from Base, can be created under parent MO instance.";
      key "puemCellProfileUeCfgId";
      leaf puemCellProfileUeCfgId {
        type leafref {
          path "../attributes/puemCellProfileUeCfgId";
        }
      }
      container attributes {
        uses PuemCellProfileUeCfg-attributes;
      }
    }
  }

  augment "/emael:ManagedElement/GNBCUCPFunction/RelaxedRrmMeas" {
    list RelaxedRrmMeasCellProfile {
      description "Additional definitions from MOM:min/max-elements:0/unbounded; Profile for configuration of relaxed RRM measurements.";
      key "relaxedRrmMeasCellProfileId";
      leaf relaxedRrmMeasCellProfileId {
        type leafref {
          path "../attributes/relaxedRrmMeasCellProfileId";
        }
      }
      container attributes {
        uses RelaxedRrmMeasCellProfile-attributes;
      }
    }
  }

  augment "/emael:ManagedElement/GNBCUCPFunction/ResourcePartitions/ResourcePartition" {
    list ResourcePartitionMember {
      description "Additional definitions from MOM:min/max-elements:0/36; Set of member information of resource partition.";
      key "resourcePartitionMemberId";
      leaf resourcePartitionMemberId {
        type leafref {
          path "../attributes/resourcePartitionMemberId";
        }
      }
      container attributes {
        uses ResourcePartitionMember-attributes;
      }
    }
  }

  augment "/emael:ManagedElement/GNBCUCPFunction/ResourcePartitions" {
    list ResourcePartition {
      description "Additional definitions from MOM:min/max-elements:0/36; Combination of attributes specifying in which resource partition a UE is included.";
      key "resourcePartitionId";
      leaf resourcePartitionId {
        type leafref {
          path "../attributes/resourcePartitionId";
        }
      }
      container attributes {
        uses ResourcePartition-attributes;
      }
    }
  }

  augment "/emael:ManagedElement/GNBCUCPFunction/UeCC/Rohc" {
    list RohcUeCfg {
      description "Additional definitions from MOM:min/max-elements:0/8; Configuration of Robust Header Compression feature for UE groups. Instance RohcUeCfg=Base is created automatically when parent MO instance is created, unless created manually in same transaction. Each UE configuration group identifier can only be defined in one ueConfGroupList among RohcUeCfg instances contained under parent Rohc instance. Any combination of one UE group identifier in ueGroupList and one preference UE group identifier in prefUeGroupList must be unique among RohcUeCfg instances contained under parent Rohc instance. Attributes prefUeGroupList, ueGroupList, and ueConfGroupList must be empty in instance RohcUeCfg=Base but cannot all be empty in any other instance of RohcUeCfg. Precondition: Instance RohcUeCfg=Base can only be created in same transaction as parent MO instance and cannot be deleted unless parent MO instance is deleted. Other instances can be created and deleted at any time. Maximum 7 RohcUeCfg instances, with RDN different from Base, can be created under parent MO instance.";
      key "rohcUeCfgId";
      leaf rohcUeCfgId {
        type leafref {
          path "../attributes/rohcUeCfgId";
        }
      }
      container attributes {
        uses RohcUeCfg-attributes;
      }
    }
  }

  augment "/emael:ManagedElement/GNBCUCPFunction/UeCC/Rrc" {
    list RrcUeCfg {
      description "Additional definitions from MOM:min/max-elements:0/8; Configuration of RRC UE groups. Instance RrcUeCfg=Base is created automatically when parent MO instance is created, unless created manually in same transaction. Attributes prefUeGroupList, ueGroupList and ueConfGroupList must be empty in instance RrcUeCfg=Base but cannot all be empty in any other instance of RrcUeCfg under same parent RrcInactiveProfile instance. Precondition: Instance RrcUeCfg=Base can only be created in same transaction as parent MO instance and cannot be deleted unless parent MO instance is deleted. Other instances can be created and deleted at any time. Maximum 7 RrcUeCfg instances, with RDN different from Base, can be created under parent MO instance.";
      key "rrcUeCfgId";
      leaf rrcUeCfgId {
        type leafref {
          path "../attributes/rrcUeCfgId";
        }
      }
      container attributes {
        uses RrcUeCfg-attributes;
      }
    }
  }

  augment "/emael:ManagedElement/GNBCUCPFunction/UeCC/RrcInactiveProfile" {
    list RrcInactiveProfileUeCfg {
      description "Additional definitions from MOM:min/max-elements:0/8; Configuration of RRC inactive profile for UE groups. Instance RrcInactiveProfileUeCfg=Base is created automatically when parent MO instance is created, unless created manually in same transaction. Attributes prefUeGroupList, ueGroupList and ueConfGroupList must be empty in instance RrcInactiveProfileUeCfg=Base but cannot all be empty in any other instance of RrcInactiveProfileUeCfg under same parent RrcInactiveProfile instance. Precondition: Instance RrcInactiveProfileUeCfg=Base can only be created in same transaction as parent MO instance and cannot be deleted unless parent MO instance is deleted. Other instances can be created and deleted at any time. Maximum 7 RrcInactiveProfileUeCfg instances, with RDN different from Base, can be created under parent MO instance.";
      key "rrcInactiveProfileUeCfgId";
      leaf rrcInactiveProfileUeCfgId {
        type leafref {
          path "../attributes/rrcInactiveProfileUeCfgId";
        }
      }
      container attributes {
        uses RrcInactiveProfileUeCfg-attributes;
      }
    }
  }

  augment "/emael:ManagedElement/GNBCUCPFunction/TermPointToAmf" {
    list TnlAssociation {
      description "Additional definitions from MOM:min/max-elements:0/32;systemCreated; Transport Network Layer association between gNodeB and AMF. Created when new SCTP association is successfully established between gNodeB and AMF. Deleted when SCTP association removal is ordered by AMF or when NG-C connection between gNodeB and AMF is released. The RDN of this MO is TnlAssociation=[Remote Port]_[Remote IP]. Example: TnlAssociation=38412_2001:0db8:85a3:0000:0000:8a2e:0370:7334. Length of RDN value is up to 45 characters. Instance can be created without a preceding user-initiated transaction.";
      key "tnlAssociationId";
      leaf tnlAssociationId {
        type leafref {
          path "../attributes/tnlAssociationId";
        }
      }
      container attributes {
        uses TnlAssociation-attributes;
      }
    }
  }

  augment "/emael:ManagedElement/GNBCUCPFunction/TimeSchedulingGroup" {
    list TimeSchedulingWindow {
      description "Additional definitions from MOM:min/max-elements:0/30; Configuration of time scheduling window. In addition to time scheduling configuration, it also includes a reference to EpBoosterCellProfile instance for cell sleep configuration.";
      key "timeSchedulingWindowId";
      leaf timeSchedulingWindowId {
        type leafref {
          path "../attributes/timeSchedulingWindowId";
        }
      }
      container attributes {
        uses TimeSchedulingWindow-attributes;
      }
    }
  }

  augment "/emael:ManagedElement/GNBCUCPFunction/TrafficSteering/TrStPSCellNrFreqRelProfile" {
    list TrStPSCellNrFreqRelProfileUeCfg {
      description "Additional definitions from MOM:min/max-elements:0/32; Traffic steering function for PSCell in NR EN-DC, UE configuration group. Applicable to UEs that use this cell as PSCell in NR EN-DC. Attributes are used on NR frequency relation level. Instance TrStPSCellNrFreqRelProfileUeCfg=Base is created automatically when parent MO instance is created, unless created manually in same transaction. Attributes prefUeGroupList, ueGroupList and ueConfGroupList must be empty in instance TrStPSCellNrFreqRelProfileUeCfg=Base but cannot all be empty in any other instance of TrStPSCellNrFreqRelProfileUeCfg under same parent TrStPSCellNrFreqRelProfile instance. Precondition: Instance TrStPSCellNrFreqRelProfileUeCfg=Base can only be created in same transaction as parent MO instance and cannot be deleted unless parent MO instance is deleted. Other instances can be created and deleted at any time. Maximum 31 TrStPSCellNrFreqRelProfileUeCfg instances, with RDN different from Base, can be created under parent MO instance.";
      key "trStPSCellNrFreqRelProfileUeCfgId";
      leaf trStPSCellNrFreqRelProfileUeCfgId {
        type leafref {
          path "../attributes/trStPSCellNrFreqRelProfileUeCfgId";
        }
      }
      container attributes {
        uses TrStPSCellNrFreqRelProfileUeCfg-attributes;
      }
    }
  }

  augment "/emael:ManagedElement/GNBCUCPFunction/TrafficSteering/TrStPSCellProfile" {
    list TrStPSCellProfileUeCfg {
      description "Additional definitions from MOM:min/max-elements:0/32; Traffic steering function for PSCell in EN-DC, UE configuration group. Applies to UEs that use this cell as PSCell in EN-DC. Attributes are used on cell level. Instance TrStPSCellProfileUeCfg=Base is created automatically when parent MO instance is created, unless created manually in same transaction. Attributes prefUeGroupList, ueGroupList and ueConfGroupList must be empty in instance TrStPSCellProfileUeCfg=Base but cannot all be empty in any other instance of TrStPSCellProfileUeCfg under same parent TrStPSCellProfile instance. Precondition: Instance TrStPSCellProfileUeCfg=Base can only be created in same transaction as parent MO instance and cannot be deleted unless parent MO instance is deleted. Other instances can be created and deleted at any time. Maximum 31 TrStPSCellProfileUeCfg instances, with RDN different from Base, can be created under parent MO instance.";
      key "trStPSCellProfileUeCfgId";
      leaf trStPSCellProfileUeCfgId {
        type leafref {
          path "../attributes/trStPSCellProfileUeCfgId";
        }
      }
      container attributes {
        uses TrStPSCellProfileUeCfg-attributes;
      }
    }
  }

  augment "/emael:ManagedElement/GNBCUCPFunction/TrafficSteering/TrStSaCellProfile" {
    list TrStSaCellProfileUeCfg {
      description "Additional definitions from MOM:min/max-elements:0/32; Traffic steering function for PCell and SCells in NR Standalone, UE configuration group. Applicable to UEs that use this cell as PCell in NR Standalone. Attributes are used on cell level. Instance TrStSaCellProfileUeCfg=Base is created automatically when parent MO instance is created, unless created manually in same transaction. Attributes prefUeGroupList, ueGroupList and ueConfGroupList must be empty in instance TrStSaCellProfileUeCfg=Base but cannot all be empty in any other instance of TrStSaCellProfileUeCfg under same parent TrStSaCellProfile instance. Precondition: Instance TrStSaCellProfileUeCfg=Base can only be created in same transaction as parent MO instance and cannot be deleted unless parent MO instance is deleted. Other instances can be created and deleted at any time. Maximum 31 TrStSaCellProfileUeCfg instances, with RDN different from Base, can be created under parent MO instance.";
      key "trStSaCellProfileUeCfgId";
      leaf trStSaCellProfileUeCfgId {
        type leafref {
          path "../attributes/trStSaCellProfileUeCfgId";
        }
      }
      container attributes {
        uses TrStSaCellProfileUeCfg-attributes;
      }
    }
  }

  augment "/emael:ManagedElement/GNBCUCPFunction/TrafficSteering/TrStSaEUtranFreqRelProfile" {
    list TrStSaEUtranFreqRelProfileUeCfg {
      description "Additional definitions from MOM:min/max-elements:0/32; Traffic steering function for PCell NR Standalone, UE configuration group. Applicable to UEs that use this cell as PCell in NR Standalone. Attributes are used on E-UTRAN frequency relation level. Instance TrStSaEUtranFreqRelProfileUeCfg=Base is created automatically when parent MO instance is created, unless created manually in same transaction. Attributes prefUeGroupList, ueGroupList and ueConfGroupList must be empty in instance TrStSaEUtranFreqRelProfileUeCfg=Base but cannot all be empty in any other instance of TrStSaEUtranFreqRelProfileUeCfg under same parent TrStSaEUtranFreqRelProfile instance. Precondition: Instance TrStSaEUtranFreqRelProfileUeCfg=Base can only be created in same transaction as parent MO instance and cannot be deleted unless parent MO instance is deleted. Other instances can be created and deleted at any time. Maximum 31 TrStSaEUtranFreqRelProfileUeCfg instances, with RDN different from Base, can be created under parent MO instance.";
      key "trStSaEUtranFreqRelProfileUeCfgId";
      leaf trStSaEUtranFreqRelProfileUeCfgId {
        type leafref {
          path "../attributes/trStSaEUtranFreqRelProfileUeCfgId";
        }
      }
      container attributes {
        uses TrStSaEUtranFreqRelProfileUeCfg-attributes;
      }
    }
  }

  augment "/emael:ManagedElement/GNBCUCPFunction/TrafficSteering/TrStSaNrFreqRelProfile" {
    list TrStSaNrFreqRelProfileUeCfg {
      description "Additional definitions from MOM:min/max-elements:0/32; Traffic steering function for PCell and SCells in NR Standalone, UE configuration group. Applicable to UEs that use this cell as PCell in NR Standalone. Attributes are used on NR frequency relation level. Instance TrStSaNrFreqRelProfileUeCfg=Base is created automatically when parent MO instance is created, unless created manually in same transaction. Attributes prefUeGroupList, ueGroupList and ueConfGroupList must be empty in instance TrStSaNrFreqRelProfileUeCfg=Base but cannot all be empty in any other instance of TrStSaNrFreqRelProfileUeCfg under same parent TrStSaNrFreqRelProfile instance. Precondition: Instance TrStSaNrFreqRelProfileUeCfg=Base can only be created in same transaction as parent MO instance and cannot be deleted unless parent MO instance is deleted. Other instances can be created and deleted at any time. Maximum 31 TrStSaNrFreqRelProfileUeCfg instances, with RDN different from Base, can be created under parent MO instance.";
      key "trStSaNrFreqRelProfileUeCfgId";
      leaf trStSaNrFreqRelProfileUeCfgId {
        type leafref {
          path "../attributes/trStSaNrFreqRelProfileUeCfgId";
        }
      }
      container attributes {
        uses TrStSaNrFreqRelProfileUeCfg-attributes;
      }
    }
  }

  augment "/emael:ManagedElement/GNBCUCPFunction/TrafficOffload" {
    list OffloadCellProfile {
      description "Additional definitions from MOM:min/max-elements:0/unbounded; Traffic offload profile. Attributes are used on cell level. Instance OffloadCellProfile=Default is created automatically when parent MO instance is created, unless created manually in same transaction. NRCellCU::offloadCellProfileRef is automatically set to OffloadCellProfile=Default instance, unless manually set to refer to another MO instance. Precondition: Instance OffloadCellProfile=Default can only be created in same transaction as parent MO instance and cannot be deleted unless parent MO instance is deleted. Other instances can be created and deleted at any time.";
      key "offloadCellProfileId";
      leaf offloadCellProfileId {
        type leafref {
          path "../attributes/offloadCellProfileId";
        }
      }
      container attributes {
        uses OffloadCellProfile-attributes;
      }
    }
  }

  augment "/emael:ManagedElement/GNBCUCPFunction/TrafficOffload" {
    list OffloadEUtranFreqRelProfile {
      description "Additional definitions from MOM:min/max-elements:0/unbounded; Traffic offload profile. Attributes are used on EUtran frequency relation level. Instance OffloadEUtranFreqRelProfile=Default is created automatically when parent MO instance is created, unless created manually in same transaction. EUtranFreqRelation::offloadEUtranFreqRelProfileRef is automatically set to OffloadEUtranFreqRelProfile=Default instance, unless manually set to refer to another MO instance. Precondition: Instance OffloadEUtranFreqRelProfile=Default can only be created in same transaction as parent MO instance and cannot be deleted unless parent MO instance is deleted. Other instances can be created and deleted at any time.";
      key "offloadEUtranFreqRelProfileId";
      leaf offloadEUtranFreqRelProfileId {
        type leafref {
          path "../attributes/offloadEUtranFreqRelProfileId";
        }
      }
      container attributes {
        uses OffloadEUtranFreqRelProfile-attributes;
      }
    }
  }

  augment "/emael:ManagedElement/GNBCUCPFunction/TrafficOffload" {
    list OffloadNrFreqRelProfile {
      description "Additional definitions from MOM:min/max-elements:0/unbounded; Traffic offload profile. Attributes are used on NR frequency relation level. Instance OffloadNrFreqRelProfile=Default is created automatically when parent MO instance is created, unless created manually in same transaction. NRFreqRelation::offloadNrFreqRelProfileRef is automatically set to OffloadNrFreqRelProfile=Default instance, unless manually set to refer to another MO instance. Precondition: Instance OffloadNrFreqRelProfile=Default can only be created in same transaction as parent MO instance and cannot be deleted unless parent MO instance is deleted. Other instances can be created and deleted at any time.";
      key "offloadNrFreqRelProfileId";
      leaf offloadNrFreqRelProfileId {
        type leafref {
          path "../attributes/offloadNrFreqRelProfileId";
        }
      }
      container attributes {
        uses OffloadNrFreqRelProfile-attributes;
      }
    }
  }

  augment "/emael:ManagedElement/GNBCUCPFunction/TrafficSteering" {
    list TrStPSCellNrFreqRelProfile {
      description "Additional definitions from MOM:min/max-elements:0/unbounded; Traffic steering function for PSCell in NR EN-DC. Applicable to UEs that use this cell as PSCell in NR EN-DC. Attributes are used on NR frequency relation level. Instance TrStPSCellNrFreqRelProfile=Default is created automatically when parent MO instance is created, unless created manually in same transaction. NRFreqRelation::trStPSCellNrFreqRelProfileRef is automatically set to TrStPSCellNrFreqRelProfile=Default instance, unless manually set to refer to another MO instance. Precondition: Instance TrStPSCellNrFreqRelProfile=Default can only be created in same transaction as parent MO instance and cannot be deleted unless parent MO instance is deleted. Other instances can be created and deleted at any time.";
      key "trStPSCellNrFreqRelProfileId";
      leaf trStPSCellNrFreqRelProfileId {
        type leafref {
          path "../attributes/trStPSCellNrFreqRelProfileId";
        }
      }
      container attributes {
        uses TrStPSCellNrFreqRelProfile-attributes;
      }
    }
  }

  augment "/emael:ManagedElement/GNBCUCPFunction/TrafficSteering" {
    list TrStPSCellProfile {
      description "Additional definitions from MOM:min/max-elements:0/unbounded; Traffic steering function for PSCell in EN-DC. Applies to UEs that use this cell as PSCell in EN-DC. Attributes are used on cell level. Instance TrStPSCellProfile=Default is created automatically when parent MO instance is created, unless created manually in same transaction. NRCellCU::trStPSCellProfileRef is automatically set to TrStPSCellProfile=Default instance, unless manually set to refer to another MO instance. Precondition: Instance TrStPSCellProfile=Default can only be created in same transaction as parent MO instance and cannot be deleted unless parent MO instance is deleted. Other instances can be created and deleted at any time.";
      key "trStPSCellProfileId";
      leaf trStPSCellProfileId {
        type leafref {
          path "../attributes/trStPSCellProfileId";
        }
      }
      container attributes {
        uses TrStPSCellProfile-attributes;
      }
    }
  }

  augment "/emael:ManagedElement/GNBCUCPFunction/TrafficSteering" {
    list TrStSaCellProfile {
      description "Additional definitions from MOM:min/max-elements:0/unbounded; Traffic steering function for PCell and SCells in NR Standalone. Applicable to UEs that use this cell as PCell in NR Standalone. Attributes are used on cell level. Instance TrStSaCellProfile=Default is created automatically when parent MO instance is created, unless created manually in same transaction. NRCellCU::trStSaCellProfileRef is automatically set to TrStSaCellProfile=Default instance, unless manually set to refer to another MO instance. Precondition: Instance TrStSaCellProfile=Default can only be created in same transaction as parent MO instance and cannot be deleted unless parent MO instance is deleted. Other instances can be created and deleted at any time.";
      key "trStSaCellProfileId";
      leaf trStSaCellProfileId {
        type leafref {
          path "../attributes/trStSaCellProfileId";
        }
      }
      container attributes {
        uses TrStSaCellProfile-attributes;
      }
    }
  }

  augment "/emael:ManagedElement/GNBCUCPFunction/TrafficSteering" {
    list TrStSaEUtranFreqRelProfile {
      description "Additional definitions from MOM:min/max-elements:0/unbounded; Traffic steering function for PCell in NR Standalone. Applicable to UEs that use this cell as PCell in NR Standalone. Attributes are used on E-UTRAN frequency relation level. Instance TrStSaEUtranFreqRelProfile=Default is created automatically when parent MO instance is created, unless created manually in same transaction. EUtranFreqRelation::trStSaEUtranFreqRelProfileRef is automatically set to TrStSaEUtranFreqRelProfile=Default instance, unless manually set to refer to another MO instance. Precondition: Instance TrStSaEUtranFreqRelProfile=Default can only be created in same transaction as parent MO instance and cannot be deleted unless parent MO instance is deleted. Other instances can be created and deleted at any time.";
      key "trStSaEUtranFreqRelProfileId";
      leaf trStSaEUtranFreqRelProfileId {
        type leafref {
          path "../attributes/trStSaEUtranFreqRelProfileId";
        }
      }
      container attributes {
        uses TrStSaEUtranFreqRelProfile-attributes;
      }
    }
  }

  augment "/emael:ManagedElement/GNBCUCPFunction/TrafficSteering" {
    list TrStSaNrFreqRelProfile {
      description "Additional definitions from MOM:min/max-elements:0/unbounded; Traffic steering function for PCell and SCells in NR Standalone. Applicable to UEs that use this cell as PCell in NR Standalone. Attributes are used on NR frequency relation level. Instance TrStSaNrFreqRelProfile=Default is created automatically when parent MO instance is created, unless created manually in same transaction. NRFreqRelation::trStSaNrFreqRelProfileRef is automatically set to TrStSaNrFreqRelProfile=Default instance, unless manually set to refer to another MO instance. Precondition: Instance TrStSaNrFreqRelProfile=Default can only be created in same transaction as parent MO instance and cannot be deleted unless parent MO instance is deleted. Other instances can be created and deleted at any time.";
      key "trStSaNrFreqRelProfileId";
      leaf trStSaNrFreqRelProfileId {
        type leafref {
          path "../attributes/trStSaNrFreqRelProfileId";
        }
      }
      container attributes {
        uses TrStSaNrFreqRelProfile-attributes;
      }
    }
  }

  augment "/emael:ManagedElement/GNBCUCPFunction/AdmissionControl/Uac" {
    list UacProfile {
      description "Additional definitions from MOM:min/max-elements:0/12; Configuration profile for NR Unified Access Control. Instance UacProfile=Default is created automatically when parent MO instance is created, unless created manually in same transaction. NRCellCU::uacProfileRef is automatically set to UacProfile=Default instance, unless manually set to refer to another MO instance. Precondition: Instance UacProfile=Default can only be created in same transaction as parent MO instance and cannot be deleted unless parent MO instance is deleted. Other instances can be created and deleted at any time. Maximum 11 UacProfile instances, with RDN different from Default, can be created under parent MO instance.";
      key "uacProfileId";
      leaf uacProfileId {
        type leafref {
          path "../attributes/uacProfileId";
        }
      }
      container attributes {
        uses UacProfile-attributes;
      }
    }
  }

  augment "/emael:ManagedElement/GNBCUCPFunction/AdmissionControl/Uac/UacProfile" {
    list BarringGroup {
      description "Additional definitions from MOM:min/max-elements:0/8; Thresholds and parameters for barring group used by NR Unified Access Control. Default values for attributes in this MO are set so that barring triggered by unified access is not sent out in SIB1. Instance BarringGroup=Default is created automatically when parent MO instance is created, unless created manually in same transaction. Precondition: Instance BarringGroup=Default can only be created in same transaction as parent MO instance and cannot be deleted unless parent MO instance is deleted. Other instances can be created and deleted at any time. Maximum 7 BarringGroup instances, with RDN different from Default, can be created under parent MO instance.";
      key "barringGroupId";
      leaf barringGroupId {
        type leafref {
          path "../attributes/barringGroupId";
        }
      }
      container attributes {
        uses BarringGroup-attributes;
      }
    }
  }

  augment "/emael:ManagedElement/GNBCUCPFunction/UeCC/UaiProfile" {
    list UaiProfileUeCfg {
      description "Additional definitions from MOM:min/max-elements:0/8; Configuration of UE Assistance Information profile for UE groups. Instance UaiProfileUeCfg=Base is created automatically when parent MO instance is created, unless created manually in same transaction. Attributes prefUeGroupList, ueGroupList and ueConfGroupList must be empty in instance UaiProfileUeCfg=Base but cannot all be empty in any other instance of UaiProfileUeCfg. Precondition: Instance UaiProfileUeCfg=Base can only be created in same transaction as parent MO instance and cannot be deleted unless parent MO instance is deleted. Other instances can be created and deleted at any time. Maximum 7 UaiProfileUeCfg instances, with RDN different from Base, can be created under parent MO instance.";
      key "uaiProfileUeCfgId";
      leaf uaiProfileUeCfgId {
        type leafref {
          path "../attributes/uaiProfileUeCfgId";
        }
      }
      container attributes {
        uses UaiProfileUeCfg-attributes;
      }
    }
  }

  augment "/emael:ManagedElement/GNBCUCPFunction/UeCovMeas/UcmCellProfile" {
    list UcmCellProfileUeCfg {
      description "Additional definitions from MOM:min/max-elements:0/32; UE coverage measurement configuration group. Instance UcmCellProfileUeCfg=Base is created automatically when parent MO instance is created, unless created manually in same transaction. Each UE configuration group identifier can only be defined in one ueConfGroupList among UcmCellProfileUeCfg instances under parent UcmCellProfile instance. Any combination of one UE group identifier in ueGroupList attribute and one preference UE group identifier in prefUeGroupList must be unique among UcmCellProfileUeCfg instances under parent UcmCellProfile instance. Attributes prefUeGroupList, ueGroupList, and ueConfGroupList must be empty in instance UcmCellProfileUeCfg=Base but cannot all be empty in any other instance of UcmCellProfileUeCfg under same parent UcmCellProfile instance. NRCellCU::ucmCellProfileRef is automatically set to UcmCellProfile=Default instance, unless manually set to refer to another MO instance. Precondition: Instance UcmCellProfileUeCfg=Base can only be created in same transaction as parent MO instance and cannot be deleted unless parent MO instance is deleted. Other instances can be created and deleted at any time. Maximum 31 UcmCellProfileUeCfg instances, with RDN different from Base, can be created under parent MO instance.";
      key "ucmCellProfileUeCfgId";
      leaf ucmCellProfileUeCfgId {
        type leafref {
          path "../attributes/ucmCellProfileUeCfgId";
        }
      }
      container attributes {
        uses UcmCellProfileUeCfg-attributes;
      }
    }
  }

  augment "/emael:ManagedElement/GNBCUCPFunction/UeCC" {
    list CapabilityHandling {
      description "Additional definitions from MOM:min/max-elements:0/1; This is a container for Capability Handling UE Configurations. Instance CapabilityHandling=1 is created automatically when parent MO instance is created, unless created manually in same transaction. The RDN of this MO must be CapabilityHandling=1. Precondition: Instance CapabilityHandling=1 can only be created in same transaction as parent MO instance and cannot be deleted unless parent MO instance is deleted.";
      key "capabilityHandlingId";
      leaf capabilityHandlingId {
        type leafref {
          path "../attributes/capabilityHandlingId";
        }
      }
      container attributes {
        uses CapabilityHandling-attributes;
      }
    }
  }

  augment "/emael:ManagedElement/GNBCUCPFunction/UeCC" {
    list DrbData {
      description "Additional definitions from MOM:min/max-elements:0/8; Data radio bearer user plane profile. Instance DrbData=Default is created automatically when parent MO instance is created, unless created manually in same transaction. If CUCP5qi::drbDataRef is non-empty, attributes from referenced MO instance are used. If CUCP5qi::drbDataRef is empty, attribute default values according to DrbData and DrbDataUeCfg MO class definitions are used. Precondition: Instance DrbData=Default can only be created in same transaction as parent MO instance and cannot be deleted unless parent MO instance is deleted. Other instances can be created and deleted at any time. Maximum 7 DrbData instances, with RDN different from Default, can be created under parent MO instance.";
      key "drbDataId";
      leaf drbDataId {
        type leafref {
          path "../attributes/drbDataId";
        }
      }
      container attributes {
        uses DrbData-attributes;
      }
    }
  }

  augment "/emael:ManagedElement/GNBCUCPFunction/UeCC" {
    list InactivityProfile {
      description "Additional definitions from MOM:min/max-elements:0/1; Inactivity profile used for current UE. Instance InactivityProfile=Default is created automatically when parent MO instance is created, unless created manually in same transaction. Precondition: Instance InactivityProfile=Default can only be created in same transaction as parent MO instance and cannot be deleted unless parent MO instance is deleted.";
      key "inactivityProfileId";
      leaf inactivityProfileId {
        type leafref {
          path "../attributes/inactivityProfileId";
        }
      }
      container attributes {
        uses InactivityProfile-attributes;
      }
    }
  }

  augment "/emael:ManagedElement/GNBCUCPFunction/UeCC" {
    list InitialCg {
      description "Additional definitions from MOM:min/max-elements:0/8; Initial cell group profile. Instance InitialCg=Default is created automatically when parent MO instance is created, unless created manually in same transaction. NRCellCU::endcInitialCgRef and NRCellCU::nrdcInitialCgRef are automatically set to InitialCg=Default instance, unless manually set to refer to another MO instance. Precondition: Instance InitialCg=Default can only be created in same transaction as parent MO instance and cannot be deleted unless parent MO instance is deleted. Other instances can be created and deleted at any time. Maximum 7 InitialCg instance, with RDN different from Default, can be created under parent MO instance.";
      key "initialCgId";
      leaf initialCgId {
        type leafref {
          path "../attributes/initialCgId";
        }
      }
      container attributes {
        uses InitialCg-attributes;
      }
    }
  }

  augment "/emael:ManagedElement/GNBCUCPFunction/UeCC" {
    list Rohc {
      description "Additional definitions from MOM:min/max-elements:0/1; Container class for ROHC configuration classes. Instance Rohc=1 is created automatically when parent MO instance is created, unless created manually in same transaction. The RDN of this MO must be Rohc=1. Precondition: Instance Rohc=1 can only be created in same transaction as parent MO instance and cannot be deleted unless parent MO instance is deleted.";
      key "rohcId";
      leaf rohcId {
        type leafref {
          path "../attributes/rohcId";
        }
      }
      container attributes {
        uses Rohc-attributes;
      }
    }
  }

  augment "/emael:ManagedElement/GNBCUCPFunction/UeCC" {
    list Rrc {
      description "Additional definitions from MOM:min/max-elements:0/1; Container class for RRC UE configuration classes. Instance Rrc=1 is created automatically when parent MO instance is created, unless created manually in same transaction. The RDN of this MO must be Rrc=1. Precondition: Instance Rrc=1 can only be created in same transaction as parent MO instance and cannot be deleted unless parent MO instance is deleted.";
      key "rrcId";
      leaf rrcId {
        type leafref {
          path "../attributes/rrcId";
        }
      }
      container attributes {
        uses Rrc-attributes;
      }
    }
  }

  augment "/emael:ManagedElement/GNBCUCPFunction/UeCC" {
    list RrcInactiveProfile {
      description "Additional definitions from MOM:min/max-elements:0/1; RRC inactive profile used for current UE. Instance RrcInactiveProfile=Default is created automatically when parent MO instance is created, unless created manually in same transaction. The RDN of this MO must be RrcInactiveProfile=Default. Precondition: Instance RrcInactiveProfile=Default can only be created in same transaction as parent MO instance and cannot be deleted unless parent MO instance is deleted.";
      key "rrcInactiveProfileId";
      leaf rrcInactiveProfileId {
        type leafref {
          path "../attributes/rrcInactiveProfileId";
        }
      }
      container attributes {
        uses RrcInactiveProfile-attributes;
      }
    }
  }

  augment "/emael:ManagedElement/GNBCUCPFunction/UeCC" {
    list UaiProfile {
      description "Additional definitions from MOM:min/max-elements:0/1; UE Assistance Information profile for current UE. Instance UaiProfile=Default is created automatically when parent MO instance is created, unless created manually in same transaction. The RDN of this MO must be UaiProfile=Default. Precondition: Instance UaiProfile=Default can only be created in same transaction as parent MO instance and cannot be deleted unless parent MO instance is deleted.";
      key "uaiProfileId";
      leaf uaiProfileId {
        type leafref {
          path "../attributes/uaiProfileId";
        }
      }
      container attributes {
        uses UaiProfile-attributes;
      }
    }
  }

  augment "/emael:ManagedElement/GNBCUCPFunction/UeCC" {
    list UlDataSplit {
      description "Additional definitions from MOM:min/max-elements:0/8; Uplink PDCP data split profile. Instances UlDataSplit=Default_endc and UlDataSplit=Default_nrdc are created automatically when parent MO instance is created, unless created manually in same transaction. CUCP5qi::endcUlDataSplitRef is automatically set to UlDataSplit=Default_endc instance, unless manually set to refer to another MO instance. CUCP5qi::nrdcUlDataSplitRef is automatically set to UlDataSplit=Default_nrdc instance, unless manually set to refer to another MO instance. UlDataSplit=Default_endc and UlDataSplit=Default_nrdc instances are used for DRBs when CUCP5qi instance with matching profile5qi does not exist or feature Service-Adaptive Uplink User Plane Profile is deactivated. Precondition: Instances UlDataSplit=Default_endc and UlDataSplit=Default_nrdc can only be created in same transaction as parent MO instance and cannot be deleted unless parent MO instance is deleted. Other instances can be created and deleted at any time. Maximum 6 UlDataSplit instances, with RDN different from Default_endc and Default_nrdc, can be created under parent MO instance.";
      key "ulDataSplitId";
      leaf ulDataSplitId {
        type leafref {
          path "../attributes/ulDataSplitId";
        }
      }
      container attributes {
        uses UlDataSplit-attributes;
      }
    }
  }

  augment "/emael:ManagedElement/GNBCUCPFunction/UeCovMeas" {
    list UcmCellProfile {
      description "Additional definitions from MOM:min/max-elements:0/unbounded; UE coverage measurement profile for cell level. Instance UcmCellProfile=Default is created automatically when parent MO instance is created, unless created manually in same transaction. Precondition: Instance UcmCellProfile=Default can only be created in same transaction as parent MO instance and cannot be deleted unless parent MO instance is deleted. Other instances can be created and deleted at any time.";
      key "ucmCellProfileId";
      leaf ucmCellProfileId {
        type leafref {
          path "../attributes/ucmCellProfileId";
        }
      }
      container attributes {
        uses UcmCellProfile-attributes;
      }
    }
  }

  augment "/emael:ManagedElement/GNBCUCPFunction/UeCovMeas" {
    list UcmEUtranFreqRelProfile {
      description "Additional definitions from MOM:min/max-elements:0/unbounded; UE coverage measurement attributes used on frequency relation level. Instance UcmEUtranFreqRelProfile=Default is created automatically when parent MO instance is created, unless created manually in same transaction. EUtranFreqRelation::ucmEUtranFreqRelProfileRef is automatically set to UcmEUtranFreqRelProfile=Default instance, unless manually set to refer to another MO instance. Precondition: Instance UcmEUtranFreqRelProfile=Default can only be created in same transaction as parent MO instance and cannot be deleted unless parent MO instance is deleted. Other instances can be created and deleted at any time.";
      key "ucmEUtranFreqRelProfileId";
      leaf ucmEUtranFreqRelProfileId {
        type leafref {
          path "../attributes/ucmEUtranFreqRelProfileId";
        }
      }
      container attributes {
        uses UcmEUtranFreqRelProfile-attributes;
      }
    }
  }

  augment "/emael:ManagedElement/GNBCUCPFunction/UeCovMeas" {
    list UcmNrFreqRelProfile {
      description "Additional definitions from MOM:min/max-elements:0/unbounded; UE coverage measurement attributes used on frequency relation level. Instance UcmNrFreqRelProfile=Default is created automatically when parent MO instance is created, unless created manually in same transaction. NRFreqRelation::ucmNrFreqRelProfileRef is automatically set to UcmNrFreqRelProfile=Default instance, unless manually set to refer to another MO instance. Precondition: Instance UcmNrFreqRelProfile=Default can only be created in same transaction as parent MO instance and cannot be deleted unless parent MO instance is deleted. Other instances can be created and deleted at any time.";
      key "ucmNrFreqRelProfileId";
      leaf ucmNrFreqRelProfileId {
        type leafref {
          path "../attributes/ucmNrFreqRelProfileId";
        }
      }
      container attributes {
        uses UcmNrFreqRelProfile-attributes;
      }
    }
  }

  augment "/emael:ManagedElement/GNBCUCPFunction/UeGroupSelection" {
    list Chipsets {
      description "Additional definitions from MOM:min/max-elements:0/22; A set of chipset identifiers used to define a subset of all UEs.";
      key "chipsetsId";
      leaf chipsetsId {
        type leafref {
          path "../attributes/chipsetsId";
        }
      }
      container attributes {
        uses Chipsets-attributes;
      }
    }
  }

  augment "/emael:ManagedElement/GNBCUCPFunction/UeGroupSelection" {
    list ImeiSvGroups {
      description "Additional definitions from MOM:min/max-elements:0/1; Container class for MO classes defining different IMEISV groups. Instance ImeiSvGroups=1 is created automatically when parent MO instance is created, unless created manually in same transaction. The RDN of this MO must be ImeiSvGroups=1. Precondition: Instance ImeiSvGroups=1 can only be created in same transaction as parent MO instance and cannot be deleted unless parent MO instance is deleted.";
      key "imeiSvGroupsId";
      leaf imeiSvGroupsId {
        type leafref {
          path "../attributes/imeiSvGroupsId";
        }
      }
      container attributes {
        uses ImeiSvGroups-attributes;
      }
    }
  }

  augment "/emael:ManagedElement/GNBCUCPFunction/UeGroupSelection" {
    list ImeiSvs {
      description "Additional definitions from MOM:min/max-elements:0/22; A set of IMEISV groups used to define a subset of all UEs.";
      key "imeiSvsId";
      leaf imeiSvsId {
        type leafref {
          path "../attributes/imeiSvsId";
        }
      }
      container attributes {
        uses ImeiSvs-attributes;
      }
    }
  }

  augment "/emael:ManagedElement/GNBCUCPFunction/UeGroupSelection" {
    list PrefUeGroupSelectionProfile {
      description "Additional definitions from MOM:min/max-elements:0/32; A set of preference UE group selection criteria used to define a subset of all UEs.";
      key "prefUeGroupSelectionProfileId";
      leaf prefUeGroupSelectionProfileId {
        type leafref {
          path "../attributes/prefUeGroupSelectionProfileId";
        }
      }
      container attributes {
        uses PrefUeGroupSelectionProfile-attributes;
      }
    }
  }

  augment "/emael:ManagedElement/GNBCUCPFunction/UeGroupSelection" {
    list UeAdmissionGroupDefinition {
      description "Additional definitions from MOM:min/max-elements:0/32; UE admission group definition.";
      key "ueAdmissionGroupDefinitionId";
      leaf ueAdmissionGroupDefinitionId {
        type leafref {
          path "../attributes/ueAdmissionGroupDefinitionId";
        }
      }
      container attributes {
        uses UeAdmissionGroupDefinition-attributes;
      }
    }
  }

  augment "/emael:ManagedElement/GNBCUCPFunction/UeGroupSelection" {
    list UeGroupSelectionProfile {
      description "Additional definitions from MOM:min/max-elements:0/32; A set of UE group selection criteria used to define a subset of all UEs.";
      key "ueGroupSelectionProfileId";
      leaf ueGroupSelectionProfileId {
        type leafref {
          path "../attributes/ueGroupSelectionProfileId";
        }
      }
      container attributes {
        uses UeGroupSelectionProfile-attributes;
      }
    }
  }

  augment "/emael:ManagedElement/GNBCUCPFunction/UeGroupSelection" {
    list UeMobilityGroupDefinition {
      description "Additional definitions from MOM:min/max-elements:0/32; UE mobility group definition.";
      key "ueMobilityGroupDefinitionId";
      leaf ueMobilityGroupDefinitionId {
        type leafref {
          path "../attributes/ueMobilityGroupDefinitionId";
        }
      }
      container attributes {
        uses UeMobilityGroupDefinition-attributes;
      }
    }
  }

  augment "/emael:ManagedElement/GNBCUCPFunction/UeGroupSelection" {
    list UeServiceGroupDefinition {
      description "Additional definitions from MOM:min/max-elements:0/32; UE service group definition.";
      key "ueServiceGroupDefinitionId";
      leaf ueServiceGroupDefinitionId {
        type leafref {
          path "../attributes/ueServiceGroupDefinitionId";
        }
      }
      container attributes {
        uses UeServiceGroupDefinition-attributes;
      }
    }
  }

  augment "/emael:ManagedElement/GNBCUCPFunction/UeMC" {
    list UeMCCellProfile {
      description "Additional definitions from MOM:min/max-elements:0/unbounded; UE mobility control attributes. The attributes are used on cell level. Instance UeMCCellProfile=Default is created automatically when parent MO instance is created, unless created manually in same transaction. NRCellCU::ueMCCellProfileRef is automatically set to UeMCCellProfile=Default instance, unless manually set to refer to another MO instance. Precondition: Instance UeMCCellProfile=Default can only be created in same transaction as parent MO instance and cannot be deleted unless parent MO instance is deleted. Other instances can be created and deleted at any time.";
      key "ueMCCellProfileId";
      leaf ueMCCellProfileId {
        type leafref {
          path "../attributes/ueMCCellProfileId";
        }
      }
      container attributes {
        uses UeMCCellProfile-attributes;
      }
    }
  }

  augment "/emael:ManagedElement/GNBCUCPFunction/UeMC" {
    list UeMCEUtranFreqRelProfile {
      description "Additional definitions from MOM:min/max-elements:0/unbounded; UE mobility control attributes used on E-UTRAN frequency relation level. Instance UeMCEUtranFreqRelProfile=Default is created automatically when parent MO instance is created, unless created manually in same transaction. EUtranFreqRelation::ueMCEUtranFreqRelProfileRef is automatically set to UeMCEUtranFreqRelProfile=Default instance, unless manually set to refer to another MO instance. Precondition: Instance UeMCEUtranFreqRelProfile=Default can only be created in same transaction as parent MO instance and cannot be deleted unless parent MO instance is deleted. Other instances can be created and deleted at any time.";
      key "ueMCEUtranFreqRelProfileId";
      leaf ueMCEUtranFreqRelProfileId {
        type leafref {
          path "../attributes/ueMCEUtranFreqRelProfileId";
        }
      }
      container attributes {
        uses UeMCEUtranFreqRelProfile-attributes;
      }
    }
  }

  augment "/emael:ManagedElement/GNBCUCPFunction/UeMC" {
    list UeMCNrFreqRelProfile {
      description "Additional definitions from MOM:min/max-elements:0/unbounded; UE mobility control attributes. Attributes are used on NR frequency relation level. Instance UeMCNrFreqRelProfile=Default is created automatically when parent MO instance is created, unless created manually in same transaction. NRFreqRelation::ueMCNrFreqRelProfileRef is automatically set to UeMCNrFreqRelProfile=Default instance, unless manually set to refer to another MO instance. Precondition: Instance UeMCNrFreqRelProfile=Default can only be created in same transaction as parent MO instance and cannot be deleted unless parent MO instance is deleted. Other instances can be created and deleted at any time.";
      key "ueMCNrFreqRelProfileId";
      leaf ueMCNrFreqRelProfileId {
        type leafref {
          path "../attributes/ueMCNrFreqRelProfileId";
        }
      }
      container attributes {
        uses UeMCNrFreqRelProfile-attributes;
      }
    }
  }

  augment "/emael:ManagedElement/GNBCUCPFunction/UeMC" {
    list UeMCUeCfg {
      description "Additional definitions from MOM:min/max-elements:0/32; Mobility control for UE configuration group. Attributes are used on gNodeB level. Instance UeMCUeCfg=Base is created automatically when parent MO instance is created, unless created manually in same transaction. Attributes prefUeGroupList, ueGroupList and ueConfGroupList must be empty in instance UeMCUeCfg=Base but cannot all be empty in any other instance of UeMCUeCfg under same parent MO instance. Precondition: Instance UeMCUeCfg=Base can only be created in same transaction as parent MO instance and cannot be deleted unless parent MO instance is deleted. Other instances can be created and deleted at any time. Maximum 31 UeMCUeCfg instances, with RDN different from Base, can be created under parent MO instance.";
      key "ueMCUeCfgId";
      leaf ueMCUeCfgId {
        type leafref {
          path "../attributes/ueMCUeCfgId";
        }
      }
      container attributes {
        uses UeMCUeCfg-attributes;
      }
    }
  }

  augment "/emael:ManagedElement/GNBCUCPFunction/UeMC/UeMCCellProfile" {
    list UeMCCellProfileUeCfg {
      description "Additional definitions from MOM:min/max-elements:0/32; UE mobility control for UE groups. Instance UeMCCellProfileUeCfg=Base is created automatically when parent MO instance is created, unless created manually in same transaction. Each UE configuration group identifier can only be defined in one ueConfGroupList among UeMCCellProfileUeCfg instances contained under parent UeMCCellProfile instance. Any combination of one UE group identifier in ueGroupList and one preference UE group identifier in prefUeGroupList must be unique among UeMCCellProfileUeCfg instances contained under parent UeMCCellProfile instance. Attributes prefUeGroupList, ueGroupList, and ueConfGroupList must be empty in instance UeMCCellProfileUeCfg=Base but cannot all be empty in any other instance of UeMCCellProfileUeCfg. Precondition: Instance UeMCCellProfileUeCfg=Base can only be created in same transaction as parent MO instance and cannot be deleted unless parent MO instance is deleted. Other instances can be created and deleted at any time. Maximum 31 UeMCCellProfileUeCfg instances, with RDN different from Base, can be created under parent MO instance.";
      key "ueMCCellProfileUeCfgId";
      leaf ueMCCellProfileUeCfgId {
        type leafref {
          path "../attributes/ueMCCellProfileUeCfgId";
        }
      }
      container attributes {
        uses UeMCCellProfileUeCfg-attributes;
      }
    }
  }

  augment "/emael:ManagedElement/GNBCUCPFunction/UeMC/UeMCEUtranFreqRelProfile" {
    list UeMCEUtranFreqRelProfileUeCfg {
      description "Additional definitions from MOM:min/max-elements:0/32; Mobility control for UE configuration group. The attributes are used on E-UTRAN frequency relation level. Instance UeMCEUtranFreqRelProfileUeCfg=Base is created automatically when parent MO instance is created, unless created manually in same transaction. Attributes prefUeGroupList, ueGroupList and ueConfGroupList must be empty in instance UeMCEUtranFreqRelProfileUeCfg=Base but cannot all be empty in any other instance of UeMCEUtranFreqRelProfileUeCfg under same parent UeMCEUtranFreqRelProfile instance. Precondition: Instance UeMCEUtranFreqRelProfileUeCfg=Base can only be created in same transaction as parent MO instance and cannot be deleted unless parent MO instance is deleted. Other instances can be created and deleted at any time. Maximum 31 UeMCEUtranFreqRelProfileUeCfg instances, with RDN different from Base, can be created under parent MO instance.";
      key "ueMCEUtranFreqRelProfileUeCfgId";
      leaf ueMCEUtranFreqRelProfileUeCfgId {
        type leafref {
          path "../attributes/ueMCEUtranFreqRelProfileUeCfgId";
        }
      }
      container attributes {
        uses UeMCEUtranFreqRelProfileUeCfg-attributes;
      }
    }
  }

  augment "/emael:ManagedElement/GNBCUCPFunction/UeMC/UeMCNrFreqRelProfile" {
    list UeMCNrFreqRelProfileUeCfg {
      description "Additional definitions from MOM:min/max-elements:0/32; Mobility control for UE configuration group. Attributes are used on NR frequency relation level. Instance UeMCNrFreqRelProfileUeCfg=Base is created automatically when parent MO instance is created, unless created manually in same transaction. Attributes prefUeGroupList, ueGroupList and ueConfGroupList must be empty in instance UeMCNrFreqRelProfileUeCfg=Base but cannot all be empty in any other instance of UeMCNrFreqRelProfileUeCfg under same parent UeMCNrFreqRelProfile instance. Precondition: Instance UeMCNrFreqRelProfileUeCfg=Base can only be created in same transaction as parent MO instance and cannot be deleted unless parent MO instance is deleted. Other instances can be created and deleted at any time. Maximum 31 UeMCNrFreqRelProfileUeCfg instances, with RDN different from Base, can be created under parent MO instance.";
      key "ueMCNrFreqRelProfileUeCfgId";
      leaf ueMCNrFreqRelProfileUeCfgId {
        type leafref {
          path "../attributes/ueMCNrFreqRelProfileUeCfgId";
        }
      }
      container attributes {
        uses UeMCNrFreqRelProfileUeCfg-attributes;
      }
    }
  }

  augment "/emael:ManagedElement/GNBCUCPFunction/UeNoDrb" {
    list UeNoDrbPCellProfile {
      description "Additional definitions from MOM:min/max-elements:0/unbounded; UE context without DRBs for PCell. Applies to UEs that use the cell as PCell. Attributes are used on cell level. Instance UeNoDrbPCellProfile=Default is created automatically when parent MO instance is created, unless created manually in same transaction. NRCellCU::ueNoDrbPCellProfileRef is automatically set to UeNoDrbPCellProfile=Default instance, unless manually set to refer to another MO instance. Precondition: Instance UeNoDrbPCellProfile=Default can only be created in same transaction as parent MO instance and cannot be deleted unless parent MO instance is deleted. Other instances can be created and deleted at any time.";
      key "ueNoDrbPCellProfileId";
      leaf ueNoDrbPCellProfileId {
        type leafref {
          path "../attributes/ueNoDrbPCellProfileId";
        }
      }
      container attributes {
        uses UeNoDrbPCellProfile-attributes;
      }
    }
  }

  augment "/emael:ManagedElement/GNBCUCPFunction/UeNoDrb/UeNoDrbPCellProfile" {
    list UeNoDrbPCellProfileUeCfg {
      description "Additional definitions from MOM:min/max-elements:0/8; UE context without DRBs for PCell, UE configuration group. Applies to UEs that use cell as PCell. Attributes are used on cell level. Instance UeNoDrbPCellProfileUeCfg=Base is created automatically when parent MO instance is created, unless created manually in same transaction. Attributes ueGroupList and ueConfGroupList must be empty in instance UeNoDrbPCellProfileUeCfg=Base but cannot all be empty in any other instance of UeNoDrbPCellProfileUeCfg under same parent UeNoDrbPCellProfile instance. Precondition: Instance UeNoDrbPCellProfileUeCfg=Base can only be created in same transaction as parent MO instance and cannot be deleted unless parent MO instance is deleted. Other instances can be created and deleted at any time. Maximum 7 UeNoDrbPCellProfileUeCfg instances, with RDN different from Base, can be created under parent MO instance.";
      key "ueNoDrbPCellProfileUeCfgId";
      leaf ueNoDrbPCellProfileUeCfgId {
        type leafref {
          path "../attributes/ueNoDrbPCellProfileUeCfgId";
        }
      }
      container attributes {
        uses UeNoDrbPCellProfileUeCfg-attributes;
      }
    }
  }

  augment "/emael:ManagedElement/GNBCUCPFunction/UeUlResMon" {
    list UlBufferMonCfg {
      description "Additional definitions from MOM:min/max-elements:0/16; Uplink buffer monitoring configurations. Instance UlBufferMonCfg=Default is created automatically when parent MO instance is created, unless created manually in same transaction. NrdcMnCellProfileUeCfg::nrdcSetupUlBufferMonCfgRef is automatically set to UlBufferMonCfg=Default instance, unless manually set to refer to another MO instance. Precondition: Instance UlBufferMonCfg=Default can only be created in same transaction as parent MO instance and cannot be deleted unless parent MO instance is deleted. Other instances can be created and deleted at any time. Maximum 15 UlBufferMonCfg instances, with RDN different from Default, can be created under parent MO instance.";
      key "ulBufferMonCfgId";
      leaf ulBufferMonCfgId {
        type leafref {
          path "../attributes/ulBufferMonCfgId";
        }
      }
      container attributes {
        uses UlBufferMonCfg-attributes;
      }
    }
  }

  augment "/emael:ManagedElement/GNBCUCPFunction/UeUlResMon" {
    list UlQualMcpcMeasCfg {
      description "Additional definitions from MOM:min/max-elements:0/8; Uplink quality measurement configuration for Mobility Control at Poor Coverage (MCPC). Instance UlQualMcpcMeasCfg=Default is created automatically when parent MO instance is created, unless created manually in same transaction. McpcPCellProfileUeCfg::ulQualMcpcMeasCfgRef is automatically set to UlQualMcpcMeasCfg=Default instance, unless manually set to refer to another MO instance. Precondition: Instance UlQualMcpcMeasCfg=Default can only be created in same transaction as parent MO instance and cannot be deleted unless parent MO instance is deleted. Other instances can be created and deleted at any time. Maximum 7 UlQualMcpcMeasCfg instances, with RDN different from Default, can be created under parent MO instance.";
      key "ulQualMcpcMeasCfgId";
      leaf ulQualMcpcMeasCfgId {
        type leafref {
          path "../attributes/ulQualMcpcMeasCfgId";
        }
      }
      container attributes {
        uses UlQualMcpcMeasCfg-attributes;
      }
    }
  }

  augment "/emael:ManagedElement/GNBCUCPFunction/UeCC/UlDataSplit" {
    list UlDataSplitUeCfg {
      description "Additional definitions from MOM:min/max-elements:0/8; Uplink PDCP data split UE configuration group. Instance UlDataSplitUeCfg=Base is created automatically when parent MO instance is created, unless created manually in same transaction. Each UE configuration group identifier can only be defined in one ueConfGroupList among UlDataSplitUeCfg instances contained under parent UlDataSplit instance. Any combination of one UE group identifier in ueGroupList and one preference UE group identifier in prefUeGroupList must be unique among UlDataSplitUeCfg instances contained under parent UlDataSplit instance. Attributes prefUeGroupList, ueGroupList and ueConfGroupList must be empty in instance UlDataSplitUeCfg=Base but cannot all be empty in any other instance of UlDataSplitUeCfg under same parent UlDataSplit instance. Precondition: Instance UlDataSplitUeCfg=Base can only be created in same transaction as parent MO instance and cannot be deleted unless parent MO instance is deleted. Other instances can be created and deleted at any time. Maximum 7 UlDataSplitUeCfg instances, with RDN different from Base, can be created under parent MO instance.";
      key "ulDataSplitUeCfgId";
      leaf ulDataSplitUeCfgId {
        type leafref {
          path "../attributes/ulDataSplitUeCfgId";
        }
      }
      container attributes {
        uses UlDataSplitUeCfg-attributes;
      }
    }
  }
  typedef AcaOperationMode {
    type enumeration {
      enum AUTO;
      enum MANUAL;
    }
  }
  typedef ActionAtRelease {
    type enumeration {
      enum DISABLED;
      enum CA_CONF;
      enum PRIORITY_LIST;
      enum CRP_MLC_CONDITIONAL;
      enum RANDOM_REDIRECT;
    }
  }
  typedef AdmState {
    type enumeration {
      enum LOCKED;
      enum UNLOCKED;
      enum SHUTTINGDOWN;
    }
  }
  typedef AdvancedUePositioningMode {
    type enumeration {
      enum NONE;
      enum ALL;
      enum TA_ONLY;
    }
  }
  typedef AggressorNodeType {
    type enumeration {
      enum LOCAL_NODE;
      enum EXTERNAL_ENODEB;
      enum EXTERNAL_GNODEB;
    }
  }
  typedef AllowedBarredCellType {
    type enumeration {
      enum ALL;
      enum SPCELL_ONLY;
      enum SCELL_ONLY;
      enum NONE;
    }
  }
  typedef AnrCgiMeasInterFreqMode {
    type enumeration {
      enum DISABLED;
      enum FR1;
    }
  }
  typedef AutoEpCellRelUpdateMode {
    type enumeration {
      enum __UNDEFINED__;
    }
  }
  typedef AvailStatus {
    type enumeration {
      enum IN_TEST;
      enum FAILED;
      enum POWER_OFF;
      enum OFF_LINE;
      enum OFF_DUTY;
      enum DEPENDENCY;
      enum DEGRADED;
      enum NOT_INSTALLED;
      enum LOG_FULL;
      enum DEPENDENCY_LOCKED;
      enum DEPENDENCY_FAILED;
      enum DEPENDENCY_SHUTTINGDOWN;
      enum DEPENDENCY_RECOVERY;
      enum DEPENDENCY_HOLDING;
    }
  }
  typedef CaStatusCause {
    type enumeration {
      enum E5_TUNNEL_CAP;
      enum E5_TUNNEL_CAP_REMOTE;
      enum E5_CELL_ALLOC_CAP;
      enum E5_CELL_ALLOC_CAP_REMOTE;
      enum E5_SW_VERSION_MISMATCH;
      enum E5_MAND_CAP_MISMATCH;
      enum E5_DLCA_CAP_ONLY;
      enum INTRA_BAND_CA_BLOCKED;
      enum ESS_ULCA_BLOCKED;
    }
  }
  typedef CellRelationOutput {
    type enumeration {
      enum UNFORMATTED_TEXT;
      enum FORMATTED_TEXT;
    }
  }
  typedef CipheringAlgorithmID {
    type enumeration {
      enum NEA0;
      enum NEA1;
      enum NEA2;
      enum NEA3;
    }
  }
  typedef Colocation {
    type enumeration {
      enum UNKNOWN;
      enum COLOCATED;
      enum NON_COLOCATED;
    }
  }
  typedef CoordinationType {
    type enumeration {
      enum INTRA_CM;
      enum INTER_CM;
      enum EXT_CM;
    }
  }
  typedef DayOfWeekOnly {
    type enumeration {
      enum MON;
      enum TUE;
      enum WED;
      enum THU;
      enum FRI;
      enum SAT;
      enum SUN;
    }
  }
  typedef DrxInactivityTimer {
    type enumeration {
      enum INACTIVITYTIMER_0MS;
      enum INACTIVITYTIMER_1MS;
      enum INACTIVITYTIMER_2MS;
      enum INACTIVITYTIMER_3MS;
      enum INACTIVITYTIMER_4MS;
      enum INACTIVITYTIMER_5MS;
      enum INACTIVITYTIMER_6MS;
      enum INACTIVITYTIMER_8MS;
      enum INACTIVITYTIMER_10MS;
      enum INACTIVITYTIMER_20MS;
      enum INACTIVITYTIMER_30MS;
      enum INACTIVITYTIMER_40MS;
      enum INACTIVITYTIMER_50MS;
      enum INACTIVITYTIMER_60MS;
      enum INACTIVITYTIMER_80MS;
      enum INACTIVITYTIMER_100MS;
      enum INACTIVITYTIMER_200MS;
      enum INACTIVITYTIMER_300MS;
      enum INACTIVITYTIMER_500MS;
      enum INACTIVITYTIMER_750MS;
      enum INACTIVITYTIMER_1280MS;
      enum INACTIVITYTIMER_1920MS;
      enum INACTIVITYTIMER_2560MS;
    }
  }
  typedef DrxLongCycle {
    type enumeration {
      enum LONGCYCLE_10MS;
      enum LONGCYCLE_20MS;
      enum LONGCYCLE_32MS;
      enum LONGCYCLE_40MS;
      enum LONGCYCLE_60MS;
      enum LONGCYCLE_64MS;
      enum LONGCYCLE_70MS;
      enum LONGCYCLE_80MS;
      enum LONGCYCLE_128MS;
      enum LONGCYCLE_160MS;
      enum LONGCYCLE_256MS;
      enum LONGCYCLE_320MS;
      enum LONGCYCLE_512MS;
      enum LONGCYCLE_640MS;
      enum LONGCYCLE_1024MS;
      enum LONGCYCLE_1280MS;
      enum LONGCYCLE_2048MS;
      enum LONGCYCLE_2560MS;
      enum LONGCYCLE_5120MS;
      enum LONGCYCLE_10240MS;
    }
  }
  typedef DrxOnDurationTimer {
    type enumeration {
      enum ONDURATIONTIMER_1SUBMS;
      enum ONDURATIONTIMER_2SUBMS;
      enum ONDURATIONTIMER_3SUBMS;
      enum ONDURATIONTIMER_4SUBMS;
      enum ONDURATIONTIMER_5SUBMS;
      enum ONDURATIONTIMER_6SUBMS;
      enum ONDURATIONTIMER_7SUBMS;
      enum ONDURATIONTIMER_8SUBMS;
      enum ONDURATIONTIMER_9SUBMS;
      enum ONDURATIONTIMER_10SUBMS;
      enum ONDURATIONTIMER_11SUBMS;
      enum ONDURATIONTIMER_12SUBMS;
      enum ONDURATIONTIMER_13SUBMS;
      enum ONDURATIONTIMER_14SUBMS;
      enum ONDURATIONTIMER_15SUBMS;
      enum ONDURATIONTIMER_16SUBMS;
      enum ONDURATIONTIMER_17SUBMS;
      enum ONDURATIONTIMER_18SUBMS;
      enum ONDURATIONTIMER_19SUBMS;
      enum ONDURATIONTIMER_20SUBMS;
      enum ONDURATIONTIMER_21SUBMS;
      enum ONDURATIONTIMER_22SUBMS;
      enum ONDURATIONTIMER_23SUBMS;
      enum ONDURATIONTIMER_24SUBMS;
      enum ONDURATIONTIMER_25SUBMS;
      enum ONDURATIONTIMER_26SUBMS;
      enum ONDURATIONTIMER_27SUBMS;
      enum ONDURATIONTIMER_28SUBMS;
      enum ONDURATIONTIMER_29SUBMS;
      enum ONDURATIONTIMER_30SUBMS;
      enum ONDURATIONTIMER_31SUBMS;
      enum ONDURATIONTIMER_1MS;
      enum ONDURATIONTIMER_2MS;
      enum ONDURATIONTIMER_3MS;
      enum ONDURATIONTIMER_4MS;
      enum ONDURATIONTIMER_5MS;
      enum ONDURATIONTIMER_6MS;
      enum ONDURATIONTIMER_8MS;
      enum ONDURATIONTIMER_10MS;
      enum ONDURATIONTIMER_20MS;
      enum ONDURATIONTIMER_30MS;
      enum ONDURATIONTIMER_40MS;
      enum ONDURATIONTIMER_50MS;
      enum ONDURATIONTIMER_60MS;
      enum ONDURATIONTIMER_80MS;
      enum ONDURATIONTIMER_100MS;
      enum ONDURATIONTIMER_200MS;
      enum ONDURATIONTIMER_300MS;
      enum ONDURATIONTIMER_400MS;
      enum ONDURATIONTIMER_500MS;
      enum ONDURATIONTIMER_600MS;
      enum ONDURATIONTIMER_800MS;
      enum ONDURATIONTIMER_1000MS;
      enum ONDURATIONTIMER_1200MS;
      enum ONDURATIONTIMER_1600MS;
    }
  }
  typedef EndcMobilityAction {
    type enumeration {
      enum RELEASE;
      enum IGNORE;
    }
  }
  typedef EnergySavingState {
    type enumeration {
      enum NOT_ENERGYSAVING;
      enum ENERGYSAVING;
    }
  }
  typedef EnergyState {
    type enumeration {
      enum IS_NOT_ENERGYSAVING;
      enum IS_ENERGYSAVING;
    }
  }
  typedef EpBoCSMode {
    type enumeration {
      enum DISABLED;
      enum TIME;
      enum MULTI_LAYER_TRAFFIC;
    }
  }
  typedef EpsFallbackOperationType {
    type enumeration {
      enum INACTIVE;
      enum ACTIVE;
      enum FORCED;
      enum ACTIVE_MEAS_RWR;
      enum ACTIVE_MEAS_IRAT_HO;
      enum FORCED_MEAS_RWR;
      enum FORCED_MEAS_IRAT_HO;
    }
  }
  typedef EpsFbAtSessionSetupType {
    type enumeration {
      enum INACTIVE;
      enum ACTIVE;
    }
  }
  typedef EpsFbOperationTypeEm {
    type enumeration {
      enum ACTIVE;
      enum FORCED;
      enum ACTIVE_MEAS_RWR;
      enum ACTIVE_MEAS_IRAT_HO;
      enum FORCED_MEAS_RWR;
      enum FORCED_MEAS_IRAT_HO;
    }
  }
  typedef EpsFbPrioritizationType {
    type enumeration {
      enum PRIO_OVER_XN_HO;
    }
  }
  typedef ExtNrCellMgmtPolicyType {
    type enumeration {
      enum __UNDEFINED__;
    }
  }
  typedef FeatCtrlState {
    type enumeration {
      enum OFF;
      enum ON;
    }
  }
  typedef InitialUlPrimaryPathMode {
    type enumeration {
      enum MCG;
      enum COVERAGE_BASED;
      enum SCG;
    }
  }
  typedef InitialUplinkConf {
    type enumeration {
      enum MCG;
      enum SCG;
    }
  }
  typedef IntegProtLowRateHandling {
    type enumeration {
      enum REJECT;
      enum NO_INTEGRITY_PROTECTION;
    }
  }
  typedef IntegrityAlgorithmID {
    type enumeration {
      enum NIA1;
      enum NIA2;
      enum NIA3;
    }
  }
  typedef InterFreqMeasType {
    type enumeration {
      enum EVENT_A5;
      enum EVENT_A3;
    }
  }
  typedef InterfaceName {
    type enumeration {
      enum C5;
      enum E1;
      enum E6;
      enum F1;
      enum NG;
      enum S1;
      enum XN;
      enum X2;
    }
  }
  typedef InterfaceSupervision {
    type enumeration {
      enum ALL_LINKS;
      enum NO_SUPERVISION;
      enum NG_ONLY;
      enum X2_ONLY;
      enum XN_ONLY;
      enum NG_X2_COEXISTENCE;
      enum NG_XN_COEXISTENCE;
      enum X2_XN_COEXISTENCE;
    }
  }
  typedef LowPrioSpCellCandHandling {
    type enumeration {
      enum STORE_LATEST_RECEIVED;
      enum STORE_HIGHEST_PRIO;
    }
  }
  typedef McpcNrdcQuantity {
    type enumeration {
      enum NONE;
      enum RSRP;
      enum RSRQ;
      enum SINR_FALLBACK_RSRP;
      enum SINR_FALLBACK_RSRQ;
      enum RSRP_AND_RSRQ;
      enum RSRP_AND_SINR_FALLBACK_RSRQ;
      enum RSRP_AND_SINR_NO_FALLBACK;
    }
  }
  typedef McpcQuantity {
    type enumeration {
      enum RSRP;
      enum RSRQ;
      enum SINR_NO_FALLBACK;
      enum SINR_FALLBACK_RSRQ;
      enum SINR_FALLBACK_RSRP;
      enum UL_SINR;
    }
  }
  typedef MdtMeasurementName {
    type enumeration {
      enum NONE;
      enum M1;
      enum M6;
      enum MDT_UE_LOCATION;
    }
  }
  typedef MdtReportIntervalNR {
    type enumeration {
      enum MS_1024;
      enum MS_2048;
      enum MS_5120;
      enum MS_10240;
      enum MS_20480;
      enum MS_40960;
      enum MIN_1;
    }
  }
  typedef MdtReportQuantityNR {
    type enumeration {
      enum RSRP;
      enum RSRQ;
      enum SINR;
      enum RSRP_RSRQ;
      enum RSRP_SINR;
      enum RSRQ_SINR;
      enum RSRP_RSRQ_SINR;
      enum NO_QUANTITY;
    }
  }
  typedef MdtReportingTrigger {
    type enumeration {
      enum PERIODIC;
      enum A2EVENT_TRIGGERED;
      enum A2EVENT_TRIGGERED_PERIODIC;
    }
  }
  typedef MdtTriggerQuantityNR {
    type enumeration {
      enum RSRP;
      enum RSRQ;
      enum SINR;
    }
  }
  typedef MlcCellSetChangeAction {
    type enumeration {
      enum HANDOVER;
      enum SCELL_RESELECTION;
      enum HO_AND_SCELL_RESELECTION;
    }
  }
  typedef NRCellServiceState {
    type enumeration {
      enum OUT_OF_SERVICE;
      enum IN_SERVICE;
    }
  }
  typedef NRCellState {
    type enumeration {
      enum IDLE;
      enum INACTIVE;
      enum ACTIVE;
    }
  }
  typedef NrdcQuantity {
    type enumeration {
      enum RSRP;
      enum RSRQ;
      enum SINR_FALLBACK_RSRP;
      enum SINR_FALLBACK_RSRQ;
      enum RSRP_AND_RSRQ;
      enum RSRP_AND_SINR_FALLBACK_RSRQ;
      enum RSRP_AND_SINR_NO_FALLBACK;
    }
  }
  typedef OperState {
    type enumeration {
      enum DISABLED;
      enum ENABLED;
    }
  }
  typedef PWSRestartHandling {
    type enumeration {
      enum DISABLED;
      enum ENABLED;
    }
  }
  typedef PciConflictDetectionEcgiMeas {
    type enumeration {
      enum DISABLED;
      enum ENABLED;
    }
  }
  typedef PciConflictDetectionNcgiMeas {
    type enumeration {
      enum DISABLED;
      enum FR1;
    }
  }
  typedef PciConflictMobilityEcgiMeas {
    type enumeration {
      enum DISABLED;
      enum ENABLED;
    }
  }
  typedef PciConflictMobilityNcgiMeas {
    type enumeration {
      enum DISABLED;
      enum FR1;
    }
  }
  typedef PciConflictTargetSelectMode {
    type enumeration {
      enum DISABLED;
      enum HITRATE_BASED;
      enum MANUAL_BASED;
      enum HITRATE_MANUAL_BASED;
      enum MANUAL_HITRATE_BASED;
    }
  }
  typedef PciConflicted {
    type enumeration {
      enum NO;
      enum YES;
    }
  }
  typedef PimDetectionRole {
    type enumeration {
      enum AGGRESSOR;
      enum VICTIM;
      enum VICTIM_AND_AGGRESSOR;
    }
  }
  typedef PimDetectionStatus {
    type enumeration {
      enum NOT_APPLICABLE;
      enum NO_PIM_DETECTED;
      enum PIM_DETECTED;
    }
  }
  typedef PimType {
    type enumeration {
      enum CLEAR;
      enum LIKELY;
    }
  }
  typedef PmUeReportType {
    type enumeration {
      enum PERIODICAL;
      enum EVENT_A2;
      enum EVENT_A3;
    }
  }
  typedef PowerClass {
    type enumeration {
      enum PC_1;
      enum PC_1_5;
      enum PC_2;
    }
  }
  typedef PredUeCapConfig {
    type enumeration {
      enum INCOMPLETE_CAPS;
    }
  }
  typedef PrefInterGnbHoType {
    type enumeration {
      enum XN_HO;
      enum NG_HO;
    }
  }
  typedef ProhibitCellTriggerConfig {
    type enumeration {
      enum DISABLED;
      enum ENABLED_EUTRAN_ONLY;
      enum ENABLED_ALL;
    }
  }
  typedef PuemReportQuantity {
    type enumeration {
      enum RSRP;
      enum RSRQ;
      enum SINR;
      enum RSRP_RSRQ;
      enum RSRP_SINR;
      enum RSRQ_SINR;
      enum RSRP_RSRQ_SINR;
      enum NO_QUANTITY;
    }
  }
  typedef RelPrefProhibitTimerLength {
    type enumeration {
      enum S0;
      enum S0DOT5;
      enum S1;
      enum S2;
      enum S3;
      enum S4;
      enum S5;
      enum S6;
      enum S7;
      enum S8;
      enum S9;
      enum S10;
      enum S20;
      enum S30;
      enum INFINITY;
    }
  }
  typedef ReleasePrefOverride {
    type enumeration {
      enum IDLE;
      enum INACTIVE;
      enum NO_PREFERENCE;
    }
  }
  typedef ReportAmount {
    type enumeration {
      enum R1;
      enum R2;
      enum R4;
      enum R8;
      enum R16;
      enum R32;
      enum R64;
      enum INFINITY;
    }
  }
  typedef ReportConfigA6Mode {
    type enumeration {
      enum ALWAYS;
      enum CONDITIONAL;
    }
  }
  typedef ReportInterval {
    type enumeration {
      enum MS_120;
      enum MS_240;
      enum MS_480;
      enum MS_640;
      enum MS_1024;
      enum MS_2048;
      enum MS_5120;
      enum MS_10240;
      enum MS_20480;
      enum MS_40960;
      enum MIN_1;
      enum MIN_6;
      enum MIN_12;
      enum MIN_30;
    }
  }
  typedef RibTmAdditionalInfo {
    type enumeration {
      enum FEATURE_DEACTIVATED;
      enum PEER_FEATURE_DEACTIVATED;
      enum UNSUPP_HW_CONF;
      enum PEER_UNSUPP_HW_CONF;
      enum MAX_PAIRS;
      enum PEER_MAX_PAIRS;
      enum NO_RESP_FROM_PEER;
      enum PCI_CONFLICT;
      enum INCOMPATIBLE_CELLS;
      enum CELL_DISABLED;
      enum PEER_CELL_DISABLED;
    }
  }
  typedef RibTmMeasurementQuality {
    type enumeration {
      enum NO_MEASUREMENTS;
      enum UNKNOWN;
      enum RELIABLE;
      enum UNRELIABLE;
    }
  }
  typedef RimOffloadType {
    type enumeration {
      enum NOT_ALLOWED;
      enum BLIND_RWR;
    }
  }
  typedef RlcMode {
    type enumeration {
      enum AM;
      enum UM;
    }
  }
  typedef RobustUeCapEnquiryUseCase {
    type enumeration {
      enum COMBINED_THEN_SPLIT;
      enum SPLIT_ONLY;
      enum COMBINED_ONLY;
    }
  }
  typedef RreSupportType {
    type enumeration {
      enum NO_RRE_SUPPORT;
      enum INTRA_GNB_RRE;
      enum INTRA_INTER_GNB_RRE;
    }
  }
  typedef RsrpAddQuantityEval {
    type enumeration {
      enum NONE;
      enum RSRQ;
      enum SINR_FALLBACK_RSRQ;
      enum SINR_NO_FALLBACK_RSRQ;
    }
  }
  typedef RsrqAddQuantityEval {
    type enumeration {
      enum NONE;
      enum RSRP;
    }
  }
  typedef SCellCandidate {
    type enumeration {
      enum NOT_ALLOWED;
      enum ALLOWED;
      enum ONLY_ALLOWED_FOR_DL;
    }
  }
  typedef ServingCellSelectionPolicy {
    type enumeration {
      enum PRIORITIZE_DL_THP;
      enum PRIORITIZE_UL_THP;
      enum PRIO_DL_THP_THEN_PCELL_UL_THP;
    }
  }
  typedef SinrAddQuantityEval {
    type enumeration {
      enum NONE;
      enum RSRP;
      enum RSRQ;
      enum RSRP_AND_RSRQ;
    }
  }
  typedef SnssaiValidationMode {
    type enumeration {
      enum NORMAL;
      enum DISABLED;
    }
  }
  typedef SpCellCapabilityType {
    type enumeration {
      enum __UNDEFINED__;
    }
  }
  typedef SupportedCoverage {
    type enumeration {
      enum NONE;
      enum COVERS;
      enum OVERLAP;
      enum CONTAINED_IN;
    }
  }
  typedef TnlAssocUsage {
    type enumeration {
      enum BOTH;
      enum UE;
      enum NON_UE;
    }
  }
  typedef TriggerQuantity {
    type enumeration {
      enum RSRP;
      enum RSRQ;
    }
  }
  typedef TriggerQuantity2 {
    type enumeration {
      enum RSRP;
      enum RSRQ;
      enum SINR_FALLBACK_RSRP;
      enum SINR_FALLBACK_RSRQ;
    }
  }
  typedef UcmReportQuantity {
    type enumeration {
      enum RSRP;
      enum RSRQ;
      enum SINR;
      enum RSRP_RSRQ;
      enum RSRP_SINR;
      enum RSRQ_SINR;
      enum RSRP_RSRQ_SINR;
      enum NO_QUANTITY;
    }
  }
  typedef UeConfGroupType {
    type enumeration {
      enum UE_MOBILITY_GROUP;
      enum UE_SERVICE_GROUP;
      enum UE_ADMISSION_GROUP;
    }
  }
  typedef UePositioningPeriodicityMode {
    type enumeration {
      enum COMB_PERIODICITY;
      enum AOA_PERIODICITY;
    }
  }
  typedef UlCaConfigurationMode {
    type enumeration {
      enum IMMEDIATE;
      enum DELAYED_ALWAYS;
      enum DELAYED_CONDITIONAL;
    }
  }
  typedef UlCompCellCandidate {
    type enumeration {
      enum __UNDEFINED__;
    }
  }
  typedef UlCompStatusCause {
    type enumeration {
      enum __UNDEFINED__;
    }
  }
  typedef UlSuMimoFr1Prevention {
    type enumeration {
      enum NONE;
      enum TDD;
      enum FDD;
      enum TDD_AND_FDD;
    }
  }
  typedef UpdateAmfConnectionOption {
    type enumeration {
      enum RETAIN_EXISTING;
      enum RENEW_ALL;
    }
  }
  grouping AdditionalPLMNInfo-attributes {
    leaf additionalPLMNInfoId {
      type string;
      mandatory true;
    }
    leaf nRTAC {
      type int32;
      config false;
    }
    list pLMNIdList {
      config false;
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
  }
  grouping AdmissionControl-attributes {
    leaf admissionControlId {
      type string;
      mandatory true;
    }
  }
  grouping AdmissionLimit-attributes {
    leaf admissionLimitId {
      type string;
      mandatory true;
    }
    leaf ccLoadThreshold {
      type eytypes:int32_range_0-100;
      default "0";
      units "percent";
      description "range 0..100; Default value: 0.";
    }
    leaf maxConnectedUe {
      type int32 {
        range "0..10000";
      }
      default "0";
      description "range 0..10000; Default value: 0.";
    }
    leaf maxConnectedUeOffloadISHo {
      type int32 {
        range "0..10000";
      }
      default "10000";
      description "range 0..10000; Default value: 10000.";
    }
    leaf preemptionRate {
      type eytypes:int32_range_0-100;
      default "80";
      units "percent";
      description "range 0..100; Default value: 80.";
    }
    leaf-list reservedBy {
      type string;
    }
  }
  grouping AdmissionPriority-attributes {
    leaf admissionPriorityId {
      type string;
      mandatory true;
    }
    leaf-list reservedBy {
      type string;
    }
    leaf ueConfGroupType {
      type enumeration {
        enum UE_MOBILITY_GROUP;
        enum UE_SERVICE_GROUP;
        enum UE_ADMISSION_GROUP;
      }
    }
  }
  grouping AdmissionPriorityUeCfg-attributes {
    leaf admissionPriorityUeCfgId {
      type string;
      mandatory true;
    }
    leaf-list prefUeGroupList {
      type eytypes:int32_range_1-255;
      ordered-by user;
    }
    leaf-list ueConfGroupList {
      type eytypes:int32_range_1-255;
      ordered-by user;
    }
    leaf-list ueGroupList {
      type eytypes:int32_range_1-255;
      ordered-by user;
    }
    leaf uePriority {
      type eytypes:int32_range_1-255;
      default "255";
      description "range 1..255; Default value: 255.";
    }
  }
  grouping AnrFunction-attributes {
    leaf anrFunctionId {
      type string;
      mandatory true;
    }
    leaf demoteCellRelMobAttThresh {
      type eytypes:int32_range_1-1000-7;
      description "range 1..1000.";
    }
    leaf lwCellRelationRatio {
      type eytypes:int32_range_0-100;
      config false;
      units "percent";
      description "range 0..100.";
    }
    leaf promoteCellRelMobAttThresh {
      type eytypes:int32_range_1-1000-7;
      description "range 1..1000.";
    }
    leaf removeEnbTime {
      type eytypes:int32_range_1-1000;
      default "7";
      units "day";
      description "range 1..1000; Default value: 7.";
    }
    leaf removeEUtranFreqRelTime {
      type int32 {
        range "10..10000";
      }
      default "10000";
      units "minute";
      description "range 10..10000; Default value: 10000.";
    }
    leaf removeFreqRelTime {
      type int32 {
        range "10..10000";
      }
      default "15";
      units "minute";
      description "range 10..10000; Default value: 15.";
    }
    leaf removeGnbTime {
      type eytypes:int32_range_1-1000;
      default "7";
      units "day";
      description "range 1..1000; Default value: 7.";
    }
    leaf removeNrelTime {
      type eytypes:int32_range_1-1000;
      default "7";
      units "day";
      description "range 1..1000; Default value: 7.";
    }
  }
  grouping AnrFunctionEUtran-attributes {
    leaf anrCgiMeasEUtranEnabled {
      type boolean;
      default "false";
      description "Default value: false.";
    }
    leaf anrFunctionEUtranId {
      type string;
      mandatory true;
    }
  }
  grouping AnrFunctionEUtranUeCfg-attributes {
    leaf anrFunctionEUtranUeCfgId {
      type string;
      mandatory true;
    }
    leaf ecgiDuringEpsFbEnabled {
      type boolean;
      default "true";
      description "Default value: true.";
    }
  }
  grouping AnrFunctionNR-attributes {
    leaf anrAutoCreateXnForEndc {
      type boolean;
      default "false";
      description "Default value: false.";
    }
    leaf anrCgiMeasInterFreqMode {
      type enumeration {
        enum DISABLED;
        enum FR1;
      }
    }
    leaf anrCgiMeasIntraFreqEnabled {
      type boolean;
      default "false";
      description "Default value: false.";
    }
    leaf anrEndcX2Enabled {
      type boolean;
      default "false";
      description "Default value: false.";
    }
    leaf anrFunctionNRId {
      type string;
      mandatory true;
    }
  }
  grouping AnrFunctionNRUeCfg-attributes {
    leaf adjustedAnrRsrpThreshold {
      type eytypes:int32_range_-156--29;
      config false;
      units "dBm";
      description "range -156..-29.";
    }
    leaf anrFunctionNRUeCfgId {
      type string;
      mandatory true;
    }
    leaf anrRsrpThreshold {
      type eytypes:int32_range_-156--29;
      default "-156";
      units "dBm";
      description "range -156..-29; Default value: -156.";
    }
    leaf anrRsrqThreshold {
      type eytypes:int32_range_-435-200;
      default "-435";
      units "dB";
      description "range -435..200; Default value: -435.";
    }
    leaf anrSinrThreshold {
      type eytypes:int32_range_-230-405;
      default "-230";
      units "dB";
      description "range -230..405; Default value: -230.";
    }
    leaf offsetAdjustAnrRsrpThreshold {
      type int32 {
        range "0..127";
      }
      default "10";
      units "dB";
      description "range 0..127; Default value: 10.";
    }
  }
  grouping AnrPLMNTable-attributes {
    leaf anrPLMNTableId {
      type string;
      mandatory true;
    }
    leaf gNBIdLength {
      type eytypes:int32_range_22-32;
      mandatory true;
      description "range 22..32.";
    }
    list pLMNIdList {
      key "id";
      leaf id {
        type uint32;
        description "Synthetic key for struct sequence entry.";
      }
      ordered-by user;
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
  }
  grouping BarringGroup-attributes {
    leaf-list accessCategoryList {
      type eytypes:int32_range_1-10;
      ordered-by user;
    }
    leaf barringGroupId {
      type string;
      mandatory true;
    }
    leaf barringTime {
      type int32 {
        range "4 | 8 | 16 | 32 | 64 | 128 | 256 | 512";
      }
      default "16";
      units "s";
      description "Default value: 16.";
    }
    leaf bgCounterId {
      type eytypes:int32_range_1-8;
      config false;
      description "range 1..8.";
    }
    leaf ccLoadBarringMax {
      type eytypes:int32_range_0-100;
      default "100";
      units "percent";
      description "range 0..100; Default value: 100.";
    }
    leaf ccLoadBarringStart {
      type eytypes:int32_range_0-100;
      default "100";
      units "percent";
      description "range 0..100; Default value: 100.";
    }
    leaf cellUsageBarringMax {
      type eytypes:int32_range_0-100;
      default "100";
      units "percent";
      description "range 0..100; Default value: 100.";
    }
    leaf cellUsageBarringStart {
      type eytypes:int32_range_0-100;
      default "100";
      units "percent";
      description "range 0..100; Default value: 100.";
    }
    leaf maxBarringProbability {
      type int32 {
        range "0 | 5 | 10 | 15 | 20 | 25 | 30 | 40 | 50 | 60 | 70 | 75 | 80 | 85 | 90 | 95 | 100";
      }
      default "0";
      units "percent";
      description "Default value: 0.";
    }
    list pLMNIdList {
      key "id";
      leaf id {
        type uint32;
        description "Synthetic key for struct sequence entry.";
      }
      ordered-by user;
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
    leaf rejRatioBarringMax {
      type eytypes:int32_range_0-100;
      default "100";
      units "percent";
      description "range 0..100; Default value: 100.";
    }
    leaf rejRatioBarringStart {
      type eytypes:int32_range_0-100;
      default "100";
      units "percent";
      description "range 0..100; Default value: 100.";
    }
    leaf startBarringAi1 {
      type int32 {
        range "0 | 5 | 10 | 15 | 20 | 25 | 30 | 40 | 50 | 60 | 70 | 75 | 80 | 85 | 90 | 95 | 100";
      }
      default "100";
      units "percent";
      description "Default value: 100.";
    }
    leaf startBarringAi11 {
      type int32 {
        range "0 | 5 | 10 | 15 | 20 | 25 | 30 | 40 | 50 | 60 | 70 | 75 | 80 | 85 | 90 | 95 | 100";
      }
      default "100";
      units "percent";
      description "Default value: 100.";
    }
    leaf startBarringAi12 {
      type int32 {
        range "0 | 5 | 10 | 15 | 20 | 25 | 30 | 40 | 50 | 60 | 70 | 75 | 80 | 85 | 90 | 95 | 100";
      }
      default "100";
      units "percent";
      description "Default value: 100.";
    }
    leaf startBarringAi13 {
      type int32 {
        range "0 | 5 | 10 | 15 | 20 | 25 | 30 | 40 | 50 | 60 | 70 | 75 | 80 | 85 | 90 | 95 | 100";
      }
      default "100";
      units "percent";
      description "Default value: 100.";
    }
    leaf startBarringAi14 {
      type int32 {
        range "0 | 5 | 10 | 15 | 20 | 25 | 30 | 40 | 50 | 60 | 70 | 75 | 80 | 85 | 90 | 95 | 100";
      }
      default "100";
      units "percent";
      description "Default value: 100.";
    }
    leaf startBarringAi15 {
      type int32 {
        range "0 | 5 | 10 | 15 | 20 | 25 | 30 | 40 | 50 | 60 | 70 | 75 | 80 | 85 | 90 | 95 | 100";
      }
      default "100";
      units "percent";
      description "Default value: 100.";
    }
    leaf startBarringAi2 {
      type int32 {
        range "0 | 5 | 10 | 15 | 20 | 25 | 30 | 40 | 50 | 60 | 70 | 75 | 80 | 85 | 90 | 95 | 100";
      }
      default "100";
      units "percent";
      description "Default value: 100.";
    }
  }
  grouping BlockedGNodeB-attributes {
    leaf blockedGNodeBId {
      type string;
      mandatory true;
    }
    leaf directPacketForwarding {
      type boolean;
    }
    leaf gNBId {
      type int64 {
        range "-1..4294967295";
      }
      description "range -1..4294967295.";
    }
    leaf mcc {
      type int32 {
        range "-1..999";
      }
      description "range -1..999.";
    }
    leaf mnc {
      type eytypes:int32_range_0-999;
      description "range 0..999.";
    }
    leaf mncLength {
      type eytypes:int32_range_2-3;
      description "range 2..3.";
    }
  }
  grouping CaCellMeasProfile-attributes {
    leaf caCellMeasProfileId {
      type string;
      mandatory true;
    }
    leaf-list reservedBy {
      type string;
    }
    leaf ueConfGroupType {
      type enumeration {
        enum UE_MOBILITY_GROUP;
        enum UE_SERVICE_GROUP;
        enum UE_ADMISSION_GROUP;
      }
    }
    leaf userLabel {
      type string;
    }
  }
  grouping CaCellMeasProfileUeCfg-attributes {
    leaf betterSCellReportConfigMode {
      type ietfinet:port-number;
    }
    leaf betterSCellTriggerQuantity {
      type enumeration {
        enum RSRP;
        enum RSRQ;
        enum SINR_FALLBACK_RSRP;
        enum SINR_FALLBACK_RSRQ;
      }
    }
    leaf caCellMeasProfileUeCfgId {
      type string;
      mandatory true;
    }
    leaf maxReportCells {
      type ietfinet:port-number;
      default "1";
      description "range 1..8; Default value: 1.";
    }
    leaf-list prefUeGroupList {
      type eytypes:int32_range_1-255;
      ordered-by user;
    }
    list rsrpBetterSCell {
      key "id";
      leaf id {
        type uint32;
        description "Synthetic key for struct entry.";
      }
      container attributes {
      leaf hysteresis {
        type eytypes:int32_range_0-150;
        default "10";
        units "dB";
        description "range 0..150; Default value: 10.";
      }
      leaf offset {
        type eytypes:int32_range_-150-150;
        default "30";
        units "dB";
        description "range -150..150; Default value: 30.";
      }
      leaf timeToTrigger {
        type int32;
        default "160";
        units "ms";
        description "Default value: 160.";
      }
      }
    }
    list rsrpSCellCoverage {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-156--29;
        default "-156";
        units "dBm";
        description "range -156..-29; Default value: -156.";
      }
      leaf timeToTrigger {
        type int32;
        default "160";
        units "ms";
        description "Default value: 160.";
      }
      leaf timeToTriggerA1 {
        type int32;
        default "-1";
        units "ms";
        description "Default value: -1.";
      }
      }
    }
    list rsrqBetterSCell {
      key "id";
      leaf id {
        type uint32;
        description "Synthetic key for struct entry.";
      }
      container attributes {
      leaf hysteresis {
        type eytypes:int32_range_0-150;
        default "10";
        units "dB";
        description "range 0..150; Default value: 10.";
      }
      leaf offset {
        type eytypes:int32_range_-150-150;
        default "30";
        units "dB";
        description "range -150..150; Default value: 30.";
      }
      leaf timeToTrigger {
        type int32;
        default "160";
        units "ms";
        description "Default value: 160.";
      }
      }
    }
    list rsrqSCellCoverage {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-435-200;
        default "-435";
        units "dB";
        description "range -435..200; Default value: -435.";
      }
      leaf timeToTrigger {
        type int32;
        default "160";
        units "ms";
        description "Default value: 160.";
      }
      leaf timeToTriggerA1 {
        type int32;
        default "-1";
        units "ms";
        description "Default value: -1.";
      }
      }
    }
    leaf sCellCoverageTriggerQuantity {
      type enumeration {
        enum RSRP;
        enum RSRQ;
        enum SINR_FALLBACK_RSRP;
        enum SINR_FALLBACK_RSRQ;
      }
    }
    list sinrBetterSCell {
      key "id";
      leaf id {
        type uint32;
        description "Synthetic key for struct entry.";
      }
      container attributes {
      leaf hysteresis {
        type eytypes:int32_range_0-150;
        default "10";
        units "dB";
        description "range 0..150; Default value: 10.";
      }
      leaf offset {
        type eytypes:int32_range_-150-150;
        default "30";
        units "dB";
        description "range -150..150; Default value: 30.";
      }
      leaf timeToTrigger {
        type int32;
        default "160";
        units "ms";
        description "Default value: 160.";
      }
      }
    }
    list sinrSCellCoverage {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-230-405;
        default "-230";
        units "dB";
        description "range -230..405; Default value: -230.";
      }
      leaf timeToTrigger {
        type int32;
        default "640";
        units "ms";
        description "Default value: 640.";
      }
      leaf timeToTriggerA1 {
        type int32;
        default "-1";
        units "ms";
        description "Default value: -1.";
      }
      }
    }
    leaf-list ueConfGroupList {
      type eytypes:int32_range_1-255;
      ordered-by user;
    }
    leaf-list ueGroupList {
      type eytypes:int32_range_1-255;
      ordered-by user;
    }
    leaf userLabel {
      type string;
    }
  }
  grouping CaCellProfile-attributes {
    leaf caCellProfileId {
      type string;
      mandatory true;
    }
    leaf-list reservedBy {
      type string;
    }
    leaf ueConfGroupType {
      type enumeration {
        enum UE_MOBILITY_GROUP;
        enum UE_SERVICE_GROUP;
        enum UE_ADMISSION_GROUP;
      }
    }
    leaf userLabel {
      type string;
    }
  }
  grouping CaCellProfileUeCfg-attributes {
    leaf-list blockedSCellFreqList {
      type eytypes:int32_range_0-3279165;
      ordered-by user;
    }
    leaf caCellProfileUeCfgId {
      type string;
      mandatory true;
    }
    leaf effectiveBwImpactUl2Layer {
      type int32 {
        range "0..200";
      }
      default "180";
      description "range 0..200; Default value: 180.";
    }
    leaf maxDlCcAllowed {
      type eytypes:int32_range_1-32;
      default "32";
      description "range 1..32; Default value: 32.";
    }
    leaf maxUlCcAllowed {
      type eytypes:int32_range_1-32;
      default "32";
      description "range 1..32; Default value: 32.";
    }
    leaf-list prefUeGroupList {
      type eytypes:int32_range_1-255;
      ordered-by user;
    }
    leaf servingCellSelectionPolicy {
      type enumeration {
        enum PRIORITIZE_DL_THP;
        enum PRIORITIZE_UL_THP;
        enum PRIO_DL_THP_THEN_PCELL_UL_THP;
      }
    }
    leaf-list ueConfGroupList {
      type eytypes:int32_range_1-255;
      ordered-by user;
    }
    leaf-list ueGroupList {
      type eytypes:int32_range_1-255;
      ordered-by user;
    }
    leaf ulCaConfigurationMode {
      type enumeration {
        enum IMMEDIATE;
        enum DELAYED_ALWAYS;
        enum DELAYED_CONDITIONAL;
      }
    }
    leaf ulSuMimoFr1Prevention {
      type enumeration {
        enum NONE;
        enum TDD;
        enum FDD;
        enum TDD_AND_FDD;
      }
    }
    leaf ulTxSwitchingAllowed {
      type boolean;
      default "false";
      description "Default value: false.";
    }
    leaf userLabel {
      type string;
    }
  }
  grouping CaFreqRelMeasProfile-attributes {
    leaf caFreqRelMeasProfileId {
      type string;
      mandatory true;
    }
    leaf-list reservedBy {
      type string;
    }
    leaf ueConfGroupType {
      type enumeration {
        enum UE_MOBILITY_GROUP;
        enum UE_SERVICE_GROUP;
        enum UE_ADMISSION_GROUP;
      }
    }
    leaf userLabel {
      type string;
    }
  }
  grouping CaFreqRelMeasProfileUeCfg-attributes {
    leaf caFreqRelMeasProfileUeCfgId {
      type string;
      mandatory true;
    }
    leaf-list prefUeGroupList {
      type eytypes:int32_range_1-255;
      ordered-by user;
    }
    leaf rsrpSCellCoverageThrOffset {
      type eytypes:int32_range_-30-30;
      default "0";
      units "dB";
      description "range -30..30; Default value: 0.";
    }
    leaf rsrqSCellCoverageThrOffset {
      type eytypes:int32_range_-300-300;
      default "0";
      units "dB";
      description "range -300..300; Default value: 0.";
    }
    leaf sinrSCellCoverageThrOffset {
      type eytypes:int32_range_-100-100;
      default "0";
      units "dB";
      description "range -100..100; Default value: 0.";
    }
    leaf-list ueConfGroupList {
      type eytypes:int32_range_1-255;
      ordered-by user;
    }
    leaf-list ueGroupList {
      type eytypes:int32_range_1-255;
      ordered-by user;
    }
    leaf userLabel {
      type string;
    }
    leaf waitForBetterSCellRep {
      type eytypes:int32_range_-1-32000;
      default "-1";
      units "ms";
      description "range -1..32000; Default value: -1.";
    }
  }
  grouping CapabilityHandling-attributes {
    leaf capabilityHandlingId {
      type string;
      mandatory true;
    }
    leaf predUeCap {
      type string {
        length "0..2000";
        pattern "([0-9a-fA-F][0-9a-fA-F])*";
      }
      description "length 0..2000.";
    }
    leaf-list predUeCapConfig {
      type enumeration {
        enum INCOMPLETE_CAPS;
      }
      ordered-by user;
    }
    leaf ueConfGroupType {
      type enumeration {
        enum UE_MOBILITY_GROUP;
        enum UE_SERVICE_GROUP;
        enum UE_ADMISSION_GROUP;
      }
    }
  }
  grouping CapabilityHandlingUeCfg-attributes {
    leaf capabilityHandlingUeCfgId {
      type string;
      mandatory true;
    }
    leaf gaplessFr2InterFreqMeasSupp {
      type boolean;
      default "false";
      description "Default value: false.";
    }
    leaf-list prefUeGroupList {
      type eytypes:int32_range_1-255;
      ordered-by user;
    }
    leaf-list ueConfGroupList {
      type eytypes:int32_range_1-255;
      ordered-by user;
    }
    leaf-list ueGroupList {
      type eytypes:int32_range_1-255;
      ordered-by user;
    }
    leaf ulRrcSegAllowedForUeCapInfo {
      type boolean;
      status deprecated;
      default "true";
      description "Default value: true; Takes effect: New connection; Status info: Since 23.Q4. Planned to be removed..";
      reference "Takes effect: New connection.";
    }
    leaf userLabel {
      type string;
    }
  }
  grouping CardinalityLimits-attributes {
    leaf cardinalityLimitsId {
      type string;
      mandatory true;
    }
    leaf maxNRCellCU {
      type int32;
      config false;
    }
  }
  grouping CarrierAggregation-attributes {
    leaf carrierAggregationId {
      type string;
      mandatory true;
    }
  }
  grouping CellGroupCategoryDefinition-attributes {
    leaf categoryCriteria {
      type string {
        length "0..1000";
      }
      description "length 0..1000.";
    }
    leaf cellGroupCategoryDefinitionId {
      type string;
      mandatory true;
    }
    leaf cgCategoryId {
      type eytypes:int32_range_0-255;
      mandatory true;
      description "range 0..255.";
    }
    leaf userLabel {
      type string;
    }
  }
  grouping Chipsets-attributes {
    list chipsetList {
      key "id";
      leaf id {
        type uint32;
        description "Synthetic key for struct sequence entry.";
      }
      ordered-by user;
      container attributes {
      leaf maxVer {
        type int32 {
          range "0..99999";
        }
        default "99999";
        description "range 0..99999; Default value: 99999.";
      }
      leaf minVer {
        type int32 {
          range "0..128";
        }
        default "0";
        description "range 0..128; Default value: 0.";
      }
      leaf variant {
        type int32 {
          range "0..64";
        }
        default "0";
        description "range 0..64; Default value: 0.";
      }
      leaf vendor {
        type eytypes:int32_range_0-16;
        default "0";
        description "range 0..16; Default value: 0.";
      }
      }
    }
    leaf chipsetsId {
      type ietfinet:ip-address;
      mandatory true;
    }
    leaf-list reservedBy {
      type string;
    }
    leaf userLabel {
      type string;
    }
  }
  grouping CUCP5qi-attributes {
    leaf cUCP5qiId {
      type string;
      mandatory true;
    }
    leaf drbDataRef {
      type string;
    }
    leaf endcUlDataSplitRef {
      type string;
    }
    leaf nrdcSnTerminationRef {
      type string;
    }
    leaf nrdcUlDataSplitRef {
      type string;
    }
    leaf pdcpSnSize {
      type int32 {
        range "12 | 18";
      }
      default "18";
      description "Default value: 18.";
    }
    leaf profile5qi {
      type eytypes:int32_range_0-255;
      mandatory true;
      description "range 0..255.";
    }
    leaf rlcMode {
      type enumeration {
        enum AM;
        enum UM;
      }
    }
    leaf tPdcpDiscard {
      type int32 {
        range "10 | 20 | 30 | 40 | 50 | 60 | 75 | 100 | 150 | 200 | 250 | 300 | 500 | 750 | 1500..2147483646";
      }
      default "1500";
      units "ms";
      description "Default value: 1500.";
    }
    leaf tReorderingDl {
      type int32 {
        range "0..2 | 4..5 | 8 | 10 | 15 | 20 | 30 | 40 | 50 | 60 | 80 | 100 | 120 | 140 | 160 | 180 | 200 | 220 | 240 | 260 | 280 | 300 | 500 | 750 | 1000 | 1250 | 1500 | 1750 | 2000 | 2250 | 2500 | 2750 | 3000";
      }
      default "200";
      units "ms";
      description "Default value: 200.";
    }
    leaf tReorderingUl {
      type int32 {
        range "0..2 | 4..5 | 8 | 10 | 15 | 20 | 30 | 40 | 50 | 60 | 80 | 100 | 120 | 140 | 160 | 180 | 200 | 220 | 240 | 260 | 280 | 300 | 500 | 750 | 1000 | 1250 | 1500 | 1750 | 2000 | 2250 | 2500 | 2750 | 3000";
      }
      default "20";
      units "ms";
      description "Default value: 20.";
    }
    leaf userLabel {
      type string;
    }
  }
  grouping CUCP5qiTable-attributes {
    leaf cUCP5qiTableId {
      type string;
      mandatory true;
    }
    leaf default5qiTable {
      type boolean;
      default "false";
      description "Default value: false.";
    }
    leaf-list reservedBy {
      type string;
    }
  }
  grouping DESManagementFunction-attributes {
    leaf dESManagementFunctionId {
      type string;
      mandatory true;
    }
    leaf desSwitch {
      type boolean;
      default "false";
      description "Default value: false.";
    }
    leaf energySavingState {
      type enumeration {
        enum IS_NOT_ENERGYSAVING;
        enum IS_ENERGYSAVING;
      }
      config false;
    }
    list esNotAllowedTimePeriod {
      key "id";
      leaf id {
        type uint32;
        description "Synthetic key for struct sequence entry.";
      }
      ordered-by user;
      container attributes {
      leaf endTime {
        type string {
          length "5";
          pattern "([0-1][0-9]|2[0-3]):([0-5][0-9])";
        }
        default "22:00";
        description "length 5..5; Default value: 22:00.";
      }
      leaf fri {
        type boolean;
        default "true";
        description "Default value: true.";
      }
      leaf mon {
        type boolean;
        default "true";
        description "Default value: true.";
      }
      leaf sat {
        type boolean;
        default "true";
        description "Default value: true.";
      }
      leaf startTime {
        type string {
          length "5";
          pattern "([0-1][0-9]|2[0-3]):([0-5][0-9])";
        }
        default "06:00";
        description "length 5..5; Default value: 06:00.";
      }
      leaf sun {
        type boolean;
        default "true";
        description "Default value: true.";
      }
      leaf thu {
        type boolean;
        default "true";
        description "Default value: true.";
      }
      leaf tue {
        type boolean;
        default "true";
        description "Default value: true.";
      }
      leaf wed {
        type boolean;
        default "true";
        description "Default value: true.";
      }
      }
    }
    list intraRatEsActivationOriginalCellLoadParameters {
      key "id";
      leaf id {
        type uint32;
        description "Synthetic key for struct entry.";
      }
      container attributes {
      leaf threshold {
        type eytypes:int32_range_0-100;
        default "10";
        units "percent";
        description "range 0..100; Default value: 10.";
      }
      leaf timeDuration {
        type int32 {
          range "60..86400";
        }
        default "900";
        units "s";
        description "range 60..86400; Default value: 900.";
      }
      }
    }
    leaf periodicEsDuration {
      type int32 {
        range "0 | 5..1440";
      }
      default "120";
      units "minute";
      description "Default value: 120.";
    }
    leaf requiredWakeUpTime {
      type int32 {
        range "15..600";
      }
      default "180";
      units "s";
      description "range 15..600; Default value: 180.";
    }
  }
  grouping DrbData-attributes {
    leaf drbDataId {
      type string;
      mandatory true;
    }
    leaf-list reservedBy {
      type string;
    }
    leaf ueConfGroupType {
      type enumeration {
        enum UE_MOBILITY_GROUP;
        enum UE_SERVICE_GROUP;
        enum UE_ADMISSION_GROUP;
      }
    }
    leaf userLabel {
      type string;
    }
  }
  grouping DrbDataUeCfg-attributes {
    leaf drbDataUeCfgId {
      type string;
      mandatory true;
    }
    leaf drbDlDataDuringHoEnabled {
      type boolean;
      default "false";
      description "Default value: false.";
    }
    leaf-list prefUeGroupList {
      type eytypes:int32_range_1-255;
      ordered-by user;
    }
    leaf-list ueConfGroupList {
      type eytypes:int32_range_1-255;
      ordered-by user;
    }
    leaf-list ueGroupList {
      type eytypes:int32_range_1-255;
      ordered-by user;
    }
    leaf userLabel {
      type string;
    }
  }
  grouping EmCall-attributes {
    leaf-list arpPrioEm5qi1List {
      type eytypes:int32_range_1-15-8;
      ordered-by user;
    }
    leaf-list arpPrioEm5qi5List {
      type eytypes:int32_range_1-15-8;
      ordered-by user;
    }
    leaf emCallId {
      type string;
      mandatory true;
    }
    leaf mobilityRestrictionsApplied {
      type boolean;
      default "true";
      description "Default value: true.";
    }
    list pLMNIdList {
      key "id";
      leaf id {
        type uint32;
        description "Synthetic key for struct sequence entry.";
      }
      ordered-by user;
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
    leaf userLabel {
      type string;
    }
  }
  grouping EndpointResource-attributes {
    leaf endpointResourceId {
      type string;
      mandatory true;
    }
    leaf-list reservedBy {
      type string;
    }
    leaf userLabel {
      type string;
    }
  }
  grouping EnergyPerformance-attributes {
    leaf energyPerformanceId {
      type string;
      mandatory true;
    }
  }
  grouping EpBoCS-attributes {
    leaf epBoCSId {
      type string;
      mandatory true;
    }
  }
  grouping EpBoosterAdvCfg-attributes {
    leaf epBoosterAdvCfgId {
      type string;
      mandatory true;
    }
    leaf-list reservedBy {
      type string;
    }
    leaf sleepEvaluateTimeWindow {
      type int32 {
        range "60..3600";
      }
      default "600";
      units "s";
      description "range 60..3600; Default value: 600.";
    }
    leaf sleepFilterTimePercentage {
      type eytypes:int32_range_0-100;
      default "90";
      units "percent";
      description "range 0..100; Default value: 90.";
    }
    leaf sleepRelBoosterFilterTimePerc {
      type eytypes:int32_range_0-100;
      default "90";
      units "percent";
      description "range 0..100; Default value: 90.";
    }
    leaf sleepUcfWakeupThreshFactor {
      type eytypes:int32_range_0-100;
      default "25";
      units "percent";
      description "range 0..100; Default value: 25.";
    }
    leaf userLabel {
      type string;
    }
    leaf wakeupEvaluateTimeWindow {
      type int32 {
        range "60..3600";
      }
      default "360";
      units "s";
      description "range 60..3600; Default value: 360.";
    }
    leaf wakeupFilterTimePercentage {
      type eytypes:int32_range_0-100;
      default "80";
      units "percent";
      description "range 0..100; Default value: 80.";
    }
    leaf wakeupMissingSampleTime {
      type eytypes:int32_range_5-300;
      default "300";
      units "s";
      description "range 5..300; Default value: 300.";
    }
    leaf wakeupPeriodicEsDuration {
      type int32 {
        range "0 | 5..1440";
      }
      default "0";
      units "minute";
      description "Default value: 0.";
    }
  }
  grouping EpBoosterCellProfile-attributes {
    leaf epBoosterAdvCfgRef {
      type string;
    }
    leaf epBoosterCellProfileId {
      type string;
      mandatory true;
    }
    leaf-list reservedBy {
      type string;
    }
    leaf sleepUcfThreshBooster {
      type int32 {
        range "0..10000";
      }
      default "500";
      units "percent";
      description "range 0..10000; Default value: 500.";
    }
    leaf userLabel {
      type string;
    }
    leaf wakeupRequiredTime {
      type int32 {
        range "2..600";
      }
      default "180";
      units "s";
      description "range 2..600; Default value: 180.";
    }
    leaf wakeupUcfThresh {
      type int32 {
        range "0..10000";
      }
      default "2000";
      units "percent";
      description "range 0..10000; Default value: 2000.";
    }
  }
  grouping EUtranCellRelation-attributes {
    leaf cellIndividualOffset {
      type int32 {
        range "-24 | -22 | -20 | -18 | -16 | -14 | -12 | -10 | -8 | -6..6 | 8 | 10 | 12 | 14 | 16 | 18 | 20 | 22 | 24";
      }
      default "0";
      units "dB";
      description "Default value: 0.";
    }
    list essCellScPairs {
      config false;
      container attributes {
      leaf eNBessLocalScId {
        type int32 {
          range "0..99999";
        }
        default "0";
        description "range 0..99999; Default value: 0.";
      }
      leaf essScPairId {
        type int64 {
          range "0..9223372036854775807";
        }
        default "0";
        description "range 0..9223372036854775807; Default value: 0.";
      }
      leaf gNBessLocalScId {
        type int32 {
          range "0..99999";
        }
        default "0";
        description "range 0..99999; Default value: 0.";
      }
      }
    }
    leaf essEnabled {
      type boolean;
      default "false";
      description "Default value: false.";
    }
    leaf eUtranCellRelationId {
      type string;
      mandatory true;
    }
    leaf isHoAllowed {
      type boolean;
      default "true";
      description "Default value: true.";
    }
    leaf isRemoveAllowed {
      type boolean;
      default "false";
      description "Default value: false.";
    }
    leaf neighborCellRef {
      type string;
      mandatory true;
    }
    leaf preferredCellManual {
      type boolean;
      default "false";
      description "Default value: false.";
    }
    leaf timeOfCreation {
      type string;
      config false;
    }
    leaf userLabel {
      type string;
    }
  }
  grouping EUtraNetwork-attributes {
    leaf eUtraNetworkId {
      type string;
      mandatory true;
    }
    leaf userLabel {
      type string;
    }
  }
  grouping EUtranFreqRelation-attributes {
    leaf allowedMeasBandwidth {
      type int32 {
        range "6 | 15 | 25 | 50 | 75 | 100";
      }
      default "6";
      units "PRB";
      description "Default value: 6.";
    }
    list allowedPlmnList {
      key "id";
      leaf id {
        type uint32;
        description "Synthetic key for struct sequence entry.";
      }
      ordered-by user;
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
    leaf anrMeasOn {
      type boolean;
      default "true";
      description "Default value: true.";
    }
    leaf candidateForSib5 {
      type boolean;
      default "true";
      description "Default value: true.";
    }
    leaf cellReselectionPriority {
      type eytypes:int32_range_-1-7;
      default "6";
      description "range -1..7; Default value: 6.";
    }
    leaf cellReselectionSubPriority {
      type int32 {
        range "2 | 4 | 6 | 8";
      }
    }
    leaf eUtranFallbackPrioEc {
      type eytypes:int32_range_-1-7;
      default "0";
      description "range -1..7; Default value: 0.";
    }
    leaf eUtranFreqRelationId {
      type string;
      mandatory true;
    }
    leaf eUtranFrequencyRef {
      type string;
      mandatory true;
    }
    leaf mcpcPCellEUtranFreqRelProfileRef {
      type string;
    }
    leaf offloadEUtranFreqRelProfileRef {
      type string;
    }
    leaf pMaxEUtra {
      type int32 {
        range "-30..33";
      }
      default "23";
      units "dBm";
      description "range -30..33; Default value: 23.";
    }
    leaf presenceAntennaPort1 {
      type ietfinet:port-number;
      description "Default value: false.";
    }
    leaf qQualMin {
      type eytypes:int32_range_-43--12;
      default "-34";
      units "dB";
      description "range -43..-12; Default value: -34.";
    }
    leaf qRxLevMin {
      type eytypes:int32_range_-140--44;
      default "-140";
      units "dBm";
      description "range -140..-44; Default value: -140.";
    }
    leaf threshXHighP {
      type eytypes:int32_range_0-62;
      default "4";
      units "dB";
      description "range 0..62; Default value: 4.";
    }
    leaf threshXHighQ {
      type eytypes:int32_range_0-31;
      units "dB";
      description "range 0..31.";
    }
    leaf threshXLowP {
      type eytypes:int32_range_0-62;
      default "0";
      units "dB";
      description "range 0..62; Default value: 0.";
    }
    leaf threshXLowQ {
      type eytypes:int32_range_0-31;
      units "dB";
      description "range 0..31.";
    }
    leaf tReselectionEUtra {
      type eytypes:int32_range_0-7-9;
      default "2";
      units "s";
      description "range 0..7; Default value: 2.";
    }
    leaf tReselectionEutraSfHigh {
      type uint32 {
        range "25 | 50 | 75 | 100";
      }
    }
    leaf tReselectionEutraSfMedium {
      type uint32 {
        range "25 | 50 | 75 | 100";
      }
    }
    leaf trStSaEUtranFreqRelProfileRef {
      type string;
    }
    leaf ucmEUtranFreqRelProfileRef {
      type string;
    }
    leaf ueMCEUtranFreqRelProfileRef {
      type string;
    }
    leaf userLabel {
      type string;
    }
    leaf voicePrio {
      type eytypes:int32_range_-1-7;
      default "0";
      description "range -1..7; Default value: 0.";
    }
  }
  grouping EUtranFrequency-attributes {
    leaf arfcnValueEUtranDl {
      type int32 {
        range "0..17999 | 36000..262143";
      }
      mandatory true;
    }
    leaf eUtranFrequencyId {
      type string;
      mandatory true;
    }
    leaf-list reservedBy {
      type string;
    }
    leaf userLabel {
      type string;
    }
  }
  grouping ExternalBroadcastPLMNInfo-attributes {
    leaf externalBroadcastPLMNInfoId {
      type string;
      mandatory true;
    }
    leaf nRTAC {
      type eytypes:int32_range_0-16777215;
      mandatory true;
      description "range 0..16777215.";
    }
    list pLMNIdList {
      key "id";
      leaf id {
        type uint32;
        description "Synthetic key for struct sequence entry.";
      }
      ordered-by user;
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
  }
  grouping ExternalENodeBFunction-attributes {
    leaf eNodeBId {
      type eytypes:int32_range_0-1048575;
      mandatory true;
      description "range 0..1048575.";
    }
    leaf externalENodeBFunctionId {
      type string;
      mandatory true;
    }
    leaf independentGapConfigSupported {
      type ietfinet:port-number;
      description "Default value: false.";
    }
    leaf isRemoveAllowed {
      type boolean;
      default "false";
      description "Default value: false.";
    }
    leaf noRelationTimeStamp {
      type int64;
      config false;
    }
    leaf pimDetectionRemoteSelected {
      type boolean;
      default "false";
      description "Default value: false.";
    }
    list pLMNId {
      key "id";
      leaf id {
        type uint32;
        description "Synthetic key for struct entry.";
      }
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
    leaf ulTrigHoAllowed {
      type boolean;
      default "false";
      description "Default value: false.";
    }
    leaf userLabel {
      type string;
    }
  }
  grouping ExternalEUtranCell-attributes {
    list additionalPlmnList {
      key "id";
      leaf id {
        type uint32;
        description "Synthetic key for struct sequence entry.";
      }
      ordered-by user;
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
    leaf cellLocalId {
      type eytypes:int32_range_0-255;
      default "0";
      description "range 0..255; Default value: 0.";
    }
    leaf dlChannelBandwidth {
      type int32 {
        range "1400 | 3000 | 5000 | 10000 | 15000 | 20000";
      }
      config false;
      units "kHz";
    }
    leaf earfcndl {
      type int32 {
        range "1..17999 | 46590..262143";
      }
      config false;
    }
    leaf earfcnul {
      type int32 {
        range "0 | 18000..35999 | 46590..262143";
      }
      config false;
    }
    leaf eUtranFrequencyRef {
      type string;
    }
    leaf externalEUtranCellId {
      type string;
      mandatory true;
    }
    leaf-list isPciConflicted {
      type enumeration {
        enum NO;
        enum YES;
      }
    }
    leaf operationalState {
      type enumeration {
        enum DISABLED;
        enum ENABLED;
      }
      config false;
    }
    list pciConflictDetectingCell {
      config false;
      container attributes {
      leaf cellLocalId {
        type eytypes:int32_range_0-16383;
        default "0";
        description "range 0..16383; Default value: 0.";
      }
      leaf gNBId {
        type eytypes:int64_range_0-4294967295;
        default "0";
        description "range 0..4294967295; Default value: 0.";
      }
      leaf gNBIdLength {
        type eytypes:int32_range_22-32;
        default "22";
        description "range 22..32; Default value: 22.";
      }
      leaf mcc {
        type eytypes:int32_range_0-999;
        default "1";
        description "range 0..999; Default value: 1.";
      }
      leaf mnc {
        type eytypes:int32_range_0-999;
        default "1";
        description "range 0..999; Default value: 1.";
      }
      leaf mncLength {
        type eytypes:int32_range_2-3;
        default "2";
        description "range 2..3; Default value: 2.";
      }
      }
    }
    list pciConflictedCell {
      config false;
      container attributes {
      leaf cellLocalId {
        type eytypes:int32_range_0-255;
        default "0";
        description "range 0..255; Default value: 0.";
      }
      leaf eNodeBId {
        type eytypes:int32_range_0-1048575;
        default "0";
        description "range 0..1048575; Default value: 0.";
      }
      leaf mcc {
        type eytypes:int32_range_0-999;
        default "1";
        description "range 0..999; Default value: 1.";
      }
      leaf mnc {
        type eytypes:int32_range_0-999;
        default "1";
        description "range 0..999; Default value: 1.";
      }
      leaf mncLength {
        type eytypes:int32_range_2-3;
        default "2";
        description "range 2..3; Default value: 2.";
      }
      }
    }
    leaf physicalLayerCellId {
      type eytypes:int32_range_0-503;
      default "0";
      description "range 0..503; Default value: 0.";
    }
    leaf pimDetectionRole {
      type enumeration {
        enum AGGRESSOR;
        enum VICTIM;
        enum VICTIM_AND_AGGRESSOR;
      }
      config false;
    }
    leaf-list reservedBy {
      type string;
    }
    leaf tac {
      type eytypes:int32_range_0-65535-10;
      default "0";
      description "range 0..65535; Default value: 0.";
    }
    leaf ulChannelBandwidth {
      type int32 {
        range "1400 | 3000 | 5000 | 10000 | 15000 | 20000";
      }
      config false;
      units "kHz";
    }
  }
  grouping ExternalGNBCUCPFunction-attributes {
    list amfRegionInfoList {
      key "id";
      leaf id {
        type uint32;
        description "Synthetic key for struct sequence entry.";
      }
      ordered-by user;
      container attributes {
      leaf amfRegionId {
        type eytypes:int32_range_0-255;
        default "0";
        description "range 0..255; Default value: 0.";
      }
      leaf mcc {
        type string {
          length "3";
          pattern "[02345679][0-9][0-9]";
        }
        default "001";
        description "length 3..3; Default value: 001.";
      }
      leaf mnc {
        type string {
          length "2..3";
          pattern "(([0-9][0-9][0-9])|([0-9][0-9]))";
        }
        default "01";
        description "length 2..3; Default value: 01.";
      }
      }
    }
    leaf externalGNBCUCPFunctionId {
      type string;
      mandatory true;
    }
    leaf gNBId {
      type eytypes:int64_range_0-4294967295;
      mandatory true;
      description "range 0..4294967295.";
    }
    leaf gNBIdLength {
      type eytypes:int32_range_22-32;
      default "22";
      description "range 22..32; Default value: 22.";
    }
    leaf isRemoveAllowed {
      type boolean;
      default "false";
      description "Default value: false.";
    }
    leaf noRelationTimeStamp {
      type int64;
      config false;
    }
    list pLMNId {
      key "id";
      leaf id {
        type uint32;
        description "Synthetic key for struct entry.";
      }
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
    leaf sameUeGroupSelection {
      type boolean;
      config false;
    }
    leaf timeOfCreation {
      type string;
      config false;
    }
    leaf ulTrigHoAllowed {
      type boolean;
      default "false";
      description "Default value: false.";
    }
    leaf ulTrigHoSupport {
      type ietfinet:port-number;
      config false;
    }
  }
  grouping ExternalNRCellCU-attributes {
    leaf cellLocalId {
      type eytypes:int32_range_0-16383;
      default "0";
      description "range 0..16383; Default value: 0.";
    }
    leaf externalNRCellCUId {
      type string;
      mandatory true;
    }
    leaf-list isPciConflicted {
      type enumeration {
        enum NO;
        enum YES;
      }
    }
    leaf nRFrequencyRef {
      type string;
      mandatory true;
    }
    leaf nRPCI {
      type int32 {
        range "0..1007";
      }
      mandatory true;
      description "range 0..1007.";
    }
    leaf nRTAC {
      type uint32 {
        range "0..16777215";
      }
      description "range 0..16777215.";
    }
    list pciConflictDetectingCell {
      config false;
      container attributes {
      leaf cellLocalId {
        type eytypes:int32_range_0-16383;
        default "0";
        description "range 0..16383; Default value: 0.";
      }
      leaf gNBId {
        type eytypes:int64_range_0-4294967295;
        default "0";
        description "range 0..4294967295; Default value: 0.";
      }
      leaf gNBIdLength {
        type eytypes:int32_range_22-32;
        default "22";
        description "range 22..32; Default value: 22.";
      }
      leaf mcc {
        type eytypes:int32_range_0-999;
        default "1";
        description "range 0..999; Default value: 1.";
      }
      leaf mnc {
        type eytypes:int32_range_0-999;
        default "1";
        description "range 0..999; Default value: 1.";
      }
      leaf mncLength {
        type eytypes:int32_range_2-3;
        default "2";
        description "range 2..3; Default value: 2.";
      }
      }
    }
    list pciConflictedCell {
      config false;
      container attributes {
      leaf cellLocalId {
        type eytypes:int32_range_0-16383;
        default "0";
        description "range 0..16383; Default value: 0.";
      }
      leaf gNBId {
        type eytypes:int64_range_0-4294967295;
        default "0";
        description "range 0..4294967295; Default value: 0.";
      }
      leaf gNBIdLength {
        type eytypes:int32_range_22-32;
        default "22";
        description "range 22..32; Default value: 22.";
      }
      leaf mcc {
        type eytypes:int32_range_0-999;
        default "1";
        description "range 0..999; Default value: 1.";
      }
      leaf mnc {
        type eytypes:int32_range_0-999;
        default "1";
        description "range 0..999; Default value: 1.";
      }
      leaf mncLength {
        type eytypes:int32_range_2-3;
        default "2";
        description "range 2..3; Default value: 2.";
      }
      }
    }
    list plmnIdList {
      key "id";
      leaf id {
        type uint32;
        description "Synthetic key for struct sequence entry.";
      }
      ordered-by user;
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
    list primaryPLMNId {
      config false;
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
    leaf-list reservedBy {
      type string;
    }
    leaf serviceState {
      type enumeration {
        enum OUT_OF_SERVICE;
        enum IN_SERVICE;
      }
      config false;
    }
    list sNSSAIList {
      key "id";
      leaf id {
        type uint32;
        description "Synthetic key for struct sequence entry.";
      }
      ordered-by user;
      container attributes {
      leaf sd {
        type eytypes:int32_range_0-16777215;
        description "range 0..16777215.";
      }
      leaf sst {
        type eytypes:int32_range_0-255;
        description "range 0..255.";
      }
      }
    }
    leaf timeOfCreation {
      type string;
      config false;
    }
  }
  grouping GNBCUCPFunction-attributes {
    leaf advUePosPeriodicityMode {
      type enumeration {
        enum COMB_PERIODICITY;
        enum AOA_PERIODICITY;
      }
    }
    leaf altDepHBoCSEnabled {
      type boolean;
      default "false";
      description "Default value: false.";
    }
    leaf altDepHNasInactTimeEnabled {
      type boolean;
      default "false";
      description "Default value: false.";
    }
    leaf autoNRCellCUCleanupSupported {
      type ietfinet:port-number;
      description "Default value: false.";
    }
    list blockedGNodeBList {
      key "id";
      leaf id {
        type uint32;
        description "Synthetic key for struct sequence entry.";
      }
      ordered-by user;
      container attributes {
      leaf directPacketForwarding {
        type boolean;
        default "true";
        description "Default value: true.";
      }
      leaf gNBId {
        type int64 {
          range "-1..4294967295";
        }
        default "0";
        description "range -1..4294967295; Default value: 0.";
      }
      leaf gNBIdLength {
        type eytypes:int32_range_22-32;
        default "22";
        description "range 22..32; Default value: 22.";
      }
      leaf mcc {
        type eytypes:int32_range_0-999;
        default "1";
        description "range 0..999; Default value: 1.";
      }
      leaf mnc {
        type eytypes:int32_range_0-999;
        default "1";
        description "range 0..999; Default value: 1.";
      }
      leaf mncLength {
        type eytypes:int32_range_2-3;
        default "2";
        description "range 2..3; Default value: 2.";
      }
      }
    }
    leaf caDepHEnabled {
      type boolean;
      default "true";
      description "Default value: true.";
    }
    leaf cellRelationMOThresh {
      type int32 {
        range "0 | 320..7000";
      }
      default "1500";
      description "Default value: 1500.";
    }
    leaf completeCellListXnEnabled {
      type boolean;
      default "false";
      description "Default value: false.";
    }
    leaf dnsLookup5GsTaiPeriodicTimer {
      type ietfinet:ip-address;
      units "h";
      description "range 0..1000; Default value: 0.";
    }
    leaf dnsLookupOn5GsTai {
      type boolean;
      default "false";
      description "Default value: false.";
    }
    leaf endcMdtM1DelayTimeForMeasGap {
      type int32 {
        range "0..2000";
      }
      default "1";
      units "ms";
      description "range 0..2000; Default value: 1.";
    }
    leaf endpointResourceRef {
      type string;
    }
    leaf extEnbRemoveTime {
      type uint32 {
        range "0..10080";
      }
      default "1440";
      units "minute";
      description "range 0..10080; Default value: 1440.";
    }
    leaf extendedBandN77Supported {
      type ietfinet:port-number;
      description "Default value: false.";
    }
    leaf extendedBandN77TwoSupported {
      type ietfinet:port-number;
      description "Default value: false.";
    }
    leaf extendedXnConnAllowed {
      type boolean;
    }
    leaf extNrCellRemovalByXnSupported {
      type ietfinet:port-number;
      description "Default value: false.";
    }
    leaf gNBCUCPFunctionId {
      type string;
      mandatory true;
    }
    leaf gNBCUName {
      type string {
        length "1..150";
      }
      description "length 1..150.";
    }
    leaf gNBId {
      type eytypes:int64_range_0-4294967295;
      mandatory true;
      description "range 0..4294967295.";
    }
    leaf gNBIdLength {
      type eytypes:int32_range_22-32;
      default "22";
      description "range 22..32; Default value: 22.";
    }
    leaf iratDirectPktFwdEnabled {
      type boolean;
      default "true";
      description "Default value: true.";
    }
    leaf lastUpdateAca {
      type string;
      config false;
    }
    leaf maxCommonProcTime {
      type eytypes:int32_range_1-60;
      default "30";
      units "s";
      description "range 1..60; Default value: 30.";
    }
    leaf maxNgRetryTime {
      type int32 {
        range "1..3600";
      }
      default "30";
      units "s";
      description "range 1..3600; Default value: 30.";
    }
    leaf nasInactivityTime {
      type eytypes:int32_range_1-60;
      default "5";
      units "s";
      description "range 1..60; Default value: 5.";
    }
    leaf networkIdInUeCapEnq {
      type boolean;
      default "false";
      description "Default value: false.";
    }
    leaf ngapHoAtXnHoFailEnabled {
      type boolean;
      default "false";
      description "Default value: false.";
    }
    leaf ngcDedProcTime {
      type eytypes:int32_range_1-60;
      default "5";
      units "s";
      description "range 1..60; Default value: 5.";
    }
    leaf noOfSupportedNRCellCU {
      type ietfinet:port-number;
      config false;
      status deprecated;
      description "MOM flags: noNotification, isNillable=true; Status info: Since 24.Q4. Replaced by CardinalityLimits::maxNRCellCU. Planned to be removed..";
    }
    leaf nrNeedForGapsSupported {
      type ietfinet:port-number;
      description "Default value: true.";
    }
    leaf pimAutoDetectionEnabled {
      type boolean;
      status deprecated;
      default "false";
      description "Default value: false; Status info: Since 25.Q3. Replaced by pimDetectionEnabled. Planned to be removed..";
    }
    leaf pimDetectionEnabled {
      type boolean;
      default "false";
      description "Default value: false.";
    }
    list pLMNId {
      key "id";
      leaf id {
        type uint32;
        description "Synthetic key for struct entry.";
      }
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
    leaf prefInterGnbHo {
      type enumeration {
        enum XN_HO;
        enum NG_HO;
      }
    }
    leaf pwsBroadcastStarted {
      type boolean;
      config false;
    }
    leaf ranNodeName {
      type string {
        length "1..150";
        pattern "[A-Za-z0-9 '()+\\,./:=?-]+";
      }
      description "length 1..150.";
    }
    leaf release {
      type string;
      config false;
    }
    leaf resourceStatusReportDefault {
      type ietfinet:port-number;
      description "Default value: -2.";
    }
    leaf resourceStatusReportF1Enabled {
      type ietfinet:port-number;
      description "Default value: true.";
    }
    list rfspSpidPairList {
      key "id";
      leaf id {
        type uint32;
        description "Synthetic key for struct sequence entry.";
      }
      ordered-by user;
      container attributes {
      leaf rfsp {
        type eytypes:int32_range_1-256;
        description "range 1..256.";
      }
      leaf spid {
        type eytypes:int32_range_1-256;
        description "range 1..256.";
      }
      }
    }
    leaf ribTmAutoMax {
      type eytypes:int32_range_0-20;
      default "0";
      description "range 0..20; Default value: 0.";
    }
    leaf rrcReestSupportType {
      type ietfinet:port-number;
    }
    leaf servAdapUPProfUlDepHEnabled {
      type boolean;
      default "true";
      description "Default value: true.";
    }
    leaf tCellStateSupervision {
      type int32 {
        range "4..3600";
      }
      default "300";
      units "s";
      description "range 4..3600; Default value: 300.";
    }
    leaf tDcOverall {
      type eytypes:int32_range_1-20;
      default "7";
      units "s";
      description "range 1..20; Default value: 7.";
    }
    leaf tInHoRrcReconfigComplete {
      type eytypes:int32_range_1-60;
      default "5";
      units "s";
      description "range 1..60; Default value: 5.";
    }
    leaf tNgPathSwitchRequest {
      type eytypes:int32_range_1-60;
      default "5";
      units "s";
      description "range 1..60; Default value: 5.";
    }
    leaf tNgRelocOverall {
      type eytypes:int32_range_1-60;
      default "5";
      units "s";
      description "range 1..60; Default value: 5.";
    }
    leaf tNgRelocPrep {
      type eytypes:int32_range_1-60;
      default "5";
      units "s";
      description "range 1..60; Default value: 5.";
    }
    leaf tXnDcOverall {
      type eytypes:int32_range_1-20;
      default "5";
      units "s";
      description "range 1..20; Default value: 5.";
    }
    leaf tXnDcPrep {
      type eytypes:int32_range_1-20;
      default "5";
      units "s";
      description "range 1..20; Default value: 5.";
    }
    leaf tXnRelocOverall {
      type eytypes:int32_range_1-60;
      default "5";
      units "s";
      description "range 1..60; Default value: 5.";
    }
    leaf tXnRelocPrep {
      type eytypes:int32_range_1-60;
      default "5";
      units "s";
      description "range 1..60; Default value: 5.";
    }
    leaf userLabel {
      type string;
    }
    leaf xnIpAddrViaNgActive {
      type ietfinet:ip-address;
      description "Default value: true.";
    }
    leaf pmPagDiscardedMpLoadEdrx {
      type uint64;
      config false;
    }
    leaf pmRrcConnLevelSamp {
      type uint64;
      config false;
    }
    leaf pmNgLinkBreak {
      type uint64;
      config false;
    }
    leaf-list pmFwkStreamProducedEventDistr {
      type uint64;
    }
    leaf pmPagDiscardedMpLoad {
      type uint64;
      config false;
    }
    leaf-list pmFwkStreamDroppedEventSlowStreamDistr {
      type uint64;
    }
    leaf pmXnSetupRequestOut {
      type uint64;
      config false;
    }
    leaf pmRrcInactRedCapLevelMax {
      type int64;
      config false;
    }
    leaf pmEndcInitAccessRejGnbBbIntens {
      type uint64;
      config false;
    }
    leaf pmNrdcInitAccessRejUeCapacityLimit {
      type uint64;
      config false;
    }
    leaf pmEndcPSCellChangeRejInInterGnbUeAdmission {
      type uint64;
      config false;
      status deprecated;
      description "MOM flags: noNotification.";
    }
    leaf pmXnSetupRequestIn {
      type uint64;
      config false;
    }
    leaf pmRrcInactLevelSum {
      type uint64;
      config false;
    }
    leaf pmEndcPSCellChangeRejInInterGnbUeCapacityLimit {
      type uint64;
      config false;
    }
    leaf pmPagNgReceivedEdrx {
      type uint64;
      config false;
    }
    leaf-list pmFwkStreamDroppedEventSocketConnectionFailDistr {
      type uint64;
    }
    leaf pmXnNodeConfigUpdateAckIn {
      type uint64;
      config false;
    }
    leaf pmEndcPSCellChangeRejInInterGnbBbIntens {
      type uint64;
      config false;
    }
    leaf pmNrdcPSCellChangeRejInInterGnbUeCapacityLimit {
      type uint64;
      config false;
    }
    leaf pmEndcPSCellChangeRejInInterGnbMpLoad {
      type uint64;
      config false;
    }
    leaf pmRrcInactRedCapLevelSum {
      type uint64;
      config false;
    }
    leaf pmNrdcInitAccessRejUeAdmission {
      type uint64;
      config false;
      status deprecated;
      description "MOM flags: noNotification.";
    }
    leaf pmNrdcPSCellChangeRejInInterGnbUeAdmission {
      type uint64;
      config false;
      status deprecated;
      description "MOM flags: noNotification.";
    }
    leaf-list pmFwkStreamDroppedEventDistr {
      type uint64;
    }
    leaf pmXnNodeConfigUpdateOut {
      type uint64;
      config false;
    }
    leaf pmRrcConnLevelSumNrDc {
      type uint64;
      config false;
    }
    leaf pmPagNgReceivedPriority {
      type uint64;
      config false;
    }
    leaf pmRrcConnLevelMaxEnDc {
      type int64;
      config false;
    }
    leaf pmXnSetupResponseIn {
      type uint64;
      config false;
    }
    leaf-list pmFwkStreamDroppedEventSocketErrorDistr {
      type uint64;
    }
    leaf pmXnNodeConfigUpdateFailIn {
      type uint64;
      config false;
    }
    leaf pmRrcConnLevelSumEnDc {
      type uint64;
      config false;
    }
    leaf pmRrcInactLevelMax {
      type int64;
      config false;
    }
    leaf pmRrcConnLevelMaxNrDc {
      type int64;
      config false;
    }
    leaf pmEndcInitAccessRejUeCapacityLimit {
      type uint64;
      config false;
    }
    leaf pmXnNodeConfigUpdateFailOut {
      type uint64;
      config false;
    }
    leaf pmPagRanIntraGnbNonTrig {
      type uint64;
      config false;
    }
    leaf pmRrcConnLevelMax {
      type int64;
      config false;
    }
    leaf pmXnSetupFailIn {
      type uint64;
      config false;
    }
    leaf pmPagNgDiscardedEdrx {
      type uint64;
      config false;
    }
    leaf pmEndcInitAccessRejUeAdmission {
      type uint64;
      config false;
      status deprecated;
      description "MOM flags: noNotification.";
    }
    leaf pmRrcConnLevelSumSa {
      type uint64;
      config false;
    }
    leaf pmPagNgReceived {
      type uint64;
      config false;
    }
    leaf pmUeCtxtRetrieveFailRrcReestNoUeCtxt {
      type uint64;
      config false;
    }
    leaf pmPagNgDiscarded {
      type uint64;
      config false;
    }
    leaf-list pmFwkStreamDroppedEventLicenseUnavailableDistr {
      type uint64;
    }
    leaf pmXnSetupResponseOut {
      type uint64;
      config false;
    }
    leaf pmEndcInitAccessRejGnbMpLoad {
      type uint64;
      config false;
    }
    leaf-list pmFwkStreamDroppedEventSocketSetupFailDistr {
      type uint64;
    }
    leaf pmPagRanIntraGnbTrig {
      type uint64;
      config false;
    }
    leaf pmXnSetupFailOut {
      type uint64;
      config false;
    }
    leaf pmXnNodeConfigUpdateIn {
      type uint64;
      config false;
    }
    leaf pmRrcConnLevelMaxSa {
      type int64;
      config false;
    }
    leaf pmRrcConnRedCapLevelSum {
      type uint64;
      config false;
    }
    leaf pmRrcConnRedCapLevelMax {
      type int64;
      config false;
    }
    leaf pmXnNodeConfigUpdateAckOut {
      type uint64;
      config false;
    }
    leaf pmRrcInactLevelSamp {
      type uint64;
      config false;
    }
    leaf pmNeighborObjFootprint {
      type int64;
      config false;
    }
  }
  grouping ImeiSvGroup-attributes {
    leaf imeiSvGroupId {
      type string;
      mandatory true;
    }
    list imeiTacSvSnList {
      key "id";
      leaf id {
        type uint32;
        description "Synthetic key for struct sequence entry.";
      }
      ordered-by user;
      container attributes {
      leaf maxSn {
        type int32 {
          range "0..999999";
        }
        default "999999";
        description "range 0..999999; Default value: 999999.";
      }
      leaf maxSvn {
        type eytypes:int32_range_0-99;
        default "99";
        description "range 0..99; Default value: 99.";
      }
      leaf minSn {
        type int32 {
          range "0..999999";
        }
        default "0";
        description "range 0..999999; Default value: 0.";
      }
      leaf minSvn {
        type eytypes:int32_range_0-99;
        default "0";
        description "range 0..99; Default value: 0.";
      }
      leaf tac {
        type int32 {
          range "0..99999999";
        }
        default "0";
        description "range 0..99999999; Default value: 0.";
      }
      }
    }
    leaf-list reservedBy {
      type string;
    }
    leaf userLabel {
      type string;
    }
  }
  grouping ImeiSvGroups-attributes {
    leaf imeiSvGroupsId {
      type string;
      mandatory true;
    }
    leaf userLabel {
      type string;
    }
  }
  grouping ImeiSvs-attributes {
    leaf-list imeiSvsGroupRef {
      type string;
      ordered-by user;
    }
    leaf imeiSvsId {
      type string;
      mandatory true;
    }
    leaf-list reservedBy {
      type string;
    }
    leaf userLabel {
      type string;
    }
  }
  grouping InactivityProfile-attributes {
    leaf inactivityProfileId {
      type string;
      mandatory true;
    }
    leaf ueConfGroupType {
      type enumeration {
        enum UE_MOBILITY_GROUP;
        enum UE_SERVICE_GROUP;
        enum UE_ADMISSION_GROUP;
      }
    }
  }
  grouping InactivityProfileUeCfg-attributes {
    leaf inactivityProfileUeCfgId {
      type string;
      mandatory true;
    }
    leaf nasInactivityTime {
      type eytypes:int32_range_1-60;
      default "5";
      units "s";
      description "range 1..60; Default value: 5.";
    }
    leaf-list prefUeGroupList {
      type eytypes:int32_range_0-255;
      ordered-by user;
    }
    leaf tInactivityTimer {
      type eytypes:int32_range_1-7200;
      default "10";
      units "s";
      description "range 1..7200; Default value: 10.";
    }
    leaf tInactivityTimerEndcSn {
      type eytypes:int32_range_1-7200;
      default "5";
      units "s";
      description "range 1..7200; Default value: 5.";
    }
    leaf tInactivityTimerNrdcSn {
      type eytypes:int32_range_1-7200;
      default "10";
      units "s";
      description "range 1..7200; Default value: 10.";
    }
    leaf-list ueConfGroupList {
      type eytypes:int32_range_1-255;
      ordered-by user;
    }
    leaf-list ueGroupList {
      type eytypes:int32_range_0-255;
      ordered-by user;
    }
    leaf userLabel {
      type string;
    }
  }
  grouping InitialCg-attributes {
    leaf initialCgId {
      type string;
      mandatory true;
    }
    leaf-list reservedBy {
      type string;
    }
    leaf ueConfGroupType {
      type enumeration {
        enum UE_MOBILITY_GROUP;
        enum UE_SERVICE_GROUP;
        enum UE_ADMISSION_GROUP;
      }
    }
    leaf userLabel {
      type string;
    }
  }
  grouping InitialCgUeCfg-attributes {
    leaf initialCgUeCfgId {
      type string;
      mandatory true;
    }
    leaf-list prefUeGroupList {
      type eytypes:int32_range_1-255;
      ordered-by user;
    }
    leaf-list ueConfGroupList {
      type eytypes:int32_range_1-255;
      ordered-by user;
    }
    leaf-list ueGroupList {
      type eytypes:int32_range_1-255;
      ordered-by user;
    }
    leaf ulScgInitialCritRsrpThresh {
      type eytypes:int32_range_-156--29;
      default "-140";
      units "dBm";
      description "range -156..-29; Default value: -140.";
    }
    leaf ulScgInitialLowRsrpThresh {
      type eytypes:int32_range_-156--29;
      default "-110";
      units "dBm";
      description "range -156..-29; Default value: -110.";
    }
    leaf userLabel {
      type string;
    }
  }
  grouping IntraFreqMC-attributes {
    leaf intraFreqMCId {
      type string;
      mandatory true;
    }
    leaf sCellDepHEnabled {
      type boolean;
    }
  }
  grouping IntraFreqMCCellProfile-attributes {
    leaf betterSpCellTriggerQuantity {
      type enumeration {
        enum RSRP;
        enum RSRQ;
      }
    }
    leaf endcActionEvalFail {
      type enumeration {
        enum RELEASE;
        enum IGNORE;
      }
    }
    leaf intraFreqMCCellProfileId {
      type string;
      mandatory true;
    }
    leaf-list reservedBy {
      type string;
    }
    list rsrpBetterSCell {
      key "id";
      leaf id {
        type uint32;
        description "Synthetic key for struct entry.";
      }
      container attributes {
      leaf hysteresis {
        type eytypes:int32_range_0-150;
        default "10";
        units "dB";
        description "range 0..150; Default value: 10.";
      }
      leaf offset {
        type eytypes:int32_range_-150-150;
        default "30";
        units "dB";
        description "range -150..150; Default value: 30.";
      }
      leaf timeToTrigger {
        type int32;
        default "160";
        units "ms";
        description "Default value: 160.";
      }
      }
    }
    list rsrpBetterSpCell {
      key "id";
      leaf id {
        type uint32;
        description "Synthetic key for struct entry.";
      }
      container attributes {
      leaf hysteresis {
        type eytypes:int32_range_0-150;
        default "10";
        units "dB";
        description "range 0..150; Default value: 10.";
      }
      leaf offset {
        type eytypes:int32_range_-150-150;
        default "30";
        units "dB";
        description "range -150..150; Default value: 30.";
      }
      leaf timeToTrigger {
        type int32;
        default "640";
        units "ms";
        description "Default value: 640.";
      }
      }
    }
    list rsrpSCellCoverage {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-156--29;
        default "-156";
        units "dBm";
        description "range -156..-29; Default value: -156.";
      }
      leaf timeToTrigger {
        type int32;
        default "160";
        units "ms";
        description "Default value: 160.";
      }
      leaf timeToTriggerA1 {
        type int32;
        default "-1";
        units "ms";
        description "Default value: -1.";
      }
      }
    }
    list rsrqBetterSpCell {
      key "id";
      leaf id {
        type uint32;
        description "Synthetic key for struct entry.";
      }
      container attributes {
      leaf hysteresis {
        type eytypes:int32_range_0-150;
        default "10";
        units "dB";
        description "range 0..150; Default value: 10.";
      }
      leaf offset {
        type eytypes:int32_range_-150-150;
        default "30";
        units "dB";
        description "range -150..150; Default value: 30.";
      }
      leaf timeToTrigger {
        type int32;
        default "640";
        units "ms";
        description "Default value: 640.";
      }
      }
    }
    list rsrqSCellCoverage {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-435-200;
        default "-435";
        units "dB";
        description "range -435..200; Default value: -435.";
      }
      leaf timeToTrigger {
        type int32;
        default "160";
        units "ms";
        description "Default value: 160.";
      }
      leaf timeToTriggerA1 {
        type int32;
        default "-1";
        units "ms";
        description "Default value: -1.";
      }
      }
    }
    leaf sCellCoverageTriggerQuantity {
      type enumeration {
        enum RSRP;
        enum RSRQ;
      }
    }
    leaf ueConfGroupType {
      type enumeration {
        enum UE_MOBILITY_GROUP;
        enum UE_SERVICE_GROUP;
        enum UE_ADMISSION_GROUP;
      }
    }
    leaf userLabel {
      type string;
    }
  }
  grouping IntraFreqMCCellProfileUeCfg-attributes {
    leaf betterSCellReportConfigMode {
      type ietfinet:port-number;
      status deprecated;
      description "Default value: ALWAYS; Takes effect: New connection; Status info: Since 24.Q1. Replaced by CaCellMeasProfileUeCfg::betterSCellReportConfigMode. Planned to be removed..";
      reference "Takes effect: New connection.";
    }
    leaf betterSpCellTriggerQuantity {
      type enumeration {
        enum RSRP;
        enum RSRQ;
        enum SINR_FALLBACK_RSRP;
        enum SINR_FALLBACK_RSRQ;
      }
    }
    leaf endcActionEvalFail {
      type enumeration {
        enum RELEASE;
        enum IGNORE;
      }
    }
    leaf intraFreqMCCellProfileUeCfgId {
      type string;
      mandatory true;
    }
    leaf maxReportCells {
      type ietfinet:port-number;
      default "1";
      description "range 1..8; Default value: 1.";
    }
    leaf-list prefUeGroupList {
      type eytypes:int32_range_1-255;
      ordered-by user;
    }
    list rsrpBetterSCell {
      key "id";
      leaf id {
        type uint32;
        description "Synthetic key for struct entry.";
      }
      description "Takes effect: New connection; Status info: Since 24.Q1. Replaced by CaCellMeasProfileUeCfg::rsrpBetterSCell. Planned to be removed.; Specification: 3GPP TS 38.331.";
      container attributes {
      leaf hysteresis {
        type eytypes:int32_range_0-150;
        default "10";
        units "dB";
        description "range 0..150; Default value: 10.";
      }
      leaf offset {
        type eytypes:int32_range_-150-150;
        default "30";
        units "dB";
        description "range -150..150; Default value: 30.";
      }
      leaf timeToTrigger {
        type int32;
        default "160";
        units "ms";
        description "Default value: 160.";
      }
      }
    }
    list rsrpBetterSpCell {
      key "id";
      leaf id {
        type uint32;
        description "Synthetic key for struct entry.";
      }
      container attributes {
      leaf hysteresis {
        type eytypes:int32_range_0-150;
        default "10";
        units "dB";
        description "range 0..150; Default value: 10.";
      }
      leaf offset {
        type eytypes:int32_range_-150-150;
        default "30";
        units "dB";
        description "range -150..150; Default value: 30.";
      }
      leaf timeToTrigger {
        type int32;
        default "640";
        units "ms";
        description "Default value: 640.";
      }
      }
    }
    list rsrpSCellCoverage {
      key "id";
      leaf id {
        type uint32;
        description "Synthetic key for struct entry.";
      }
      description "Takes effect: New connection; Status info: Since 24.Q1. Replaced by CaCellMeasProfileUeCfg::rsrpSCellCoverage. Planned to be removed.; Specification: 3GPP TS 38.331.";
      container attributes {
      leaf hysteresis {
        type eytypes:int32_range_0-150;
        default "10";
        units "dB";
        description "range 0..150; Default value: 10.";
      }
      leaf threshold {
        type eytypes:int32_range_-156--29;
        default "-156";
        units "dBm";
        description "range -156..-29; Default value: -156.";
      }
      leaf timeToTrigger {
        type int32;
        default "160";
        units "ms";
        description "Default value: 160.";
      }
      leaf timeToTriggerA1 {
        type int32;
        default "-1";
        units "ms";
        description "Default value: -1.";
      }
      }
    }
    list rsrqBetterSpCell {
      key "id";
      leaf id {
        type uint32;
        description "Synthetic key for struct entry.";
      }
      container attributes {
      leaf hysteresis {
        type eytypes:int32_range_0-150;
        default "10";
        units "dB";
        description "range 0..150; Default value: 10.";
      }
      leaf offset {
        type eytypes:int32_range_-150-150;
        default "30";
        units "dB";
        description "range -150..150; Default value: 30.";
      }
      leaf timeToTrigger {
        type int32;
        default "640";
        units "ms";
        description "Default value: 640.";
      }
      }
    }
    list rsrqSCellCoverage {
      key "id";
      leaf id {
        type uint32;
        description "Synthetic key for struct entry.";
      }
      description "Takes effect: New connection; Status info: Since 24.Q1. Replaced by CaCellMeasProfileUeCfg::rsrqSCellCoverage. Planned to be removed.; Specification: 3GPP TS 38.331.";
      container attributes {
      leaf hysteresis {
        type eytypes:int32_range_0-150;
        default "10";
        units "dB";
        description "range 0..150; Default value: 10.";
      }
      leaf threshold {
        type eytypes:int32_range_-435-200;
        default "-435";
        units "dB";
        description "range -435..200; Default value: -435.";
      }
      leaf timeToTrigger {
        type int32;
        default "160";
        units "ms";
        description "Default value: 160.";
      }
      leaf timeToTriggerA1 {
        type int32;
        default "-1";
        units "ms";
        description "Default value: -1.";
      }
      }
    }
    leaf sCellCoverageTriggerQuantity {
      type enumeration {
        enum RSRP;
        enum RSRQ;
      }
      status deprecated;
      default "RSRP";
      description "Default value: RSRP; Takes effect: New connection; Status info: Since 24.Q1. Replaced by CaCellMeasProfileUeCfg::sCellCoverageTriggerQuantity. Planned to be removed.; Specification: 3GPP TS 38.331.";
      reference "Takes effect: New connection.";
    }
    list sinrBetterSpCell {
      key "id";
      leaf id {
        type uint32;
        description "Synthetic key for struct entry.";
      }
      container attributes {
      leaf hysteresis {
        type eytypes:int32_range_0-150;
        default "10";
        units "dB";
        description "range 0..150; Default value: 10.";
      }
      leaf offset {
        type eytypes:int32_range_-150-150;
        default "30";
        units "dB";
        description "range -150..150; Default value: 30.";
      }
      leaf timeToTrigger {
        type int32;
        default "640";
        units "ms";
        description "Default value: 640.";
      }
      }
    }
    leaf-list ueConfGroupList {
      type eytypes:int32_range_1-255;
      ordered-by user;
    }
    leaf-list ueGroupList {
      type eytypes:int32_range_1-255;
      ordered-by user;
    }
    leaf userLabel {
      type string;
    }
    leaf useT312BetterPCellCandidateA3 {
      type boolean;
      default "false";
      description "Default value: false.";
    }
  }
  grouping IntraFreqMCFreqRelProfile-attributes {
    leaf intraFreqMCFreqRelProfileId {
      type string;
      mandatory true;
      status deprecated;
      description "MOM flags: restricted, noNotification; Status info: Since 24.Q1. Planned to be removed..";
    }
    leaf-list reservedBy {
      type string;
      description "Status info: Since 24.Q1. Planned to be removed..";
    }
    leaf ueConfGroupType {
      type enumeration {
        enum UE_MOBILITY_GROUP;
        enum UE_SERVICE_GROUP;
        enum UE_ADMISSION_GROUP;
      }
      status deprecated;
      default "UE_MOBILITY_GROUP";
      description "Default value: UE_MOBILITY_GROUP; Takes effect: Next usage; Status info: Since 24.Q1. Replaced by CaFreqRelMeasProfile::ueConfGroupType. Planned to be removed..";
      reference "Takes effect: Next usage.";
    }
    leaf userLabel {
      type string;
      status deprecated;
      description "MOM flags: isNillable=true; Status info: Since 24.Q1. Planned to be removed..";
    }
  }
  grouping IntraFreqMCFreqRelProfileUeCfg-attributes {
    leaf intraFreqMCFreqRelProfileUeCfgId {
      type string;
      mandatory true;
      status deprecated;
      description "MOM flags: restricted, noNotification; Status info: Since 24.Q1. Planned to be removed..";
    }
    leaf-list prefUeGroupList {
      type eytypes:int32_range_1-255;
      ordered-by user;
      description "Takes effect: Next usage; Status info: Since 24.Q1. Replaced by CaFreqRelMeasProfileUeCfg::prefUeGroupList. Planned to be removed..";
    }
    leaf rsrpSCellCoverageThrOffset {
      type eytypes:int32_range_-30-30;
      status deprecated;
      default "0";
      units "dB";
      description "range -30..30; Default value: 0; Takes effect: Next usage; Status info: Since 24.Q1. Replaced by CaFreqRelMeasProfileUeCfg::rsrpSCellCoverageThrOffset. Planned to be removed.; Specification: 3GPP TS 38.331.";
      reference "Takes effect: Next usage.";
    }
    leaf rsrqSCellCoverageThrOffset {
      type eytypes:int32_range_-300-300;
      status deprecated;
      default "0";
      units "dB";
      description "range -300..300; Default value: 0; Takes effect: Next usage; Status info: Since 24.Q1. Replaced by CaFreqRelMeasProfileUeCfg::rsrqSCellCoverageThrOffset. Planned to be removed.; Specification: 3GPP TS 38.331.";
      reference "Takes effect: Next usage.";
    }
    leaf-list ueConfGroupList {
      type eytypes:int32_range_1-255;
      ordered-by user;
      description "Takes effect: Next usage; Status info: Since 24.Q1. Replaced by CaFreqRelMeasProfileUeCfg::ueConfGroupList. Planned to be removed..";
    }
    leaf-list ueGroupList {
      type eytypes:int32_range_1-255;
      ordered-by user;
      description "Takes effect: Next usage; Status info: Since 24.Q1. Replaced by CaFreqRelMeasProfileUeCfg::ueGroupList. Planned to be removed..";
    }
    leaf userLabel {
      type string;
      status deprecated;
      description "MOM flags: isNillable=true; Status info: Since 24.Q1. Planned to be removed..";
    }
    leaf waitForBetterSCellRep {
      type eytypes:int32_range_-1-32000;
      status deprecated;
      default "-1";
      units "ms";
      description "range -1..32000; Default value: -1; Takes effect: New connection; Status info: Since 24.Q1. Replaced by CaFreqRelMeasProfileUeCfg::waitForBetterSCellRep. Planned to be removed..";
      reference "Takes effect: New connection.";
    }
  }
  grouping LocalA1Endpoint-attributes {
    leaf addressRef {
      type string;
      mandatory true;
    }
    leaf localA1EndpointId {
      type string;
      mandatory true;
    }
    leaf nodeCredentialRef {
      type string;
      mandatory true;
    }
    leaf portNumber {
      type ietfinet:port-number;
      default "7443";
      description "range 1..65535; Default value: 7443.";
    }
    leaf trustCategoryRef {
      type string;
      mandatory true;
    }
  }
  grouping LocalDnsEndpoint-attributes {
    leaf dnsClientRef {
      type string;
      mandatory true;
    }
    leaf interfaceUsed {
      type enumeration {
        enum C5;
        enum E1;
        enum E6;
        enum F1;
        enum NG;
        enum S1;
        enum XN;
        enum X2;
      }
      mandatory true;
    }
    leaf localDnsEndpointId {
      type string;
      mandatory true;
    }
  }
  grouping LocalIpEndpoint-attributes {
    leaf-list addressRef {
      type string;
      ordered-by user;
      min-elements 1;
    }
    leaf-list interfaceList {
      type enumeration {
        enum C5;
        enum E1;
        enum E6;
        enum F1;
        enum NG;
        enum S1;
        enum XN;
        enum X2;
      }
      ordered-by user;
      min-elements 1;
    }
    leaf localIpEndpointId {
      type ietfinet:ip-address;
      mandatory true;
    }
  }
  grouping LocalSctpEndpoint-attributes {
    leaf interfaceUsed {
      type enumeration {
        enum C5;
        enum E1;
        enum E6;
        enum F1;
        enum NG;
        enum S1;
        enum XN;
        enum X2;
      }
      mandatory true;
    }
    leaf localSctpEndpointId {
      type string;
      mandatory true;
    }
    leaf sctpEndpointRef {
      type string;
      mandatory true;
    }
    leaf pmSctpDtlsNegotiationFailed {
      type uint64;
      config false;
      status deprecated;
      description "MOM flags: noNotification.";
    }
  }
  grouping Mcfb-attributes {
    leaf epsFbDepHEnabled {
      type boolean;
    }
    leaf mcfbId {
      type string;
      mandatory true;
    }
    leaf voiceEpsFbPossible {
      type boolean;
      default "true";
      description "Default value: true.";
    }
  }
  grouping McfbCellProfile-attributes {
    leaf epsFallbackOperation {
      type enumeration {
        enum INACTIVE;
        enum ACTIVE;
        enum FORCED;
        enum ACTIVE_MEAS_RWR;
        enum ACTIVE_MEAS_IRAT_HO;
        enum FORCED_MEAS_RWR;
        enum FORCED_MEAS_IRAT_HO;
      }
    }
    leaf epsFallbackOperationEm {
      type enumeration {
        enum ACTIVE;
        enum FORCED;
        enum ACTIVE_MEAS_RWR;
        enum ACTIVE_MEAS_IRAT_HO;
        enum FORCED_MEAS_RWR;
        enum FORCED_MEAS_IRAT_HO;
      }
    }
    leaf-list epsFallbackPrioritization {
      type enumeration {
        enum PRIO_OVER_XN_HO;
      }
      ordered-by user;
    }
    leaf epsFbAtSessionSetup {
      type enumeration {
        enum INACTIVE;
        enum ACTIVE;
      }
    }
    leaf epsFbTargetSearchTimer {
      type eytypes:int32_range_1-12000;
      units "ms";
      description "range 1..12000.";
    }
    leaf mcfbCellProfileId {
      type string;
      mandatory true;
    }
    leaf rejectVoiceIncHoAtEpsFb {
      type boolean;
    }
    leaf-list reservedBy {
      type string;
    }
    list rsrpCellCandidate {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-140--44;
        default "-140";
        units "dBm";
        description "range -140..-44; Default value: -140.";
      }
      leaf timeToTrigger {
        type int32;
        default "40";
        units "ms";
        description "Default value: 40.";
      }
      }
    }
    list rsrpCriticalCoverage {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-156--29;
        default "-156";
        units "dBm";
        description "range -156..-29; Default value: -156.";
      }
      leaf timeToTrigger {
        type int32;
        default "160";
        units "ms";
        description "Default value: 160.";
      }
      leaf timeToTriggerA1 {
        type int32;
        default "-1";
        units "ms";
        description "Default value: -1.";
      }
      }
    }
    list rsrqCellCandidate {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-195--30;
        default "-195";
        units "dB";
        description "range -195..-30; Default value: -195.";
      }
      leaf timeToTrigger {
        type int32;
        default "40";
        units "ms";
        description "Default value: 40.";
      }
      }
    }
    list rsrqCriticalCoverage {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-435-200;
        default "-435";
        units "dB";
        description "range -435..200; Default value: -435.";
      }
      leaf timeToTrigger {
        type int32;
        default "160";
        units "ms";
        description "Default value: 160.";
      }
      leaf timeToTriggerA1 {
        type int32;
        default "-1";
        units "ms";
        description "Default value: -1.";
      }
      }
    }
    leaf triggerQuantity {
      type enumeration {
        enum RSRP;
        enum RSRQ;
      }
    }
    leaf ueConfGroupType {
      type enumeration {
        enum UE_MOBILITY_GROUP;
        enum UE_SERVICE_GROUP;
        enum UE_ADMISSION_GROUP;
      }
    }
  }
  grouping McfbCellProfileUeCfg-attributes {
    leaf epsFallbackOperation {
      type enumeration {
        enum INACTIVE;
        enum ACTIVE;
        enum FORCED;
        enum ACTIVE_MEAS_RWR;
        enum ACTIVE_MEAS_IRAT_HO;
        enum FORCED_MEAS_RWR;
        enum FORCED_MEAS_IRAT_HO;
      }
    }
    leaf epsFallbackOperationEm {
      type enumeration {
        enum ACTIVE;
        enum FORCED;
        enum ACTIVE_MEAS_RWR;
        enum ACTIVE_MEAS_IRAT_HO;
        enum FORCED_MEAS_RWR;
        enum FORCED_MEAS_IRAT_HO;
      }
    }
    leaf epsFbAtSessionSetup {
      type enumeration {
        enum INACTIVE;
        enum ACTIVE;
      }
    }
    leaf epsFbTargetSearchTimer {
      type eytypes:int32_range_1-12000;
      default "500";
      units "ms";
      description "range 1..12000; Default value: 500.";
    }
    leaf epsFbVoiceIndication {
      type boolean;
      default "false";
      description "Default value: false.";
    }
    leaf maxReportCells {
      type ietfinet:port-number;
      default "4";
      description "range 1..8; Default value: 4.";
    }
    leaf mcfbCellProfileUeCfgId {
      type string;
      mandatory true;
    }
    leaf-list prefUeGroupList {
      type eytypes:int32_range_1-255;
      ordered-by user;
    }
    leaf rejectVoiceIncHoAtEpsFb {
      type boolean;
      default "false";
      description "Default value: false.";
    }
    list rsrpCellCandidate {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-140--44;
        default "-140";
        units "dBm";
        description "range -140..-44; Default value: -140.";
      }
      leaf timeToTrigger {
        type int32;
        default "40";
        units "ms";
        description "Default value: 40.";
      }
      }
    }
    list rsrpCriticalCoverage {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-156--29;
        default "-156";
        units "dBm";
        description "range -156..-29; Default value: -156.";
      }
      leaf timeToTrigger {
        type int32;
        default "160";
        units "ms";
        description "Default value: 160.";
      }
      leaf timeToTriggerA1 {
        type int32;
        default "-1";
        units "ms";
        description "Default value: -1.";
      }
      }
    }
    list rsrqCellCandidate {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-195--30;
        default "-195";
        units "dB";
        description "range -195..-30; Default value: -195.";
      }
      leaf timeToTrigger {
        type int32;
        default "40";
        units "ms";
        description "Default value: 40.";
      }
      }
    }
    list rsrqCriticalCoverage {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-435-200;
        default "-435";
        units "dB";
        description "range -435..200; Default value: -435.";
      }
      leaf timeToTrigger {
        type int32;
        default "160";
        units "ms";
        description "Default value: 160.";
      }
      leaf timeToTriggerA1 {
        type int32;
        default "-1";
        units "ms";
        description "Default value: -1.";
      }
      }
    }
    list sinrCellCandidate {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-230-405;
        default "-230";
        units "dB";
        description "range -230..405; Default value: -230.";
      }
      leaf timeToTrigger {
        type int32;
        default "40";
        units "ms";
        description "Default value: 40.";
      }
      }
    }
    list sinrCriticalCoverage {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-230-405;
        default "-230";
        units "dB";
        description "range -230..405; Default value: -230.";
      }
      leaf timeToTrigger {
        type int32;
        default "160";
        units "ms";
        description "Default value: 160.";
      }
      }
    }
    leaf triggerQuantity {
      type enumeration {
        enum RSRP;
        enum RSRQ;
        enum SINR_FALLBACK_RSRP;
        enum SINR_FALLBACK_RSRQ;
      }
    }
    leaf-list ueConfGroupList {
      type eytypes:int32_range_1-255;
      ordered-by user;
    }
    leaf-list ueGroupList {
      type eytypes:int32_range_1-255;
      ordered-by user;
    }
    leaf userLabel {
      type string;
    }
  }
  grouping Mcpc-attributes {
    leaf endcLowPrioPSCellCandHandling {
      type enumeration {
        enum STORE_LATEST_RECEIVED;
        enum STORE_HIGHEST_PRIO;
      }
    }
    leaf mcpcId {
      type string;
      mandatory true;
    }
    leaf nrLowPrioPCellCandHandling {
      type enumeration {
        enum STORE_LATEST_RECEIVED;
        enum STORE_HIGHEST_PRIO;
      }
    }
  }
  grouping McpcNrdcPSCellProfile-attributes {
    leaf mcpcNrdcPSCellProfileId {
      type string;
      mandatory true;
    }
    leaf-list reservedBy {
      type string;
    }
    list rsrpCritical {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-156--29;
        default "-156";
        units "dBm";
        description "range -156..-29; Default value: -156.";
      }
      leaf timeToTrigger {
        type int32;
        default "160";
        units "ms";
        description "Default value: 160.";
      }
      }
    }
    leaf rsrpCriticalEnabled {
      type boolean;
    }
    leaf ueConfGroupType {
      type enumeration {
        enum UE_MOBILITY_GROUP;
        enum UE_SERVICE_GROUP;
        enum UE_ADMISSION_GROUP;
      }
    }
    leaf userLabel {
      type string;
    }
  }
  grouping McpcNrdcPSCellProfileUeCfg-attributes {
    leaf mcpcA2Quantity {
      type enumeration {
        enum NONE;
        enum RSRP;
        enum RSRQ;
        enum SINR_FALLBACK_RSRP;
        enum SINR_FALLBACK_RSRQ;
        enum RSRP_AND_RSRQ;
        enum RSRP_AND_SINR_FALLBACK_RSRQ;
        enum RSRP_AND_SINR_NO_FALLBACK;
      }
    }
    leaf mcpcNrdcPSCellProfileUeCfgId {
      type string;
      mandatory true;
    }
    leaf-list prefUeGroupList {
      type eytypes:int32_range_1-255;
      ordered-by user;
    }
    list rsrpCritical {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-156--29;
        default "-156";
        units "dBm";
        description "range -156..-29; Default value: -156.";
      }
      leaf timeToTrigger {
        type int32;
        default "160";
        units "ms";
        description "Default value: 160.";
      }
      }
    }
    list rsrqCritical {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-435-200;
        default "-435";
        units "dB";
        description "range -435..200; Default value: -435.";
      }
      leaf timeToTrigger {
        type int32;
        default "160";
        units "ms";
        description "Default value: 160.";
      }
      }
    }
    list sinrCritical {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-230-405;
        default "-230";
        units "dB";
        description "range -230..405; Default value: -230.";
      }
      leaf timeToTrigger {
        type int32;
        default "160";
        units "ms";
        description "Default value: 160.";
      }
      }
    }
    leaf-list ueConfGroupList {
      type eytypes:int32_range_1-255;
      ordered-by user;
    }
    leaf-list ueGroupList {
      type eytypes:int32_range_1-255;
      ordered-by user;
    }
    leaf userLabel {
      type string;
    }
  }
  grouping McpcPCellEUtranFreqRelProfile-attributes {
    leaf inhibitMeasForCellCandidate {
      type boolean;
    }
    leaf mcpcPCellEUtranFreqRelProfileId {
      type string;
      mandatory true;
    }
    leaf-list reservedBy {
      type string;
    }
    list rsrpCandidateB2Offsets {
      key "id";
      leaf id {
        type uint32;
        description "Synthetic key for struct entry.";
      }
      container attributes {
      leaf threshold1Offset {
        type eytypes:int32_range_-100-100;
        default "0";
        units "dB";
        description "range -100..100; Default value: 0.";
      }
      leaf threshold2EUtraOffset {
        type eytypes:int32_range_-100-100;
        default "0";
        units "dB";
        description "range -100..100; Default value: 0.";
      }
      }
    }
    leaf ueConfGroupType {
      type enumeration {
        enum UE_MOBILITY_GROUP;
        enum UE_SERVICE_GROUP;
        enum UE_ADMISSION_GROUP;
      }
    }
    leaf userLabel {
      type string;
    }
  }
  grouping McpcPCellEUtranFreqRelProfileUeCfg-attributes {
    leaf inhibitMeasForCellCandidate {
      type boolean;
      default "false";
      description "Default value: false.";
    }
    leaf mcpcPCellEUtranFreqRelProfileUeCfgId {
      type string;
      mandatory true;
    }
    leaf-list prefUeGroupList {
      type eytypes:int32_range_1-255;
      ordered-by user;
    }
    list rsrpCandidateB2Offsets {
      key "id";
      leaf id {
        type uint32;
        description "Synthetic key for struct entry.";
      }
      container attributes {
      leaf threshold1Offset {
        type eytypes:int32_range_-100-100;
        default "0";
        units "dB";
        description "range -100..100; Default value: 0.";
      }
      leaf threshold2EUtraOffset {
        type eytypes:int32_range_-100-100;
        default "0";
        units "dB";
        description "range -100..100; Default value: 0.";
      }
      }
    }
    list rsrqCandidateB2Offsets {
      key "id";
      leaf id {
        type uint32;
        description "Synthetic key for struct entry.";
      }
      container attributes {
      leaf threshold1Offset {
        type eytypes:int32_range_-100-100;
        default "0";
        units "dB";
        description "range -100..100; Default value: 0.";
      }
      leaf threshold2EUtraOffset {
        type eytypes:int32_range_-100-100;
        default "0";
        units "dB";
        description "range -100..100; Default value: 0.";
      }
      }
    }
    list sinrCandidateB2Offsets {
      key "id";
      leaf id {
        type uint32;
        description "Synthetic key for struct entry.";
      }
      container attributes {
      leaf threshold1Offset {
        type eytypes:int32_range_-100-100;
        default "0";
        units "dB";
        description "range -100..100; Default value: 0.";
      }
      leaf threshold2EUtraOffset {
        type eytypes:int32_range_-100-100;
        default "0";
        units "dB";
        description "range -100..100; Default value: 0.";
      }
      }
    }
    leaf-list ueConfGroupList {
      type eytypes:int32_range_1-255;
      ordered-by user;
    }
    leaf-list ueGroupList {
      type eytypes:int32_range_1-255;
      ordered-by user;
    }
    leaf userLabel {
      type string;
    }
  }
  grouping McpcPCellNrFreqRelProfile-attributes {
    leaf inhibitMeasForCellCandidate {
      type boolean;
    }
    leaf mcpcPCellNrFreqRelProfileId {
      type string;
      mandatory true;
    }
    leaf-list reservedBy {
      type string;
    }
    list rsrpCandidateA5Offsets {
      key "id";
      leaf id {
        type uint32;
        description "Synthetic key for struct entry.";
      }
      container attributes {
      leaf threshold1Offset {
        type eytypes:int32_range_-100-100;
        default "0";
        units "dB";
        description "range -100..100; Default value: 0.";
      }
      leaf threshold2Offset {
        type eytypes:int32_range_-100-100;
        default "0";
        units "dB";
        description "range -100..100; Default value: 0.";
      }
      }
    }
    leaf ueConfGroupType {
      type enumeration {
        enum UE_MOBILITY_GROUP;
        enum UE_SERVICE_GROUP;
        enum UE_ADMISSION_GROUP;
      }
    }
    leaf userLabel {
      type string;
    }
  }
  grouping McpcPCellNrFreqRelProfileUeCfg-attributes {
    leaf inhibitMeasForCellCandidate {
      type boolean;
      default "false";
      description "Default value: false.";
    }
    leaf interFreqMeasType {
      type enumeration {
        enum EVENT_A5;
        enum EVENT_A3;
      }
    }
    leaf mcpcPCellNrFreqRelProfileUeCfgId {
      type string;
      mandatory true;
    }
    leaf-list prefUeGroupList {
      type eytypes:int32_range_1-255;
      ordered-by user;
    }
    leaf rsrpCandidateA3Adjustment {
      type eytypes:int32_range_-150-150;
      default "0";
      units "dB";
      description "range -150..150; Default value: 0.";
    }
    list rsrpCandidateA5Offsets {
      key "id";
      leaf id {
        type uint32;
        description "Synthetic key for struct entry.";
      }
      container attributes {
      leaf threshold1Offset {
        type eytypes:int32_range_-100-100;
        default "0";
        units "dB";
        description "range -100..100; Default value: 0.";
      }
      leaf threshold2Offset {
        type eytypes:int32_range_-100-100;
        default "0";
        units "dB";
        description "range -100..100; Default value: 0.";
      }
      }
    }
    leaf rsrqCandidateA3Adjustment {
      type eytypes:int32_range_-150-150;
      default "0";
      units "dB";
      description "range -150..150; Default value: 0.";
    }
    list rsrqCandidateA5Offsets {
      key "id";
      leaf id {
        type uint32;
        description "Synthetic key for struct entry.";
      }
      container attributes {
      leaf threshold1Offset {
        type eytypes:int32_range_-100-100;
        default "0";
        units "dB";
        description "range -100..100; Default value: 0.";
      }
      leaf threshold2Offset {
        type eytypes:int32_range_-100-100;
        default "0";
        units "dB";
        description "range -100..100; Default value: 0.";
      }
      }
    }
    leaf sinrCandidateA3Adjustment {
      type eytypes:int32_range_-150-150;
      default "0";
      units "dB";
      description "range -150..150; Default value: 0.";
    }
    list sinrCandidateA5Offsets {
      key "id";
      leaf id {
        type uint32;
        description "Synthetic key for struct entry.";
      }
      container attributes {
      leaf threshold1Offset {
        type eytypes:int32_range_-100-100;
        default "0";
        units "dB";
        description "range -100..100; Default value: 0.";
      }
      leaf threshold2Offset {
        type eytypes:int32_range_-100-100;
        default "0";
        units "dB";
        description "range -100..100; Default value: 0.";
      }
      }
    }
    leaf-list ueConfGroupList {
      type eytypes:int32_range_1-255;
      ordered-by user;
    }
    leaf-list ueGroupList {
      type eytypes:int32_range_1-255;
      ordered-by user;
    }
    leaf userLabel {
      type string;
    }
  }
  grouping McpcPCellProfile-attributes {
    leaf lowHighFreqPrioClassification {
      type eytypes:int32_range_0-7;
      description "range 0..7.";
    }
    leaf mcpcPCellProfileId {
      type string;
      mandatory true;
    }
    leaf mcpcQuantityList {
      type enumeration {
        enum RSRP;
        enum RSRQ;
        enum SINR_NO_FALLBACK;
        enum SINR_FALLBACK_RSRQ;
        enum SINR_FALLBACK_RSRP;
        enum UL_SINR;
      }
    }
    leaf-list reservedBy {
      type string;
    }
    list rsrpCandidateA5 {
      key "id";
      leaf id {
        type uint32;
        description "Synthetic key for struct entry.";
      }
      container attributes {
      leaf hysteresis {
        type eytypes:int32_range_0-150;
        default "10";
        units "dB";
        description "range 0..150; Default value: 10.";
      }
      leaf threshold1 {
        type eytypes:int32_range_-156--29;
        default "-156";
        units "dBm";
        description "range -156..-29; Default value: -156.";
      }
      leaf threshold2 {
        type eytypes:int32_range_-156--29;
        default "-156";
        units "dBm";
        description "range -156..-29; Default value: -156.";
      }
      leaf timeToTrigger {
        type int32;
        default "640";
        units "ms";
        description "Default value: 640.";
      }
      }
    }
    list rsrpCandidateB2 {
      key "id";
      leaf id {
        type uint32;
        description "Synthetic key for struct entry.";
      }
      container attributes {
      leaf hysteresis {
        type eytypes:int32_range_0-150;
        default "10";
        units "dB";
        description "range 0..150; Default value: 10.";
      }
      leaf threshold1 {
        type eytypes:int32_range_-156--29;
        default "-156";
        units "dBm";
        description "range -156..-29; Default value: -156.";
      }
      leaf threshold2EUtra {
        type eytypes:int32_range_-140--44;
        default "-140";
        units "dBm";
        description "range -140..-44; Default value: -140.";
      }
      leaf timeToTrigger {
        type int32;
        default "640";
        units "ms";
        description "Default value: 640.";
      }
      }
    }
    list rsrpCritical {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-156--29;
        default "-156";
        units "dBm";
        description "range -156..-29; Default value: -156.";
      }
      leaf timeToTrigger {
        type int32;
        default "160";
        units "ms";
        description "Default value: 160.";
      }
      leaf timeToTriggerA1 {
        type int32;
        default "-1";
        units "ms";
        description "Default value: -1.";
      }
      }
    }
    leaf rsrpCriticalEnabled {
      type boolean;
    }
    leaf rsrpSearchTimeRestriction {
      type int32 {
        range "-1 | 10..12000";
      }
      units "ms";
    }
    list rsrpSearchZone {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-156--29;
        default "-156";
        units "dBm";
        description "range -156..-29; Default value: -156.";
      }
      leaf timeToTrigger {
        type int32;
        default "160";
        units "ms";
        description "Default value: 160.";
      }
      leaf timeToTriggerA1 {
        type int32;
        default "-1";
        units "ms";
        description "Default value: -1.";
      }
      }
    }
    leaf ueConfGroupType {
      type enumeration {
        enum UE_MOBILITY_GROUP;
        enum UE_SERVICE_GROUP;
        enum UE_ADMISSION_GROUP;
      }
    }
    leaf userLabel {
      type string;
    }
  }
  grouping McpcPCellProfileUeCfg-attributes {
    leaf lowHighFreqPrioClassification {
      type eytypes:int32_range_0-7;
      default "7";
      description "range 0..7; Default value: 7.";
    }
    leaf maxReportCells {
      type ietfinet:port-number;
      default "1";
      description "range 1..8; Default value: 1.";
    }
    leaf mcpcPCellProfileUeCfgId {
      type string;
      mandatory true;
    }
    leaf-list mcpcQuantityList {
      type enumeration {
        enum RSRP;
        enum RSRQ;
        enum SINR_NO_FALLBACK;
        enum SINR_FALLBACK_RSRQ;
        enum SINR_FALLBACK_RSRP;
        enum UL_SINR;
      }
      ordered-by user;
    }
    leaf-list prefUeGroupList {
      type eytypes:int32_range_1-255;
      ordered-by user;
    }
    list rsrpCandidateA3 {
      key "id";
      leaf id {
        type uint32;
        description "Synthetic key for struct entry.";
      }
      container attributes {
      leaf hysteresis {
        type eytypes:int32_range_0-150;
        default "10";
        units "dB";
        description "range 0..150; Default value: 10.";
      }
      leaf offset {
        type eytypes:int32_range_-150-150;
        default "30";
        units "dB";
        description "range -150..150; Default value: 30.";
      }
      leaf timeToTrigger {
        type int32;
        default "640";
        units "ms";
        description "Default value: 640.";
      }
      }
    }
    leaf rsrpCandidateA3AddTargEval {
      type enumeration {
        enum NONE;
        enum RSRQ;
        enum SINR_FALLBACK_RSRQ;
        enum SINR_NO_FALLBACK_RSRQ;
      }
    }
    list rsrpCandidateA5 {
      key "id";
      leaf id {
        type uint32;
        description "Synthetic key for struct entry.";
      }
      container attributes {
      leaf hysteresis {
        type eytypes:int32_range_0-150;
        default "10";
        units "dB";
        description "range 0..150; Default value: 10.";
      }
      leaf threshold1 {
        type eytypes:int32_range_-156--29;
        default "-156";
        units "dBm";
        description "range -156..-29; Default value: -156.";
      }
      leaf threshold2 {
        type eytypes:int32_range_-156--29;
        default "-156";
        units "dBm";
        description "range -156..-29; Default value: -156.";
      }
      leaf timeToTrigger {
        type int32;
        default "640";
        units "ms";
        description "Default value: 640.";
      }
      }
    }
    leaf rsrpCandidateA5AddTargEval {
      type enumeration {
        enum NONE;
        enum RSRQ;
        enum SINR_FALLBACK_RSRQ;
        enum SINR_NO_FALLBACK_RSRQ;
      }
    }
    list rsrpCandidateA5PcOffset {
      key "id";
      leaf id {
        type uint32;
        description "Synthetic key for struct sequence entry.";
      }
      ordered-by user;
      container attributes {
      leaf powerClass {
        type enumeration {
          enum PC_1;
          enum PC_1_5;
          enum PC_2;
        }
      }
      leaf threshold1Offset {
        type eytypes:int32_range_-100-100;
        default "0";
        units "dB";
        description "range -100..100; Default value: 0.";
      }
      leaf threshold2Offset {
        type eytypes:int32_range_-100-100;
        default "0";
        units "dB";
        description "range -100..100; Default value: 0.";
      }
      }
    }
    list rsrpCandidateB2 {
      key "id";
      leaf id {
        type uint32;
        description "Synthetic key for struct entry.";
      }
      container attributes {
      leaf hysteresis {
        type eytypes:int32_range_0-150;
        default "10";
        units "dB";
        description "range 0..150; Default value: 10.";
      }
      leaf threshold1 {
        type eytypes:int32_range_-156--29;
        default "-156";
        units "dBm";
        description "range -156..-29; Default value: -156.";
      }
      leaf threshold2EUtra {
        type eytypes:int32_range_-140--44;
        default "-140";
        units "dBm";
        description "range -140..-44; Default value: -140.";
      }
      leaf timeToTrigger {
        type int32;
        default "640";
        units "ms";
        description "Default value: 640.";
      }
      }
    }
    leaf rsrpCandidateB2AddTargEval {
      type enumeration {
        enum NONE;
        enum RSRQ;
        enum SINR_FALLBACK_RSRQ;
        enum SINR_NO_FALLBACK_RSRQ;
      }
    }
    list rsrpCandidateB2PcOffset {
      key "id";
      leaf id {
        type uint32;
        description "Synthetic key for struct sequence entry.";
      }
      ordered-by user;
      container attributes {
      leaf powerClass {
        type enumeration {
          enum PC_1;
          enum PC_1_5;
          enum PC_2;
        }
      }
      leaf threshold1Offset {
        type eytypes:int32_range_-100-100;
        default "0";
        units "dB";
        description "range -100..100; Default value: 0.";
      }
      }
    }
    list rsrpCritical {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-156--29;
        default "-156";
        units "dBm";
        description "range -156..-29; Default value: -156.";
      }
      leaf timeToTrigger {
        type int32;
        default "160";
        units "ms";
        description "Default value: 160.";
      }
      leaf timeToTriggerA1 {
        type int32;
        default "-1";
        units "ms";
        description "Default value: -1.";
      }
      }
    }
    leaf rsrpCriticalEnabled {
      type boolean;
      default "false";
      description "Default value: false.";
    }
    list rsrpCriticalPcOffset {
      key "id";
      leaf id {
        type uint32;
        description "Synthetic key for struct sequence entry.";
      }
      ordered-by user;
      container attributes {
      leaf powerClass {
        type enumeration {
          enum PC_1;
          enum PC_1_5;
          enum PC_2;
        }
      }
      leaf thresholdOffset {
        type eytypes:int32_range_-100-100;
        default "0";
        units "dB";
        description "range -100..100; Default value: 0.";
      }
      }
    }
    leaf rsrpSearchTimeRestriction {
      type int32 {
        range "-1 | 10..12000";
      }
      default "-1";
      units "ms";
      description "Default value: -1.";
    }
    leaf rsrpSearchTimeRestrictionByUl {
      type int32 {
        range "-1 | 10..12000";
      }
      default "-1";
      units "ms";
      description "Default value: -1.";
    }
    list rsrpSearchZone {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-156--29;
        default "-156";
        units "dBm";
        description "range -156..-29; Default value: -156.";
      }
      leaf timeToTrigger {
        type int32;
        default "160";
        units "ms";
        description "Default value: 160.";
      }
      leaf timeToTriggerA1 {
        type int32;
        default "-1";
        units "ms";
        description "Default value: -1.";
      }
      }
    }
    list rsrpSearchZonePcOffset {
      key "id";
      leaf id {
        type uint32;
        description "Synthetic key for struct sequence entry.";
      }
      ordered-by user;
      container attributes {
      leaf powerClass {
        type enumeration {
          enum PC_1;
          enum PC_1_5;
          enum PC_2;
        }
      }
      leaf thresholdOffset {
        type eytypes:int32_range_-100-100;
        default "0";
        units "dB";
        description "range -100..100; Default value: 0.";
      }
      }
    }
    list rsrqCandidateA3 {
      key "id";
      leaf id {
        type uint32;
        description "Synthetic key for struct entry.";
      }
      container attributes {
      leaf hysteresis {
        type eytypes:int32_range_0-150;
        default "10";
        units "dB";
        description "range 0..150; Default value: 10.";
      }
      leaf offset {
        type eytypes:int32_range_-150-150;
        default "30";
        units "dB";
        description "range -150..150; Default value: 30.";
      }
      leaf timeToTrigger {
        type int32;
        default "640";
        units "ms";
        description "Default value: 640.";
      }
      }
    }
    leaf rsrqCandidateA3AddTargEval {
      type enumeration {
        enum NONE;
        enum RSRP;
      }
    }
    list rsrqCandidateA5 {
      key "id";
      leaf id {
        type uint32;
        description "Synthetic key for struct entry.";
      }
      container attributes {
      leaf hysteresis {
        type eytypes:int32_range_0-150;
        default "10";
        units "dB";
        description "range 0..150; Default value: 10.";
      }
      leaf threshold1 {
        type eytypes:int32_range_-435-200;
        default "-435";
        units "dB";
        description "range -435..200; Default value: -435.";
      }
      leaf threshold2 {
        type eytypes:int32_range_-435-200;
        default "-435";
        units "dB";
        description "range -435..200; Default value: -435.";
      }
      leaf timeToTrigger {
        type int32;
        default "640";
        units "ms";
        description "Default value: 640.";
      }
      }
    }
    leaf rsrqCandidateA5AddTargEval {
      type enumeration {
        enum NONE;
        enum RSRP;
      }
    }
    list rsrqCandidateB2 {
      key "id";
      leaf id {
        type uint32;
        description "Synthetic key for struct entry.";
      }
      container attributes {
      leaf hysteresis {
        type eytypes:int32_range_0-150;
        default "10";
        units "dB";
        description "range 0..150; Default value: 10.";
      }
      leaf threshold1 {
        type eytypes:int32_range_-435-200;
        default "-435";
        units "dB";
        description "range -435..200; Default value: -435.";
      }
      leaf threshold2EUtra {
        type eytypes:int32_range_-195--30;
        default "-195";
        units "dB";
        description "range -195..-30; Default value: -195.";
      }
      leaf timeToTrigger {
        type int32;
        default "640";
        units "ms";
        description "Default value: 640.";
      }
      }
    }
    leaf rsrqCandidateB2AddTargEval {
      type enumeration {
        enum NONE;
        enum RSRP;
      }
    }
    list rsrqCritical {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-435-200;
        default "-435";
        units "dB";
        description "range -435..200; Default value: -435.";
      }
      leaf timeToTrigger {
        type int32;
        default "160";
        units "ms";
        description "Default value: 160.";
      }
      }
    }
    leaf rsrqCriticalEnabled {
      type boolean;
      default "false";
      description "Default value: false.";
    }
    leaf rsrqSearchTimeRestriction {
      type int32 {
        range "-1 | 10..12000";
      }
      default "-1";
      units "ms";
      description "Default value: -1.";
    }
    list rsrqSearchZone {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-435-200;
        default "-435";
        units "dB";
        description "range -435..200; Default value: -435.";
      }
      leaf timeToTrigger {
        type int32;
        default "160";
        units "ms";
        description "Default value: 160.";
      }
      leaf timeToTriggerA1 {
        type int32;
        default "-1";
        units "ms";
        description "Default value: -1.";
      }
      }
    }
    list sinrCandidateA3 {
      key "id";
      leaf id {
        type uint32;
        description "Synthetic key for struct entry.";
      }
      container attributes {
      leaf hysteresis {
        type eytypes:int32_range_0-150;
        default "10";
        units "dB";
        description "range 0..150; Default value: 10.";
      }
      leaf offset {
        type eytypes:int32_range_-150-150;
        default "30";
        units "dB";
        description "range -150..150; Default value: 30.";
      }
      leaf timeToTrigger {
        type int32;
        default "640";
        units "ms";
        description "Default value: 640.";
      }
      }
    }
    leaf sinrCandidateA3AddTargEval {
      type enumeration {
        enum NONE;
        enum RSRP;
        enum RSRQ;
        enum RSRP_AND_RSRQ;
      }
    }
    list sinrCandidateA5 {
      key "id";
      leaf id {
        type uint32;
        description "Synthetic key for struct entry.";
      }
      container attributes {
      leaf hysteresis {
        type eytypes:int32_range_0-150;
        default "10";
        units "dB";
        description "range 0..150; Default value: 10.";
      }
      leaf threshold1 {
        type eytypes:int32_range_-230-405;
        default "-230";
        units "dB";
        description "range -230..405; Default value: -230.";
      }
      leaf threshold2 {
        type eytypes:int32_range_-230-405;
        default "-230";
        units "dB";
        description "range -230..405; Default value: -230.";
      }
      leaf timeToTrigger {
        type int32;
        default "640";
        units "ms";
        description "Default value: 640.";
      }
      }
    }
    leaf sinrCandidateA5AddTargEval {
      type enumeration {
        enum NONE;
        enum RSRP;
        enum RSRQ;
        enum RSRP_AND_RSRQ;
      }
    }
    list sinrCandidateB2 {
      key "id";
      leaf id {
        type uint32;
        description "Synthetic key for struct entry.";
      }
      container attributes {
      leaf hysteresis {
        type eytypes:int32_range_0-150;
        default "10";
        units "dB";
        description "range 0..150; Default value: 10.";
      }
      leaf threshold1 {
        type eytypes:int32_range_-230-405;
        default "-230";
        units "dB";
        description "range -230..405; Default value: -230.";
      }
      leaf threshold2EUtra {
        type eytypes:int32_range_-230-405;
        default "-230";
        units "dB";
        description "range -230..405; Default value: -230.";
      }
      leaf timeToTrigger {
        type int32;
        default "640";
        units "ms";
        description "Default value: 640.";
      }
      }
    }
    leaf sinrCandidateB2AddTargEval {
      type enumeration {
        enum NONE;
        enum RSRP;
        enum RSRQ;
        enum RSRP_AND_RSRQ;
      }
    }
    list sinrCritical {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-230-405;
        default "-230";
        units "dB";
        description "range -230..405; Default value: -230.";
      }
      leaf timeToTrigger {
        type int32;
        default "160";
        units "ms";
        description "Default value: 160.";
      }
      }
    }
    leaf sinrCriticalEnabled {
      type boolean;
      default "false";
      description "Default value: false.";
    }
    leaf sinrSearchTimeRestriction {
      type int32 {
        range "-1 | 10..12000";
      }
      default "-1";
      units "ms";
      description "Default value: -1.";
    }
    list sinrSearchZone {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-230-405;
        default "-230";
        units "dB";
        description "range -230..405; Default value: -230.";
      }
      leaf timeToTrigger {
        type int32;
        default "640";
        units "ms";
        description "Default value: 640.";
      }
      leaf timeToTriggerA1 {
        type int32;
        default "-1";
        units "ms";
        description "Default value: -1.";
      }
      }
    }
    leaf-list ueConfGroupList {
      type eytypes:int32_range_1-255;
      ordered-by user;
    }
    leaf-list ueGroupList {
      type eytypes:int32_range_1-255;
      ordered-by user;
    }
    leaf ulQualCriticalEnabled {
      type boolean;
      default "false";
      description "Default value: false.";
    }
    leaf ulQualMcpcMeasCfgRef {
      type string;
    }
    leaf userLabel {
      type string;
    }
    leaf useT312CandidateA3 {
      type boolean;
      default "false";
      description "Default value: false.";
    }
    leaf useT312CandidateA5 {
      type boolean;
      default "false";
      description "Default value: false.";
    }
  }
  grouping McpcPSCellNrFreqRelProfile-attributes {
    leaf mcpcPSCellNrFreqRelProfileId {
      type string;
      mandatory true;
    }
    leaf-list reservedBy {
      type string;
    }
    leaf ueConfGroupType {
      type enumeration {
        enum UE_MOBILITY_GROUP;
        enum UE_SERVICE_GROUP;
        enum UE_ADMISSION_GROUP;
      }
    }
    leaf userLabel {
      type string;
    }
  }
  grouping McpcPSCellNrFreqRelProfileUeCfg-attributes {
    leaf inhibitMeasForCellCandidate {
      type boolean;
      default "false";
      description "Default value: false.";
    }
    leaf mcpcPSCellNrFreqRelProfileUeCfgId {
      type string;
      mandatory true;
    }
    leaf-list prefUeGroupList {
      type eytypes:int32_range_1-255;
      ordered-by user;
    }
    list rsrpCandidateA5Offsets {
      key "id";
      leaf id {
        type uint32;
        description "Synthetic key for struct entry.";
      }
      container attributes {
      leaf threshold1Offset {
        type eytypes:int32_range_-100-100;
        default "0";
        units "dB";
        description "range -100..100; Default value: 0.";
      }
      leaf threshold2Offset {
        type eytypes:int32_range_-100-100;
        default "0";
        units "dB";
        description "range -100..100; Default value: 0.";
      }
      }
    }
    list rsrqCandidateA5Offsets {
      key "id";
      leaf id {
        type uint32;
        description "Synthetic key for struct entry.";
      }
      container attributes {
      leaf threshold1Offset {
        type eytypes:int32_range_-100-100;
        default "0";
        units "dB";
        description "range -100..100; Default value: 0.";
      }
      leaf threshold2Offset {
        type eytypes:int32_range_-100-100;
        default "0";
        units "dB";
        description "range -100..100; Default value: 0.";
      }
      }
    }
    list sinrCandidateA5Offsets {
      key "id";
      leaf id {
        type uint32;
        description "Synthetic key for struct entry.";
      }
      container attributes {
      leaf threshold1Offset {
        type eytypes:int32_range_-100-100;
        default "0";
        units "dB";
        description "range -100..100; Default value: 0.";
      }
      leaf threshold2Offset {
        type eytypes:int32_range_-100-100;
        default "0";
        units "dB";
        description "range -100..100; Default value: 0.";
      }
      }
    }
    leaf-list ueConfGroupList {
      type eytypes:int32_range_1-255;
      ordered-by user;
    }
    leaf-list ueGroupList {
      type eytypes:int32_range_1-255;
      ordered-by user;
    }
    leaf userLabel {
      type string;
    }
  }
  grouping McpcPSCellProfile-attributes {
    leaf mcpcPSCellProfileId {
      type string;
      mandatory true;
    }
    leaf-list reservedBy {
      type string;
    }
    leaf ueConfGroupType {
      type enumeration {
        enum UE_MOBILITY_GROUP;
        enum UE_SERVICE_GROUP;
        enum UE_ADMISSION_GROUP;
      }
    }
    leaf userLabel {
      type string;
    }
  }
  grouping McpcPSCellProfileUeCfg-attributes {
    leaf lowHighFreqPrioClassification {
      type eytypes:int32_range_0-7;
      default "7";
      description "range 0..7; Default value: 7.";
    }
    leaf maxReportCells {
      type ietfinet:port-number;
      default "1";
      description "range 1..8; Default value: 1.";
    }
    leaf mcpcPSCellProfileUeCfgId {
      type string;
      mandatory true;
    }
    leaf-list mcpcQuantityList {
      type enumeration {
        enum RSRP;
        enum RSRQ;
        enum SINR_NO_FALLBACK;
        enum SINR_FALLBACK_RSRQ;
        enum SINR_FALLBACK_RSRP;
        enum UL_SINR;
      }
      ordered-by user;
    }
    leaf-list prefUeGroupList {
      type eytypes:int32_range_1-255;
      ordered-by user;
    }
    list rsrpCandidateA5 {
      key "id";
      leaf id {
        type uint32;
        description "Synthetic key for struct entry.";
      }
      container attributes {
      leaf hysteresis {
        type eytypes:int32_range_0-150;
        default "10";
        units "dB";
        description "range 0..150; Default value: 10.";
      }
      leaf threshold1 {
        type eytypes:int32_range_-156--29;
        default "-156";
        units "dBm";
        description "range -156..-29; Default value: -156.";
      }
      leaf threshold2 {
        type eytypes:int32_range_-156--29;
        default "-156";
        units "dBm";
        description "range -156..-29; Default value: -156.";
      }
      leaf timeToTrigger {
        type int32;
        default "640";
        units "ms";
        description "Default value: 640.";
      }
      }
    }
    leaf rsrpCandidateA5AddTargEval {
      type enumeration {
        enum NONE;
        enum RSRQ;
        enum SINR_FALLBACK_RSRQ;
        enum SINR_NO_FALLBACK_RSRQ;
      }
    }
    list rsrpCritical {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-156--29;
        default "-156";
        units "dBm";
        description "range -156..-29; Default value: -156.";
      }
      leaf timeToTrigger {
        type int32;
        default "160";
        units "ms";
        description "Default value: 160.";
      }
      }
    }
    leaf rsrpCriticalEnabled {
      type boolean;
      default "false";
      description "Default value: false.";
    }
    leaf rsrpSearchTimeRestriction {
      type int32 {
        range "-1 | 200..12000";
      }
      default "-1";
      units "ms";
      description "Default value: -1.";
    }
    list rsrpSearchZone {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-156--29;
        default "-156";
        units "dBm";
        description "range -156..-29; Default value: -156.";
      }
      leaf timeToTrigger {
        type int32;
        default "160";
        units "ms";
        description "Default value: 160.";
      }
      leaf timeToTriggerA1 {
        type int32;
        default "-1";
        units "ms";
        description "Default value: -1.";
      }
      }
    }
    list rsrqCandidateA5 {
      key "id";
      leaf id {
        type uint32;
        description "Synthetic key for struct entry.";
      }
      container attributes {
      leaf hysteresis {
        type eytypes:int32_range_0-150;
        default "10";
        units "dB";
        description "range 0..150; Default value: 10.";
      }
      leaf threshold1 {
        type eytypes:int32_range_-435-200;
        default "-435";
        units "dB";
        description "range -435..200; Default value: -435.";
      }
      leaf threshold2 {
        type eytypes:int32_range_-435-200;
        default "-435";
        units "dB";
        description "range -435..200; Default value: -435.";
      }
      leaf timeToTrigger {
        type int32;
        default "640";
        units "ms";
        description "Default value: 640.";
      }
      }
    }
    leaf rsrqCandidateA5AddTargEval {
      type enumeration {
        enum NONE;
        enum RSRP;
      }
    }
    list rsrqCritical {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-435-200;
        default "-435";
        units "dB";
        description "range -435..200; Default value: -435.";
      }
      leaf timeToTrigger {
        type int32;
        default "160";
        units "ms";
        description "Default value: 160.";
      }
      }
    }
    leaf rsrqCriticalEnabled {
      type boolean;
      default "false";
      description "Default value: false.";
    }
    leaf rsrqSearchTimeRestriction {
      type int32 {
        range "-1 | 10..12000";
      }
      default "-1";
      units "ms";
      description "Default value: -1.";
    }
    list rsrqSearchZone {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-435-200;
        default "-435";
        units "dB";
        description "range -435..200; Default value: -435.";
      }
      leaf timeToTrigger {
        type int32;
        default "160";
        units "ms";
        description "Default value: 160.";
      }
      leaf timeToTriggerA1 {
        type int32;
        default "-1";
        units "ms";
        description "Default value: -1.";
      }
      }
    }
    list sinrCandidateA5 {
      key "id";
      leaf id {
        type uint32;
        description "Synthetic key for struct entry.";
      }
      container attributes {
      leaf hysteresis {
        type eytypes:int32_range_0-150;
        default "10";
        units "dB";
        description "range 0..150; Default value: 10.";
      }
      leaf threshold1 {
        type eytypes:int32_range_-230-405;
        default "-230";
        units "dB";
        description "range -230..405; Default value: -230.";
      }
      leaf threshold2 {
        type eytypes:int32_range_-230-405;
        default "-230";
        units "dB";
        description "range -230..405; Default value: -230.";
      }
      leaf timeToTrigger {
        type int32;
        default "640";
        units "ms";
        description "Default value: 640.";
      }
      }
    }
    leaf sinrCandidateA5AddTargEval {
      type enumeration {
        enum NONE;
        enum RSRP;
        enum RSRQ;
        enum RSRP_AND_RSRQ;
      }
    }
    list sinrCritical {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-230-405;
        default "-230";
        units "dB";
        description "range -230..405; Default value: -230.";
      }
      leaf timeToTrigger {
        type int32;
        default "160";
        units "ms";
        description "Default value: 160.";
      }
      }
    }
    leaf sinrCriticalEnabled {
      type boolean;
      default "false";
      description "Default value: false.";
    }
    leaf sinrSearchTimeRestriction {
      type int32 {
        range "-1 | 10..12000";
      }
      default "-1";
      units "ms";
      description "Default value: -1.";
    }
    list sinrSearchZone {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-230-405;
        default "-230";
        units "dB";
        description "range -230..405; Default value: -230.";
      }
      leaf timeToTrigger {
        type int32;
        default "640";
        units "ms";
        description "Default value: 640.";
      }
      leaf timeToTriggerA1 {
        type int32;
        default "-1";
        units "ms";
        description "Default value: -1.";
      }
      }
    }
    leaf-list ueConfGroupList {
      type eytypes:int32_range_1-255;
      ordered-by user;
    }
    leaf-list ueGroupList {
      type eytypes:int32_range_1-255;
      ordered-by user;
    }
    leaf userLabel {
      type string;
    }
  }
  grouping Mdt-attributes {
    leaf mdtId {
      type string;
      mandatory true;
    }
    leaf-list mdtUserConsentReqList {
      type enumeration {
        enum NONE;
        enum M1;
        enum M6;
        enum MDT_UE_LOCATION;
      }
      ordered-by user;
    }
    leaf userLabel {
      type string;
    }
  }
  grouping MdtCellProfile-attributes {
    leaf mdtCellProfileId {
      type string;
      mandatory true;
    }
    leaf-list reservedBy {
      type string;
    }
    leaf ueConfGroupType {
      type enumeration {
        enum UE_MOBILITY_GROUP;
        enum UE_SERVICE_GROUP;
        enum UE_ADMISSION_GROUP;
      }
    }
    leaf userLabel {
      type string;
    }
  }
  grouping MdtCellProfileUeCfg-attributes {
    leaf immediateMdtGnssR16Check {
      type boolean;
      default "false";
      description "Default value: false.";
    }
    leaf m1Enabled {
      type boolean;
      default "true";
      description "Default value: true.";
    }
    leaf m1EventA2Hysteresis {
      type eytypes:int32_range_0-150;
      default "10";
      units "dB";
      description "range 0..150; Default value: 10.";
    }
    leaf m1EventA2ThresholdRsrp {
      type eytypes:int32_range_-156--29;
      default "-156";
      units "dBm";
      description "range -156..-29; Default value: -156.";
    }
    leaf m1EventA2ThresholdRsrq {
      type eytypes:int32_range_-435-200;
      default "-435";
      units "dB";
      description "range -435..200; Default value: -435.";
    }
    leaf m1EventA2ThresholdSinr {
      type eytypes:int32_range_-230-405;
      default "-230";
      units "dB";
      description "range -230..405; Default value: -230.";
    }
    leaf m1EventA2TimeToTrigger {
      type int32 {
        range "0 | 40 | 64 | 80 | 100 | 128 | 160 | 256 | 320 | 480 | 512 | 640 | 1024 | 1280 | 2560 | 5120";
      }
      default "640";
      description "Default value: 640.";
    }
    leaf m1EventA2TriggerQuantity {
      type enumeration {
        enum RSRP;
        enum RSRQ;
        enum SINR;
      }
    }
    leaf m1IncludeBeamMeasurement {
      type boolean;
      default "false";
      description "Default value: false.";
    }
    leaf m1IncludeCommonLocationInfo {
      type boolean;
      default "true";
      description "Default value: true.";
    }
    leaf m1IncludeRrmReport {
      type ietfinet:port-number;
      description "Default value: true.";
    }
    leaf m1InterFreqMeasAllowed {
      type boolean;
      default "true";
      description "Default value: true.";
    }
    leaf m1MaxNoOfRsIndexToReport {
      type ietfinet:port-number;
      default "8";
      description "range 0..32; Default value: 8.";
    }
    leaf m1MaxReportCells {
      type ietfinet:port-number;
      default "8";
      description "range 1..8; Default value: 8.";
    }
    leaf m1ReportAmount {
      type ietfinet:port-number;
    }
    leaf m1ReportInterval {
      type ietfinet:port-number;
    }
    leaf m1ReportQuantityCell {
      type ietfinet:port-number;
    }
    leaf m1ReportQuantityRsIndex {
      type ietfinet:port-number;
    }
    leaf m1ReportTrigger {
      type ietfinet:port-number;
    }
    leaf m6Enabled {
      type boolean;
      default "true";
      description "Default value: true.";
    }
    leaf m6ReportAmount {
      type ietfinet:port-number;
    }
    leaf m6ReportInterval {
      type ietfinet:port-number;
    }
    leaf mdtCellProfileUeCfgId {
      type string;
      mandatory true;
    }
    leaf mdtUeSelectionRatio {
      type eytypes:int32_range_0-1000-2;
      default "1000";
      description "range 0..1000; Default value: 1000.";
    }
    leaf-list prefUeGroupList {
      type eytypes:int32_range_1-255;
      ordered-by user;
    }
    leaf reportAddNeighMeas {
      type ietfinet:port-number;
      description "Default value: true.";
    }
    leaf-list ueConfGroupList {
      type eytypes:int32_range_1-255;
      ordered-by user;
    }
    leaf-list ueGroupList {
      type eytypes:int32_range_1-255;
      ordered-by user;
    }
    leaf userLabel {
      type string;
    }
  }
  grouping Nccm-attributes {
    leaf nccmId {
      type string;
      mandatory true;
    }
    leaf ueConfGroupType {
      type enumeration {
        enum UE_MOBILITY_GROUP;
        enum UE_SERVICE_GROUP;
        enum UE_ADMISSION_GROUP;
      }
    }
    leaf userLabel {
      type string;
    }
  }
  grouping NccmUeCfg-attributes {
    leaf nccmEnabled {
      type boolean;
    }
    leaf nccmUeCfgId {
      type string;
      mandatory true;
    }
    leaf-list prefUeGroupList {
      type eytypes:int32_range_1-255;
      ordered-by user;
    }
    leaf-list ueConfGroupList {
      type eytypes:int32_range_1-255;
      ordered-by user;
    }
    leaf-list ueGroupList {
      type eytypes:int32_range_1-255;
      ordered-by user;
    }
    leaf userLabel {
      type string;
    }
  }
  grouping NRCellCU-attributes {
    leaf admissionLimitRef {
      type string;
    }
    leaf admissionPriorityRef {
      type string;
    }
    leaf advUePosMode {
      type enumeration {
        enum NONE;
        enum ALL;
        enum TA_ONLY;
      }
    }
    leaf autoCleanupAllowed {
      type boolean;
      default "true";
      description "Default value: true.";
    }
    leaf caCellMeasProfileRef {
      type string;
    }
    leaf caCellProfileRef {
      type string;
    }
    leaf cellLocalId {
      type eytypes:int32_range_0-16383;
      mandatory true;
      description "range 0..16383.";
    }
    leaf cellState {
      type enumeration {
        enum IDLE;
        enum INACTIVE;
        enum ACTIVE;
      }
      config false;
    }
    leaf checkUeGrpAtCellOffload {
      type boolean;
      default "false";
      description "Default value: false.";
    }
    leaf endcInitialCgRef {
      type string;
    }
    leaf epBoCSEnergySavingState {
      type enumeration {
        enum NOT_ENERGYSAVING;
        enum ENERGYSAVING;
      }
      config false;
    }
    leaf epBoCSMode {
      type enumeration {
        enum DISABLED;
        enum TIME;
        enum MULTI_LAYER_TRAFFIC;
      }
    }
    leaf epBoCSTimeSchedulingGroupRef {
      type string;
    }
    leaf hiPrioDetEnabled {
      type ietfinet:ip-address;
      description "Default value: false.";
    }
    leaf interfaceSupervision {
      type enumeration {
        enum ALL_LINKS;
        enum NO_SUPERVISION;
        enum NG_ONLY;
        enum X2_ONLY;
        enum XN_ONLY;
        enum NG_X2_COEXISTENCE;
        enum NG_XN_COEXISTENCE;
        enum X2_XN_COEXISTENCE;
      }
    }
    leaf intraFreqMCCellProfileRef {
      type string;
    }
    leaf-list isPciConflicted {
      type enumeration {
        enum NO;
        enum YES;
      }
    }
    list lwNeighborRel {
      config false;
      container attributes {
      leaf cellLocalId {
        type eytypes:int32_range_0-16383;
        description "range 0..16383.";
      }
      leaf gNBId {
        type eytypes:int64_range_0-4294967295;
        description "range 0..4294967295.";
      }
      leaf gNBIdLength {
        type eytypes:int32_range_22-32;
        description "range 22..32.";
      }
      leaf mcc {
        type string {
          length "3";
        }
        description "length 3..3.";
      }
      leaf mnc {
        type string {
          length "2..3";
        }
        description "length 2..3.";
      }
      leaf nRPCI {
        type int32 {
          range "0..1007";
        }
        description "range 0..1007.";
      }
      }
    }
    list lwNeighborRelEUtran {
      config false;
      container attributes {
      leaf cellLocalId {
        type eytypes:int32_range_0-255;
        description "range 0..255.";
      }
      leaf eNBId {
        type eytypes:int32_range_0-1048575;
        description "range 0..1048575.";
      }
      leaf eUtranPCI {
        type eytypes:int32_range_0-503;
        description "range 0..503.";
      }
      leaf mcc {
        type string {
          length "3";
        }
        description "length 3..3.";
      }
      leaf mnc {
        type string {
          length "2..3";
        }
        description "length 2..3.";
      }
      }
    }
    leaf mcfbCellProfileRef {
      type string;
    }
    leaf mcpcNrdcPSCellEnabled {
      type boolean;
    }
    leaf mcpcNrdcPSCellProfileRef {
      type string;
    }
    leaf mcpcPCellEnabled {
      type boolean;
      default "false";
      description "Default value: false.";
    }
    leaf mcpcPCellProfileRef {
      type string;
    }
    leaf mcpcPSCellEnabled {
      type boolean;
      default "false";
      description "Default value: false.";
    }
    leaf mcpcPSCellProfileRef {
      type string;
    }
    leaf mdtCellProfileRef {
      type string;
    }
    leaf mdtEnabled {
      type boolean;
      default "false";
      description "Default value: false.";
    }
    leaf nCellChangeHigh {
      type uint32 {
        range "1..16";
      }
      description "range 1..16.";
    }
    leaf nCellChangeMedium {
      type uint32 {
        range "1..16";
      }
      description "range 1..16.";
    }
    leaf nCI {
      type eytypes:int64_range_0-68719476735;
      config false;
      description "range 0..68719476735.";
    }
    leaf nRCellCUId {
      type string;
      mandatory true;
    }
    leaf nrdcInitialCgRef {
      type string;
    }
    leaf nrdcMnCellProfileRef {
      type string;
    }
    leaf nRFrequencyRef {
      type string;
    }
    leaf nRTAC {
      type int32;
      config false;
    }
    leaf offloadCellProfileRef {
      type string;
    }
    list pciConflictDetectingCell {
      config false;
      container attributes {
      leaf cellLocalId {
        type eytypes:int32_range_0-16383;
        default "0";
        description "range 0..16383; Default value: 0.";
      }
      leaf gNBId {
        type eytypes:int64_range_0-4294967295;
        default "0";
        description "range 0..4294967295; Default value: 0.";
      }
      leaf gNBIdLength {
        type eytypes:int32_range_22-32;
        default "22";
        description "range 22..32; Default value: 22.";
      }
      leaf mcc {
        type eytypes:int32_range_0-999;
        default "1";
        description "range 0..999; Default value: 1.";
      }
      leaf mnc {
        type eytypes:int32_range_0-999;
        default "1";
        description "range 0..999; Default value: 1.";
      }
      leaf mncLength {
        type eytypes:int32_range_2-3;
        default "2";
        description "range 2..3; Default value: 2.";
      }
      }
    }
    list pciConflictedCell {
      config false;
      container attributes {
      leaf cellLocalId {
        type eytypes:int32_range_0-16383;
        default "0";
        description "range 0..16383; Default value: 0.";
      }
      leaf gNBId {
        type eytypes:int64_range_0-4294967295;
        default "0";
        description "range 0..4294967295; Default value: 0.";
      }
      leaf gNBIdLength {
        type eytypes:int32_range_22-32;
        default "22";
        description "range 22..32; Default value: 22.";
      }
      leaf mcc {
        type eytypes:int32_range_0-999;
        default "1";
        description "range 0..999; Default value: 1.";
      }
      leaf mnc {
        type eytypes:int32_range_0-999;
        default "1";
        description "range 0..999; Default value: 1.";
      }
      leaf mncLength {
        type eytypes:int32_range_2-3;
        default "2";
        description "range 2..3; Default value: 2.";
      }
      }
    }
    leaf pimDetectionReportedTime {
      type ietfinet:port-number;
      config false;
    }
    list pimDetectionResultList {
      config false;
      container attributes {
      leaf aggressor1CellId {
        type eytypes:int32_range_0-16383;
        description "range 0..16383.";
      }
      leaf aggressor1NodeId {
        type eytypes:int64_range_0-4294967295;
        description "range 0..4294967295.";
      }
      leaf aggressor1NodeType {
        type enumeration {
          enum LOCAL_NODE;
          enum EXTERNAL_ENODEB;
          enum EXTERNAL_GNODEB;
        }
      }
      leaf aggressor2CellId {
        type eytypes:int32_range_0-16383;
        description "range 0..16383.";
      }
      leaf aggressor2NodeId {
        type eytypes:int64_range_0-4294967295;
        description "range 0..4294967295.";
      }
      leaf aggressor2NodeType {
        type enumeration {
          enum LOCAL_NODE;
          enum EXTERNAL_ENODEB;
          enum EXTERNAL_GNODEB;
        }
      }
      leaf imOrderLevel {
        type int32 {
          range "2..5";
        }
        description "range 2..5.";
      }
      leaf pimOverlapRatio {
        type eytypes:int32_range_1-100-4;
        description "range 1..100.";
      }
      leaf pimType {
        type enumeration {
          enum CLEAR;
          enum LIKELY;
        }
      }
      }
    }
    leaf pimDetectionRole {
      type enumeration {
        enum AGGRESSOR;
        enum VICTIM;
        enum VICTIM_AND_AGGRESSOR;
      }
      config false;
    }
    leaf pimDetectionStatus {
      type enumeration {
        enum NOT_APPLICABLE;
        enum NO_PIM_DETECTED;
        enum PIM_DETECTED;
      }
      config false;
    }
    list pLMNIdList {
      config false;
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
    leaf pmUeIntraFreqCellProfileRef {
      type string;
    }
    leaf pmUeIntraFreqEnabled {
      type boolean;
      default "false";
      description "Default value: false.";
    }
    list primaryPLMNId {
      key "id";
      leaf id {
        type uint32;
        description "Synthetic key for struct entry.";
      }
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
    leaf pSCellCapable {
      type boolean;
      config false;
    }
    leaf puemCellProfileRef {
      type string;
    }
    leaf puemEnabled {
      type boolean;
      default "false";
      description "Default value: false.";
    }
    leaf-list pwsEmergencyAreaIdList {
      type eytypes:int32_range_0-16777215;
      ordered-by user;
    }
    leaf qHyst {
      type int32 {
        range "0..6 | 8 | 10 | 12 | 14 | 16 | 18 | 20 | 22 | 24";
      }
      default "4";
      units "dB";
      description "Default value: 4.";
    }
    leaf qHystSfHigh {
      type int32 {
        range "-6 | -4 | -2 | 0";
      }
      units "dB";
    }
    leaf qHystSfMedium {
      type int32 {
        range "-6 | -4 | -2 | 0";
      }
      units "dB";
    }
    leaf relaxedRrmMeasCellProfileRef {
      type string;
    }
    leaf relaxedRrmMeasEnabled {
      type boolean;
      default "false";
      description "Default value: false.";
    }
    leaf-list reservedBy {
      type string;
    }
    leaf resourceStatusMaxConnUe {
      type int32 {
        range "-2 | 1..65535";
      }
      default "-2";
      description "Default value: -2.";
    }
    leaf robustUeCapEnquiryMode {
      type enumeration {
        enum COMBINED_THEN_SPLIT;
        enum SPLIT_ONLY;
        enum COMBINED_ONLY;
      }
    }
    leaf serviceState {
      type enumeration {
        enum OUT_OF_SERVICE;
        enum IN_SERVICE;
      }
      config false;
    }
    leaf smtcDuration {
      type eytypes:int32_range_1-5;
      config false;
      units "ms";
      description "range 1..5.";
    }
    leaf smtcOffset {
      type eytypes:int32_range_0-159;
      config false;
      units "ms";
      description "range 0..159.";
    }
    leaf smtcPeriodicity {
      type int32 {
        range "5 | 10 | 20 | 40 | 80 | 160";
      }
      config false;
      units "ms";
    }
    leaf sNonIntraSearchP {
      type int32 {
        range "-1..62";
      }
      default "0";
      units "dB";
      description "range -1..62; Default value: 0.";
    }
    leaf sNonIntraSearchQ {
      type eytypes:int32_range_0-31;
      units "dB";
      description "range 0..31.";
    }
    list sNSSAIList {
      config false;
      container attributes {
      leaf sd {
        type eytypes:int32_range_0-16777215;
        description "range 0..16777215.";
      }
      leaf sst {
        type eytypes:int32_range_0-255;
        description "range 0..255.";
      }
      }
    }
    leaf snssaiValidationMode {
      type enumeration {
        enum NORMAL;
        enum DISABLED;
      }
    }
    leaf tEvaluation {
      type uint32 {
        range "30 | 60 | 120 | 180 | 240";
      }
      units "s";
    }
    leaf threshServingLowP {
      type eytypes:int32_range_0-62;
      default "0";
      units "dB";
      description "range 0..62; Default value: 0.";
    }
    leaf threshServingLowQ {
      type eytypes:int32_range_0-31;
      units "dB";
      description "range 0..31.";
    }
    leaf tHystNormal {
      type uint32 {
        range "30 | 60 | 120 | 180 | 240";
      }
      units "s";
    }
    leaf transmitSib2 {
      type boolean;
      default "false";
      description "Default value: false.";
    }
    leaf transmitSib4 {
      type boolean;
      default "false";
      description "Default value: false.";
    }
    leaf transmitSib5 {
      type boolean;
      default "false";
      description "Default value: false.";
    }
    leaf transmitSib9 {
      type boolean;
      default "false";
      description "Default value: false.";
    }
    leaf trStPSCellProfileRef {
      type string;
    }
    leaf trStSaCellProfileRef {
      type string;
    }
    leaf uacBroadcast {
      type boolean;
      config false;
    }
    leaf uacProfileRef {
      type string;
    }
    leaf ucmCellProfileRef {
      type string;
    }
    leaf ueMCCellProfileRef {
      type string;
    }
    leaf ueNoDrbPCellProfileRef {
      type string;
    }
    leaf userLabel {
      type string;
    }
    leaf pmHoPrepAttOutEutranPciHandling {
      type uint64;
      config false;
    }
    leaf pmUeMeasEcgiFailUeCapPciHandling {
      type uint64;
      config false;
    }
    leaf pmRrcInactLevelSamp {
      type uint64;
      config false;
    }
    leaf pmHoPrepRejInEutranUeCapacityLimit {
      type uint64;
      config false;
    }
    leaf-list pmDrbResumeSuccArp {
      type uint64;
    }
    leaf pmUeCtxtRelAbnormalGnb {
      type uint64;
      config false;
    }
    leaf pmRrcConnEstabAttReattEm {
      type uint64;
      config false;
    }
    leaf pmEndcPSCellChangeRejInIntraGnbMpLoad {
      type uint64;
      config false;
    }
    leaf pmUeCapabilityInfoSegmented {
      type uint64;
      config false;
    }
    leaf pmHoExeSuccOutInterGnb {
      type uint64;
      config false;
    }
    leaf pmHoPrepFailInInterGnbPoorUl {
      type uint64;
      config false;
    }
    leaf pmDrbRopEndEndc {
      type int64;
      config false;
    }
    leaf pmEndcRelUeAbnormalSgnb {
      type uint64;
      config false;
    }
    leaf pmNrdcSetupUeMnAttHoIntraGnb {
      type uint64;
      config false;
    }
    leaf-list pmDrbRelAbnormalGnbArp {
      type uint64;
      description "MOM flags: noNotification.";
    }
    leaf pmHoExeAttOutIntraGnbTs {
      type uint64;
      config false;
    }
    leaf pmRrcConnEstabSuccEm {
      type uint64;
      config false;
    }
    leaf pmPduSessionRelAbnormalAmf {
      type uint64;
      config false;
    }
    leaf pmEndcPSCellChangeSuccInterSgnb {
      type uint64;
      config false;
    }
    leaf pmHoPrepSuccOutInterGnbPciHandling {
      type uint64;
      config false;
    }
    leaf pmHoPrepRejInCellBarred {
      type uint64;
      config false;
      status deprecated;
      description "MOM flags: noNotification.";
    }
    leaf pmHoPrepAttInNg {
      type uint64;
      config false;
    }
    leaf-list pmSessionTimeDrb5qi {
      type uint64;
    }
    leaf pmRrcInitAccessRejUeCapacityLimit {
      type uint64;
      config false;
    }
    leaf pmHoPrepAttOutEutran {
      type uint64;
      config false;
    }
    leaf pmEndcRelUeAbnormalMenbActRaProblem {
      type uint64;
      config false;
    }
    leaf pmNgSigConnEstabAttEm {
      type uint64;
      config false;
    }
    leaf pmUeCapRefreshFailHoInEutranIncompleteUeCap {
      type uint64;
      config false;
    }
    leaf-list pmDrbRelNormal5qi {
      type uint64;
    }
    leaf pmRrcConnLevelMaxNrDc {
      type int64;
      config false;
    }
    leaf pmUeCtxtEstabAttMdtConsent {
      type uint64;
      config false;
    }
    leaf pmEndcUeMeasurementReportPuem {
      type ietfinet:port-number;
      config false;
    }
    leaf pmHoPrepRejCellInvalid {
      type uint64;
      config false;
    }
    leaf pmNrdcRelUeSnAbnormalSnInit {
      type uint64;
      config false;
    }
    leaf pmDrbLevelSumEndc {
      type uint64;
      config false;
    }
    leaf pmHoPrepSuccOutInterGnb {
      type uint64;
      config false;
    }
    leaf pmHoPrepRejInInterGnbUeAdmission {
      type uint64;
      config false;
      status deprecated;
      description "MOM flags: noNotification.";
    }
    leaf pmHoExeAttOutInterGnbIntraF {
      type uint64;
      config false;
    }
    leaf pmNrdcSetupUeRejCellInvalid {
      type uint64;
      config false;
    }
    leaf pmNrdcPSCellChangeResAllocSnAttInterSgnb {
      type uint64;
      config false;
    }
    leaf-list pmDrbEstabAttInit5qi {
      type uint64;
    }
    leaf pmHoPrepSuccOutIntraGnb {
      type uint64;
      config false;
    }
    leaf pmSaUeMeasurementReport {
      type ietfinet:port-number;
      config false;
    }
    leaf pmUeCtxtRetrieveSuccRrcReest {
      type uint64;
      config false;
    }
    leaf pmEndcRelUeAbnormalMenbActRlcMaxRetx {
      type uint64;
      config false;
    }
    leaf pmHoPrepSuccOutEutranTs {
      type uint64;
      config false;
    }
    leaf pmHoPrepSuccOutIntraGnbIntraF {
      type uint64;
      config false;
    }
    leaf-list pmDrbRelAbnormalAmfAct5qi {
      type uint64;
    }
    leaf pmNgSigConnEstabSuccMos {
      type uint64;
      config false;
    }
    leaf pmEndcCaConfigSucc {
      type uint64;
      config false;
    }
    leaf pmEndcPSCellChangeAttIntraSgnbIntraF {
      type uint64;
      config false;
    }
    leaf pmCaConfigSucc {
      type uint64;
      config false;
      status deprecated;
      description "MOM flags: noNotification.";
    }
    leaf pmDrbLevelMaxSa {
      type int64;
      config false;
    }
    leaf pmCaSCellReselectionSuccTs {
      type uint64;
      config false;
    }
    leaf pmNrdcSetupUeSnSucc {
      type uint64;
      config false;
    }
    leaf pmRrcConnEstabSuccMos {
      type uint64;
      config false;
    }
    leaf pmHoPrepAttOutInterGnb {
      type uint64;
      config false;
    }
    leaf pmEndcPSCellChangeAttInterSgnbIntraF {
      type uint64;
      config false;
    }
    leaf pmHoPrepRejInIntraGnbMpLoad {
      type uint64;
      config false;
    }
    leaf pmAnrNeighbRelAddNr {
      type uint64;
      config false;
    }
    leaf pmCaConfigMaxSa {
      type int64;
      config false;
    }
    leaf pmAnrNeighbRelDemoteEutran {
      type uint64;
      config false;
    }
    leaf pmRrcResumeAttFallbackEm {
      type uint64;
      config false;
    }
    leaf pmCaConfigDelaySum {
      type uint64;
      config false;
    }
    leaf pmCaDeconfigSucc {
      type uint64;
      config false;
      status deprecated;
      description "MOM flags: noNotification.";
    }
    leaf-list pmCaConfigUlSumSaDistr {
      type uint64;
    }
    leaf pmEndcUeCapabilityGnssLocation {
      type uint64;
      config false;
    }
    leaf pmNrdcPSCellChangeMnAttInterSgnb {
      type uint64;
      config false;
    }
    leaf pmCellBoosterCarrWakeUp {
      type uint64;
      config false;
    }
    leaf-list pmCaConfigDlSumEndcDistr {
      type uint64;
    }
    leaf pmNrdcSetupUeMnAttInitBufUl {
      type uint64;
      config false;
    }
    leaf-list pmDrbEstabSucc5qi {
      type uint64;
    }
    leaf pmPduSessionEstabAtt {
      type uint64;
      config false;
    }
    leaf pmRrcConnLevelSumEnDc {
      type uint64;
      config false;
    }
    leaf pmHoPrepSuccOutEutranPciHandling {
      type uint64;
      config false;
    }
    leaf pmEndcPSCellChangeSuccInterSgnbIntraF {
      type uint64;
      config false;
    }
    leaf pmNrdcPSCellChangeSnAttIntraSgnb {
      type uint64;
      config false;
    }
    leaf pmEndcMnHoPSCellKeepAtt {
      type uint64;
      config false;
    }
    leaf pmUeCtxtRetrieveResponse {
      type uint64;
      config false;
      status deprecated;
      description "MOM flags: noNotification.";
    }
    leaf pmRrcConnLevelSumNrDc {
      type uint64;
      config false;
    }
    leaf pmEndcMnHoPSCellKeepSucc {
      type uint64;
      config false;
    }
    leaf pmNgSigConnEstabAtt {
      type uint64;
      config false;
    }
    leaf pmHoPrepRejInInterGnbBbIntens {
      type uint64;
      config false;
    }
    leaf pmEndcRelUeAbnormalMenbRlcMaxRetx {
      type uint64;
      config false;
    }
    leaf pmEndcRelUeAbnormalMenbSyncReconfigFail {
      type uint64;
      config false;
    }
    leaf-list pmDrbEstabSuccInitArp {
      type uint64;
    }
    leaf pmNrdcPSCellChangeResAllocSnSuccInterSgnb {
      type uint64;
      config false;
    }
    leaf-list pmDrbEstabSuccArp {
      type uint64;
    }
    leaf pmAnrNcgiMeasFailUeCap {
      type uint64;
      config false;
    }
    leaf pmRrcConnLevelSumSa {
      type uint64;
      config false;
    }
    leaf pmRrcConnRedCapLevelSum {
      type uint64;
      config false;
    }
    leaf pmHoPrepAttInNgMdtConsent {
      type uint64;
      config false;
    }
    leaf pmEndcCaDeconfigSucc {
      type uint64;
      config false;
    }
    leaf pmHoPrepRejInEutranBbIntens {
      type uint64;
      config false;
    }
    leaf pmHoExeSuccOutEutranOffload {
      type uint64;
      config false;
    }
    leaf pmNrdcPSCellChangeSnSuccIntraSgnb {
      type uint64;
      config false;
    }
    leaf pmCaSCellConfigAtt {
      type uint64;
      config false;
    }
    leaf pmPduSessionEstabSucc {
      type uint64;
      config false;
    }
    leaf pmAnrNcgiMeasRcvNoSib1NoTacCell {
      type uint64;
      config false;
    }
    leaf pmMeasReportUlSa {
      type ietfinet:port-number;
      config false;
    }
    leaf pmHoExeAttOutIntraGnbIntraF {
      type uint64;
      config false;
    }
    leaf pmHoExeSuccOutIntraGnbIntraF {
      type uint64;
      config false;
    }
    leaf pmHoExeSuccOutEutranPciHandling {
      type uint64;
      config false;
    }
    leaf-list pmUeMeasSsRsrpEndcDistr {
      type uint64;
      description "MOM flags: noNotification.";
    }
    leaf pmHoPrepAttOutIntraGnbOffload {
      type uint64;
      config false;
    }
    leaf pmAnrNcgiMeasRcvDrx {
      type uint64;
      config false;
    }
    leaf-list pmDrbRelAbnormalGnb2Arp {
      type uint64;
    }
    leaf pmCaConfiguredSwitchedUl {
      type uint64;
      config false;
    }
    leaf pmCaSCellDeconfigAtt {
      type uint64;
      config false;
    }
    leaf pmEndcSetupScgUeSucc {
      type uint64;
      config false;
    }
    leaf pmRrcConnEstabAttEm {
      type uint64;
      config false;
    }
    leaf pmEndcRelUeAbnormalMenbScgReconfigFail {
      type uint64;
      config false;
    }
    leaf pmAnrNeighbRelPromoteRejNr {
      type uint64;
      config false;
    }
    leaf pmRrcResumeRelIdle {
      type uint64;
      config false;
    }
    leaf-list pmDrbRelNormalArp {
      type uint64;
    }
    leaf pmUeMeasNcgiFailUeCapPciHandling {
      type uint64;
      config false;
    }
    leaf pmPwsCancelRespEtws {
      type uint64;
      config false;
    }
    leaf-list pmDrbRelAbnormalAmfActArp {
      type uint64;
    }
    leaf pmRrcResumeAttRnaUpdate {
      type uint64;
      config false;
    }
    leaf pmHoPrepRejInInterGnbMpLoad {
      type uint64;
      config false;
    }
    leaf pmRrcConnRedCapLevelMax {
      type int64;
      config false;
    }
    leaf pmRwrEutranUeSuccTs {
      type uint64;
      config false;
    }
    leaf pmUeMeasEcgiRcvDrxPciHandling {
      type uint64;
      config false;
    }
    leaf pmNrdcRelUeSnNormal {
      type uint64;
      config false;
    }
    leaf pmHoExeSuccOutInterGnbOffload {
      type uint64;
      config false;
    }
    leaf-list pmUeCtxtLowEndDistr {
      type uint64;
    }
    leaf-list pmDrbRelAbnormalGnbInact5qi {
      type uint64;
    }
    leaf pmPwsReqSuccCmas {
      type uint64;
      config false;
    }
    leaf pmHoPrepAttOutEutranTs {
      type uint64;
      config false;
    }
    leaf pmEndcSetupFailReconfigFail {
      type uint64;
      config false;
    }
    leaf pmAnrEcgiMeasTriggerDrx {
      type uint64;
      config false;
    }
    leaf pmPwsReqSuccEtwsSecondary {
      type uint64;
      config false;
    }
    leaf pmPwsCancelRespCmas {
      type uint64;
      config false;
    }
    leaf pmEndcPSCellChangeResAllocReqInterSgnb {
      type uint64;
      config false;
    }
    leaf pmPwsReqSuccEtwsPrimary {
      type uint64;
      config false;
    }
    leaf-list pmHoExeSuccOutDrbEutran5qi {
      type uint64;
    }
    leaf pmEndcUeCapabilityUlPdcpDelay {
      type uint64;
      config false;
    }
    leaf pmHoPrepSuccOutEutranOffload {
      type uint64;
      config false;
    }
    leaf pmNrdcSetupUeMnSucc {
      type uint64;
      config false;
    }
    leaf pmRrcResumeAttRelInact {
      type uint64;
      config false;
    }
    leaf pmNrdcSetupUeMnAttHoIntraCell {
      type uint64;
      config false;
    }
    leaf pmEndcSetupScgUeAtt {
      type uint64;
      config false;
    }
    leaf pmNrdcSetupUeMnSuccHoIntraCell {
      type uint64;
      config false;
    }
    leaf pmAnrNeighbRelRemEutran {
      type uint64;
      config false;
    }
    leaf pmCaConfigDelaySamp {
      type uint64;
      config false;
    }
    leaf-list pmDrbRelAbnormalAmfArp {
      type uint64;
    }
    leaf pmRrcResumeSuccRnaUpdate {
      type uint64;
      config false;
    }
    leaf pmX2DowntimeInterfaceSupervision {
      type uint64;
      config false;
    }
    leaf pmCaSCellReselectionAttTs {
      type uint64;
      config false;
    }
    leaf pmSaUeCapabilityUlPdcpDelay {
      type uint64;
      config false;
    }
    leaf pmEndcRelUeNormal {
      type uint64;
      config false;
    }
    leaf pmNrdcSetupUeMnSuccHoInterGnb {
      type uint64;
      config false;
    }
    leaf pmEndcRelUeAbnormalMenbActT310Expiry {
      type uint64;
      config false;
    }
    leaf pmUeCtxtEstabAtt {
      type uint64;
      config false;
    }
    leaf pmEndcRejCellBarred {
      type uint64;
      config false;
      status deprecated;
      description "MOM flags: noNotification.";
    }
    leaf pmRwrEutranUeNonPerfEpsfbEm {
      type uint64;
      config false;
    }
    leaf pmEndcPSCellChangeSuccIntraSgnbIntraF {
      type uint64;
      config false;
    }
    leaf pmEndcRelUeNormalUeAssisted {
      type uint64;
      config false;
    }
    leaf pmEndcRelUeAbnormalMenbT310Expiry {
      type uint64;
      config false;
    }
    leaf pmNrdcRelRelocUeMnSucc {
      type uint64;
      config false;
    }
    leaf pmRrcInactRedCapLevelMax {
      type int64;
      config false;
    }
    leaf pmEndcRelUeAbnormalMenbActSyncReconfigFail {
      type uint64;
      config false;
    }
    leaf pmRrcInactRedCapLevelSum {
      type uint64;
      config false;
    }
    leaf pmHoExeAttOutIntraGnbPciHandling {
      type uint64;
      config false;
    }
    leaf pmSaUeCapabilityGnssLocation {
      type uint64;
      config false;
    }
    leaf pmCaSCellDeconfigAttUl {
      type uint64;
      config false;
    }
    leaf pmUeCapabilityRefresh {
      type uint64;
      config false;
      status deprecated;
      description "MOM flags: noNotification.";
    }
    leaf pmNrdcPSCellChangeMnSuccInterSgnb {
      type uint64;
      config false;
    }
    leaf pmNrdcPSCellChangeSnAttInterSgnb {
      type uint64;
      config false;
    }
    leaf pmCellBoosterCarrSleep {
      type uint64;
      config false;
    }
    leaf pmRwrEutranUeSuccEpsfb {
      type uint64;
      config false;
    }
    leaf pmHoExeAttOutInterGnb {
      type uint64;
      config false;
    }
    leaf pmEndcPSCellChangeAttInterSgnb {
      type uint64;
      config false;
    }
    leaf pmPduSessionRelNormal {
      type uint64;
      config false;
    }
    leaf pmPwsReqAttEtwsPrimary {
      type uint64;
      config false;
    }
    leaf pmPwsReqAttCmas {
      type uint64;
      config false;
    }
    leaf pmEndcCaConfigAtt {
      type uint64;
      config false;
    }
    leaf-list pmDrbResumeAtt5qi {
      type uint64;
    }
    leaf pmUeCtxtRelAbnormalAmf {
      type uint64;
      config false;
    }
    leaf pmNgSigConnEstabSuccEm {
      type uint64;
      config false;
    }
    leaf pmEndcRelUeAbnormalMenb {
      type uint64;
      config false;
    }
    leaf pmHoExeSuccOutInterGnbTs {
      type uint64;
      config false;
    }
    leaf-list pmUeMeasSaSsRsrp {
      type uint64;
    }
    leaf pmNrdcSetupUeMnSuccHoInterGnbPSCellKeep {
      type uint64;
      config false;
    }
    leaf pmRrcConnReestSuccInterGnb {
      type uint64;
      config false;
    }
    leaf pmHoExeAttOutIntraGnbOffload {
      type uint64;
      config false;
    }
    leaf-list pmCellBoosterCarrSleepReadyNoSchedDistr {
      type uint64;
    }
    leaf pmAnrNcgiMeasTriggerDrx {
      type uint64;
      config false;
    }
    leaf pmNrdcSetupUeMnSuccInit {
      type uint64;
      config false;
    }
    leaf pmHoExeAttOutEutranOffload {
      type uint64;
      config false;
    }
    leaf pmAnrNeighbRelRemNr {
      type uint64;
      config false;
    }
    leaf-list pmRrcConnDrbLevelSumSaDistr {
      type uint64;
    }
    leaf pmRwrEutranUeSuccRi {
      type uint64;
      config false;
    }
    leaf pmHoPrepSuccOutInterGnbOffload {
      type uint64;
      config false;
    }
    leaf pmHoPrepFailInEutranRi {
      type uint64;
      config false;
    }
    leaf pmHoPrepAttInXn {
      type uint64;
      config false;
    }
    leaf-list pmDrbEstabSuccInit5qi {
      type uint64;
    }
    leaf pmPwsReqAttEtwsSecondary {
      type uint64;
      config false;
    }
    leaf pmAnrEcgiMeasFailUeCap {
      type uint64;
      config false;
    }
    leaf-list pmDrbResumeAttArp {
      type uint64;
    }
    leaf pmCaDeconfiguredSwitchedUl {
      type uint64;
      config false;
    }
    leaf pmEndcSgnbAdditionRequestMdtConsent {
      type uint64;
      config false;
    }
    leaf pmHoExeAttOutEutran {
      type uint64;
      config false;
    }
    leaf pmCaSCellConfigSucc {
      type uint64;
      config false;
    }
    leaf pmPduSessionModifyAtt {
      type uint64;
      config false;
    }
    leaf pmRrcResumeAttFallbackRnaUpdate {
      type uint64;
      config false;
    }
    leaf pmNrdcSetupUeMnAttInit {
      type uint64;
      config false;
    }
    leaf-list pmDrbEstabAtt5qi {
      type uint64;
    }
    leaf pmHoPrepFailInEutranRiMissRsrp {
      type uint64;
      config false;
    }
    leaf pmRrcResumeAtt {
      type uint64;
      config false;
    }
    leaf pmHoPrepFailOutInterGnbTargetPoorUl {
      type uint64;
      config false;
    }
    leaf pmHoPrepAttOutIntraGnbIntraF {
      type uint64;
      config false;
    }
    leaf-list pmCaConfigDlSumSaDistr {
      type uint64;
    }
    leaf pmNgSigConnEstabAttMos {
      type uint64;
      config false;
    }
    leaf pmUeCtxtSuspend {
      type uint64;
      config false;
    }
    leaf-list pmHoExeSuccOutDrbInterGnb5qi {
      type uint64;
    }
    leaf pmRwrIntraNrUeSuccCoverage {
      type uint64;
      config false;
    }
    leaf pmHoExeAttOutInterGnbTs {
      type uint64;
      config false;
    }
    leaf pmHoExeSuccOutIntraGnb {
      type uint64;
      config false;
    }
    leaf pmRwrEutranUeSuccNrCoverage {
      type uint64;
      config false;
    }
    leaf pmNrdcUeMeasurementReport {
      type ietfinet:port-number;
      config false;
    }
    leaf pmHoPrepFailInIntraGnbRi {
      type uint64;
      config false;
      status deprecated;
      description "MOM flags: noNotification.";
    }
    leaf pmRwrEutranUeSuccEpsfbEmFbInd {
      type uint64;
      config false;
    }
    leaf pmHoPrepAttOutInterGnbOffload {
      type uint64;
      config false;
    }
    leaf pmHoExeSuccOutInterGnbIntraF {
      type uint64;
      config false;
    }
    leaf pmRrcInitAccessRejUeAdmission {
      type uint64;
      config false;
      status deprecated;
      description "MOM flags: noNotification.";
    }
    leaf-list pmDrbRelAbnormalAmfInact5qi {
      type uint64;
    }
    leaf pmRrcInactLevelSum {
      type uint64;
      config false;
    }
    leaf pmHoPrepSuccOutIntraGnbPciHandling {
      type uint64;
      config false;
    }
    leaf pmEndcCaDeconfigAtt {
      type uint64;
      config false;
    }
    leaf pmNrdcSetupUeSnAtt {
      type uint64;
      config false;
    }
    leaf pmHoPrepSuccOutInterGnbIntraF {
      type uint64;
      config false;
    }
    leaf pmHoPrepFailInInterGnbRi {
      type uint64;
      config false;
    }
    leaf-list pmRruCompAvailCapacityDlDistr2 {
      type uint64;
    }
    leaf-list pmDrbRelAbnormalGnbActArp {
      type uint64;
      description "MOM flags: noNotification.";
    }
    leaf pmHoExeSuccOutEutranTs {
      type uint64;
      config false;
    }
    leaf pmNrdcSetupUeMnSuccHoIntraGnb {
      type uint64;
      config false;
    }
    leaf-list pmDrbResumeSucc5qi {
      type uint64;
    }
    leaf pmCaConfigAttUl {
      type uint64;
      config false;
      status deprecated;
      description "MOM flags: noNotification.";
    }
    leaf pmPwsCancelReqCmas {
      type uint64;
      config false;
    }
    leaf pmEndcPSCellChangeResAllocSuccInterSgnb {
      type uint64;
      config false;
    }
    leaf pmUeCtxtRelNormalInact {
      type uint64;
      config false;
    }
    leaf pmUeCtxtRetrieveResponseMdtConsent {
      type uint64;
      config false;
      status deprecated;
      description "MOM flags: noNotification.";
    }
    leaf-list pmDrbRelAbnormalGnb25qi {
      type uint64;
    }
    leaf pmHoPrepRejInIntraGnbBbIntens {
      type uint64;
      config false;
    }
    leaf pmPduSessionModifySucc {
      type uint64;
      config false;
    }
    leaf pmNrdcSetupUeMnAttInitBufDl {
      type uint64;
      config false;
    }
    leaf pmRrcConnReestFallbackAtt {
      type uint64;
      config false;
    }
    leaf pmRrcConnEstabAttMos {
      type uint64;
      config false;
    }
    leaf pmPduSessionEstabAttIntgProt64kbps {
      type uint64;
      config false;
    }
    leaf pmNrdcSetupUeMnAtt {
      type uint64;
      config false;
    }
    leaf pmUeCtxtRelNormal {
      type uint64;
      config false;
    }
    leaf pmCaConfigDlSamp {
      type uint64;
      config false;
    }
    leaf pmHoExeSuccOutIntraGnbPciHandling {
      type uint64;
      config false;
    }
    leaf pmNrdcSetupUeMnAttHoInterGnb {
      type uint64;
      config false;
    }
    leaf pmPduSessionLevelSamp {
      type uint64;
      config false;
    }
    leaf pmCaConfigSuccUl {
      type uint64;
      config false;
      status deprecated;
      description "MOM flags: noNotification.";
    }
    leaf pmHoExeAttOutEutranPciHandling {
      type uint64;
      config false;
    }
    leaf pmRrcConnLevelMaxEnDc {
      type int64;
      config false;
    }
    leaf pmPduSessionLevelSum {
      type uint64;
      config false;
    }
    leaf pmCaSCellConfigSuccUl {
      type uint64;
      config false;
    }
    leaf pmSaUeMeasurementReportPuem {
      type ietfinet:port-number;
      config false;
    }
    leaf pmRrcConnEstabSucc {
      type uint64;
      config false;
    }
    leaf pmRrcResumeAttResumeEm {
      type uint64;
      config false;
    }
    leaf pmPduSessionRelAbnormalGnb {
      type uint64;
      config false;
      status deprecated;
      description "MOM flags: noNotification.";
    }
    leaf pmUeCtxtRelAbnormalGnbAct {
      type uint64;
      config false;
    }
    leaf pmHoPrepRejInEutranMpLoad {
      type uint64;
      config false;
    }
    leaf pmAnrNeighbRelAddEutran {
      type uint64;
      config false;
    }
    leaf pmHoExeSuccOutEutran {
      type uint64;
      config false;
    }
    leaf pmEndcPSCellChangeAttIntraSgnb {
      type uint64;
      config false;
    }
    leaf pmAnrNeighbRelPromoteRejEutran {
      type uint64;
      config false;
    }
    leaf pmHoPrepSuccOutIntraGnbOffload {
      type uint64;
      config false;
    }
    leaf-list pmDrbRelAbnormalGnbAct25qi {
      type uint64;
    }
    leaf pmHoPrepRejInEutranUeAdmission {
      type uint64;
      config false;
      status deprecated;
      description "MOM flags: noNotification.";
    }
    leaf pmPwsCancelReqEtws {
      type uint64;
      config false;
    }
    leaf pmPduSessionLevelMax {
      type int64;
      config false;
    }
    leaf pmCaDeconfigSuccUl {
      type uint64;
      config false;
      status deprecated;
      description "MOM flags: noNotification.";
    }
    leaf pmHoExeSuccOutIntraGnbTs {
      type uint64;
      config false;
    }
    leaf pmDrbRopEndSa {
      type int64;
      config false;
    }
    leaf pmRrcConnReestAtt {
      type uint64;
      config false;
    }
    leaf-list pmUeMeasEndcSsRsrp {
      type uint64;
    }
    leaf-list pmDrbEstabAttInitArp {
      type uint64;
    }
    leaf pmCaSCellDeconfigSucc {
      type uint64;
      config false;
    }
    leaf pmEndcRelUeMenbReconfigFail {
      type uint64;
      config false;
    }
    leaf pmUeCapabilityInfo {
      type uint64;
      config false;
    }
    leaf pmUeCtxtEstabSucc {
      type uint64;
      config false;
    }
    leaf pmEndcSetupUeAtt {
      type uint64;
      config false;
    }
    leaf pmCaSCellDeconfigSuccUl {
      type uint64;
      config false;
    }
    leaf pmNrdcSetupUeMnSuccHoIntraGnbPSCellKeep {
      type uint64;
      config false;
    }
    leaf pmHoPrepAttInEutranIncompleteUeCap {
      type uint64;
      config false;
    }
    leaf pmAnrNeighbRelDemoteNr {
      type uint64;
      config false;
    }
    leaf pmRwrEutranUeSuccEpsfbEm {
      type uint64;
      config false;
    }
    leaf pmHoPrepAttInXnMdtConsent {
      type uint64;
      config false;
    }
    leaf pmDrbEstabFailIntgProt {
      type uint64;
      config false;
    }
    leaf pmEndcSgnbAdditionRequest {
      type uint64;
      config false;
    }
    leaf pmRrcConnReestFallbackSucc {
      type uint64;
      config false;
    }
    leaf pmCaDeconfigAtt {
      type uint64;
      config false;
      status deprecated;
      description "MOM flags: noNotification.";
    }
    leaf pmNrdcRelUeSnAbnormalSnInitAct {
      type uint64;
      config false;
    }
    leaf pmUeMeasNcgiRcvDrxPciHandling {
      type uint64;
      config false;
    }
    leaf pmRwrIntraNrUeSuccRi {
      type uint64;
      config false;
    }
    leaf pmUeCtxtRelAbnormalGnbInact {
      type uint64;
      config false;
    }
    leaf pmHoPrepAttOutInterGnbPciHandling {
      type uint64;
      config false;
    }
    leaf pmHoPrepAttOutIntraGnbTs {
      type uint64;
      config false;
    }
    leaf pmHoPrepSuccOutEutran {
      type uint64;
      config false;
    }
    leaf-list pmDrbEstabAttArp {
      type uint64;
    }
    leaf pmRrcConnLevelSamp {
      type uint64;
      config false;
    }
    leaf-list pmDrbRelAbnormalAmf5qi {
      type uint64;
    }
    leaf-list pmDrbSuspend5qi {
      type uint64;
    }
    leaf pmRrcResumeSuccResume {
      type uint64;
      config false;
    }
    leaf-list pmDrbRelAbnormalGnbAct5qi {
      type uint64;
      description "MOM flags: noNotification.";
    }
    leaf pmRrcConnLevelMaxSa {
      type int64;
      config false;
    }
    leaf pmRrcResumeAttResume {
      type uint64;
      config false;
    }
    leaf pmRrcConnOver8DrbLevelMaxSa {
      type int64;
      config false;
    }
    leaf pmEndcRelUeAbnormalSgnbAct {
      type uint64;
      config false;
    }
    leaf pmAnrNeighbRelPromoteEutran {
      type uint64;
      config false;
    }
    leaf pmAnrNoActionTooWeakEndc {
      type uint64;
      config false;
    }
    leaf pmUeCtxtRetrieveAttRrcReest {
      type uint64;
      config false;
    }
    leaf pmRrcResumeAttFallback {
      type uint64;
      config false;
    }
    leaf pmNgDowntimeInterfaceSupervision {
      type uint64;
      config false;
    }
    leaf pmHoPrepAttOutEutranOffload {
      type uint64;
      config false;
    }
    leaf pmRrcConnReestSucc {
      type uint64;
      config false;
    }
    leaf pmHoPrepSuccOutInterGnbTs {
      type uint64;
      config false;
    }
    leaf pmXnDowntimeInterfaceSupervision {
      type uint64;
      config false;
    }
    leaf pmHoExeAttOutEutranTs {
      type uint64;
      config false;
    }
    leaf pmHoPrepAttOutInterGnbIntraF {
      type uint64;
      config false;
    }
    leaf pmNrdcRelRelocUeMnAtt {
      type uint64;
      config false;
    }
    leaf pmInterfaceSupervisionSamp {
      type uint64;
      config false;
    }
    leaf pmCellTimeBoosterCarrSleepReadyNoEpCell {
      type uint64;
      config false;
    }
    leaf pmHoExeSuccOutIntraGnbOffload {
      type uint64;
      config false;
    }
    leaf pmDrbLevelSamp {
      type uint64;
      config false;
    }
    leaf pmEndcPSCellChangeRejInIntraGnbBbIntens {
      type uint64;
      config false;
    }
    leaf pmUeCtxtRelAbnormalAmfInact {
      type uint64;
      config false;
    }
    leaf pmRrcResumeSuccResumeEm {
      type uint64;
      config false;
    }
    leaf-list pmCaConfigDlSumNrdcDistr {
      type uint64;
    }
    leaf pmEndcRelUeAbnormalMenbRaProblem {
      type uint64;
      config false;
    }
    leaf pmNrdcRelUeSnAbnormalMnInit {
      type uint64;
      config false;
    }
    leaf pmPduSessionRelAbnormalGnb2 {
      type uint64;
      config false;
    }
    leaf pmCaDeconfigAttUl {
      type uint64;
      config false;
      status deprecated;
      description "MOM flags: noNotification.";
    }
    leaf pmRrcResumeSuccFallback {
      type uint64;
      config false;
    }
    leaf pmEndcUeMeasurementReportMdt {
      type ietfinet:port-number;
      config false;
    }
    leaf pmEndcRelUeAbnormalMenbAct {
      type uint64;
      config false;
    }
    leaf pmUeCapabilityRefreshNetworkId {
      type uint64;
      config false;
      status deprecated;
      description "MOM flags: noNotification.";
    }
    leaf pmHoPrepAttOutInterGnbTs {
      type uint64;
      config false;
    }
    leaf pmRrcResumeSuccFallbackRnaUpdate {
      type uint64;
      config false;
    }
    leaf pmCaConfigAtt {
      type uint64;
      config false;
      status deprecated;
      description "MOM flags: noNotification.";
    }
    leaf-list pmRruCompAvailCapacityUlDistr {
      type uint64;
    }
    leaf-list pmRruCompAvailCapacityDlDistr {
      type uint64;
      description "MOM flags: noNotification.";
    }
    leaf pmDrbLevelMaxEndc {
      type int64;
      config false;
    }
    leaf-list pmDrbRelAbnormalAmfActNoSessionInfo5qi {
      type uint64;
    }
    leaf pmEndcRelUeAbnormalMenbActScgReconfigFail {
      type uint64;
      config false;
    }
    leaf pmRrcConnEstabAttReattMos {
      type uint64;
      config false;
    }
    leaf pmHoPrepFailOutEpsfb {
      type uint64;
      config false;
    }
    leaf pmNrdcPSCellChangeSnSuccInterSgnb {
      type uint64;
      config false;
    }
    leaf pmNrdcRejCellBarred {
      type uint64;
      config false;
      status deprecated;
      description "MOM flags: noNotification.";
    }
    leaf pmUeMeasNcgiTriggerDrxPciHandling {
      type uint64;
      config false;
    }
    leaf pmEndcUeMeasurementReport {
      type ietfinet:port-number;
      config false;
    }
    leaf-list pmDrbRelNormalInact5qi {
      type uint64;
    }
    leaf-list pmDrbRelAbnormalGnbActNoSessionInfo5qi {
      type uint64;
    }
    leaf pmAnrNeighbRelPromoteNr {
      type uint64;
      config false;
    }
    leaf pmHoExeAttOutInterGnbOffload {
      type uint64;
      config false;
    }
    leaf pmNgSigConnEstabSucc {
      type uint64;
      config false;
    }
    leaf pmSaUeMeasurementReportMdt {
      type ietfinet:port-number;
      config false;
    }
    leaf pmAnrEcgiMeasRcvDrx {
      type uint64;
      config false;
    }
    leaf pmHoPrepAttOutIntraGnbPciHandling {
      type uint64;
      config false;
    }
    leaf pmRrcConnEstabAttReatt {
      type uint64;
      config false;
    }
    leaf pmHoPrepRejInInterGnbUeCapacityLimit {
      type uint64;
      config false;
    }
    leaf pmHoExeAttOutInterGnbPciHandling {
      type uint64;
      config false;
    }
    leaf pmCaSCellConfigAttUl {
      type uint64;
      config false;
    }
    leaf pmUeMeasEcgiTriggerDrxPciHandling {
      type uint64;
      config false;
    }
    leaf pmNrdcRelUeSnAbnormalMnInitAct {
      type uint64;
      config false;
    }
    leaf pmRrcResumeSuccRelInact {
      type uint64;
      config false;
    }
    leaf pmHoPrepAttOutIntraGnb {
      type uint64;
      config false;
    }
    leaf pmRrcConnEstabAtt {
      type uint64;
      config false;
    }
    leaf pmHoPrepSuccOutIntraGnbTs {
      type uint64;
      config false;
    }
    leaf pmRrcResumeSuccFallbackEm {
      type uint64;
      config false;
    }
    leaf-list pmDrbRelAbnormalGnb5qi {
      type uint64;
      description "MOM flags: noNotification.";
    }
    leaf pmEndcSetupUeRejCellInvalid {
      type uint64;
      config false;
    }
    leaf pmHoPrepFailInInterGnbRiMissRsrp {
      type uint64;
      config false;
    }
    leaf-list pmDrbRelAbnormalGnbAct2Arp {
      type uint64;
    }
    leaf pmEndcPSCellChangeSuccIntraSgnb {
      type uint64;
      config false;
    }
    leaf pmDrbLevelSumSa {
      type uint64;
      config false;
    }
    leaf pmRrcInactLevelMax {
      type int64;
      config false;
    }
    leaf pmHoExeSuccOutInterGnbPciHandling {
      type uint64;
      config false;
    }
    leaf pmEndcSetupUeSucc {
      type uint64;
      config false;
    }
    leaf pmSaUeMeasurementReportUcm {
      type ietfinet:port-number;
      config false;
    }
    leaf pmAnrNoActionTooWeakSa {
      type uint64;
      config false;
    }
    leaf pmHoExeAttOutIntraGnb {
      type uint64;
      config false;
    }
    leaf pmRrcConnReestSuccInterGnbMdtConsent {
      type uint64;
      config false;
    }
  }
  grouping NRCellRelation-attributes {
    leaf acaMode {
      type enumeration {
        enum AUTO;
        enum MANUAL;
      }
    }
    leaf caStatusActive {
      type boolean;
      config false;
    }
    leaf caStatusInfo {
      type enumeration {
        enum E5_TUNNEL_CAP;
        enum E5_TUNNEL_CAP_REMOTE;
        enum E5_CELL_ALLOC_CAP;
        enum E5_CELL_ALLOC_CAP_REMOTE;
        enum E5_SW_VERSION_MISMATCH;
        enum E5_MAND_CAP_MISMATCH;
        enum E5_DLCA_CAP_ONLY;
        enum INTRA_BAND_CA_BLOCKED;
        enum ESS_ULCA_BLOCKED;
      }
      config false;
    }
    leaf cellIndividualOffsetNR {
      type int32 {
        range "-24 | -22 | -20 | -18 | -16 | -14 | -12 | -10 | -8 | -6..6 | 8 | 10 | 12 | 14 | 16 | 18 | 20 | 22 | 24";
      }
      default "0";
      units "dB";
      description "Default value: 0.";
    }
    leaf colocationIndicator {
      type enumeration {
        enum UNKNOWN;
        enum COLOCATED;
        enum NON_COLOCATED;
      }
    }
    leaf coordinationType {
      type enumeration {
        enum INTRA_CM;
        enum INTER_CM;
        enum EXT_CM;
      }
      config false;
    }
    leaf coverageIndicator {
      type enumeration {
        enum NONE;
        enum COVERS;
        enum OVERLAP;
        enum CONTAINED_IN;
      }
    }
    leaf epLoadMonitoringEnabled {
      type boolean;
      default "false";
      description "Default value: false.";
    }
    leaf isHoAllowed {
      type boolean;
      default "true";
      description "Default value: true.";
    }
    leaf isRemoveAllowed {
      type boolean;
      default "false";
      description "Default value: false.";
    }
    leaf nRCellRef {
      type string;
      mandatory true;
    }
    leaf nRCellRelationId {
      type string;
      mandatory true;
    }
    leaf nRFreqRelationRef {
      type string;
      mandatory true;
    }
    leaf preferredCellManual {
      type boolean;
      default "false";
      description "Default value: false.";
    }
    leaf sCellCandidate {
      type enumeration {
        enum NOT_ALLOWED;
        enum ALLOWED;
        enum ONLY_ALLOWED_FOR_DL;
      }
    }
    leaf timeOfCreation {
      type string;
      config false;
    }
  }
  grouping NrdcControl-attributes {
    leaf nrdcControlId {
      type string;
      mandatory true;
    }
  }
  grouping NrdcMnCellProfile-attributes {
    leaf nrdcMnCellProfileId {
      type string;
      mandatory true;
    }
    leaf-list reservedBy {
      type string;
    }
    leaf ueConfGroupType {
      type enumeration {
        enum UE_MOBILITY_GROUP;
        enum UE_SERVICE_GROUP;
        enum UE_ADMISSION_GROUP;
      }
    }
  }
  grouping NrdcMnCellProfileUeCfg-attributes {
    leaf maxReportCells {
      type ietfinet:port-number;
      default "1";
      description "range 1..8; Default value: 1.";
    }
    leaf nrdcEnabled {
      type boolean;
      default "false";
      description "Default value: false.";
    }
    leaf nrdcMaxMeasFreqA4 {
      type eytypes:int32_range_1-7;
      default "2";
      description "range 1..7; Default value: 2.";
    }
    leaf nrdcMeasRestartTime {
      type int32 {
        range "40..240000";
      }
      default "15000";
      units "ms";
      description "range 40..240000; Default value: 15000.";
    }
    leaf nrdcMeasTime {
      type int32 {
        range "40..120000";
      }
      default "2000";
      units "ms";
      description "range 40..120000; Default value: 2000.";
    }
    leaf nrdcMnCellProfileUeCfgId {
      type string;
      mandatory true;
    }
    leaf nrdcSetupDlPktAgeThr {
      type int32 {
        range "0 | 10..500";
      }
      default "0";
      units "ms";
      description "Default value: 0.";
    }
    leaf nrdcSetupDlPktVolThr {
      type int32 {
        range "0 | 10..30000";
      }
      default "0";
      units "kB";
      description "Default value: 0.";
    }
    leaf nrdcSetupUlBufferMonCfgRef {
      type string;
    }
    leaf-list prefUeGroupList {
      type eytypes:int32_range_1-255;
      ordered-by user;
    }
    leaf pSCellTriggerQuantity {
      type enumeration {
        enum RSRP;
        enum RSRQ;
        enum SINR_FALLBACK_RSRP;
        enum SINR_FALLBACK_RSRQ;
        enum RSRP_AND_RSRQ;
        enum RSRP_AND_SINR_FALLBACK_RSRQ;
        enum RSRP_AND_SINR_NO_FALLBACK;
      }
    }
    list rsrpPSCellCandidate {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-156--29;
        default "-156";
        units "dBm";
        description "range -156..-29; Default value: -156.";
      }
      leaf timeToTrigger {
        type int32;
        default "0";
        units "ms";
        description "Default value: 0.";
      }
      }
    }
    list rsrqPSCellCandidate {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-435-200;
        default "-435";
        units "dB";
        description "range -435..200; Default value: -435.";
      }
      leaf timeToTrigger {
        type int32;
        default "0";
        units "ms";
        description "Default value: 0.";
      }
      }
    }
    list sinrPSCellCandidate {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-230-405;
        default "-230";
        units "dB";
        description "range -230..405; Default value: -230.";
      }
      leaf timeToTrigger {
        type int32;
        default "0";
        units "ms";
        description "Default value: 0.";
      }
      }
    }
    leaf-list ueConfGroupList {
      type eytypes:int32_range_1-255;
      ordered-by user;
    }
    leaf-list ueGroupList {
      type eytypes:int32_range_1-255;
      ordered-by user;
    }
  }
  grouping NrdcSnTermination-attributes {
    leaf defaultNrdcSnTerm {
      type boolean;
      default "false";
      description "Default value: false.";
    }
    leaf nrdcSnTerminationId {
      type string;
      mandatory true;
    }
    leaf-list reservedBy {
      type string;
    }
    leaf ueConfGroupType {
      type enumeration {
        enum UE_MOBILITY_GROUP;
        enum UE_SERVICE_GROUP;
        enum UE_ADMISSION_GROUP;
      }
    }
  }
  grouping NrdcSnTerminationUeCfg-attributes {
    leaf nrdcSnTermAllowed {
      type uint16 {
        range "0..32767";
      }
      default "0";
      description "range 0..32767; Default value: 0.";
    }
    leaf nrdcSnTerminationUeCfgId {
      type string;
      mandatory true;
    }
    leaf-list prefUeGroupList {
      type eytypes:int32_range_1-255;
      ordered-by user;
    }
    leaf-list ueConfGroupList {
      type eytypes:int32_range_1-255;
      ordered-by user;
    }
    leaf-list ueGroupList {
      type eytypes:int32_range_1-255;
      ordered-by user;
    }
  }
  grouping NRFreqRelation-attributes {
    leaf addSCellCandidateThresh {
      type eytypes:int32_range_0-100;
      units "percent";
      description "range 0..100.";
    }
    leaf addSCellCandThresh {
      type eytypes:int32_range_1-100;
      default "15";
      units "percent";
      description "range 1..100; Default value: 15.";
    }
    leaf anrMeasOn {
      type boolean;
      default "true";
      description "Default value: true.";
    }
    leaf caFreqRelMeasProfileRef {
      type string;
    }
    leaf cellReselectionPriority {
      type eytypes:int32_range_-1-7;
      default "7";
      description "range -1..7; Default value: 7.";
    }
    leaf cellReselectionSubPriority {
      type int32 {
        range "2 | 4 | 6 | 8";
      }
    }
    leaf intraFreqMCFreqRelProfileRef {
      type string;
      status deprecated;
      description "Takes effect: Next usage; MOM flags: isNillable=true; Status info: Since 24.Q1. Replaced by caFreqRelMeasProfileRef. Planned to be removed..";
      reference "Takes effect: Next usage.";
    }
    leaf isRemoveAllowed {
      type boolean;
      default "false";
      description "Default value: false.";
    }
    leaf mcpcPCellNrFreqRelProfileRef {
      type string;
    }
    leaf mcpcPSCellNrFreqRelProfileRef {
      type string;
    }
    leaf mdtMeasOn {
      type boolean;
      default "true";
      description "Default value: true.";
    }
    leaf nccmTargetHigh {
      type eytypes:int32_range_0-100-3;
      description "range 0..100.";
    }
    leaf nccmTargetLow {
      type eytypes:int32_range_0-100-3;
      description "range 0..100.";
    }
    leaf nrdcA4ThrRsrpFreqOffset {
      type eytypes:int32_range_-30-30;
      default "0";
      units "dB";
      description "range -30..30; Default value: 0.";
    }
    leaf nrdcA4ThrRsrqFreqOffset {
      type eytypes:int32_range_-230-230;
      default "0";
      units "dB";
      description "range -230..230; Default value: 0.";
    }
    leaf nrdcA4ThrSinrFreqOffset {
      type eytypes:int32_range_-100-100;
      default "0";
      units "dB";
      description "range -100..100; Default value: 0.";
    }
    leaf nRFreqRelationId {
      type string;
      mandatory true;
    }
    leaf nRFrequencyRef {
      type string;
      mandatory true;
    }
    leaf offloadNrFreqRelProfileRef {
      type string;
    }
    list plmnIdList {
      key "id";
      leaf id {
        type uint32;
        description "Synthetic key for struct sequence entry.";
      }
      ordered-by user;
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
    leaf plmnRestriction {
      type boolean;
      default "false";
      description "Default value: false.";
    }
    leaf pMax {
      type int32 {
        range "-30..33 | 1000";
      }
      default "23";
      units "dBm";
      description "Default value: 23.";
    }
    leaf qOffsetFreq {
      type int32 {
        range "-24 | -22 | -20 | -18 | -16 | -14 | -12 | -10 | -8 | -6..6 | 8 | 10 | 12 | 14 | 16 | 18 | 20 | 22 | 24";
      }
      default "0";
      units "dB";
      description "Default value: 0.";
    }
    leaf qQualMin {
      type eytypes:int32_range_-43--12;
      units "dB";
      description "range -43..-12.";
    }
    leaf qRxLevMin {
      type eytypes:int32_range_-140--44;
      default "-140";
      units "dBm";
      description "range -140..-44; Default value: -140.";
    }
    leaf redCapEnabled {
      type boolean;
      default "false";
      description "Default value: false.";
    }
    leaf removeSCellCandidateThresh {
      type eytypes:int32_range_0-100;
      units "percent";
      description "range 0..100.";
    }
    leaf removeSCellCandThresh {
      type int32 {
        range "0..99";
      }
      default "5";
      units "percent";
      description "range 0..99; Default value: 5.";
    }
    leaf-list reservedBy {
      type string;
    }
    leaf sIntraSearchP {
      type eytypes:int32_range_0-62;
      default "62";
      units "dB";
      description "range 0..62; Default value: 62.";
    }
    leaf sIntraSearchQ {
      type eytypes:int32_range_0-31;
      units "dB";
      description "range 0..31.";
    }
    leaf threshXHighP {
      type eytypes:int32_range_0-62;
      default "4";
      units "dB";
      description "range 0..62; Default value: 4.";
    }
    leaf threshXHighQ {
      type eytypes:int32_range_0-31;
      units "dB";
      description "range 0..31.";
    }
    leaf threshXLowP {
      type eytypes:int32_range_0-62;
      default "0";
      units "dB";
      description "range 0..62; Default value: 0.";
    }
    leaf threshXLowQ {
      type eytypes:int32_range_0-31;
      units "dB";
      description "range 0..31.";
    }
    leaf tReselectionNR {
      type eytypes:int32_range_0-7-9;
      default "2";
      units "s";
      description "range 0..7; Default value: 2.";
    }
    leaf tReselectionNrSfHigh {
      type uint32 {
        range "25 | 50 | 75 | 100";
      }
    }
    leaf tReselectionNrSfMedium {
      type uint32 {
        range "25 | 50 | 75 | 100";
      }
    }
    leaf trStPSCellNrFreqRelProfileRef {
      type string;
    }
    leaf trStSaNrFreqRelProfileRef {
      type string;
    }
    leaf ucmNrFreqRelProfileRef {
      type string;
    }
    leaf ueMCNrFreqRelProfileRef {
      type string;
    }
  }
  grouping NRFreqRelationTemplate-attributes {
    leaf arfcnValueNRDlHigh {
      type eytypes:int32_range_0-3279165;
      description "range 0..3279165.";
    }
    leaf arfcnValueNRDlLow {
      type eytypes:int32_range_0-3279165;
      description "range 0..3279165.";
    }
    leaf defaultNRFreqRelationRef {
      type string;
    }
    leaf nRFreqRelationTemplateId {
      type string;
      mandatory true;
    }
  }
  grouping NRFrequency-attributes {
    leaf arfcnValueNRDl {
      type eytypes:int32_range_0-3279165;
      mandatory true;
      description "range 0..3279165.";
    }
    leaf-list bandList {
      type eytypes:int32_range_1-1024;
    }
    leaf-list bandListManual {
      type int32 {
        range "1..3 | 5 | 7..8 | 12..14 | 18 | 20 | 24..26 | 28..31 | 34 | 38..41 | 46 | 48 | 50..51 | 53..54 | 65..68 | 70..72 | 74..102 | 104..106 | 109..110 | 257..262";
      }
      ordered-by user;
    }
    leaf gscn {
      type int32;
      config false;
    }
    leaf isRemoveAllowed {
      type boolean;
      default "false";
      description "Default value: false.";
    }
    leaf nRFrequencyId {
      type string;
      mandatory true;
    }
    leaf-list reservedBy {
      type string;
    }
    leaf smtcDuration {
      type eytypes:int32_range_1-5;
      default "5";
      units "ms";
      description "range 1..5; Default value: 5.";
    }
    leaf smtcOffset {
      type eytypes:int32_range_0-159;
      default "0";
      units "ms";
      description "range 0..159; Default value: 0.";
    }
    leaf smtcPeriodicity {
      type int32 {
        range "5 | 10 | 20 | 40 | 80 | 160";
      }
      default "20";
      units "ms";
      description "Default value: 20.";
    }
    leaf smtcScs {
      type int32 {
        range "15 | 30 | 120 | 240";
      }
      mandatory true;
      units "kHz";
    }
    leaf ssbToMeasureIdle {
      type string {
        length "1..64";
        pattern "[0]*1[01]*";
      }
      description "length 1..64.";
    }
    list ssRssiMeasIdle {
      key "id";
      leaf id {
        type uint32;
        description "Synthetic key for struct entry.";
      }
      container attributes {
      leaf endSymbol {
        type int32;
      }
      leaf measurementSlots {
        type string {
          length "1..80";
          pattern "[0]*1[01]*";
        }
        description "length 1..80.";
      }
      }
    }
    leaf ueConfGroupType {
      type enumeration {
        enum UE_MOBILITY_GROUP;
        enum UE_SERVICE_GROUP;
        enum UE_ADMISSION_GROUP;
      }
    }
  }
  grouping NRFrequencyUeCfg-attributes {
    leaf nRFrequencyUeCfgId {
      type string;
      mandatory true;
    }
    leaf-list prefUeGroupList {
      type eytypes:int32_range_1-255;
      ordered-by user;
    }
    leaf ssbToMeasureConnected {
      type string {
        length "1..64";
        pattern "[0]*1[01]*";
      }
      description "length 1..64.";
    }
    list ssRssiMeasConnected {
      key "id";
      leaf id {
        type uint32;
        description "Synthetic key for struct entry.";
      }
      container attributes {
      leaf endSymbol {
        type int32;
      }
      leaf measurementSlots {
        type string {
          length "1..80";
          pattern "[0]*1[01]*";
        }
        description "length 1..80.";
      }
      }
    }
    leaf-list ueConfGroupList {
      type eytypes:int32_range_1-255;
      ordered-by user;
    }
    leaf-list ueGroupList {
      type eytypes:int32_range_1-255;
      ordered-by user;
    }
    leaf userLabel {
      type string;
    }
  }
  grouping NRNetwork-attributes {
    leaf nRNetworkId {
      type string;
      mandatory true;
    }
  }
  grouping OffloadCellProfile-attributes {
    leaf offloadCellProfileId {
      type string;
      mandatory true;
    }
    leaf-list reservedBy {
      type string;
    }
    leaf softUeReleaseTime {
      type int32 {
        range "10..180";
      }
      units "s";
      description "range 10..180.";
    }
    leaf ueConfGroupType {
      type enumeration {
        enum UE_MOBILITY_GROUP;
        enum UE_SERVICE_GROUP;
        enum UE_ADMISSION_GROUP;
      }
    }
  }
  grouping OffloadCellProfileUeCfg-attributes {
    leaf cellOffloadPriority {
      type eytypes:int32_range_0-7;
      default "1";
      description "range 0..7; Default value: 1.";
    }
    leaf checkForOffloadEnd {
      type boolean;
      default "false";
      description "Default value: false.";
    }
    leaf maxReportCells {
      type ietfinet:port-number;
      default "1";
      description "range 1..8; Default value: 1.";
    }
    leaf offloadCellProfileUeCfgId {
      type string;
      mandatory true;
    }
    leaf offloadIncomingHoEnabled {
      type boolean;
      default "true";
      description "Default value: true.";
    }
    leaf offloadISHoEnabled {
      type boolean;
      default "false";
      description "Default value: false.";
    }
    leaf pCellCandidateTriggerQuantity {
      type enumeration {
        enum RSRP;
        enum RSRQ;
        enum SINR_FALLBACK_RSRP;
        enum SINR_FALLBACK_RSRQ;
      }
    }
    leaf-list prefUeGroupList {
      type eytypes:int32_range_1-255;
      ordered-by user;
    }
    leaf rimOffloadIncHoNoRsrpAllowed {
      type boolean;
      default "false";
      description "Default value: false.";
    }
    leaf rimOffloadIncHoRsrpThresh {
      type eytypes:int32_range_-140--44;
      units "dBm";
      description "range -140..-44.";
    }
    leaf rsrpPCellCandAddTargEval {
      type enumeration {
        enum NONE;
        enum RSRQ;
        enum SINR_FALLBACK_RSRQ;
        enum SINR_NO_FALLBACK_RSRQ;
      }
    }
    leaf rsrpPCellCandB1AddTargEval {
      type enumeration {
        enum NONE;
        enum RSRQ;
        enum SINR_FALLBACK_RSRQ;
        enum SINR_NO_FALLBACK_RSRQ;
      }
    }
    list rsrpPCellCandidate {
      key "id";
      leaf id {
        type uint32;
        description "Synthetic key for struct entry.";
      }
      container attributes {
      leaf hysteresis {
        type eytypes:int32_range_0-150;
        default "10";
        units "dB";
        description "range 0..150; Default value: 10.";
      }
      leaf threshold2 {
        type eytypes:int32_range_-156--29;
        default "-156";
        units "dBm";
        description "range -156..-29; Default value: -156.";
      }
      leaf timeToTrigger {
        type int32;
        default "640";
        units "ms";
        description "Default value: 640.";
      }
      }
    }
    list rsrpPCellCandidateB1 {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-140--44;
        default "-140";
        units "dBm";
        description "range -140..-44; Default value: -140.";
      }
      leaf timeToTrigger {
        type int32;
        default "40";
        units "ms";
        description "Default value: 40.";
      }
      }
    }
    leaf rsrqPCellCandAddTargEval {
      type enumeration {
        enum NONE;
        enum RSRP;
      }
    }
    leaf rsrqPCellCandB1AddTargEval {
      type enumeration {
        enum NONE;
        enum RSRP;
      }
    }
    list rsrqPCellCandidate {
      key "id";
      leaf id {
        type uint32;
        description "Synthetic key for struct entry.";
      }
      container attributes {
      leaf hysteresis {
        type eytypes:int32_range_0-150;
        default "10";
        units "dB";
        description "range 0..150; Default value: 10.";
      }
      leaf threshold2 {
        type eytypes:int32_range_-435-200;
        default "-435";
        units "dB";
        description "range -435..200; Default value: -435.";
      }
      leaf timeToTrigger {
        type int32;
        default "640";
        units "ms";
        description "Default value: 640.";
      }
      }
    }
    list rsrqPCellCandidateB1 {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-195--30;
        default "-195";
        units "dB";
        description "range -195..-30; Default value: -195.";
      }
      leaf timeToTrigger {
        type int32;
        default "40";
        units "ms";
        description "Default value: 40.";
      }
      }
    }
    leaf sinrPCellCandAddTargEval {
      type enumeration {
        enum NONE;
        enum RSRP;
        enum RSRQ;
        enum RSRP_AND_RSRQ;
      }
    }
    leaf sinrPCellCandB1AddTargEval {
      type enumeration {
        enum NONE;
        enum RSRP;
        enum RSRQ;
        enum RSRP_AND_RSRQ;
      }
    }
    list sinrPCellCandidate {
      key "id";
      leaf id {
        type uint32;
        description "Synthetic key for struct entry.";
      }
      container attributes {
      leaf hysteresis {
        type eytypes:int32_range_0-150;
        default "10";
        units "dB";
        description "range 0..150; Default value: 10.";
      }
      leaf threshold2 {
        type eytypes:int32_range_-230-405;
        default "-230";
        units "dB";
        description "range -230..405; Default value: -230.";
      }
      leaf timeToTrigger {
        type int32;
        default "640";
        units "ms";
        description "Default value: 640.";
      }
      }
    }
    list sinrPCellCandidateB1 {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-230-405;
        default "-230";
        units "dB";
        description "range -230..405; Default value: -230.";
      }
      leaf timeToTrigger {
        type int32;
        default "40";
        units "ms";
        description "Default value: 40.";
      }
      }
    }
    leaf softUeReleasePriority {
      type eytypes:int32_range_0-7;
      description "range 0..7.";
    }
    leaf-list ueConfGroupList {
      type eytypes:int32_range_1-255;
      ordered-by user;
    }
    leaf-list ueGroupList {
      type eytypes:int32_range_1-255;
      ordered-by user;
    }
    leaf ueOffloadISHoRatio {
      type eytypes:int32_range_0-1000-11;
      default "1000";
      units "percent";
      description "range 0..1000; Default value: 1000.";
    }
  }
  grouping OffloadEUtranFreqRelProfile-attributes {
    leaf offloadEUtranFreqRelProfileId {
      type string;
      mandatory true;
    }
    leaf-list reservedBy {
      type string;
    }
    leaf ueConfGroupType {
      type enumeration {
        enum UE_MOBILITY_GROUP;
        enum UE_SERVICE_GROUP;
        enum UE_ADMISSION_GROUP;
      }
    }
  }
  grouping OffloadEUtranFreqRelProfileUeCfg-attributes {
    leaf offloadEUtranFreqRelProfileUeCfgId {
      type string;
      mandatory true;
    }
    leaf offloadISHoAllowed {
      type boolean;
      default "false";
      description "Default value: false.";
    }
    leaf-list prefUeGroupList {
      type eytypes:int32_range_1-255;
      ordered-by user;
    }
    leaf rimOffloadType {
      type enumeration {
        enum NOT_ALLOWED;
        enum BLIND_RWR;
      }
    }
    leaf rsrpPCellCandidateB1Offset {
      type eytypes:int32_range_-100-100;
      default "0";
      units "dB";
      description "range -100..100; Default value: 0.";
    }
    leaf rsrqPCellCandidateB1Offset {
      type eytypes:int32_range_-100-100;
      default "0";
      units "dB";
      description "range -100..100; Default value: 0.";
    }
    leaf sinrPCellCandidateB1Offset {
      type eytypes:int32_range_-100-100;
      default "0";
      units "dB";
      description "range -100..100; Default value: 0.";
    }
    leaf-list ueConfGroupList {
      type eytypes:int32_range_1-255;
      ordered-by user;
    }
    leaf-list ueGroupList {
      type eytypes:int32_range_1-255;
      ordered-by user;
    }
  }
  grouping OffloadNrFreqRelProfile-attributes {
    leaf offloadNrFreqRelProfileId {
      type string;
      mandatory true;
    }
    leaf-list reservedBy {
      type string;
    }
    leaf ueConfGroupType {
      type enumeration {
        enum UE_MOBILITY_GROUP;
        enum UE_SERVICE_GROUP;
        enum UE_ADMISSION_GROUP;
      }
    }
  }
  grouping OffloadNrFreqRelProfileUeCfg-attributes {
    leaf offloadNrFreqRelProfileUeCfgId {
      type string;
      mandatory true;
    }
    leaf-list prefUeGroupList {
      type eytypes:int32_range_1-255;
      ordered-by user;
    }
    leaf rimOffloadType {
      type enumeration {
        enum NOT_ALLOWED;
        enum BLIND_RWR;
      }
    }
    leaf rsrpPCellCandidateOffset {
      type eytypes:int32_range_-100-100;
      default "0";
      units "dB";
      description "range -100..100; Default value: 0.";
    }
    leaf rsrqPCellCandidateOffset {
      type eytypes:int32_range_-100-100;
      default "0";
      units "dB";
      description "range -100..100; Default value: 0.";
    }
    leaf sinrPCellCandidateOffset {
      type eytypes:int32_range_-100-100;
      default "0";
      units "dB";
      description "range -100..100; Default value: 0.";
    }
    leaf-list ueConfGroupList {
      type eytypes:int32_range_1-255;
      ordered-by user;
    }
    leaf-list ueGroupList {
      type eytypes:int32_range_1-255;
      ordered-by user;
    }
  }
  grouping PciConflictEUtran-attributes {
    leaf pciConflictDetectionThreshLTE {
      type eytypes:int32_range_1-99;
      description "range 1..99.";
    }
    leaf pciConflictEUtranId {
      type string;
      mandatory true;
    }
    leaf ueConfGroupType {
      type enumeration {
        enum UE_MOBILITY_GROUP;
        enum UE_SERVICE_GROUP;
        enum UE_ADMISSION_GROUP;
      }
    }
  }
  grouping PciConflictEUtranUeCfg-attributes {
    leaf pciConflictDetectionEcgiMeas {
      type enumeration {
        enum DISABLED;
        enum ENABLED;
      }
    }
    leaf pciConflictDrxInactivityTimer {
      type enumeration {
        enum INACTIVITYTIMER_0MS;
        enum INACTIVITYTIMER_1MS;
        enum INACTIVITYTIMER_2MS;
        enum INACTIVITYTIMER_3MS;
        enum INACTIVITYTIMER_4MS;
        enum INACTIVITYTIMER_5MS;
        enum INACTIVITYTIMER_6MS;
        enum INACTIVITYTIMER_8MS;
        enum INACTIVITYTIMER_10MS;
        enum INACTIVITYTIMER_20MS;
        enum INACTIVITYTIMER_30MS;
        enum INACTIVITYTIMER_40MS;
        enum INACTIVITYTIMER_50MS;
        enum INACTIVITYTIMER_60MS;
        enum INACTIVITYTIMER_80MS;
        enum INACTIVITYTIMER_100MS;
        enum INACTIVITYTIMER_200MS;
        enum INACTIVITYTIMER_300MS;
        enum INACTIVITYTIMER_500MS;
        enum INACTIVITYTIMER_750MS;
        enum INACTIVITYTIMER_1280MS;
        enum INACTIVITYTIMER_1920MS;
        enum INACTIVITYTIMER_2560MS;
      }
    }
    leaf pciConflictDrxLongCycle {
      type enumeration {
        enum LONGCYCLE_10MS;
        enum LONGCYCLE_20MS;
        enum LONGCYCLE_32MS;
        enum LONGCYCLE_40MS;
        enum LONGCYCLE_60MS;
        enum LONGCYCLE_64MS;
        enum LONGCYCLE_70MS;
        enum LONGCYCLE_80MS;
        enum LONGCYCLE_128MS;
        enum LONGCYCLE_160MS;
        enum LONGCYCLE_256MS;
        enum LONGCYCLE_320MS;
        enum LONGCYCLE_512MS;
        enum LONGCYCLE_640MS;
        enum LONGCYCLE_1024MS;
        enum LONGCYCLE_1280MS;
        enum LONGCYCLE_2048MS;
        enum LONGCYCLE_2560MS;
        enum LONGCYCLE_5120MS;
        enum LONGCYCLE_10240MS;
      }
    }
    leaf pciConflictDrxOnDurationTimer {
      type enumeration {
        enum ONDURATIONTIMER_1SUBMS;
        enum ONDURATIONTIMER_2SUBMS;
        enum ONDURATIONTIMER_3SUBMS;
        enum ONDURATIONTIMER_4SUBMS;
        enum ONDURATIONTIMER_5SUBMS;
        enum ONDURATIONTIMER_6SUBMS;
        enum ONDURATIONTIMER_7SUBMS;
        enum ONDURATIONTIMER_8SUBMS;
        enum ONDURATIONTIMER_9SUBMS;
        enum ONDURATIONTIMER_10SUBMS;
        enum ONDURATIONTIMER_11SUBMS;
        enum ONDURATIONTIMER_12SUBMS;
        enum ONDURATIONTIMER_13SUBMS;
        enum ONDURATIONTIMER_14SUBMS;
        enum ONDURATIONTIMER_15SUBMS;
        enum ONDURATIONTIMER_16SUBMS;
        enum ONDURATIONTIMER_17SUBMS;
        enum ONDURATIONTIMER_18SUBMS;
        enum ONDURATIONTIMER_19SUBMS;
        enum ONDURATIONTIMER_20SUBMS;
        enum ONDURATIONTIMER_21SUBMS;
        enum ONDURATIONTIMER_22SUBMS;
        enum ONDURATIONTIMER_23SUBMS;
        enum ONDURATIONTIMER_24SUBMS;
        enum ONDURATIONTIMER_25SUBMS;
        enum ONDURATIONTIMER_26SUBMS;
        enum ONDURATIONTIMER_27SUBMS;
        enum ONDURATIONTIMER_28SUBMS;
        enum ONDURATIONTIMER_29SUBMS;
        enum ONDURATIONTIMER_30SUBMS;
        enum ONDURATIONTIMER_31SUBMS;
        enum ONDURATIONTIMER_1MS;
        enum ONDURATIONTIMER_2MS;
        enum ONDURATIONTIMER_3MS;
        enum ONDURATIONTIMER_4MS;
        enum ONDURATIONTIMER_5MS;
        enum ONDURATIONTIMER_6MS;
        enum ONDURATIONTIMER_8MS;
        enum ONDURATIONTIMER_10MS;
        enum ONDURATIONTIMER_20MS;
        enum ONDURATIONTIMER_30MS;
        enum ONDURATIONTIMER_40MS;
        enum ONDURATIONTIMER_50MS;
        enum ONDURATIONTIMER_60MS;
        enum ONDURATIONTIMER_80MS;
        enum ONDURATIONTIMER_100MS;
        enum ONDURATIONTIMER_200MS;
        enum ONDURATIONTIMER_300MS;
        enum ONDURATIONTIMER_400MS;
        enum ONDURATIONTIMER_500MS;
        enum ONDURATIONTIMER_600MS;
        enum ONDURATIONTIMER_800MS;
        enum ONDURATIONTIMER_1000MS;
        enum ONDURATIONTIMER_1200MS;
        enum ONDURATIONTIMER_1600MS;
      }
    }
    leaf pciConflictEUtranUeCfgId {
      type string;
      mandatory true;
    }
    leaf pciConflictMobilityEcgiMeas {
      type enumeration {
        enum DISABLED;
        enum ENABLED;
      }
    }
    leaf pciConflictTargetSelectMode {
      type enumeration {
        enum DISABLED;
        enum HITRATE_BASED;
        enum MANUAL_BASED;
        enum HITRATE_MANUAL_BASED;
        enum MANUAL_HITRATE_BASED;
      }
    }
    leaf-list prefUeGroupList {
      type eytypes:int32_range_1-255;
      ordered-by user;
    }
    leaf-list ueConfGroupList {
      type eytypes:int32_range_1-255;
      ordered-by user;
    }
    leaf-list ueGroupList {
      type eytypes:int32_range_1-255;
      ordered-by user;
    }
  }
  grouping PciConflictNR-attributes {
    leaf pciConflictDetectionThreshNr {
      type eytypes:int32_range_1-99;
      description "range 1..99.";
    }
    leaf pciConflictNRId {
      type string;
      mandatory true;
    }
    leaf ueConfGroupType {
      type enumeration {
        enum UE_MOBILITY_GROUP;
        enum UE_SERVICE_GROUP;
        enum UE_ADMISSION_GROUP;
      }
    }
  }
  grouping PciConflictNRUeCfg-attributes {
    leaf pciConflictDetectionNcgiMeas {
      type enumeration {
        enum DISABLED;
        enum FR1;
      }
    }
    leaf pciConflictDrxInactivityTimer {
      type enumeration {
        enum INACTIVITYTIMER_0MS;
        enum INACTIVITYTIMER_1MS;
        enum INACTIVITYTIMER_2MS;
        enum INACTIVITYTIMER_3MS;
        enum INACTIVITYTIMER_4MS;
        enum INACTIVITYTIMER_5MS;
        enum INACTIVITYTIMER_6MS;
        enum INACTIVITYTIMER_8MS;
        enum INACTIVITYTIMER_10MS;
        enum INACTIVITYTIMER_20MS;
        enum INACTIVITYTIMER_30MS;
        enum INACTIVITYTIMER_40MS;
        enum INACTIVITYTIMER_50MS;
        enum INACTIVITYTIMER_60MS;
        enum INACTIVITYTIMER_80MS;
        enum INACTIVITYTIMER_100MS;
        enum INACTIVITYTIMER_200MS;
        enum INACTIVITYTIMER_300MS;
        enum INACTIVITYTIMER_500MS;
        enum INACTIVITYTIMER_750MS;
        enum INACTIVITYTIMER_1280MS;
        enum INACTIVITYTIMER_1920MS;
        enum INACTIVITYTIMER_2560MS;
      }
    }
    leaf pciConflictDrxLongCycle {
      type enumeration {
        enum LONGCYCLE_10MS;
        enum LONGCYCLE_20MS;
        enum LONGCYCLE_32MS;
        enum LONGCYCLE_40MS;
        enum LONGCYCLE_60MS;
        enum LONGCYCLE_64MS;
        enum LONGCYCLE_70MS;
        enum LONGCYCLE_80MS;
        enum LONGCYCLE_128MS;
        enum LONGCYCLE_160MS;
        enum LONGCYCLE_256MS;
        enum LONGCYCLE_320MS;
        enum LONGCYCLE_512MS;
        enum LONGCYCLE_640MS;
        enum LONGCYCLE_1024MS;
        enum LONGCYCLE_1280MS;
        enum LONGCYCLE_2048MS;
        enum LONGCYCLE_2560MS;
        enum LONGCYCLE_5120MS;
        enum LONGCYCLE_10240MS;
      }
    }
    leaf pciConflictDrxOnDurationTimer {
      type enumeration {
        enum ONDURATIONTIMER_1SUBMS;
        enum ONDURATIONTIMER_2SUBMS;
        enum ONDURATIONTIMER_3SUBMS;
        enum ONDURATIONTIMER_4SUBMS;
        enum ONDURATIONTIMER_5SUBMS;
        enum ONDURATIONTIMER_6SUBMS;
        enum ONDURATIONTIMER_7SUBMS;
        enum ONDURATIONTIMER_8SUBMS;
        enum ONDURATIONTIMER_9SUBMS;
        enum ONDURATIONTIMER_10SUBMS;
        enum ONDURATIONTIMER_11SUBMS;
        enum ONDURATIONTIMER_12SUBMS;
        enum ONDURATIONTIMER_13SUBMS;
        enum ONDURATIONTIMER_14SUBMS;
        enum ONDURATIONTIMER_15SUBMS;
        enum ONDURATIONTIMER_16SUBMS;
        enum ONDURATIONTIMER_17SUBMS;
        enum ONDURATIONTIMER_18SUBMS;
        enum ONDURATIONTIMER_19SUBMS;
        enum ONDURATIONTIMER_20SUBMS;
        enum ONDURATIONTIMER_21SUBMS;
        enum ONDURATIONTIMER_22SUBMS;
        enum ONDURATIONTIMER_23SUBMS;
        enum ONDURATIONTIMER_24SUBMS;
        enum ONDURATIONTIMER_25SUBMS;
        enum ONDURATIONTIMER_26SUBMS;
        enum ONDURATIONTIMER_27SUBMS;
        enum ONDURATIONTIMER_28SUBMS;
        enum ONDURATIONTIMER_29SUBMS;
        enum ONDURATIONTIMER_30SUBMS;
        enum ONDURATIONTIMER_31SUBMS;
        enum ONDURATIONTIMER_1MS;
        enum ONDURATIONTIMER_2MS;
        enum ONDURATIONTIMER_3MS;
        enum ONDURATIONTIMER_4MS;
        enum ONDURATIONTIMER_5MS;
        enum ONDURATIONTIMER_6MS;
        enum ONDURATIONTIMER_8MS;
        enum ONDURATIONTIMER_10MS;
        enum ONDURATIONTIMER_20MS;
        enum ONDURATIONTIMER_30MS;
        enum ONDURATIONTIMER_40MS;
        enum ONDURATIONTIMER_50MS;
        enum ONDURATIONTIMER_60MS;
        enum ONDURATIONTIMER_80MS;
        enum ONDURATIONTIMER_100MS;
        enum ONDURATIONTIMER_200MS;
        enum ONDURATIONTIMER_300MS;
        enum ONDURATIONTIMER_400MS;
        enum ONDURATIONTIMER_500MS;
        enum ONDURATIONTIMER_600MS;
        enum ONDURATIONTIMER_800MS;
        enum ONDURATIONTIMER_1000MS;
        enum ONDURATIONTIMER_1200MS;
        enum ONDURATIONTIMER_1600MS;
      }
    }
    leaf pciConflictMobilityNcgiMeas {
      type enumeration {
        enum DISABLED;
        enum FR1;
      }
    }
    leaf pciConflictNRUeCfgId {
      type string;
      mandatory true;
    }
    leaf pciConflictTargetSelectMode {
      type enumeration {
        enum DISABLED;
        enum HITRATE_BASED;
        enum MANUAL_BASED;
        enum HITRATE_MANUAL_BASED;
        enum MANUAL_HITRATE_BASED;
      }
    }
    leaf-list prefUeGroupList {
      type eytypes:int32_range_1-255;
      ordered-by user;
    }
    leaf-list ueConfGroupList {
      type eytypes:int32_range_1-255;
      ordered-by user;
    }
    leaf-list ueGroupList {
      type eytypes:int32_range_1-255;
      ordered-by user;
    }
  }
  grouping PciHandling-attributes {
    leaf pciConflictHandlingEnabled {
      type boolean;
      default "false";
      description "Default value: false.";
    }
    leaf pciHandlingId {
      type string;
      mandatory true;
    }
  }
  grouping PeriodicUeMeas-attributes {
    leaf periodicUeMeasId {
      type string;
      mandatory true;
    }
    leaf userLabel {
      type string;
    }
  }
  grouping PmUeIntraFreqCellProfile-attributes {
    leaf maxReportCells {
      type ietfinet:port-number;
      default "4";
      description "range 1..8; Default value: 4.";
    }
    leaf pmUeIntraFreqCellProfileId {
      type string;
      mandatory true;
    }
    leaf pmUeReportType {
      type ietfinet:port-number;
    }
    leaf reportAmount {
      type ietfinet:port-number;
    }
    list reportConfigA2Rsrp {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-156--29;
        default "-156";
        units "dBm";
        description "range -156..-29; Default value: -156.";
      }
      leaf timeToTrigger {
        type int32;
        default "160";
        units "ms";
        description "Default value: 160.";
      }
      leaf timeToTriggerA1 {
        type int32;
        default "-1";
        units "ms";
        description "Default value: -1.";
      }
      }
    }
    list reportConfigA2Rsrq {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-435-200;
        default "-435";
        units "dB";
        description "range -435..200; Default value: -435.";
      }
      leaf timeToTrigger {
        type int32;
        default "160";
        units "ms";
        description "Default value: 160.";
      }
      leaf timeToTriggerA1 {
        type int32;
        default "-1";
        units "ms";
        description "Default value: -1.";
      }
      }
    }
    list reportConfigA3Rsrp {
      key "id";
      leaf id {
        type uint32;
        description "Synthetic key for struct entry.";
      }
      container attributes {
      leaf hysteresis {
        type eytypes:int32_range_0-150;
        default "10";
        units "dB";
        description "range 0..150; Default value: 10.";
      }
      leaf offset {
        type eytypes:int32_range_-150-150;
        default "30";
        units "dB";
        description "range -150..150; Default value: 30.";
      }
      leaf timeToTrigger {
        type int32;
        default "640";
        units "ms";
        description "Default value: 640.";
      }
      }
    }
    list reportConfigA3Rsrq {
      key "id";
      leaf id {
        type uint32;
        description "Synthetic key for struct entry.";
      }
      container attributes {
      leaf hysteresis {
        type eytypes:int32_range_0-150;
        default "10";
        units "dB";
        description "range 0..150; Default value: 10.";
      }
      leaf offset {
        type eytypes:int32_range_-150-150;
        default "30";
        units "dB";
        description "range -150..150; Default value: 30.";
      }
      leaf timeToTrigger {
        type int32;
        default "640";
        units "ms";
        description "Default value: 640.";
      }
      }
    }
    leaf reportInterval {
      type ietfinet:port-number;
    }
    list reportQuantityCell {
      key "id";
      leaf id {
        type uint32;
        description "Synthetic key for struct entry.";
      }
      container attributes {
      leaf rsrp {
        type boolean;
        default "true";
        description "Default value: true.";
      }
      leaf rsrq {
        type boolean;
        default "true";
        description "Default value: true.";
      }
      leaf sinr {
        type boolean;
        default "false";
        description "Default value: false.";
      }
      }
    }
    leaf-list reservedBy {
      type string;
    }
    leaf triggerQuantity {
      type enumeration {
        enum RSRP;
        enum RSRQ;
      }
    }
    leaf ueSelectionRatio {
      type eytypes:int32_range_0-1000-11;
      default "100";
      units "percent";
      description "range 0..1000; Default value: 100.";
    }
    leaf userLabel {
      type string;
    }
  }
  grouping PmUeMeas-attributes {
    leaf pmUeMeasId {
      type string;
      mandatory true;
    }
  }
  grouping PrefUeGroupSelectionProfile-attributes {
    leaf chipsetRef {
      type ietfinet:ip-address;
    }
    leaf imeiSvRef {
      type string;
    }
    leaf prefUeGroupId {
      type eytypes:int32_range_1-255;
      mandatory true;
      description "range 1..255.";
    }
    leaf prefUeGroupPriority {
      type eytypes:int32_range_1-65535;
      mandatory true;
      description "range 1..65535.";
    }
    leaf prefUeGroupSelectionProfileId {
      type string;
      mandatory true;
    }
    leaf selectionCriteria {
      type string {
        length "1..1000";
      }
      description "length 1..1000.";
    }
    leaf userLabel {
      type string;
    }
  }
  grouping PriorityService-attributes {
    list arp5qiPairList {
      key "id";
      leaf id {
        type uint32;
        description "Synthetic key for struct sequence entry.";
      }
      ordered-by user;
      container attributes {
      leaf arp {
        type eytypes:int32_range_0-15;
        default "0";
        description "range 0..15; Default value: 0.";
      }
      leaf profile5qi {
        type eytypes:int32_range_0-255;
        default "0";
        description "range 0..255; Default value: 0.";
      }
      }
    }
    leaf mpsPriorityForRwr {
      type boolean;
      default "false";
      description "Default value: false.";
    }
    list pLMNIdList {
      key "id";
      leaf id {
        type uint32;
        description "Synthetic key for struct sequence entry.";
      }
      ordered-by user;
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
    leaf priorityServiceId {
      type string;
      mandatory true;
    }
    leaf userLabel {
      type string;
    }
  }
  grouping PuemCellProfile-attributes {
    leaf puemCellProfileId {
      type string;
      mandatory true;
    }
    leaf puemCellTargetIntensity {
      type int32 {
        range "0..720 | 1440 | 2160 | 2880 | 3600";
      }
      default "360";
      description "Default value: 360.";
    }
    leaf-list reservedBy {
      type string;
    }
    leaf ueConfGroupType {
      type enumeration {
        enum UE_MOBILITY_GROUP;
        enum UE_SERVICE_GROUP;
        enum UE_ADMISSION_GROUP;
      }
    }
    leaf userLabel {
      type string;
    }
  }
  grouping PuemCellProfileUeCfg-attributes {
    leaf-list prefUeGroupList {
      type eytypes:int32_range_1-255;
      ordered-by user;
    }
    leaf puemCellProfileUeCfgId {
      type string;
      mandatory true;
    }
    list puemReportConfigPeriodical {
      key "id";
      leaf id {
        type uint32;
        description "Synthetic key for struct entry.";
      }
      container attributes {
      leaf includeBeamMeas {
        type boolean;
        default "true";
        description "Default value: true.";
      }
      leaf maxNoOfRsIndexesToReport {
        type ietfinet:port-number;
        default "1";
        description "range 0..32; Default value: 1.";
      }
      leaf maxReportCells {
        type ietfinet:port-number;
        default "8";
        description "range 1..8; Default value: 8.";
      }
      leaf reportAddNeighMeas {
        type ietfinet:port-number;
        description "Default value: true.";
      }
      leaf reportAmount {
        type ietfinet:port-number;
      }
      leaf reportInterval {
        type ietfinet:port-number;
      }
      leaf reportQuantityCell {
        type ietfinet:port-number;
      }
      leaf reportQuantityRsIndex {
        type ietfinet:port-number;
      }
      }
    }
    leaf puemUeGroupEnabled {
      type boolean;
      default "true";
      description "Default value: true.";
    }
    leaf-list ueConfGroupList {
      type eytypes:int32_range_1-255;
      ordered-by user;
    }
    leaf-list ueGroupList {
      type eytypes:int32_range_1-255;
      ordered-by user;
    }
    leaf userLabel {
      type string;
    }
  }
  grouping QciProfileEndcConfigExt-attributes {
    leaf initialUplinkConf {
      type enumeration {
        enum MCG;
        enum SCG;
      }
      status deprecated;
      default "MCG";
      description "Default value: MCG; Takes effect: New connection; Status info: Since 25.Q1. Replaced by UlDataSplitUeCfg::initialUlPrimaryPathMode. Planned to be removed..";
      reference "Takes effect: New connection.";
    }
    leaf qciProfileEndcConfigExtId {
      type ietfinet:ip-address;
      mandatory true;
      status deprecated;
      description "MOM flags: restricted, noNotification; Status info: Since 25.Q1. Planned to be removed..";
    }
    leaf ulDataSplitThreshold {
      type int32 {
        range "-1..0 | 100 | 200 | 400 | 800 | 1600 | 3200 | 6400 | 12800 | 25600 | 51200 | 102400 | 204800 | 409600 | 819200 | 1228800 | 1638400 | 2457600 | 3276800 | 4096000 | 4915200 | 5734400 | 6553600";
      }
      status deprecated;
      units "byte";
      description "Takes effect: New connection; MOM flags: isNillable=true; Status info: Since 25.Q1. Replaced by UlDataSplitUeCfg::ulDataSplitThreshScg. Planned to be removed.; Specification: 3GPP TS 38.463, 3GPP TS 38.331, 3GPP TS 38.323.";
      reference "Takes effect: New connection.";
    }
    leaf ulDataSplitThresholdMcg {
      type int32 {
        range "-1..0 | 100 | 200 | 400 | 800 | 1600 | 3200 | 6400 | 12800 | 25600 | 51200 | 102400 | 204800 | 409600 | 819200 | 1228800 | 1638400 | 2457600 | 3276800 | 4096000 | 4915200 | 5734400 | 6553600";
      }
      status deprecated;
      units "byte";
      description "Takes effect: New connection; MOM flags: isNillable=true; Status info: Since 25.Q1. Replaced by UlDataSplitUeCfg::ulDataSplitThreshMcg. Planned to be removed.; Specification: 3GPP TS 38.463, 3GPP TS 38.331, 3GPP TS 38.323.";
      reference "Takes effect: New connection.";
    }
  }
  grouping RelaxedRrmMeas-attributes {
    leaf relaxedRrmMeasId {
      type string;
      mandatory true;
    }
  }
  grouping RelaxedRrmMeasCellProfile-attributes {
    leaf combineRelaxedMeasCondition {
      type boolean;
      default "false";
      description "Default value: false.";
    }
    leaf combineRelaxedMeasCondition2 {
      type boolean;
      default "false";
      description "Default value: false.";
    }
    leaf highPriorityMeasRelax {
      type boolean;
      default "false";
      description "Default value: false.";
    }
    leaf relaxedRrmMeasCellProfileId {
      type string;
      mandatory true;
    }
    leaf-list reservedBy {
      type string;
    }
    leaf sSearchDeltaP {
      type int32 {
        range "3 | 6 | 9 | 12 | 15";
      }
      units "dB";
    }
    leaf sSearchDeltaPStationary {
      type int32 {
        range "2..3 | 6 | 9 | 12 | 15";
      }
      units "dB";
    }
    leaf sSearchThresholdP {
      type eytypes:int32_range_0-62;
      units "dB";
      description "range 0..62.";
    }
    leaf sSearchThresholdP2 {
      type eytypes:int32_range_0-62;
      units "dB";
      description "range 0..62.";
    }
    leaf sSearchThresholdQ {
      type eytypes:int32_range_0-31;
      units "dB";
      description "range 0..31.";
    }
    leaf sSearchThresholdQ2 {
      type eytypes:int32_range_0-31;
      units "dB";
      description "range 0..31.";
    }
    leaf tSearchDeltaP {
      type int32 {
        range "5 | 10 | 20 | 30 | 60 | 120 | 180 | 240 | 300";
      }
      units "s";
    }
    leaf tSearchDeltaPStationary {
      type int32 {
        range "5 | 10 | 20 | 30 | 60 | 120 | 180 | 240 | 300";
      }
      units "s";
    }
    leaf userLabel {
      type string;
    }
  }
  grouping ResourcePartition-attributes {
    leaf related5qiTableRef {
      type string;
    }
    leaf-list reservedBy {
      type string;
    }
    leaf resourcePartitionId {
      type string;
      mandatory true;
    }
    leaf resourcePartitionName {
      type string {
        length "1..255";
      }
      description "length 1..255.";
    }
  }
  grouping ResourcePartitionMember-attributes {
    leaf endpointResourceRef {
      type string;
    }
    list pLMNIdList {
      key "id";
      leaf id {
        type uint32;
        description "Synthetic key for struct sequence entry.";
      }
      ordered-by user;
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
    leaf resourcePartitionMemberId {
      type string;
      mandatory true;
    }
    list sNSSAIList {
      key "id";
      leaf id {
        type uint32;
        description "Synthetic key for struct sequence entry.";
      }
      ordered-by user;
      container attributes {
      leaf sd {
        type eytypes:int32_range_0-16777215;
        description "range 0..16777215.";
      }
      leaf sst {
        type eytypes:int32_range_0-255;
        description "range 0..255.";
      }
      }
    }
  }
  grouping ResourcePartitions-attributes {
    leaf resourcePartitionsId {
      type string;
      mandatory true;
    }
  }
  grouping RibTmRelation-attributes {
    leaf additionalInfo {
      type enumeration {
        enum FEATURE_DEACTIVATED;
        enum PEER_FEATURE_DEACTIVATED;
        enum UNSUPP_HW_CONF;
        enum PEER_UNSUPP_HW_CONF;
        enum MAX_PAIRS;
        enum PEER_MAX_PAIRS;
        enum NO_RESP_FROM_PEER;
        enum PCI_CONFLICT;
        enum INCOMPATIBLE_CELLS;
        enum CELL_DISABLED;
        enum PEER_CELL_DISABLED;
      }
      config false;
    }
    leaf administrativeState {
      type enumeration {
        enum LOCKED;
        enum UNLOCKED;
        enum SHUTTINGDOWN;
      }
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf isRemoveAllowed {
      type boolean;
      default "false";
      description "Default value: false.";
    }
    leaf measurementQuality {
      type enumeration {
        enum NO_MEASUREMENTS;
        enum UNKNOWN;
        enum RELIABLE;
        enum UNRELIABLE;
      }
      config false;
    }
    leaf operationalState {
      type enumeration {
        enum DISABLED;
        enum ENABLED;
      }
      config false;
    }
    leaf peerCellRef {
      type string;
      mandatory true;
    }
    leaf ribTmRelationId {
      type string;
      mandatory true;
    }
    leaf-list pmRibtmTimeErrorDistr {
      type uint64;
    }
  }
  grouping Rohc-attributes {
    leaf rohcId {
      type string;
      mandatory true;
    }
    leaf ueConfGroupType {
      type enumeration {
        enum UE_MOBILITY_GROUP;
        enum UE_SERVICE_GROUP;
        enum UE_ADMISSION_GROUP;
      }
    }
  }
  grouping RohcUeCfg-attributes {
    leaf-list prefUeGroupList {
      type eytypes:int32_range_1-255;
      ordered-by user;
    }
    leaf-list rohc5qiList {
      type int32 {
        range "1 | 65..66";
      }
      ordered-by user;
    }
    leaf rohcUeCfgId {
      type string;
      mandatory true;
    }
    leaf-list ueConfGroupList {
      type eytypes:int32_range_1-255;
      ordered-by user;
    }
    leaf-list ueGroupList {
      type eytypes:int32_range_1-255;
      ordered-by user;
    }
    leaf userLabel {
      type string;
    }
  }
  grouping Rrc-attributes {
    leaf rrcId {
      type string;
      mandatory true;
    }
    leaf t312 {
      type int32 {
        range "0 | 50 | 100 | 200 | 300 | 400 | 500 | 1000";
      }
      default "1000";
      units "ms";
      description "Default value: 1000.";
    }
    leaf ueConfGroupType {
      type enumeration {
        enum UE_MOBILITY_GROUP;
        enum UE_SERVICE_GROUP;
        enum UE_ADMISSION_GROUP;
      }
    }
  }
  grouping RrcInactiveProfile-attributes {
    leaf rrcInactiveProfileId {
      type string;
      mandatory true;
    }
    leaf ueConfGroupType {
      type enumeration {
        enum UE_MOBILITY_GROUP;
        enum UE_SERVICE_GROUP;
        enum UE_ADMISSION_GROUP;
      }
    }
  }
  grouping RrcInactiveProfileUeCfg-attributes {
    leaf periodicRnaUpdateCount {
      type eytypes:int32_range_0-5;
      default "1";
      description "range 0..5; Default value: 1.";
    }
    leaf periodicRnaUpdateTimer {
      type int32 {
        range "5 | 10 | 20 | 30 | 60 | 120 | 360 | 720";
      }
      default "60";
      units "minute";
      description "Default value: 60.";
    }
    leaf-list prefUeGroupList {
      type eytypes:int32_range_1-255;
      ordered-by user;
    }
    leaf rrcInactiveProfileUeCfgId {
      type string;
      mandatory true;
    }
    leaf rrcInactiveStateSupport {
      type ietfinet:port-number;
      description "Default value: true.";
    }
    leaf-list ueConfGroupList {
      type eytypes:int32_range_1-255;
      ordered-by user;
    }
    leaf-list ueGroupList {
      type eytypes:int32_range_1-255;
      ordered-by user;
    }
    leaf userLabel {
      type string;
    }
  }
  grouping RrcUeCfg-attributes {
    leaf dedicatedSib1AtHo {
      type boolean;
      default "false";
      description "Default value: false.";
    }
    leaf-list prefUeGroupList {
      type eytypes:int32_range_1-255;
      ordered-by user;
    }
    leaf rrcReestForcedFallback {
      type boolean;
      default "false";
      description "Default value: false.";
    }
    leaf rrcUeCfgId {
      type string;
      mandatory true;
    }
    leaf tWaitForRrcReestRequest {
      type eytypes:int32_range_1-20;
      default "6";
      units "s";
      description "range 1..20; Default value: 6.";
    }
    leaf-list ueConfGroupList {
      type eytypes:int32_range_1-255;
      ordered-by user;
    }
    leaf-list ueGroupList {
      type eytypes:int32_range_1-255;
      ordered-by user;
    }
    leaf userLabel {
      type string;
    }
  }
  grouping SecurityHandling-attributes {
    leaf-list cipheringAlgoPrio {
      type ietfinet:ip-address;
      ordered-by user;
    }
    leaf featCtrlIntegProtUserPlane {
      type enumeration {
        enum OFF;
        enum ON;
      }
    }
    leaf integProtUserPlaneLowRate {
      type enumeration {
        enum REJECT;
        enum NO_INTEGRITY_PROTECTION;
      }
    }
    leaf-list integrityProtectAlgoPrio {
      type enumeration {
        enum NIA1;
        enum NIA2;
        enum NIA3;
      }
      ordered-by user;
    }
    leaf personalDataProtectionEnabled {
      type boolean;
      default "true";
      description "Default value: true.";
    }
    leaf securityHandlingId {
      type string;
      mandatory true;
    }
  }
  grouping TermPointToAmf-attributes {
    list additionalOperatorPlmnIdList {
      key "id";
      leaf id {
        type uint32;
        description "Synthetic key for struct sequence entry.";
      }
      ordered-by user;
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
    leaf administrativeState {
      type enumeration {
        enum LOCKED;
        enum UNLOCKED;
        enum SHUTTINGDOWN;
      }
    }
    leaf amfName {
      type string;
      config false;
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf defaultAmf {
      type boolean;
      default "true";
      description "Default value: true.";
    }
    leaf domainName {
      type ietfinet:domain-name;
      description "length 1..255.";
    }
    leaf ipv4Address1 {
      type ietfinet:ipv4-address;
      default "0.0.0.0";
      description "length 7..15; Default value: 0.0.0.0.";
    }
    leaf ipv4Address2 {
      type ietfinet:ipv4-address;
      default "0.0.0.0";
      description "length 7..15; Default value: 0.0.0.0.";
    }
    leaf ipv6Address1 {
      type ietfinet:ipv6-address;
      default "::";
      description "length 2..39; Default value: ::.";
    }
    leaf ipv6Address2 {
      type ietfinet:ipv6-address;
      default "::";
      description "length 2..39; Default value: ::.";
    }
    leaf isRemoveAllowed {
      type boolean;
      default "false";
      description "Default value: false.";
    }
    leaf operationalState {
      type enumeration {
        enum DISABLED;
        enum ENABLED;
      }
      config false;
    }
    list operatorPLMNId {
      key "id";
      leaf id {
        type uint32;
        description "Synthetic key for struct entry.";
      }
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
    list pLMNIdList {
      config false;
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
    leaf pwsRestartHandling {
      type enumeration {
        enum DISABLED;
        enum ENABLED;
      }
    }
    leaf relativeCapacity {
      type eytypes:int32_range_0-255;
      config false;
      description "range 0..255.";
    }
    list servedGuamiList {
      config false;
      container attributes {
      leaf amfPointer {
        type eytypes:int32_range_0-63;
        default "0";
        description "range 0..63; Default value: 0.";
      }
      leaf amfRegionId {
        type eytypes:int32_range_0-255;
        default "0";
        description "range 0..255; Default value: 0.";
      }
      leaf amfSetId {
        type eytypes:int32_range_0-1023-23;
        default "0";
        description "range 0..1023; Default value: 0.";
      }
      leaf mcc {
        type string {
          length "3";
          pattern "[02345679][0-9][0-9]";
        }
        default "001";
        description "length 3..3; Default value: 001.";
      }
      leaf mnc {
        type string {
          length "2..3";
          pattern "(([0-9][0-9][0-9])|([0-9][0-9]))";
        }
        default "01";
        description "length 2..3; Default value: 01.";
      }
      }
    }
    list sNSSAIList {
      config false;
      container attributes {
      leaf sd {
        type eytypes:int32_range_0-16777215;
        description "range 0..16777215.";
      }
      leaf sst {
        type eytypes:int32_range_0-255;
        description "range 0..255.";
      }
      }
    }
    leaf termPointToAmfId {
      type string;
      mandatory true;
    }
    list unavailableGuamiList {
      config false;
      container attributes {
      leaf amfPointer {
        type eytypes:int32_range_0-63;
        default "0";
        description "range 0..63; Default value: 0.";
      }
      leaf amfRegionId {
        type eytypes:int32_range_0-255;
        default "0";
        description "range 0..255; Default value: 0.";
      }
      leaf amfSetId {
        type eytypes:int32_range_0-1023-23;
        default "0";
        description "range 0..1023; Default value: 0.";
      }
      leaf mcc {
        type string {
          length "3";
          pattern "[02345679][0-9][0-9]";
        }
        default "001";
        description "length 3..3; Default value: 001.";
      }
      leaf mnc {
        type string {
          length "2..3";
          pattern "(([0-9][0-9][0-9])|([0-9][0-9]))";
        }
        default "01";
        description "length 2..3; Default value: 01.";
      }
      }
    }
    leaf usedIpAddress {
      type ietfinet:ip-address;
      config false;
      description "length 2..39.";
    }
  }
  grouping TermPointToENodeB-attributes {
    leaf administrativeState {
      type enumeration {
        enum LOCKED;
        enum UNLOCKED;
        enum SHUTTINGDOWN;
      }
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf ipsecEpAddress {
      type ietfinet:ip-address;
      description "length 2..39.";
    }
    leaf operationalState {
      type enumeration {
        enum DISABLED;
        enum ENABLED;
      }
      config false;
    }
    leaf termPointToENodeBId {
      type string;
      mandatory true;
    }
    leaf upIpAddress {
      type ietfinet:ip-address;
      description "length 2..39.";
    }
  }
  grouping TermPointToGNBCUUP-attributes {
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf gNBCUUPId {
      type int64;
      config false;
    }
    leaf gNBCUUPName {
      type string;
      config false;
    }
    leaf operationalState {
      type enumeration {
        enum DISABLED;
        enum ENABLED;
      }
      config false;
    }
    leaf termPointToGNBCUUPId {
      type string;
      mandatory true;
    }
    leaf usedIpAddress {
      type ietfinet:ip-address;
      config false;
    }
  }
  grouping TermPointToGNBDU-attributes {
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf gNBDUId {
      type eytypes:int64_range_0-68719476735;
      config false;
      description "range 0..68719476735.";
    }
    leaf gNBDUName {
      type string {
        length "1..150";
      }
      config false;
      description "length 1..150.";
    }
    leaf operationalState {
      type enumeration {
        enum DISABLED;
        enum ENABLED;
      }
      config false;
    }
    leaf pwsBroadcastStarted {
      type boolean;
      config false;
    }
    leaf termPointToGNBDUId {
      type string;
      mandatory true;
    }
    leaf usedIpAddress {
      type ietfinet:ip-address;
      config false;
    }
  }
  grouping TermPointToGNodeB-attributes {
    leaf administrativeState {
      type enumeration {
        enum LOCKED;
        enum UNLOCKED;
        enum SHUTTINGDOWN;
      }
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf ipsecEpAddress {
      type ietfinet:ip-address;
      config false;
      description "length 2..39.";
    }
    leaf ipv4Address {
      type ietfinet:ipv4-address;
      default "0.0.0.0";
      description "length 7..15; Default value: 0.0.0.0.";
    }
    leaf ipv6Address {
      type ietfinet:ipv6-address;
      default "::";
      description "length 2..39; Default value: ::.";
    }
    leaf operationalState {
      type enumeration {
        enum DISABLED;
        enum ENABLED;
      }
      config false;
    }
    leaf termPointToGNodeBId {
      type string;
      mandatory true;
    }
    leaf upIpAddress {
      type ietfinet:ip-address;
      config false;
      description "length 2..39.";
    }
    leaf usedIpAddress {
      type ietfinet:ip-address;
      config false;
    }
    list usedPLMNId {
      config false;
      container attributes {
      leaf mcc {
        type string {
          length "3";
          pattern "[02345679][0-9][0-9]";
        }
        description "length 3..3.";
      }
      leaf mnc {
        type string {
          length "2..3";
          pattern "(([0-9][0-9][0-9])|([0-9][0-9]))";
        }
        description "length 2..3.";
      }
      }
    }
  }
  grouping TimeSchedulingGroup-attributes {
    leaf-list reservedBy {
      type string;
    }
    leaf timeSchedulingGroupId {
      type string;
      mandatory true;
    }
    leaf userLabel {
      type string;
    }
  }
  grouping TimeSchedulingWindow-attributes {
    leaf-list daysOfWeek {
      type enumeration {
        enum MON;
        enum TUE;
        enum WED;
        enum THU;
        enum FRI;
        enum SAT;
        enum SUN;
      }
      ordered-by user;
    }
    leaf epBoosterCellProfileRef {
      type string;
    }
    leaf startTime {
      type string {
        length "5";
        pattern "([01][0-9]|2[0-3]):([0-5][0-9])";
      }
      default "00:00";
      description "length 5..5; Default value: 00:00.";
    }
    leaf stopTime {
      type string {
        length "5";
        pattern "([01][0-9]|2[0-3]):([0-5][0-9])";
      }
      default "06:00";
      description "length 5..5; Default value: 06:00.";
    }
    leaf timeSchedulingWindowId {
      type string;
      mandatory true;
    }
    leaf userLabel {
      type string;
    }
  }
  grouping TnlAssociation-attributes {
    leaf activeForNonUe {
      type boolean;
      config false;
    }
    leaf operationalState {
      type enumeration {
        enum DISABLED;
        enum ENABLED;
      }
      config false;
    }
    leaf-list remoteIpAddress {
      type ietfinet:ip-address;
    }
    leaf remotePortNumber {
      type ietfinet:port-number;
      config false;
      description "range 1..65535.";
    }
    leaf tnlAssociationId {
      type string;
      mandatory true;
    }
    leaf usage {
      type enumeration {
        enum BOTH;
        enum UE;
        enum NON_UE;
      }
      config false;
    }
    leaf weightFactor {
      type eytypes:int32_range_0-255;
      config false;
      description "range 0..255.";
    }
  }
  grouping TrafficOffload-attributes {
    leaf trafficOffloadId {
      type string;
      mandatory true;
    }
  }
  grouping TrafficSteering-attributes {
    leaf bwtishoB1ToB2DepHEnabled {
      type boolean;
      default "true";
      description "Default value: true.";
    }
    leaf dlCellLoadAware {
      type boolean;
      default "false";
      description "Default value: false.";
    }
    leaf trafficSteeringId {
      type string;
      mandatory true;
    }
    leaf ulCellLoadAwareEnabled {
      type boolean;
      default "false";
      description "Default value: false.";
    }
    leaf userLabel {
      type string;
    }
  }
  grouping TrStPSCellNrFreqRelProfile-attributes {
    leaf-list reservedBy {
      type string;
    }
    leaf trStPSCellNrFreqRelProfileId {
      type string;
      mandatory true;
    }
    leaf ueConfGroupType {
      type enumeration {
        enum UE_MOBILITY_GROUP;
        enum UE_SERVICE_GROUP;
        enum UE_ADMISSION_GROUP;
      }
    }
    leaf userLabel {
      type string;
    }
  }
  grouping TrStPSCellNrFreqRelProfileUeCfg-attributes {
    leaf-list prefUeGroupList {
      type eytypes:int32_range_1-255;
      ordered-by user;
    }
    leaf rsrpCandidateA5Thr2Offset {
      type eytypes:int32_range_-100-100;
      default "0";
      units "dB";
      description "range -100..100; Default value: 0.";
    }
    leaf rsrqCandidateA5Thr2Offset {
      type eytypes:int32_range_-100-100;
      default "0";
      units "dB";
      description "range -100..100; Default value: 0.";
    }
    leaf sinrCandidateA5Thr2Offset {
      type eytypes:int32_range_-100-100;
      default "0";
      units "dB";
      description "range -100..100; Default value: 0.";
    }
    leaf trStPSCellNrFreqRelProfileUeCfgId {
      type string;
      mandatory true;
    }
    leaf-list ueConfGroupList {
      type eytypes:int32_range_1-255;
      ordered-by user;
    }
    leaf-list ueGroupList {
      type eytypes:int32_range_1-255;
      ordered-by user;
    }
    leaf userLabel {
      type string;
    }
  }
  grouping TrStPSCellProfile-attributes {
    leaf-list reservedBy {
      type string;
    }
    leaf trStPSCellProfileId {
      type string;
      mandatory true;
    }
    leaf ueConfGroupType {
      type enumeration {
        enum UE_MOBILITY_GROUP;
        enum UE_SERVICE_GROUP;
        enum UE_ADMISSION_GROUP;
      }
    }
    leaf userLabel {
      type string;
    }
  }
  grouping TrStPSCellProfileUeCfg-attributes {
    leaf candidateA5TriggerQuantity {
      type enumeration {
        enum RSRP;
        enum RSRQ;
        enum SINR_FALLBACK_RSRP;
        enum SINR_FALLBACK_RSRQ;
      }
    }
    leaf hiPrioAllowedForDistUeEnabled {
      type ietfinet:ip-address;
      description "Default value: false.";
    }
    leaf hiPrioDetInactiveTime {
      type ietfinet:ip-address;
      units "ms";
      description "range 500..300000; Default value: 30000.";
    }
    leaf hiPrioDetMeasurementTime {
      type ietfinet:ip-address;
      units "ms";
      description "range 500..120000; Default value: 5000.";
    }
    leaf hiPrioDetStartTime {
      type ietfinet:ip-address;
      units "ms";
      description "range 10..10000; Default value: 2000.";
    }
    leaf maxReportCells {
      type ietfinet:port-number;
      default "1";
      description "range 1..8; Default value: 1.";
    }
    leaf-list prefUeGroupList {
      type eytypes:int32_range_1-255;
      ordered-by user;
    }
    list rsrpCandidateA5 {
      key "id";
      leaf id {
        type uint32;
        description "Synthetic key for struct entry.";
      }
      container attributes {
      leaf hysteresis {
        type eytypes:int32_range_0-150;
        default "10";
        units "dB";
        description "range 0..150; Default value: 10.";
      }
      leaf threshold2 {
        type eytypes:int32_range_-156--29;
        default "-156";
        units "dBm";
        description "range -156..-29; Default value: -156.";
      }
      leaf timeToTrigger {
        type int32;
        default "640";
        units "ms";
        description "Default value: 640.";
      }
      }
    }
    leaf rsrpCandidateA5AddTargEval {
      type enumeration {
        enum NONE;
        enum RSRQ;
        enum SINR_FALLBACK_RSRQ;
        enum SINR_NO_FALLBACK_RSRQ;
      }
    }
    list rsrqCandidateA5 {
      key "id";
      leaf id {
        type uint32;
        description "Synthetic key for struct entry.";
      }
      container attributes {
      leaf hysteresis {
        type eytypes:int32_range_0-150;
        default "10";
        units "dB";
        description "range 0..150; Default value: 10.";
      }
      leaf threshold2 {
        type eytypes:int32_range_-435-200;
        default "-435";
        units "dB";
        description "range -435..200; Default value: -435.";
      }
      leaf timeToTrigger {
        type int32;
        default "640";
        units "ms";
        description "Default value: 640.";
      }
      }
    }
    leaf rsrqCandidateA5AddTargEval {
      type enumeration {
        enum NONE;
        enum RSRP;
      }
    }
    list sinrCandidateA5 {
      key "id";
      leaf id {
        type uint32;
        description "Synthetic key for struct entry.";
      }
      container attributes {
      leaf hysteresis {
        type eytypes:int32_range_0-150;
        default "10";
        units "dB";
        description "range 0..150; Default value: 10.";
      }
      leaf threshold2 {
        type eytypes:int32_range_-230-405;
        default "-230";
        units "dB";
        description "range -230..405; Default value: -230.";
      }
      leaf timeToTrigger {
        type int32;
        default "640";
        units "ms";
        description "Default value: 640.";
      }
      }
    }
    leaf sinrCandidateA5AddTargEval {
      type enumeration {
        enum NONE;
        enum RSRP;
        enum RSRQ;
        enum RSRP_AND_RSRQ;
      }
    }
    leaf trStPSCellProfileUeCfgId {
      type string;
      mandatory true;
    }
    leaf-list ueConfGroupList {
      type eytypes:int32_range_1-255;
      ordered-by user;
    }
    leaf-list ueGroupList {
      type eytypes:int32_range_1-255;
      ordered-by user;
    }
    leaf userLabel {
      type string;
    }
  }
  grouping TrStSaCellProfile-attributes {
    leaf dataAwareMobDlLowThpDuration {
      type int32 {
        range "1..10";
      }
      default "1";
      units "s";
      description "range 1..10; Default value: 1.";
    }
    leaf dataAwareMobDlThpFilterCoeff {
      type eytypes:int32_range_0-95;
      default "60";
      description "range 0..95; Default value: 60.";
    }
    leaf dataAwareMobDlThpFilterTime {
      type eytypes:int32_range_0-1000;
      default "200";
      units "ms";
      description "range 0..1000; Default value: 200.";
    }
    leaf dataAwareMobUlLowThpDuration {
      type int32 {
        range "1..10";
      }
      default "1";
      units "s";
      description "range 1..10; Default value: 1.";
    }
    leaf dataAwareMobUlThpFilterCoeff {
      type eytypes:int32_range_0-95;
      default "60";
      description "range 0..95; Default value: 60.";
    }
    leaf dataAwareMobUlThpFilterTime {
      type eytypes:int32_range_0-1000;
      default "200";
      units "ms";
      description "range 0..1000; Default value: 200.";
    }
    leaf-list reservedBy {
      type string;
    }
    leaf trStSaCellProfileId {
      type string;
      mandatory true;
    }
    leaf ueConfGroupType {
      type enumeration {
        enum UE_MOBILITY_GROUP;
        enum UE_SERVICE_GROUP;
        enum UE_ADMISSION_GROUP;
      }
    }
    leaf userLabel {
      type string;
    }
  }
  grouping TrStSaCellProfileUeCfg-attributes {
    leaf actionAtRelease {
      type enumeration {
        enum DISABLED;
        enum CA_CONF;
        enum PRIORITY_LIST;
        enum CRP_MLC_CONDITIONAL;
        enum RANDOM_REDIRECT;
      }
    }
    leaf aggregatedBwThreshold {
      type int32 {
        range "1..1000";
      }
      default "10";
      units "MHz";
      description "range 1..1000; Default value: 10.";
    }
    leaf bwTrigISHoEnabled {
      type boolean;
      default "false";
      description "Default value: false.";
    }
    leaf bwTrigISHoTriggerQuantity {
      type enumeration {
        enum RSRP;
        enum RSRQ;
        enum SINR_FALLBACK_RSRP;
        enum SINR_FALLBACK_RSRQ;
      }
    }
    leaf capAwarePCellSelEnabled {
      type boolean;
      status deprecated;
      default "false";
      description "Default value: false; Takes effect: Next usage; Status info: Since 23.Q2. Replaced by mlcEnabled. Planned to be removed..";
      reference "Takes effect: Next usage.";
    }
    leaf criterionBetterUeConfig {
      type eytypes:int32_range_1-100;
      default "100";
      units "percent";
      description "range 1..100; Default value: 100.";
    }
    leaf criterionDlAbsoluteOffset {
      type int32 {
        range "0 | 5..100";
      }
      default "5";
      units "Mbps";
      description "Default value: 5.";
    }
    leaf criterionUlAbsoluteOffset {
      type int32 {
        range "0..100";
      }
      default "2";
      units "Mbps";
      description "range 0..100; Default value: 2.";
    }
    leaf dataAwareMobDlPktAgeThr {
      type int32 {
        range "0 | 10..500";
      }
      default "0";
      units "ms";
      description "Default value: 0.";
    }
    leaf dataAwareMobDlPktVolThr {
      type int32 {
        range "0 | 10..30000";
      }
      default "0";
      units "kB";
      description "Default value: 0.";
    }
    leaf dataAwareMobLowDlThpThr {
      type int32 {
        range "0 | 500..10000";
      }
      default "0";
      units "kbps";
      description "Default value: 0.";
    }
    leaf dataAwareMobLowUlThpThr {
      type int32 {
        range "0 | 500..3000";
      }
      default "0";
      units "kbps";
      description "Default value: 0.";
    }
    leaf dlCellLoadAware {
      type boolean;
    }
    list freqPrioListEUtran {
      key "id";
      leaf id {
        type uint32;
        description "Synthetic key for struct sequence entry.";
      }
      ordered-by user;
      container attributes {
      leaf cellReselectionPriority {
        type eytypes:int32_range_0-7;
        default "7";
        description "range 0..7; Default value: 7.";
      }
      leaf cellReselectionSubPriority {
        type int32;
        default "0";
        description "Default value: 0.";
      }
      leaf eUtranArfcn {
        type int32;
      }
      }
    }
    list freqPrioListNR {
      key "id";
      leaf id {
        type uint32;
        description "Synthetic key for struct sequence entry.";
      }
      ordered-by user;
      container attributes {
      leaf cellReselectionPriority {
        type eytypes:int32_range_0-7;
        default "7";
        description "range 0..7; Default value: 7.";
      }
      leaf cellReselectionSubPriority {
        type int32;
        default "0";
        description "Default value: 0.";
      }
      leaf nrArfcn {
        type eytypes:int32_range_0-3279165;
        description "range 0..3279165.";
      }
      }
    }
    leaf maxReportCells {
      type ietfinet:port-number;
      default "1";
      description "range 1..8; Default value: 1.";
    }
    leaf mlcAllowedCellSetChangeAction {
      type enumeration {
        enum HANDOVER;
        enum SCELL_RESELECTION;
        enum HO_AND_SCELL_RESELECTION;
      }
    }
    leaf mlcEnabled {
      type boolean;
      default "false";
      description "Default value: false.";
    }
    leaf mlcPeriodicEnabled {
      type boolean;
      default "false";
      description "Default value: false.";
    }
    leaf mlcPeriodicInterval {
      type int32 {
        range "5..1000";
      }
      default "15";
      units "s";
      description "range 5..1000; Default value: 15.";
    }
    leaf mlcTriggerQuantity {
      type enumeration {
        enum RSRP;
        enum RSRQ;
        enum SINR_FALLBACK_RSRP;
        enum SINR_FALLBACK_RSRQ;
      }
    }
    leaf-list prefUeGroupList {
      type eytypes:int32_range_1-255;
      ordered-by user;
    }
    list rsrpPCellCandidate {
      key "id";
      leaf id {
        type uint32;
        description "Synthetic key for struct entry.";
      }
      container attributes {
      leaf hysteresis {
        type eytypes:int32_range_0-150;
        default "10";
        units "dB";
        description "range 0..150; Default value: 10.";
      }
      leaf threshold2 {
        type eytypes:int32_range_-156--29;
        default "-156";
        units "dBm";
        description "range -156..-29; Default value: -156.";
      }
      leaf timeToTrigger {
        type int32;
        default "640";
        units "ms";
        description "Default value: 640.";
      }
      }
    }
    leaf rsrpPCellCandidateAddTargEval {
      type enumeration {
        enum NONE;
        enum RSRQ;
        enum SINR_FALLBACK_RSRQ;
        enum SINR_NO_FALLBACK_RSRQ;
      }
    }
    list rsrpPCellCandidateB1 {
      key "id";
      leaf id {
        type uint32;
        description "Synthetic key for struct entry.";
      }
      description "Takes effect: Next usage; Status info: Since 24.Q2. Replaced by rsrpPCellCandidateB2. Planned to be removed.; Specification: 3GPP TS 38.331.";
      container attributes {
      leaf hysteresis {
        type eytypes:int32_range_0-150;
        default "10";
        units "dB";
        description "range 0..150; Default value: 10.";
      }
      leaf threshold {
        type eytypes:int32_range_-140--44;
        default "-140";
        units "dBm";
        description "range -140..-44; Default value: -140.";
      }
      leaf timeToTrigger {
        type int32;
        default "40";
        units "ms";
        description "Default value: 40.";
      }
      }
    }
    list rsrpPCellCandidateB2 {
      key "id";
      leaf id {
        type uint32;
        description "Synthetic key for struct entry.";
      }
      container attributes {
      leaf hysteresis {
        type eytypes:int32_range_0-150;
        default "10";
        units "dB";
        description "range 0..150; Default value: 10.";
      }
      leaf threshold1 {
        type eytypes:int32_range_-156--29;
        default "-156";
        units "dBm";
        description "range -156..-29; Default value: -156.";
      }
      leaf threshold2EUtra {
        type eytypes:int32_range_-140--44;
        default "-140";
        units "dBm";
        description "range -140..-44; Default value: -140.";
      }
      leaf timeToTrigger {
        type int32;
        default "640";
        units "ms";
        description "Default value: 640.";
      }
      }
    }
    leaf rsrpPCellCandidateB2AddTargEval {
      type enumeration {
        enum NONE;
        enum RSRQ;
        enum SINR_FALLBACK_RSRQ;
        enum SINR_NO_FALLBACK_RSRQ;
      }
    }
    list rsrpPCellCandidateB2PcOffset {
      key "id";
      leaf id {
        type uint32;
        description "Synthetic key for struct sequence entry.";
      }
      ordered-by user;
      container attributes {
      leaf powerClass {
        type enumeration {
          enum PC_1;
          enum PC_1_5;
          enum PC_2;
        }
      }
      leaf threshold1Offset {
        type eytypes:int32_range_-100-100;
        default "0";
        units "dB";
        description "range -100..100; Default value: 0.";
      }
      }
    }
    list rsrpPCellCandidatePcOffset {
      key "id";
      leaf id {
        type uint32;
        description "Synthetic key for struct sequence entry.";
      }
      ordered-by user;
      container attributes {
      leaf powerClass {
        type enumeration {
          enum PC_1;
          enum PC_1_5;
          enum PC_2;
        }
      }
      leaf threshold2Offset {
        type eytypes:int32_range_-100-100;
        default "0";
        units "dB";
        description "range -100..100; Default value: 0.";
      }
      }
    }
    list rsrpSCellCandidate {
      key "id";
      leaf id {
        type uint32;
        description "Synthetic key for struct entry.";
      }
      container attributes {
      leaf hysteresis {
        type eytypes:int32_range_0-150;
        default "10";
        units "dB";
        description "range 0..150; Default value: 10.";
      }
      leaf threshold2 {
        type eytypes:int32_range_-156--29;
        default "-156";
        units "dBm";
        description "range -156..-29; Default value: -156.";
      }
      leaf timeToTrigger {
        type int32;
        default "640";
        units "ms";
        description "Default value: 640.";
      }
      }
    }
    list rsrqPCellCandidate {
      key "id";
      leaf id {
        type uint32;
        description "Synthetic key for struct entry.";
      }
      container attributes {
      leaf hysteresis {
        type eytypes:int32_range_0-150;
        default "10";
        units "dB";
        description "range 0..150; Default value: 10.";
      }
      leaf threshold2 {
        type eytypes:int32_range_-435-200;
        default "-435";
        units "dB";
        description "range -435..200; Default value: -435.";
      }
      leaf timeToTrigger {
        type int32;
        default "640";
        units "ms";
        description "Default value: 640.";
      }
      }
    }
    leaf rsrqPCellCandidateAddTargEval {
      type enumeration {
        enum NONE;
        enum RSRP;
      }
    }
    list rsrqPCellCandidateB2 {
      key "id";
      leaf id {
        type uint32;
        description "Synthetic key for struct entry.";
      }
      container attributes {
      leaf hysteresis {
        type eytypes:int32_range_0-150;
        default "10";
        units "dB";
        description "range 0..150; Default value: 10.";
      }
      leaf threshold1 {
        type eytypes:int32_range_-435-200;
        default "-435";
        units "dB";
        description "range -435..200; Default value: -435.";
      }
      leaf threshold2EUtra {
        type eytypes:int32_range_-195--30;
        default "-195";
        units "dB";
        description "range -195..-30; Default value: -195.";
      }
      leaf timeToTrigger {
        type int32;
        default "640";
        units "ms";
        description "Default value: 640.";
      }
      }
    }
    leaf rsrqPCellCandidateB2AddTargEval {
      type enumeration {
        enum NONE;
        enum RSRP;
      }
    }
    list rsrqSCellCandidate {
      key "id";
      leaf id {
        type uint32;
        description "Synthetic key for struct entry.";
      }
      container attributes {
      leaf hysteresis {
        type eytypes:int32_range_0-150;
        default "10";
        units "dB";
        description "range 0..150; Default value: 10.";
      }
      leaf threshold2 {
        type eytypes:int32_range_-435-200;
        default "-435";
        units "dB";
        description "range -435..200; Default value: -435.";
      }
      leaf timeToTrigger {
        type int32;
        default "640";
        units "ms";
        description "Default value: 640.";
      }
      }
    }
    list sinrPCellCandidate {
      key "id";
      leaf id {
        type uint32;
        description "Synthetic key for struct entry.";
      }
      container attributes {
      leaf hysteresis {
        type eytypes:int32_range_0-150;
        default "10";
        units "dB";
        description "range 0..150; Default value: 10.";
      }
      leaf threshold2 {
        type eytypes:int32_range_-230-405;
        default "-230";
        units "dB";
        description "range -230..405; Default value: -230.";
      }
      leaf timeToTrigger {
        type int32;
        default "640";
        units "ms";
        description "Default value: 640.";
      }
      }
    }
    leaf sinrPCellCandidateAddTargEval {
      type enumeration {
        enum NONE;
        enum RSRP;
        enum RSRQ;
        enum RSRP_AND_RSRQ;
      }
    }
    list sinrPCellCandidateB2 {
      key "id";
      leaf id {
        type uint32;
        description "Synthetic key for struct entry.";
      }
      container attributes {
      leaf hysteresis {
        type eytypes:int32_range_0-150;
        default "10";
        units "dB";
        description "range 0..150; Default value: 10.";
      }
      leaf threshold1 {
        type eytypes:int32_range_-230-405;
        default "-230";
        units "dB";
        description "range -230..405; Default value: -230.";
      }
      leaf threshold2EUtra {
        type eytypes:int32_range_-230-405;
        default "-230";
        units "dB";
        description "range -230..405; Default value: -230.";
      }
      leaf timeToTrigger {
        type int32;
        default "640";
        units "ms";
        description "Default value: 640.";
      }
      }
    }
    leaf sinrPCellCandidateB2AddTargEval {
      type enumeration {
        enum NONE;
        enum RSRP;
        enum RSRQ;
        enum RSRP_AND_RSRQ;
      }
    }
    list sinrSCellCandidate {
      key "id";
      leaf id {
        type uint32;
        description "Synthetic key for struct entry.";
      }
      container attributes {
      leaf hysteresis {
        type eytypes:int32_range_0-150;
        default "10";
        units "dB";
        description "range 0..150; Default value: 10.";
      }
      leaf threshold2 {
        type eytypes:int32_range_-230-405;
        default "-230";
        units "dB";
        description "range -230..405; Default value: -230.";
      }
      leaf timeToTrigger {
        type int32;
        default "640";
        units "ms";
        description "Default value: 640.";
      }
      }
    }
    leaf t320 {
      type int32 {
        range "5 | 10 | 20 | 30 | 60 | 120 | 180";
      }
      default "30";
      units "minute";
      description "Default value: 30.";
    }
    leaf trStSaCellProfileUeCfgId {
      type string;
      mandatory true;
    }
    leaf-list ueConfGroupList {
      type eytypes:int32_range_1-255;
      ordered-by user;
    }
    leaf-list ueGroupList {
      type eytypes:int32_range_1-255;
      ordered-by user;
    }
    leaf userLabel {
      type string;
    }
  }
  grouping TrStSaEUtranFreqRelProfile-attributes {
    leaf-list reservedBy {
      type string;
    }
    leaf trStSaEUtranFreqRelProfileId {
      type string;
      mandatory true;
    }
    leaf ueConfGroupType {
      type enumeration {
        enum UE_MOBILITY_GROUP;
        enum UE_SERVICE_GROUP;
        enum UE_ADMISSION_GROUP;
      }
    }
    leaf userLabel {
      type string;
    }
  }
  grouping TrStSaEUtranFreqRelProfileUeCfg-attributes {
    leaf-list prefUeGroupList {
      type eytypes:int32_range_1-255;
      ordered-by user;
    }
    leaf rsrpPCellCandidateB1Offset {
      type eytypes:int32_range_-100-100;
      status deprecated;
      default "0";
      units "dB";
      description "range -100..100; Default value: 0; Takes effect: Next usage; Status info: Since 24.Q2. Replaced by rsrpPCellCandidateB2Offsets. Planned to be removed..";
      reference "Takes effect: Next usage.";
    }
    list rsrpPCellCandidateB2Offsets {
      key "id";
      leaf id {
        type uint32;
        description "Synthetic key for struct entry.";
      }
      container attributes {
      leaf threshold1Offset {
        type eytypes:int32_range_-100-100;
        default "0";
        units "dB";
        description "range -100..100; Default value: 0.";
      }
      leaf threshold2EUtraOffset {
        type eytypes:int32_range_-100-100;
        default "0";
        units "dB";
        description "range -100..100; Default value: 0.";
      }
      }
    }
    list rsrqPCellCandidateB2Offsets {
      key "id";
      leaf id {
        type uint32;
        description "Synthetic key for struct entry.";
      }
      container attributes {
      leaf threshold1Offset {
        type eytypes:int32_range_-100-100;
        default "0";
        units "dB";
        description "range -100..100; Default value: 0.";
      }
      leaf threshold2EUtraOffset {
        type eytypes:int32_range_-100-100;
        default "0";
        units "dB";
        description "range -100..100; Default value: 0.";
      }
      }
    }
    list sinrPCellCandidateB2Offsets {
      key "id";
      leaf id {
        type uint32;
        description "Synthetic key for struct entry.";
      }
      container attributes {
      leaf threshold1Offset {
        type eytypes:int32_range_-100-100;
        default "0";
        units "dB";
        description "range -100..100; Default value: 0.";
      }
      leaf threshold2EUtraOffset {
        type eytypes:int32_range_-100-100;
        default "0";
        units "dB";
        description "range -100..100; Default value: 0.";
      }
      }
    }
    leaf trStSaEUtranFreqRelProfileUeCfgId {
      type string;
      mandatory true;
    }
    leaf-list ueConfGroupList {
      type eytypes:int32_range_1-255;
      ordered-by user;
    }
    leaf-list ueGroupList {
      type eytypes:int32_range_1-255;
      ordered-by user;
    }
    leaf userLabel {
      type string;
    }
  }
  grouping TrStSaNrFreqRelProfile-attributes {
    leaf-list reservedBy {
      type string;
    }
    leaf trStSaNrFreqRelProfileId {
      type string;
      mandatory true;
    }
    leaf ueConfGroupType {
      type enumeration {
        enum UE_MOBILITY_GROUP;
        enum UE_SERVICE_GROUP;
        enum UE_ADMISSION_GROUP;
      }
    }
    leaf userLabel {
      type string;
    }
  }
  grouping TrStSaNrFreqRelProfileUeCfg-attributes {
    leaf hoToPrioritizedCell {
      type boolean;
      default "false";
      description "Default value: false.";
    }
    leaf pCellAllowed {
      type boolean;
      default "false";
      description "Default value: false.";
    }
    leaf-list prefUeGroupList {
      type eytypes:int32_range_1-255;
      ordered-by user;
    }
    leaf rsrpPCellCandidateOffset {
      type eytypes:int32_range_-100-100;
      default "0";
      units "dB";
      description "range -100..100; Default value: 0.";
    }
    leaf rsrpSCellCandidateOffset {
      type eytypes:int32_range_-100-100;
      default "0";
      units "dB";
      description "range -100..100; Default value: 0.";
    }
    leaf rsrpUl2lCoverageThrOffset {
      type eytypes:int32_range_-100-100;
      default "0";
      units "dB";
      description "range -100..100; Default value: 0.";
    }
    leaf rsrqPCellCandidateOffset {
      type eytypes:int32_range_-100-100;
      default "0";
      units "dB";
      description "range -100..100; Default value: 0.";
    }
    leaf rsrqSCellCandidateOffset {
      type eytypes:int32_range_-100-100;
      default "0";
      units "dB";
      description "range -100..100; Default value: 0.";
    }
    leaf sinrPCellCandidateOffset {
      type eytypes:int32_range_-100-100;
      default "0";
      units "dB";
      description "range -100..100; Default value: 0.";
    }
    leaf sinrSCellCandidateOffset {
      type eytypes:int32_range_-100-100;
      default "0";
      units "dB";
      description "range -100..100; Default value: 0.";
    }
    leaf trStSaNrFreqRelProfileUeCfgId {
      type string;
      mandatory true;
    }
    leaf-list ueConfGroupList {
      type eytypes:int32_range_1-255;
      ordered-by user;
    }
    leaf-list ueGroupList {
      type eytypes:int32_range_1-255;
      ordered-by user;
    }
    leaf userLabel {
      type string;
    }
  }
  grouping Uac-attributes {
    leaf uacId {
      type string;
      mandatory true;
    }
  }
  grouping UacProfile-attributes {
    leaf barringEnabled {
      type boolean;
      default "false";
      description "Default value: false.";
    }
    leaf-list reservedBy {
      type string;
    }
    leaf uacProfileId {
      type string;
      mandatory true;
    }
  }
  grouping UaiProfile-attributes {
    leaf uaiProfileId {
      type ietfinet:ip-address;
      mandatory true;
    }
    leaf ueConfGroupType {
      type enumeration {
        enum UE_MOBILITY_GROUP;
        enum UE_SERVICE_GROUP;
        enum UE_ADMISSION_GROUP;
      }
    }
  }
  grouping UaiProfileUeCfg-attributes {
    leaf overheatingAssistanceConfig {
      type boolean;
      default "false";
      description "Default value: false.";
    }
    leaf overheatingIndProhibitTimer {
      type int32 {
        range "0 | 5 | 10 | 20 | 50 | 100 | 200 | 300 | 600 | 900 | 1200 | 3000 | 6000";
      }
      default "20";
      units "s";
      description "Default value: 20.";
    }
    leaf-list prefUeGroupList {
      type eytypes:int32_range_1-255;
      ordered-by user;
    }
    leaf releasePrefConfig {
      type boolean;
      default "false";
      description "Default value: false.";
    }
    leaf releasePrefOverride {
      type enumeration {
        enum IDLE;
        enum INACTIVE;
        enum NO_PREFERENCE;
      }
    }
    leaf releasePrefProhibitTimer {
      type enumeration {
        enum S0;
        enum S0DOT5;
        enum S1;
        enum S2;
        enum S3;
        enum S4;
        enum S5;
        enum S6;
        enum S7;
        enum S8;
        enum S9;
        enum S10;
        enum S20;
        enum S30;
        enum INFINITY;
      }
    }
    leaf uaiProfileUeCfgId {
      type ietfinet:ip-address;
      mandatory true;
    }
    leaf-list ueConfGroupList {
      type eytypes:int32_range_1-255;
      ordered-by user;
    }
    leaf-list ueGroupList {
      type eytypes:int32_range_1-255;
      ordered-by user;
    }
    leaf userLabel {
      type string;
    }
  }
  grouping UcmCellProfile-attributes {
    leaf-list reservedBy {
      type string;
    }
    leaf ucmCellProfileId {
      type string;
      mandatory true;
    }
    leaf ucmCellTargetIntensity {
      type eytypes:int32_range_1-100-4;
      default "10";
      description "range 1..100; Default value: 10.";
    }
    leaf ucmEnabled {
      type boolean;
      default "false";
      description "Default value: false.";
    }
    leaf ucmSelectionProbability {
      type eytypes:int32_range_1-100;
      default "100";
      units "percent";
      description "range 1..100; Default value: 100.";
    }
    leaf ueConfGroupType {
      type enumeration {
        enum UE_MOBILITY_GROUP;
        enum UE_SERVICE_GROUP;
        enum UE_ADMISSION_GROUP;
      }
    }
    leaf userLabel {
      type string;
    }
  }
  grouping UcmCellProfileUeCfg-attributes {
    leaf-list prefUeGroupList {
      type eytypes:int32_range_1-255;
      ordered-by user;
    }
    leaf ucmCellProfileUeCfgId {
      type string;
      mandatory true;
    }
    leaf ucmMaxFreqLayerToMeas {
      type eytypes:int32_range_0-16;
      default "7";
      description "range 0..16; Default value: 7.";
    }
    leaf-list ueConfGroupList {
      type eytypes:int32_range_1-255;
      ordered-by user;
    }
    leaf-list ueGroupList {
      type eytypes:int32_range_1-255;
      ordered-by user;
    }
    leaf userLabel {
      type string;
    }
  }
  grouping UcmEUtranFreqRelProfile-attributes {
    list reportConfigPeriodicalEutran {
      key "id";
      leaf id {
        type uint32;
        description "Synthetic key for struct entry.";
      }
      container attributes {
      leaf maxReportCells {
        type ietfinet:port-number;
        default "8";
        description "range 1..8; Default value: 8.";
      }
      leaf reportAmount {
        type ietfinet:port-number;
      }
      leaf reportInterval {
        type ietfinet:port-number;
      }
      leaf reportQuantity {
        type ietfinet:port-number;
      }
      }
    }
    leaf-list reservedBy {
      type string;
    }
    leaf ucmEUtranFreqRelProfileId {
      type string;
      mandatory true;
    }
    leaf ucmTargetFactor {
      type int32 {
        range "0..36";
      }
      default "1";
      description "range 0..36; Default value: 1.";
    }
  }
  grouping UcmNrFreqRelProfile-attributes {
    list reportConfigPeriodical {
      key "id";
      leaf id {
        type uint32;
        description "Synthetic key for struct entry.";
      }
      container attributes {
      leaf includeBeamMeas {
        type boolean;
        default "false";
        description "Default value: false.";
      }
      leaf maxNoOfRsIndexesToReport {
        type ietfinet:port-number;
        default "1";
        description "range 0..32; Default value: 1.";
      }
      leaf maxReportCells {
        type ietfinet:port-number;
        default "8";
        description "range 1..8; Default value: 8.";
      }
      leaf reportAddNeighMeas {
        type ietfinet:port-number;
        description "Default value: true.";
      }
      leaf reportAmount {
        type ietfinet:port-number;
      }
      leaf reportInterval {
        type ietfinet:port-number;
      }
      leaf reportQuantityCell {
        type ietfinet:port-number;
      }
      leaf reportQuantityRsIndex {
        type ietfinet:port-number;
      }
      }
    }
    leaf-list reservedBy {
      type string;
    }
    leaf ucmNrFreqRelProfileId {
      type string;
      mandatory true;
    }
    leaf ucmTargetFactor {
      type int32 {
        range "0..36";
      }
      default "1";
      description "range 0..36; Default value: 1.";
    }
  }
  grouping UeAdmissionGroupDefinition-attributes {
    leaf chipsetRef {
      type ietfinet:ip-address;
    }
    leaf imeiSvRef {
      type string;
    }
    leaf selectionCriteria {
      type string {
        length "1..1000";
      }
      description "length 1..1000.";
    }
    leaf ueAdmissionGroupDefinitionId {
      type string;
      mandatory true;
    }
    leaf ueAdmissionGroupId {
      type eytypes:int32_range_1-255;
      mandatory true;
      description "range 1..255.";
    }
    leaf ueAdmissionGroupPriority {
      type eytypes:int32_range_1-65535;
      mandatory true;
      description "range 1..65535.";
    }
    leaf userLabel {
      type string;
    }
  }
  grouping UeCC-attributes {
    leaf ueCCId {
      type string;
      mandatory true;
    }
  }
  grouping UeCovMeas-attributes {
    leaf ueCovMeasId {
      type string;
      mandatory true;
    }
    leaf userLabel {
      type string;
    }
  }
  grouping UeGroupSelection-attributes {
    leaf ueGroupSelectionId {
      type string;
      mandatory true;
    }
    leaf validityTimeEmergencyCause {
      type int32 {
        range "1..36000";
      }
      default "6";
      units "s";
      description "range 1..36000; Default value: 6.";
    }
    leaf validityTimeHighPrioAccCause {
      type eytypes:int32_range_1-15;
      default "6";
      units "s";
      description "range 1..15; Default value: 6.";
    }
    leaf validityTimeMcsPrioAccCause {
      type eytypes:int32_range_1-15;
      default "6";
      units "s";
      description "range 1..15; Default value: 6.";
    }
    leaf validityTimeMoDataCause {
      type eytypes:int32_range_1-15;
      default "6";
      units "s";
      description "range 1..15; Default value: 6.";
    }
    leaf validityTimeMoSignallingCause {
      type eytypes:int32_range_1-15;
      default "6";
      units "s";
      description "range 1..15; Default value: 6.";
    }
    leaf validityTimeMoSmsCause {
      type eytypes:int32_range_1-15;
      default "6";
      units "s";
      description "range 1..15; Default value: 6.";
    }
    leaf validityTimeMoVideoCallCause {
      type eytypes:int32_range_1-15;
      default "6";
      units "s";
      description "range 1..15; Default value: 6.";
    }
    leaf validityTimeMoVoiceCallCause {
      type eytypes:int32_range_1-15;
      default "6";
      units "s";
      description "range 1..15; Default value: 6.";
    }
    leaf validityTimeMpsPrioAccCause {
      type eytypes:int32_range_1-15;
      default "6";
      units "s";
      description "range 1..15; Default value: 6.";
    }
    leaf validityTimeMtAccessCause {
      type eytypes:int32_range_1-15;
      default "6";
      units "s";
      description "range 1..15; Default value: 6.";
    }
    leaf validityTimePagingPrio {
      type eytypes:int32_range_1-15;
      default "6";
      units "s";
      description "range 1..15; Default value: 6.";
    }
  }
  grouping UeGroupSelectionProfile-attributes {
    leaf chipsetRef {
      type ietfinet:ip-address;
    }
    leaf imeiSvRef {
      type string;
    }
    leaf selectionCriteria {
      type string {
        length "1..1000";
      }
      description "length 1..1000.";
    }
    leaf selectionProbability {
      type eytypes:int32_range_0-100;
      default "100";
      units "percent";
      description "range 0..100; Default value: 100.";
    }
    leaf ueGroupId {
      type eytypes:int32_range_1-255;
      mandatory true;
      description "range 1..255.";
    }
    leaf ueGroupPriority {
      type eytypes:int32_range_1-65535;
      mandatory true;
      description "range 1..65535.";
    }
    leaf ueGroupSelectionProfileId {
      type string;
      mandatory true;
    }
    leaf userLabel {
      type string;
    }
  }
  grouping UeMC-attributes {
    leaf ueConfGroupType {
      type enumeration {
        enum UE_MOBILITY_GROUP;
        enum UE_SERVICE_GROUP;
        enum UE_ADMISSION_GROUP;
      }
    }
    leaf ueMCId {
      type string;
      mandatory true;
    }
    leaf userLabel {
      type string;
    }
  }
  grouping UeMCCellProfile-attributes {
    leaf connModeUeAllowedToBarredCell {
      type boolean;
      status deprecated;
      default "true";
      description "Default value: true; Status info: Since 25.Q3. Replaced by connModeUeAllowedToBarredCellType. Planned to be removed..";
    }
    leaf connModeUeAllowedToBarredCellType {
      type enumeration {
        enum ALL;
        enum SPCELL_ONLY;
        enum SCELL_ONLY;
        enum NONE;
      }
    }
    leaf filterCoefficientEUtraRsrp {
      type int32 {
        range "0..9 | 11 | 13 | 15 | 17 | 19";
      }
      default "4";
      description "Default value: 4.";
    }
    leaf filterCoefficientEUtraRsrq {
      type int32 {
        range "0..9 | 11 | 13 | 15 | 17 | 19";
      }
      default "11";
      description "Default value: 11.";
    }
    leaf filterCoefficientEUtraSinr {
      type int32 {
        range "0..9 | 11 | 13 | 15 | 17 | 19";
      }
      default "4";
      description "Default value: 4.";
    }
    leaf filterCoefficientNrRsrpHigh {
      type int32 {
        range "0..9 | 11 | 13 | 15 | 17 | 19";
      }
      default "4";
      description "Default value: 4.";
    }
    leaf filterCoefficientNrRsrpLow {
      type int32 {
        range "0..9 | 11 | 13 | 15 | 17 | 19";
      }
      default "4";
      description "Default value: 4.";
    }
    leaf filterCoefficientNrRsrqHigh {
      type int32 {
        range "0..9 | 11 | 13 | 15 | 17 | 19";
      }
      default "11";
      description "Default value: 11.";
    }
    leaf filterCoefficientNrRsrqLow {
      type int32 {
        range "0..9 | 11 | 13 | 15 | 17 | 19";
      }
      default "11";
      description "Default value: 11.";
    }
    leaf filterCoefficientNrSinrHigh {
      type int32 {
        range "0..9 | 11 | 13 | 15 | 17 | 19";
      }
      default "4";
      description "Default value: 4.";
    }
    leaf filterCoefficientNrSinrLow {
      type int32 {
        range "0..9 | 11 | 13 | 15 | 17 | 19";
      }
      default "4";
      description "Default value: 4.";
    }
    leaf freqClassificationThreshold {
      type int32 {
        range "0..3279164";
      }
      default "3279163";
      description "range 0..3279164; Default value: 3279163.";
    }
    leaf noOfInvIntraFreqTrigPCSearch {
      type eytypes:int32_range_1-3;
      default "1";
      description "range 1..3; Default value: 1.";
    }
    leaf prohibitCellTrigMob {
      type enumeration {
        enum DISABLED;
        enum ENABLED_EUTRAN_ONLY;
        enum ENABLED_ALL;
      }
    }
    leaf-list reservedBy {
      type string;
    }
    leaf sMeasure {
      type int32 {
        range "-156..-29 | 1000";
      }
      default "-29";
      units "dBm";
      description "Default value: -29.";
    }
    leaf ueConfGroupType {
      type enumeration {
        enum UE_MOBILITY_GROUP;
        enum UE_SERVICE_GROUP;
        enum UE_ADMISSION_GROUP;
      }
    }
    leaf ueMCCellProfileId {
      type string;
      mandatory true;
    }
    leaf userLabel {
      type string;
    }
  }
  grouping UeMCCellProfileUeCfg-attributes {
    leaf checkUlQualityIncomingHo {
      type boolean;
      default "false";
      description "Default value: false.";
    }
    leaf connModeUeAllowedToResCell {
      type boolean;
      default "true";
      description "Default value: true.";
    }
    leaf-list prefUeGroupList {
      type eytypes:int32_range_1-255;
      ordered-by user;
    }
    leaf-list ueConfGroupList {
      type eytypes:int32_range_1-255;
      ordered-by user;
    }
    leaf-list ueGroupList {
      type eytypes:int32_range_1-255;
      ordered-by user;
    }
    leaf ueMCCellProfileUeCfgId {
      type string;
      mandatory true;
    }
    leaf ulQualityThreshIncomingHo {
      type eytypes:int32_range_-150-500;
      default "70";
      units "dB";
      description "range -150..500; Default value: 70.";
    }
  }
  grouping UeMCEUtranFreqRelProfile-attributes {
    leaf blindRwrAllowed {
      type boolean;
    }
    leaf connModeAllowedPCell {
      type boolean;
    }
    leaf connModePrioPCell {
      type eytypes:int32_range_0-7;
      description "range 0..7.";
    }
    leaf-list reservedBy {
      type string;
    }
    leaf ueConfGroupType {
      type enumeration {
        enum UE_MOBILITY_GROUP;
        enum UE_SERVICE_GROUP;
        enum UE_ADMISSION_GROUP;
      }
    }
    leaf ueMCEUtranFreqRelProfileId {
      type string;
      mandatory true;
    }
    leaf userLabel {
      type string;
    }
  }
  grouping UeMCEUtranFreqRelProfileUeCfg-attributes {
    leaf blindRwrAllowed {
      type boolean;
      default "false";
      description "Default value: false.";
    }
    leaf connModeAllowedPCell {
      type boolean;
      default "false";
      description "Default value: false.";
    }
    leaf connModePrioPCell {
      type eytypes:int32_range_0-7;
      default "7";
      description "range 0..7; Default value: 7.";
    }
    leaf-list prefUeGroupList {
      type eytypes:int32_range_1-255;
      ordered-by user;
    }
    leaf-list ueConfGroupList {
      type eytypes:int32_range_1-255;
      ordered-by user;
    }
    leaf-list ueGroupList {
      type eytypes:int32_range_1-255;
      ordered-by user;
    }
    leaf ueMCEUtranFreqRelProfileUeCfgId {
      type string;
      mandatory true;
    }
    leaf userLabel {
      type string;
    }
  }
  grouping UeMCNrFreqRelProfile-attributes {
    leaf connModeAllowedPCell {
      type boolean;
    }
    leaf connModePrioPCell {
      type eytypes:int32_range_0-7;
      description "range 0..7.";
    }
    leaf-list reservedBy {
      type string;
    }
    leaf ueConfGroupType {
      type enumeration {
        enum UE_MOBILITY_GROUP;
        enum UE_SERVICE_GROUP;
        enum UE_ADMISSION_GROUP;
      }
    }
    leaf ueMCNrFreqRelProfileId {
      type string;
      mandatory true;
    }
    leaf userLabel {
      type string;
    }
  }
  grouping UeMCNrFreqRelProfileUeCfg-attributes {
    leaf connModeAllowedPCell {
      type boolean;
      default "false";
      description "Default value: false.";
    }
    leaf connModeAllowedPSCell {
      type boolean;
      default "false";
      description "Default value: false.";
    }
    leaf connModePrioPCell {
      type eytypes:int32_range_0-7;
      default "7";
      description "range 0..7; Default value: 7.";
    }
    leaf connModePrioPSCell {
      type eytypes:int32_range_0-7;
      default "7";
      description "range 0..7; Default value: 7.";
    }
    leaf-list prefUeGroupList {
      type eytypes:int32_range_1-255;
      ordered-by user;
    }
    leaf-list ueConfGroupList {
      type eytypes:int32_range_1-255;
      ordered-by user;
    }
    leaf-list ueGroupList {
      type eytypes:int32_range_1-255;
      ordered-by user;
    }
    leaf ueMCNrFreqRelProfileUeCfgId {
      type string;
      mandatory true;
    }
    leaf userLabel {
      type string;
    }
  }
  grouping UeMCUeCfg-attributes {
    leaf maxNrInterFreqMeasEndc {
      type eytypes:int32_range_10-32;
      default "10";
      description "range 10..32; Default value: 10.";
    }
    leaf maxNrInterFreqMeasSa {
      type eytypes:int32_range_10-32;
      default "10";
      description "range 10..32; Default value: 10.";
    }
    leaf maxNrIratMeasSa {
      type eytypes:int32_range_10-32;
      default "10";
      description "range 10..32; Default value: 10.";
    }
    leaf-list prefUeGroupList {
      type eytypes:int32_range_1-255;
      ordered-by user;
    }
    leaf-list ueConfGroupList {
      type eytypes:int32_range_1-255;
      ordered-by user;
    }
    leaf-list ueGroupList {
      type eytypes:int32_range_1-255;
      ordered-by user;
    }
    leaf ueMCUeCfgId {
      type string;
      mandatory true;
    }
    leaf userLabel {
      type string;
    }
  }
  grouping UeMobilityGroupDefinition-attributes {
    leaf chipsetRef {
      type ietfinet:ip-address;
    }
    leaf imeiSvRef {
      type string;
    }
    leaf selectionCriteria {
      type string {
        length "1..1000";
      }
      description "length 1..1000.";
    }
    leaf ueMobilityGroupDefinitionId {
      type string;
      mandatory true;
    }
    leaf ueMobilityGroupId {
      type eytypes:int32_range_1-255;
      mandatory true;
      description "range 1..255.";
    }
    leaf ueMobilityGroupPriority {
      type eytypes:int32_range_1-65535;
      mandatory true;
      description "range 1..65535.";
    }
    leaf userLabel {
      type string;
    }
  }
  grouping UeNoDrb-attributes {
    leaf ueNoDrbId {
      type string;
      mandatory true;
    }
  }
  grouping UeNoDrbPCellProfile-attributes {
    leaf-list reservedBy {
      type string;
    }
    leaf ueConfGroupType {
      type enumeration {
        enum UE_MOBILITY_GROUP;
        enum UE_SERVICE_GROUP;
        enum UE_ADMISSION_GROUP;
      }
    }
    leaf ueNoDrbPCellProfileId {
      type string;
      mandatory true;
    }
    leaf userLabel {
      type string;
    }
  }
  grouping UeNoDrbPCellProfileUeCfg-attributes {
    leaf posUeWoPduSessionEnabled {
      type boolean;
      default "false";
      description "Default value: false.";
    }
    leaf-list prefUeGroupList {
      type eytypes:int32_range_1-255;
      ordered-by user;
    }
    list rsrpBetterPCell {
      key "id";
      leaf id {
        type uint32;
        description "Synthetic key for struct entry.";
      }
      container attributes {
      leaf hysteresis {
        type eytypes:int32_range_0-150;
        default "10";
        units "dB";
        description "range 0..150; Default value: 10.";
      }
      leaf offset {
        type eytypes:int32_range_-150-150;
        default "30";
        units "dB";
        description "range -150..150; Default value: 30.";
      }
      leaf timeToTrigger {
        type int32;
        default "640";
        units "ms";
        description "Default value: 640.";
      }
      }
    }
    leaf rsrpBetterPCellEnabled {
      type boolean;
      default "false";
      description "Default value: false.";
    }
    list rsrpCritical {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-156--29;
        default "-156";
        units "dBm";
        description "range -156..-29; Default value: -156.";
      }
      leaf timeToTrigger {
        type int32;
        default "160";
        units "ms";
        description "Default value: 160.";
      }
      }
    }
    leaf rsrpCriticalEnabled {
      type boolean;
      default "false";
      description "Default value: false.";
    }
    list rsrpCriticalPcOffset {
      key "id";
      leaf id {
        type uint32;
        description "Synthetic key for struct sequence entry.";
      }
      ordered-by user;
      container attributes {
      leaf powerClass {
        type enumeration {
          enum PC_1;
          enum PC_1_5;
          enum PC_2;
        }
      }
      leaf thresholdOffset {
        type eytypes:int32_range_-100-100;
        default "0";
        units "dB";
        description "range -100..100; Default value: 0.";
      }
      }
    }
    list rsrqCritical {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-435-200;
        default "-435";
        units "dB";
        description "range -435..200; Default value: -435.";
      }
      leaf timeToTrigger {
        type int32;
        default "160";
        units "ms";
        description "Default value: 160.";
      }
      }
    }
    leaf rsrqCriticalEnabled {
      type boolean;
      default "false";
      description "Default value: false.";
    }
    list sinrCritical {
      key "id";
      leaf id {
        type uint32;
        description "Synthetic key for struct entry.";
      }
      container attributes {
      leaf hysteresis {
        type eytypes:int32_range_0-150;
        default "10";
        units "dB";
        description "range 0..150; Default value: 10.";
      }
      leaf threshold {
        type eytypes:int32_range_-230-405;
        default "-230";
        units "dB";
        description "range -230..405; Default value: -230.";
      }
      leaf timeToTrigger {
        type int32;
        default "160";
        units "ms";
        description "Default value: 160.";
      }
      }
    }
    leaf sinrCriticalEnabled {
      type boolean;
      default "false";
      description "Default value: false.";
    }
    leaf-list ueConfGroupList {
      type eytypes:int32_range_1-255;
      ordered-by user;
    }
    leaf-list ueGroupList {
      type eytypes:int32_range_1-255;
      ordered-by user;
    }
    leaf ueNoDrbPCellProfileUeCfgId {
      type string;
      mandatory true;
    }
    leaf userLabel {
      type string;
    }
  }
  grouping UeServiceGroupDefinition-attributes {
    leaf chipsetRef {
      type ietfinet:ip-address;
    }
    leaf imeiSvRef {
      type string;
    }
    leaf selectionCriteria {
      type string {
        length "1..1000";
      }
      description "length 1..1000.";
    }
    leaf ueServiceGroupDefinitionId {
      type string;
      mandatory true;
    }
    leaf ueServiceGroupId {
      type eytypes:int32_range_1-255;
      mandatory true;
      description "range 1..255.";
    }
    leaf ueServiceGroupPriority {
      type eytypes:int32_range_1-65535;
      mandatory true;
      description "range 1..65535.";
    }
    leaf userLabel {
      type string;
    }
  }
  grouping UeUlResMon-attributes {
    leaf ueUlResMonId {
      type string;
      mandatory true;
    }
  }
  grouping UlBufferMonCfg-attributes {
    leaf-list reservedBy {
      type string;
    }
    leaf ulBsVolThresh {
      type int32 {
        range "0 | 10..20 | 22..23 | 25..26 | 28 | 30 | 32 | 34 | 36 | 38 | 40 | 43 | 46 | 49 | 52 | 55 | 59 | 62 | 66 | 71 | 75 | 80 | 85 | 91 | 97 | 103 | 110 | 117 | 124 | 132 | 141 | 150 | 160 | 170 | 181 | 193 | 205 | 218 | 233 | 248 | 264 | 281 | 299 | 318 | 339 | 361 | 384 | 409 | 436 | 464 | 494 | 526 | 560 | 597 | 635 | 677 | 720 | 767 | 817 | 870 | 926 | 987 | 1051 | 1119 | 1191 | 1269 | 1351 | 1439 | 1532 | 1631 | 1737 | 1850 | 1970 | 2098 | 2234 | 2379 | 2533 | 2698 | 2873 | 3059 | 3258 | 3469 | 3694 | 3934 | 4189 | 4461 | 4751 | 5059 | 5387 | 5737 | 6109 | 6506 | 6928 | 7378 | 7857 | 8367 | 8910 | 9488 | 10104 | 10760 | 11458 | 12202 | 12994 | 13838 | 14736 | 15692 | 16711 | 17795 | 18951 | 20181 | 21491 | 22885 | 24371 | 25953 | 27638 | 29431 | 31342 | 33376 | 35543 | 37850 | 40307 | 42923 | 45709 | 48676 | 51836 | 55200 | 58784 | 62599 | 66663 | 70990 | 75598 | 80505 | 85730 | 91295 | 97221 | 103532 | 110252 | 117409 | 125030 | 133146 | 141789 | 150992 | 160793 | 171231 | 182345 | 194182 | 206786 | 220209 | 234503 | 249725 | 265935 | 283197 | 301579 | 321155 | 342002 | 364202 | 387842 | 413018 | 439827 | 468377 | 498780 | 531156 | 565634 | 602350 | 641449 | 683087 | 727427 | 774645 | 824928 | 878475 | 935498 | 996222 | 1060888 | 1129752 | 1203085 | 1281179 | 1364342 | 1452903 | 1547213 | 1647644 | 1754595 | 1868488 | 1989774 | 2118933 | 2256475 | 2402946 | 2558924 | 2725027 | 2901912 | 3090279 | 3290873 | 3504487 | 3731968 | 3974215 | 4232186 | 4506902 | 4799451 | 5110989 | 5442750 | 5796046 | 6172275 | 6572925 | 6999582 | 7453933 | 7937777 | 8453028 | 9001725 | 9586039 | 10208280 | 10870913 | 11576557 | 12328006 | 13128233 | 13980403 | 14887889 | 15854280 | 16883401 | 17979324 | 19146385 | 20389201 | 21712690 | 23122088 | 24622972 | 26221280 | 27923336 | 29735875 | 31666069 | 33721553 | 35910462 | 38241455 | 40723756 | 43367187 | 46182206 | 49179951 | 52372284 | 55771835 | 59392055 | 63247269 | 67352729 | 71724679 | 76380419 | 81338368";
      }
      default "0";
      units "byte";
      description "Default value: 0.";
    }
    leaf ulBufferMonCfgId {
      type string;
      mandatory true;
    }
  }
  grouping UlDataSplit-attributes {
    leaf-list reservedBy {
      type string;
    }
    leaf ueConfGroupType {
      type enumeration {
        enum UE_MOBILITY_GROUP;
        enum UE_SERVICE_GROUP;
        enum UE_ADMISSION_GROUP;
      }
    }
    leaf ulDataSplitId {
      type string;
      mandatory true;
    }
    leaf userLabel {
      type string;
    }
  }
  grouping UlDataSplitUeCfg-attributes {
    leaf initialUlPrimaryPathMode {
      type enumeration {
        enum MCG;
        enum COVERAGE_BASED;
        enum SCG;
      }
    }
    leaf-list prefUeGroupList {
      type eytypes:int32_range_1-255;
      ordered-by user;
    }
    leaf-list ueConfGroupList {
      type eytypes:int32_range_1-255;
      ordered-by user;
    }
    leaf-list ueGroupList {
      type eytypes:int32_range_1-255;
      ordered-by user;
    }
    leaf ulDataSplitThreshMcg {
      type int32 {
        range "-1..0 | 100 | 200 | 400 | 800 | 1600 | 3200 | 6400 | 12800 | 25600 | 51200 | 102400 | 204800 | 409600 | 819200 | 1228800 | 1638400 | 2457600 | 3276800 | 4096000 | 4915200 | 5734400 | 6553600";
      }
      units "Byte";
    }
    leaf ulDataSplitThreshScg {
      type int32 {
        range "-1..0 | 100 | 200 | 400 | 800 | 1600 | 3200 | 6400 | 12800 | 25600 | 51200 | 102400 | 204800 | 409600 | 819200 | 1228800 | 1638400 | 2457600 | 3276800 | 4096000 | 4915200 | 5734400 | 6553600";
      }
      default "51200";
      units "Byte";
      description "Default value: 51200.";
    }
    leaf ulDataSplitThreshScgLow {
      type int32 {
        range "-1..0 | 100 | 200 | 400 | 800 | 1600 | 3200 | 6400 | 12800 | 25600 | 51200 | 102400 | 204800 | 409600 | 819200 | 1228800 | 1638400 | 2457600 | 3276800 | 4096000 | 4915200 | 5734400 | 6553600";
      }
      default "3200";
      units "Byte";
      description "Default value: 3200.";
    }
    leaf ulDataSplitUeCfgId {
      type string;
      mandatory true;
    }
    leaf userLabel {
      type string;
    }
  }
  grouping UlQualMcpcMeasCfg-attributes {
    leaf-list reservedBy {
      type string;
    }
    list ulQualCritical {
      key "id";
      leaf id {
        type uint32;
        description "Synthetic key for struct entry.";
      }
      container attributes {
      leaf hysteresis {
        type eytypes:int32_range_0-150;
        default "0";
        units "dB";
        description "range 0..150; Default value: 0.";
      }
      leaf threshold {
        type eytypes:int32_range_-150-500;
        default "-50";
        units "dB";
        description "range -150..500; Default value: -50.";
      }
      leaf timeToTrigger {
        type int32;
        default "160";
        units "ms";
        description "Default value: 160.";
      }
      }
    }
    leaf ulQualMcpcMeasCfgId {
      type string;
      mandatory true;
    }
    list ulQualSearchZone {
      key "id";
      leaf id {
        type uint32;
        description "Synthetic key for struct entry.";
      }
      container attributes {
      leaf hysteresis {
        type eytypes:int32_range_0-150;
        default "40";
        units "dB";
        description "range 0..150; Default value: 40.";
      }
      leaf threshold {
        type eytypes:int32_range_-150-500;
        default "70";
        units "dB";
        description "range -150..500; Default value: 70.";
      }
      leaf timeToTrigger {
        type int32;
        default "160";
        units "ms";
        description "Default value: 160.";
      }
      leaf timeToTriggerA1 {
        type int32;
        default "-1";
        units "ms";
        description "Default value: -1.";
      }
      }
    }
    leaf userLabel {
      type string;
    }
  }
}
