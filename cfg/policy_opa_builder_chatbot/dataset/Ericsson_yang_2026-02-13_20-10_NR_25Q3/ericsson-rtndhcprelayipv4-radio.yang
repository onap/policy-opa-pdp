module ericsson-rtndhcprelayipv4-radio {
  yang-version 1.1;
  namespace "urn:com:ericsson:ecim:RtnDhcpRelayIPv4";
  prefix rtndhcpr;
  import ietf-inet-types {
    prefix ietfinet;
  }
  import ericsson-l3-router-rtn-radio {
    prefix l3rtrdo;
  }
  import ericsson-managed-element {
    prefix emael;
  }
  description "Auto-generated from Ericsson ECIM (MOM XML).";
  revision 2026-02-13 {
    description "Initial auto-generated revision. Generated at 2026-02-13 20:11.";
  }

  augment "/emael:ManagedElement/emael:Transport/l3rtrdo:Router" {
    list DhcpRelayIPv4 {
      description "Additional definitions from MOM:min/max-elements:0/unbounded;root; Represents DHCP relay agent, that can relay IPv4 DHCP messages between DHCP clients and DHCP servers.";
      key "dhcpRelayIPv4Id";
      leaf dhcpRelayIPv4Id {
        type leafref {
          path "../attributes/dhcpRelayIPv4Id";
        }
      }
      container attributes {
        uses DhcpRelayIPv4-attributes;
      }
    }
  }
  grouping DhcpRelayIPv4-attributes {
    leaf dhcpRelayIPv4Id {
      type ietfinet:ipv4-address;
      mandatory true;
    }
    leaf-list server {
      type string;
      min-elements 1;
    }
    leaf-list subnet {
      type string;
      min-elements 1;
    }
    leaf dhcpOutClientMsgsHC {
      type uint64;
      config false;
    }
    leaf dhcpInServerMsgsHC {
      type uint64;
      config false;
    }
    leaf dhcpOutServerMsgsHC {
      type uint64;
      config false;
    }
    leaf dhcpInServerErrorsHC {
      type uint64;
      config false;
    }
    leaf dhcpInClientErrorsHC {
      type uint64;
      config false;
    }
    leaf dhcpInClientMsgsHC {
      type uint64;
      config false;
    }
  }
}
