module ericsson-lrat-radio {
  yang-version 1.1;
  namespace "urn:com:ericsson:ecim:Lrat";
  prefix lrat;
  import ietf-inet-types {
    prefix ietfinet;
  }
  import ietf-yang-types {
    prefix ietfyang;
  }
  import ericsson-managed-element {
    prefix emael;
  }
  import ericsson-yang-types {
    prefix eytypes;
  }
  description "Auto-generated from Ericsson ECIM (MOM XML).";
  revision 2026-02-13 {
    description "Initial auto-generated revision. Generated at 2026-02-13 20:11.";
  }

  augment "/emael:ManagedElement" {
    list ENodeBFunction {
      description "Additional definitions from MOM:min/max-elements:0/1;root; The RDN of this MO is ENodeBFunction=1. Precondition: If TheftDeterrence::thdStatus is LOCKED or LOCKED_PERMANENTLY, instance of this MO class can only be created if eNodeBPlmnId is part of Lock Token or Operator List.";
      key "eNodeBFunctionId";
      leaf eNodeBFunctionId {
        type leafref {
          path "../attributes/eNodeBFunctionId";
        }
      }
      container attributes {
        uses ENodeBFunction-attributes;
      }
    }
  }

  augment "/emael:ManagedElement/ENodeBFunction/AdmissionControl" {
    list DiffAdmCtrlFilteringProfile {
      description "Additional definitions from MOM:min/max-elements:0/6; Filtering profile for additional level of Differentiated Admission Control. Attributes take effect only when AdmissionControl::diffAdmCtrlFilteringEnabled is true.";
      key "diffAdmCtrlFilteringProfileId";
      leaf diffAdmCtrlFilteringProfileId {
        type leafref {
          path "../attributes/diffAdmCtrlFilteringProfileId";
        }
      }
      container attributes {
        uses DiffAdmCtrlFilteringProfile-attributes;
      }
    }
  }

  augment "/emael:ManagedElement/ENodeBFunction/AnrFunction" {
    list AnrFunctionEUtran {
      description "Additional definitions from MOM:min/max-elements:1/1;systemCreated; Parameters and constraints for LTE ANR functions. The RDN of this MO is AnrFunctionEUtran=1.";
      key "anrFunctionEUtranId";
      leaf anrFunctionEUtranId {
        type leafref {
          path "../attributes/anrFunctionEUtranId";
        }
      }
      container attributes {
        uses AnrFunctionEUtran-attributes;
      }
    }
  }

  augment "/emael:ManagedElement/ENodeBFunction/AnrFunction" {
    list AnrFunctionUtran {
      description "Additional definitions from MOM:min/max-elements:1/1;systemCreated; Parameters and constraints for the UTRAN ANR functions. The RDN of this MO is AnrFunctionUtran=1.";
      key "anrFunctionUtranId";
      leaf anrFunctionUtranId {
        type leafref {
          path "../attributes/anrFunctionUtranId";
        }
      }
      container attributes {
        uses AnrFunctionUtran-attributes;
      }
    }
  }

  augment "/emael:ManagedElement/ENodeBFunction/AnrFunction" {
    list AnrFunctionGeran {
      description "Additional definitions from MOM:min/max-elements:1/1;systemCreated; Parameters and constraints for GERAN ANR functions. The RDN of this MO is AnrFunctionGeran=1.";
      key "anrFunctionGeranId";
      leaf anrFunctionGeranId {
        type leafref {
          path "../attributes/anrFunctionGeranId";
        }
      }
      container attributes {
        uses AnrFunctionGeran-attributes;
      }
    }
  }

  augment "/emael:ManagedElement/ENodeBFunction/AnrFunction" {
    list AnrFunctionNR {
      description "Additional definitions from MOM:min/max-elements:1/1;systemCreated; Parameters and constraints for NR Automated Neighbor Relation (ANR) functions. The RDN of this MO is AnrFunctionNR=1.";
      key "anrFunctionNRId";
      leaf anrFunctionNRId {
        type leafref {
          path "../attributes/anrFunctionNRId";
        }
      }
      container attributes {
        uses AnrFunctionNR-attributes;
      }
    }
  }

  augment "/emael:ManagedElement/ENodeBFunction/CarrierAggregationFunction/BandCombCompression" {
    list DiffFallback {
      description "Additional definitions from MOM:min/max-elements:0/1; List of CA band combinations requested in UE Capability Enquiry for reporting fallback band combinations. UE must report included band combinations with fallback combinations, which are supported with different capabilities. Contents are used only if BandCombCompression::requestedBandCombCompression is set to R14_DIFF_FALLBACK. If at least one BandCombination with at least one BandIndication exists, requestReducedFormat-r13 IE is sent regardless of BandCombCompression::requestReducedFormat configuration.";
      key "diffFallbackId";
      leaf diffFallbackId {
        type leafref {
          path "../attributes/diffFallbackId";
        }
      }
      container attributes {
        uses DiffFallback-attributes;
      }
    }
  }

  augment "/emael:ManagedElement/ENodeBFunction/CarrierAggregationFunction/BandCombCompression/DiffFallback/BandCombination" {
    list BandIndication {
      description "Additional definitions from MOM:min/max-elements:0/10; Structure indicating bandEUtra and bandwidthClass in downlink and optionally in uplink.";
      key "bandIndicationId";
      leaf bandIndicationId {
        type leafref {
          path "../attributes/bandIndicationId";
        }
      }
      container attributes {
        uses BandIndication-attributes;
      }
    }
  }

  augment "/emael:ManagedElement/ENodeBFunction/CarrierAggregationFunction" {
    list BandCombCompression {
      description "Additional definitions from MOM:min/max-elements:1/1;systemCreated; Compression of CA combinations. Attributes take effect only if license for Carrier Aggregation is present and the feature is active. The RDN of this MO is BandCombCompression=1.";
      key "bandCombCompressionId";
      leaf bandCombCompressionId {
        type leafref {
          path "../attributes/bandCombCompressionId";
        }
      }
      container attributes {
        uses BandCombCompression-attributes;
      }
    }
  }

  augment "/emael:ManagedElement/ENodeBFunction/CarrierAggregationFunction" {
    list AutoSCellMgmFunction {
      description "Additional definitions from MOM:min/max-elements:1/1;systemCreated; Parameters and constraints for Automatic SCell Management feature. The RDN of this MO is AutoSCellMgmFunction=1.";
      key "autoSCellMgmFunctionId";
      leaf autoSCellMgmFunctionId {
        type leafref {
          path "../attributes/autoSCellMgmFunctionId";
        }
      }
      container attributes {
        uses AutoSCellMgmFunction-attributes;
      }
    }
  }

  augment "/emael:ManagedElement/ENodeBFunction/EUtranCellFDD/Cdma20001xRttBandRelation" {
    list Cdma20001xRttFreqRelation {
      description "Additional definitions from MOM:min/max-elements:0/64; The MO represents a mobility relation between an EUtranCellFDD or an EUtranCellTDD and a Cdma20001xRTTFreq. It contains parameters that are specific for this relation.";
      key "cdma20001xRttFreqRelationId";
      leaf cdma20001xRttFreqRelationId {
        type leafref {
          path "../attributes/cdma20001xRttFreqRelationId";
        }
      }
      container attributes {
        uses Cdma20001xRttFreqRelation-attributes;
      }
    }
  }

  augment "/emael:ManagedElement/ENodeBFunction/EUtranCellFDD/Cdma20001xRttBandRelation/Cdma20001xRttFreqRelation" {
    list Cdma20001xRttCellRelation {
      description "Additional definitions from MOM:min/max-elements:0/64; The MO represents a mobility relation between an EUtranCellFDD or an EUtranCellTDD and a Cdma20001xRTTCell. It contains parameters that are specific for this relation.";
      key "cdma20001xRttCellRelationId";
      leaf cdma20001xRttCellRelationId {
        type leafref {
          path "../attributes/cdma20001xRttCellRelationId";
        }
      }
      container attributes {
        uses Cdma20001xRttCellRelation-attributes;
      }
    }
  }

  augment "/emael:ManagedElement/ENodeBFunction/Cdma2000Network/Cdma2000FreqBand/Cdma2000Freq" {
    list ExternalCdma2000Cell {
      description "Additional definitions from MOM:min/max-elements:0/392; The MO represents a CDMA2000 HRPD cell.";
      key "externalCdma2000CellId";
      leaf externalCdma2000CellId {
        type leafref {
          path "../attributes/externalCdma2000CellId";
        }
      }
      container attributes {
        uses ExternalCdma2000Cell-attributes;
      }
    }
  }

  augment "/emael:ManagedElement/ENodeBFunction/Cdma2000Network/Cdma2000FreqBand/Cdma2000Freq" {
    list ExternalCdma20001xRttCell {
      description "Additional definitions from MOM:min/max-elements:0/392; The MO represents a CDMA2000 1xRTT cell.";
      key "externalCdma20001xRttCellId";
      leaf externalCdma20001xRttCellId {
        type leafref {
          path "../attributes/externalCdma20001xRttCellId";
        }
      }
      container attributes {
        uses ExternalCdma20001xRttCell-attributes;
      }
    }
  }

  augment "/emael:ManagedElement/ENodeBFunction/Cdma2000Network/Cdma2000FreqBand" {
    list Cdma2000Freq {
      description "Additional definitions from MOM:min/max-elements:0/64; This Managed Object contains information of a specific CDMA2000 frequency within a Bandclass.";
      key "cdma2000FreqId";
      leaf cdma2000FreqId {
        type leafref {
          path "../attributes/cdma2000FreqId";
        }
      }
      container attributes {
        uses Cdma2000Freq-attributes;
      }
    }
  }

  augment "/emael:ManagedElement/ENodeBFunction/EUtranCellFDD/Cdma2000FreqBandRelation" {
    list Cdma2000CellRelation {
      description "Additional definitions from MOM:min/max-elements:0/64; This Managed Object represents a mobility relation between a EUtranCellFDD or an EUtranCellTDD and an Cdma2000Cell. It contains parameters that are specific for this relation.";
      key "cdma2000CellRelationId";
      leaf cdma2000CellRelationId {
        type leafref {
          path "../attributes/cdma2000CellRelationId";
        }
      }
      container attributes {
        uses Cdma2000CellRelation-attributes;
      }
    }
  }

  augment "/emael:ManagedElement/ENodeBFunction/EUtranCellFDD/Cdma2000FreqBandRelation" {
    list Cdma2000FreqRelation {
      description "Additional definitions from MOM:min/max-elements:0/64; This Managed Object represents a mobility relation between a EUtranCellFDD or an EUtranCellTDD and a CDMA2000Frequency. It contains parameters that are specific for this relation. Deleting this MO while the parent EUtranCellFDD/EUtranCellTDD has operationalState set to ENABLED is not recommended as it may affect traffic.";
      key "cdma2000FreqRelationId";
      leaf cdma2000FreqRelationId {
        type leafref {
          path "../attributes/cdma2000FreqRelationId";
        }
      }
      container attributes {
        uses Cdma2000FreqRelation-attributes;
      }
    }
  }

  augment "/emael:ManagedElement/ENodeBFunction/Cdma2000Network" {
    list Cdma2000FreqBand {
      description "Additional definitions from MOM:min/max-elements:0/18; This Managed Object holds information on a CDMA2000 Bandclass.";
      key "cdma2000FreqBandId";
      leaf cdma2000FreqBandId {
        type leafref {
          path "../attributes/cdma2000FreqBandId";
        }
      }
      container attributes {
        uses Cdma2000FreqBand-attributes;
      }
    }
  }

  augment "/emael:ManagedElement/ENodeBFunction/CellResources" {
    list CellResource {
      description "Additional definitions from MOM:min/max-elements:0/24; A combination of attributes which specify which cell resource partition a given UE should be included in.";
      key "cellResourceId";
      status deprecated;
      leaf cellResourceId {
        type leafref {
          path "../attributes/cellResourceId";
        }
        status deprecated;
      }
      container attributes {
        uses CellResource-attributes;
      }
    }
  }

  augment "/emael:ManagedElement/ENodeBFunction/CellSleepNodeFunction" {
    list SleepModeCovProfile {
      description "Additional definitions from MOM:min/max-elements:0/3; Contains E-UTRAN frequency reference and sequential wake-up priority in Cell Sleep Mode feature.";
      key "sleepModeCovProfileId";
      leaf sleepModeCovProfileId {
        type leafref {
          path "../attributes/sleepModeCovProfileId";
        }
      }
      container attributes {
        uses SleepModeCovProfile-attributes;
      }
    }
  }

  augment "/emael:ManagedElement/ENodeBFunction/CtsFunction" {
    list TermPointToCts {
      description "Additional definitions from MOM:min/max-elements:0/1; Models local eNodeB termination point between eNodeB and a Centralized Training System (CTS).";
      key "termPointToCtsId";
      leaf termPointToCtsId {
        type leafref {
          path "../attributes/termPointToCtsId";
        }
      }
      container attributes {
        uses TermPointToCts-attributes;
      }
    }
  }

  augment "/emael:ManagedElement/ENodeBFunction/CarrierAggregationFunction/BandCombCompression/DiffFallback" {
    list BandCombination {
      description "Additional definitions from MOM:min/max-elements:0/100; List of BandIndication structures for specified Carrier Aggregation (CA) band combination.";
      key "bandCombinationId";
      leaf bandCombinationId {
        type leafref {
          path "../attributes/bandCombinationId";
        }
      }
      container attributes {
        uses BandCombination-attributes;
      }
    }
  }

  augment "/emael:ManagedElement/ENodeBFunction" {
    list AnrFunction {
      description "Additional definitions from MOM:min/max-elements:1/1;systemCreated; Contains parameters and constraints for ANR functions, for example, adding or removing neighbor cells. The RDN of this MO is AnrFunction=1.";
      key "anrFunctionId";
      leaf anrFunctionId {
        type leafref {
          path "../attributes/anrFunctionId";
        }
      }
      container attributes {
        uses AnrFunction-attributes;
      }
    }
  }

  augment "/emael:ManagedElement/ENodeBFunction" {
    list PlmnInfo {
      description "Additional definitions from MOM:min/max-elements:0/6; PLMN specific configuration parameters.";
      key "plmnInfoId";
      leaf plmnInfoId {
        type leafref {
          path "../attributes/plmnInfoId";
        }
      }
      container attributes {
        uses PlmnInfo-attributes;
      }
    }
  }

  augment "/emael:ManagedElement/ENodeBFunction" {
    list RadioBearerTable {
      description "Additional definitions from MOM:min/max-elements:1/1;systemCreated; Contains Radio Bearer configurations. The RDN of this MO is RadioBearerTable=default.";
      key "radioBearerTableId";
      leaf radioBearerTableId {
        type leafref {
          path "../attributes/radioBearerTableId";
        }
      }
      container attributes {
        uses RadioBearerTable-attributes;
      }
    }
  }

  augment "/emael:ManagedElement/ENodeBFunction" {
    list QciTable {
      description "Additional definitions from MOM:min/max-elements:1/1;systemCreated; Contains mapping from QCIs to parameters that has impact on QoS for DRBs. The RDN of this MO is QciTable=default.";
      key "qciTableId";
      leaf qciTableId {
        type leafref {
          path "../attributes/qciTableId";
        }
      }
      container attributes {
        uses QciTable-attributes;
      }
    }
  }

  augment "/emael:ManagedElement/ENodeBFunction" {
    list RlfProfile {
      description "Additional definitions from MOM:min/max-elements:23/23;systemCreated; Contains RLF profiles and RLF parameters to map to the different QCIs. The first instance, RlfProfileId 0, is the default RLF profile. The RDNs of these MOs are RlfProfile=0 to RlfProfile=22. The timers and constants settings are provided to the UE by dedicated signaling.";
      key "rlfProfileId";
      leaf rlfProfileId {
        type leafref {
          path "../attributes/rlfProfileId";
        }
      }
      container attributes {
        uses RlfProfile-attributes;
      }
    }
  }

  augment "/emael:ManagedElement/ENodeBFunction" {
    list TimerProfile {
      description "Additional definitions from MOM:min/max-elements:0/22; Contains internal eNodeB timer profiles to be mapped to different QCIs.";
      key "timerProfileId";
      leaf timerProfileId {
        type leafref {
          path "../attributes/timerProfileId";
        }
      }
      container attributes {
        uses TimerProfile-attributes;
      }
    }
  }

  augment "/emael:ManagedElement/ENodeBFunction" {
    list ResourcePartitions {
      description "Additional definitions from MOM:min/max-elements:1/1;systemCreated; Set of resource partitions defined for use in the node. The RDN of this MO is ResourcePartitions=1.";
      key "resourcePartitionsId";
      leaf resourcePartitionsId {
        type leafref {
          path "../attributes/resourcePartitionsId";
        }
      }
      container attributes {
        uses ResourcePartitions-attributes;
      }
    }
  }

  augment "/emael:ManagedElement/ENodeBFunction" {
    list ResourcePartitionGroup {
      description "Additional definitions from MOM:min/max-elements:0/24; Group of resource partitions used together in a cell. All partitions in a group must contain the same empty attribute (plmnList or spidList). Multiple partitions in the same group must not be applicable to the same UE.";
      key "resourcePartitionGroupId";
      leaf resourcePartitionGroupId {
        type leafref {
          path "../attributes/resourcePartitionGroupId";
        }
      }
      container attributes {
        uses ResourcePartitionGroup-attributes;
      }
    }
  }

  augment "/emael:ManagedElement/ENodeBFunction" {
    list FlexibleQoSFunction {
      description "Additional definitions from MOM:min/max-elements:1/1;systemCreated; Contains eNB specific configuration used for feature Flexible QoS. The RDN of this MO is FlexibleQoSFunction=1.";
      key "flexibleQoSFunctionId";
      leaf flexibleQoSFunctionId {
        type leafref {
          path "../attributes/flexibleQoSFunctionId";
        }
      }
      container attributes {
        uses FlexibleQoSFunction-attributes;
      }
    }
  }

  augment "/emael:ManagedElement/ENodeBFunction" {
    list SubscriberGroupProfile {
      description "Additional definitions from MOM:min/max-elements:0/10; Contains set of trigger conditions used to select subset of all subscribers as well as a number of parameters/functions that are applied to this group.";
      key "subscriberGroupProfileId";
      leaf subscriberGroupProfileId {
        type leafref {
          path "../attributes/subscriberGroupProfileId";
        }
      }
      container attributes {
        uses SubscriberGroupProfile-attributes;
      }
    }
  }

  augment "/emael:ManagedElement/ENodeBFunction" {
    list CellResources {
      description "Additional definitions from MOM:min/max-elements:1/1;systemCreated; Set of cell resource partitions defined for use in the node. The RDN of this MO is CellResources=1.";
      key "cellResourcesId";
      status deprecated;
      leaf cellResourcesId {
        type leafref {
          path "../attributes/cellResourcesId";
        }
        status deprecated;
      }
      container attributes {
        uses CellResources-attributes;
      }
    }
  }

  augment "/emael:ManagedElement/ENodeBFunction" {
    list MeasCellGroup {
      description "Additional definitions from MOM:min/max-elements:0/24; Set of measurement group defined for use in the node.";
      key "measCellGroupId";
      leaf measCellGroupId {
        type leafref {
          path "../attributes/measCellGroupId";
        }
      }
      container attributes {
        uses MeasCellGroup-attributes;
      }
    }
  }

  augment "/emael:ManagedElement/ENodeBFunction" {
    list EndcProfile {
      description "Additional definitions from MOM:min/max-elements:0/16; EN-DC profiles and EN-DC parameters that map to different QCIs.";
      key "endcProfileId";
      leaf endcProfileId {
        type leafref {
          path "../attributes/endcProfileId";
        }
      }
      container attributes {
        uses EndcProfile-attributes;
      }
    }
  }

  augment "/emael:ManagedElement/ENodeBFunction" {
    list EndcProfilePredefined {
      description "Additional definitions from MOM:min/max-elements:3/3;systemCreated; Predefined EN-DC profiles and EN-DC parameters that map to different QCIs. The RDNs of these MOs are EndcProfilePredefined=1 to EndcProfilePredefined=3.";
      key "endcProfilePredefinedId";
      leaf endcProfilePredefinedId {
        type leafref {
          path "../attributes/endcProfilePredefinedId";
        }
      }
      container attributes {
        uses EndcProfilePredefined-attributes;
      }
    }
  }

  augment "/emael:ManagedElement/ENodeBFunction" {
    list EUtraNetwork {
      description "Additional definitions from MOM:min/max-elements:1/1;systemCreated; Container for MOs related to EUTRA networks. The RDN of this MO is EUtraNetwork=1.";
      key "eUtraNetworkId";
      leaf eUtraNetworkId {
        type leafref {
          path "../attributes/eUtraNetworkId";
        }
      }
      container attributes {
        uses EUtraNetwork-attributes;
      }
    }
  }

  augment "/emael:ManagedElement/ENodeBFunction" {
    list PmEventService {
      description "Additional definitions from MOM:min/max-elements:1/1;systemCreated; Contains the parameters for PM event handling functions. The RDN of this MO is PmEventService=1.";
      key "pmEventServiceId";
      leaf pmEventServiceId {
        type leafref {
          path "../attributes/pmEventServiceId";
        }
      }
      container attributes {
        uses PmEventService-attributes;
      }
    }
  }

  augment "/emael:ManagedElement/ENodeBFunction" {
    list Rrc {
      description "Additional definitions from MOM:min/max-elements:1/1;systemCreated; Models the manageable RRC protocol characteristics. The RDN of this MO is Rrc=1.";
      key "rrcId";
      leaf rrcId {
        type leafref {
          path "../attributes/rrcId";
        }
      }
      container attributes {
        uses Rrc-attributes;
      }
    }
  }

  augment "/emael:ManagedElement/ENodeBFunction" {
    list UtraNetwork {
      description "Additional definitions from MOM:min/max-elements:0/1; This managed object represents a Utra network.";
      key "utraNetworkId";
      leaf utraNetworkId {
        type leafref {
          path "../attributes/utraNetworkId";
        }
      }
      container attributes {
        uses UtraNetwork-attributes;
      }
    }
  }

  augment "/emael:ManagedElement/ENodeBFunction" {
    list Paging {
      description "Additional definitions from MOM:min/max-elements:1/1;systemCreated; Configuration parameters for Paging feature in the RBS and applies to all cells. The RDN of this MO is Paging=1.";
      key "pagingId";
      leaf pagingId {
        type leafref {
          path "../attributes/pagingId";
        }
      }
      container attributes {
        uses Paging-attributes;
      }
    }
  }

  augment "/emael:ManagedElement/ENodeBFunction" {
    list Rcs {
      description "Additional definitions from MOM:min/max-elements:1/1;systemCreated; Models the manageable characteristics of Radio Connection Supervision feature. The RDN of this MO is Rcs=1.";
      key "rcsId";
      leaf rcsId {
        type leafref {
          path "../attributes/rcsId";
        }
      }
      container attributes {
        uses Rcs-attributes;
      }
    }
  }

  augment "/emael:ManagedElement/ENodeBFunction" {
    list SecurityHandling {
      description "Additional definitions from MOM:min/max-elements:1/1;systemCreated; Models manageable characteristics of security handling except security handling during X2 handover and S1 handover. These characteristics are then used by all instances of RRC dedicated protocol. The RDN of this MO is SecurityHandling=1.";
      key "securityHandlingId";
      leaf securityHandlingId {
        type leafref {
          path "../attributes/securityHandlingId";
        }
      }
      container attributes {
        uses SecurityHandling-attributes;
      }
    }
  }

  augment "/emael:ManagedElement/ENodeBFunction" {
    list GeraNetwork {
      description "Additional definitions from MOM:min/max-elements:0/1; This managed object represents a Gera network.";
      key "geraNetworkId";
      leaf geraNetworkId {
        type leafref {
          path "../attributes/geraNetworkId";
        }
      }
      container attributes {
        uses GeraNetwork-attributes;
      }
    }
  }

  augment "/emael:ManagedElement/ENodeBFunction" {
    list EUtranCellFDD {
      description "Additional definitions from MOM:min/max-elements:0/48; This MO represents a Cell and contains parameters needed by the cell. It also contains parameters for the mandatory common channels. Precondition: If TheftDeterrence::thdStatus is LOCKED or LOCKED_PERMANENTLY, instance of this MO class can only be created if cellDefinedPrimaryPlmnId and all PLMN IDs on additionalPlmnList are part of Lock Token or Operator List.";
      key "eUtranCellFDDId";
      leaf eUtranCellFDDId {
        type leafref {
          path "../attributes/eUtranCellFDDId";
        }
      }
      container attributes {
        uses EUtranCellFDD-attributes;
      }
    }
  }

  augment "/emael:ManagedElement/ENodeBFunction" {
    list Cdma2000Network {
      description "Additional definitions from MOM:min/max-elements:0/1; This Managed Object is a container for CDMA2000 related Managed Objects.";
      key "cdma2000NetworkId";
      leaf cdma2000NetworkId {
        type leafref {
          path "../attributes/cdma2000NetworkId";
        }
      }
      container attributes {
        uses Cdma2000Network-attributes;
      }
    }
  }

  augment "/emael:ManagedElement/ENodeBFunction" {
    list EUtranCellTDD {
      description "Additional definitions from MOM:min/max-elements:0/48; This MO represents a TDD cell and contains parameters needed by the cell. It also contains parameters for the mandatory common channels. The cell need to have the same duplex mode (FDD or TDD) as the already existing intra-RBS cells, if any. Precondition: If TheftDeterrence::thdStatus is LOCKED or LOCKED_PERMANENTLY, instance of this MO class can only be created if cellDefinedPrimaryPlmnId and all PLMN IDs on additionalPlmnList are part of Lock Token or Operator List.";
      key "eUtranCellTDDId";
      leaf eUtranCellTDDId {
        type leafref {
          path "../attributes/eUtranCellTDDId";
        }
      }
      container attributes {
        uses EUtranCellTDD-attributes;
      }
    }
  }

  augment "/emael:ManagedElement/ENodeBFunction" {
    list AirIfLoadProfile {
      description "Additional definitions from MOM:min/max-elements:0/24; Contains parameters and constraints for Air Interface Load Generator needed to start the function in a Cell.";
      key "airIfLoadProfileId";
      leaf airIfLoadProfileId {
        type leafref {
          path "../attributes/airIfLoadProfileId";
        }
      }
      container attributes {
        uses AirIfLoadProfile-attributes;
      }
    }
  }

  augment "/emael:ManagedElement/ENodeBFunction" {
    list AdmissionControl {
      description "Additional definitions from MOM:min/max-elements:1/1;systemCreated; Contains parameters for admission control function. The RDN of this MO is AdmissionControl=1.";
      key "admissionControlId";
      leaf admissionControlId {
        type leafref {
          path "../attributes/admissionControlId";
        }
      }
      container attributes {
        uses AdmissionControl-attributes;
      }
    }
  }

  augment "/emael:ManagedElement/ENodeBFunction" {
    list SubscriberProfileID {
      description "Additional definitions from MOM:min/max-elements:0/1; Parent for all SPID related MOCs";
      key "subscriberProfileIDId";
      leaf subscriberProfileIDId {
        type leafref {
          path "../attributes/subscriberProfileIDId";
        }
      }
      container attributes {
        uses SubscriberProfileID-attributes;
      }
    }
  }

  augment "/emael:ManagedElement/ENodeBFunction" {
    list LoadBalancingFunction {
      description "Additional definitions from MOM:min/max-elements:1/1;systemCreated; Contains parameters and constraints for Idle Mode Load Balancing feature. The RDN of this MO is LoadBalancingFunction=1.";
      key "loadBalancingFunctionId";
      leaf loadBalancingFunctionId {
        type leafref {
          path "../attributes/loadBalancingFunctionId";
        }
      }
      container attributes {
        uses LoadBalancingFunction-attributes;
      }
    }
  }

  augment "/emael:ManagedElement/ENodeBFunction" {
    list ParameterChangeRequests {
      description "Additional definitions from MOM:min/max-elements:1/1;systemCreated; Contains list of parameter change requests produced by open loop SON functions. The RDN of this MO is ParameterChangeRequests=1.";
      key "parameterChangeRequestsId";
      leaf parameterChangeRequestsId {
        type leafref {
          path "../attributes/parameterChangeRequestsId";
        }
      }
      container attributes {
        uses ParameterChangeRequests-attributes;
      }
    }
  }

  augment "/emael:ManagedElement/ENodeBFunction" {
    list DrxProfile {
      description "Additional definitions from MOM:min/max-elements:19/19;systemCreated; DRX profiles and DRX parameters that map to different QCIs. First instance, DrxProfileId 0, is default DRX profile. Profile eMBMS VoLTE DRX (drxProfile=18) is used when DRX is combined with eMBMS and VoLTE coexistence. The RDNs of these MOs are DrxProfile=0 to DrxProfile=18.";
      key "drxProfileId";
      leaf drxProfileId {
        type leafref {
          path "../attributes/drxProfileId";
        }
      }
      container attributes {
        uses DrxProfile-attributes;
      }
    }
  }

  augment "/emael:ManagedElement/ENodeBFunction" {
    list PwsCmas {
      description "Additional definitions from MOM:min/max-elements:0/64;systemCreated; This MO class stores warning information to be broadcast in SIB12. The RDNs of these MOs are PwsCmas=1 to PwsCmas=64.";
      key "pwsCmasId";
      leaf pwsCmasId {
        type leafref {
          path "../attributes/pwsCmasId";
        }
      }
      container attributes {
        uses PwsCmas-attributes;
      }
    }
  }

  augment "/emael:ManagedElement/ENodeBFunction" {
    list Mbms {
      description "Additional definitions from MOM:min/max-elements:0/1; This MO is the top level MO for Multimedia Broadcast Multicast Service (MBMS). It contains attributes, which are common for all parts of MBMS in the node.";
      key "mbmsId";
      leaf mbmsId {
        type leafref {
          path "../attributes/mbmsId";
        }
      }
      container attributes {
        uses Mbms-attributes;
      }
    }
  }

  augment "/emael:ManagedElement/ENodeBFunction" {
    list SectorCarrier {
      description "Additional definitions from MOM:min/max-elements:0/48; This MO represents the power and frequency usage of the SectorEquipmentFunction that covers an area.";
      key "sectorCarrierId";
      leaf sectorCarrierId {
        type leafref {
          path "../attributes/sectorCarrierId";
        }
      }
      container attributes {
        uses SectorCarrier-attributes;
      }
    }
  }

  augment "/emael:ManagedElement/ENodeBFunction" {
    list UlCompGroup {
      description "Additional definitions from MOM:min/max-elements:0/24; Defines a set of sectorCarriers. Uplink Coordinated multi-point reception of antenna signals is possible only between antenna signals from sectorCarriers within the same set of sectorCarriers.";
      key "ulCompGroupId";
      leaf ulCompGroupId {
        type leafref {
          path "../attributes/ulCompGroupId";
        }
      }
      container attributes {
        uses UlCompGroup-attributes;
      }
    }
  }

  augment "/emael:ManagedElement/ENodeBFunction" {
    list CarrierAggregationFunction {
      description "Additional definitions from MOM:min/max-elements:1/1;systemCreated; Parameters and constraints for Carrier Aggregation feature. The RDN of this MO is CarrierAggregationFunction=1.";
      key "carrierAggregationFunctionId";
      leaf carrierAggregationFunctionId {
        type leafref {
          path "../attributes/carrierAggregationFunctionId";
        }
      }
      container attributes {
        uses CarrierAggregationFunction-attributes;
      }
    }
  }

  augment "/emael:ManagedElement/ENodeBFunction" {
    list AutoCellCapEstFunction {
      description "Additional definitions from MOM:min/max-elements:1/1;systemCreated; Parameters for Automated Cell Capacity Estimation feature. The RDN of this MO is AutoCellCapEstFunction=1.";
      key "autoCellCapEstFunctionId";
      leaf autoCellCapEstFunctionId {
        type leafref {
          path "../attributes/autoCellCapEstFunctionId";
        }
      }
      container attributes {
        uses AutoCellCapEstFunction-attributes;
      }
    }
  }

  augment "/emael:ManagedElement/ENodeBFunction" {
    list PreschedulingProfile {
      description "Additional definitions from MOM:min/max-elements:1/1;systemCreated; Contains prescheduling profiles, prescheduling parameters, to map towards the different QCIs. The RDN of this MO is PreschedulingProfile=initial.";
      key "preschedulingProfileId";
      leaf preschedulingProfileId {
        type leafref {
          path "../attributes/preschedulingProfileId";
        }
      }
      container attributes {
        uses PreschedulingProfile-attributes;
      }
    }
  }

  augment "/emael:ManagedElement/ENodeBFunction" {
    list NonPlannedPciDrxProfile {
      description "Additional definitions from MOM:min/max-elements:1/1;systemCreated; Contains DRX profiles, DRX parameters, to map with non-planned PCI, CSG cell and Hybrid CSG cell CGI reading. The RDN of this MO is NonPlannedPciDrxProfile=1.";
      key "nonPlannedPciDrxProfileId";
      leaf nonPlannedPciDrxProfileId {
        type leafref {
          path "../attributes/nonPlannedPciDrxProfileId";
        }
      }
      container attributes {
        uses NonPlannedPciDrxProfile-attributes;
      }
    }
  }

  augment "/emael:ManagedElement/ENodeBFunction" {
    list DlComp {
      description "Additional definitions from MOM:min/max-elements:1/1;systemCreated; This MO contains configuration settings for Downlink Coordinated Multi-Point. The RDN of this MO is DlComp=1.";
      key "dlCompId";
      leaf dlCompId {
        type leafref {
          path "../attributes/dlCompId";
        }
      }
      container attributes {
        uses DlComp-attributes;
      }
    }
  }

  augment "/emael:ManagedElement/ENodeBFunction" {
    list ImeisvTable {
      description "Additional definitions from MOM:min/max-elements:1/1;systemCreated; Contains eNB specific configuration used for feature Differentiated UE Handling. The RDN of this MO is ImeisvTable=1.";
      key "imeisvTableId";
      leaf imeisvTableId {
        type leafref {
          path "../attributes/imeisvTableId";
        }
      }
      container attributes {
        uses ImeisvTable-attributes;
      }
    }
  }

  augment "/emael:ManagedElement/ENodeBFunction" {
    list MdtConfiguration {
      description "Additional definitions from MOM:min/max-elements:1/1;systemCreated; Contains the parameters for the Minimization of Drive Tests (MDT). The RDN of this MO is MdtConfiguration=1.";
      key "mdtConfigurationId";
      leaf mdtConfigurationId {
        type leafref {
          path "../attributes/mdtConfigurationId";
        }
      }
      container attributes {
        uses MdtConfiguration-attributes;
      }
    }
  }

  augment "/emael:ManagedElement/ENodeBFunction" {
    list CellSleepNodeFunction {
      description "Additional definitions from MOM:min/max-elements:1/1;systemCreated; Contains parameters for Cell Sleep Mode support in the node that are common for all cells. The RDN of this MO is CellSleepNodeFunction=1.";
      key "cellSleepNodeFunctionId";
      leaf cellSleepNodeFunctionId {
        type leafref {
          path "../attributes/cellSleepNodeFunctionId";
        }
      }
      container attributes {
        uses CellSleepNodeFunction-attributes;
      }
    }
  }

  augment "/emael:ManagedElement/ENodeBFunction" {
    list UnlicensedAccessFunction {
      description "Additional definitions from MOM:min/max-elements:0/1; Definitions of LAA properties, for example LBT and DRS attributes.";
      key "unlicensedAccessFunctionId";
      leaf unlicensedAccessFunctionId {
        type leafref {
          path "../attributes/unlicensedAccessFunctionId";
        }
      }
      container attributes {
        uses UnlicensedAccessFunction-attributes;
      }
    }
  }

  augment "/emael:ManagedElement/ENodeBFunction" {
    list AmoFunction {
      description "Additional definitions from MOM:min/max-elements:1/1;systemCreated; Contains parameters for Automated Mobility Optimization function. The RDN of this MO is AmoFunction=1.";
      key "amoFunctionId";
      leaf amoFunctionId {
        type leafref {
          path "../attributes/amoFunctionId";
        }
      }
      container attributes {
        uses AmoFunction-attributes;
      }
    }
  }

  augment "/emael:ManagedElement/ENodeBFunction" {
    list NbIotCell {
      description "Additional definitions from MOM:min/max-elements:0/36; This MO represents a Nb-Iot cell and contains parameters needed by the cell. Precondition: If TheftDeterrence::thdStatus is LOCKED or LOCKED_PERMANENTLY, instance of this MO class can only be created if all PLMN IDs on plmnIdList are part of Lock Token or Operator List.";
      key "nbIotCellId";
      leaf nbIotCellId {
        type leafref {
          path "../attributes/nbIotCellId";
        }
      }
      container attributes {
        uses NbIotCell-attributes;
      }
    }
  }

  augment "/emael:ManagedElement/ENodeBFunction" {
    list PmFlexCounterFilter {
      description "Additional definitions from MOM:min/max-elements:0/48; Filter parameters applied to the flexible counters. Same filter combinations between instances of this class are not allowed.";
      key "pmFlexCounterFilterId";
      leaf pmFlexCounterFilterId {
        type leafref {
          path "../attributes/pmFlexCounterFilterId";
        }
      }
      container attributes {
        uses PmFlexCounterFilter-attributes;
      }
    }
  }

  augment "/emael:ManagedElement/ENodeBFunction" {
    list AnrPciConflictDrxProfile {
      description "Additional definitions from MOM:min/max-elements:1/1;systemCreated; DRX profiles, DRX parameters to map with ANR PCI conflict CGI reading. The RDN of this MO is AnrPciConflictDrxProfile=1.";
      key "anrPciConflictDrxProfileId";
      leaf anrPciConflictDrxProfileId {
        type leafref {
          path "../attributes/anrPciConflictDrxProfileId";
        }
      }
      container attributes {
        uses AnrPciConflictDrxProfile-attributes;
      }
    }
  }

  augment "/emael:ManagedElement/ENodeBFunction" {
    list Band46UnlicensedProfile {
      description "Additional definitions from MOM:min/max-elements:0/1; Contains information about the regulatory requirements for each frequency in Band 46.";
      key "band46UnlicensedProfileId";
      leaf band46UnlicensedProfileId {
        type leafref {
          path "../attributes/band46UnlicensedProfileId";
        }
      }
      container attributes {
        uses Band46UnlicensedProfile-attributes;
      }
    }
  }

  augment "/emael:ManagedElement/ENodeBFunction" {
    list GUtraNetwork {
      description "Additional definitions from MOM:min/max-elements:0/1; This managed object is a container for Managed Objects related to GUTRA networks.";
      key "gUtraNetworkId";
      leaf gUtraNetworkId {
        type leafref {
          path "../attributes/gUtraNetworkId";
        }
      }
      container attributes {
        uses GUtraNetwork-attributes;
      }
    }
  }

  augment "/emael:ManagedElement/ENodeBFunction" {
    list PreschedProfile {
      description "Additional definitions from MOM:min/max-elements:5/5;systemCreated; Prescheduling profiles and parameters to map towards different advanced subscriber groups. The RDNs of these MOs are PreschedProfile=0 to PreschedProfile=4.";
      key "preschedProfileId";
      leaf preschedProfileId {
        type leafref {
          path "../attributes/preschedProfileId";
        }
      }
      container attributes {
        uses PreschedProfile-attributes;
      }
    }
  }

  augment "/emael:ManagedElement/ENodeBFunction" {
    list EricssonLeanCarrierFunction {
      description "Additional definitions from MOM:min/max-elements:1/1;systemCreated; Contains set of Ericsson Lean Carrier feature related parameters. Attributes take effect only if license for Ericsson Lean Carrier is present and the feature is active. The RDN of this MO is EricssonLeanCarrierFunction=1.";
      key "ericssonLeanCarrierFunctionId";
      leaf ericssonLeanCarrierFunctionId {
        type leafref {
          path "../attributes/ericssonLeanCarrierFunctionId";
        }
      }
      container attributes {
        uses EricssonLeanCarrierFunction-attributes;
      }
    }
  }

  augment "/emael:ManagedElement/ENodeBFunction" {
    list NodePerformance {
      description "Additional definitions from MOM:min/max-elements:1/1;systemCreated; Contains parameters related to node level performance improvement. The RDN of this MO is NodePerformance=1.";
      key "nodePerformanceId";
      leaf nodePerformanceId {
        type leafref {
          path "../attributes/nodePerformanceId";
        }
      }
      container attributes {
        uses NodePerformance-attributes;
      }
    }
  }

  augment "/emael:ManagedElement/ENodeBFunction" {
    list NbIdleModeLoadDistr {
      description "Additional definitions from MOM:min/max-elements:0/1; Distribution model data for the Pre-Distribution At Release feature that controls the priority of the frequencies in redirectedCarrierInfo in the RRC Connection Release message.";
      key "nbIdleModeLoadDistrId";
      leaf nbIdleModeLoadDistrId {
        type leafref {
          path "../attributes/nbIdleModeLoadDistrId";
        }
      }
      container attributes {
        uses NbIdleModeLoadDistr-attributes;
      }
    }
  }

  augment "/emael:ManagedElement/ENodeBFunction" {
    list PlmnAbConfProfile {
      description "Additional definitions from MOM:min/max-elements:0/6; Access Barring configuration for PLMN.";
      key "plmnAbConfProfileId";
      leaf plmnAbConfProfileId {
        type leafref {
          path "../attributes/plmnAbConfProfileId";
        }
      }
      container attributes {
        uses PlmnAbConfProfile-attributes;
      }
    }
  }

  augment "/emael:ManagedElement/ENodeBFunction" {
    list PtmFunction {
      description "Additional definitions from MOM:min/max-elements:1/1;systemCreated; Contains eNodeB-specific configuration for Preferential Traffic Management. The RDN of this MO is PtmFunction=1.";
      key "ptmFunctionId";
      leaf ptmFunctionId {
        type leafref {
          path "../attributes/ptmFunctionId";
        }
      }
      container attributes {
        uses PtmFunction-attributes;
      }
    }
  }

  augment "/emael:ManagedElement/ENodeBFunction" {
    list IuaProfile {
      description "Additional definitions from MOM:min/max-elements:5/5;systemCreated; IUA profiles and parameters to map towards different advanced subscriber groups. The RDNs of these MOs are IuaProfile=0 to IuaProfile=4.";
      key "iuaProfileId";
      leaf iuaProfileId {
        type leafref {
          path "../attributes/iuaProfileId";
        }
      }
      container attributes {
        uses IuaProfile-attributes;
      }
    }
  }

  augment "/emael:ManagedElement/ENodeBFunction" {
    list UePolicyOptimization {
      description "Additional definitions from MOM:min/max-elements:0/1; Contains parameters for UE capability prioritization. Used in optional features that control frequency priority for idle mode control.";
      key "uePolicyOptimizationId";
      leaf uePolicyOptimizationId {
        type leafref {
          path "../attributes/uePolicyOptimizationId";
        }
      }
      container attributes {
        uses UePolicyOptimization-attributes;
      }
    }
  }

  augment "/emael:ManagedElement/ENodeBFunction" {
    list UeMeasControlCommon {
      description "Additional definitions from MOM:min/max-elements:0/1; Manageable characteristics for UE measurements. Contains UE measurement controls that can be shared among frequency relations in different cells.";
      key "ueMeasControlCommonId";
      status deprecated;
      leaf ueMeasControlCommonId {
        type leafref {
          path "../attributes/ueMeasControlCommonId";
        }
        status deprecated;
      }
      container attributes {
        uses UeMeasControlCommon-attributes;
      }
    }
  }

  augment "/emael:ManagedElement/ENodeBFunction" {
    list SpectrumSharingFunction {
      description "Additional definitions from MOM:min/max-elements:0/1; Spectrum sharing function and configuration parameters.";
      key "spectrumSharingFunctionId";
      leaf spectrumSharingFunctionId {
        type leafref {
          path "../attributes/spectrumSharingFunctionId";
        }
      }
      container attributes {
        uses SpectrumSharingFunction-attributes;
      }
    }
  }

  augment "/emael:ManagedElement/ENodeBFunction" {
    list TermPointToMme {
      description "Additional definitions from MOM:min/max-elements:0/64; Models the MME termination point of an S1 link between the RBS and the MME node.";
      key "termPointToMmeId";
      leaf termPointToMmeId {
        type leafref {
          path "../attributes/termPointToMmeId";
        }
      }
      container attributes {
        uses TermPointToMme-attributes;
      }
    }
  }

  augment "/emael:ManagedElement/ENodeBFunction" {
    list TermPointToSGW {
      description "Additional definitions from MOM:min/max-elements:0/unbounded;systemCreated; Models SGW termination point of S1 link between RBS and SGW node. The RDNs of these MOs are TermPointToSGW=1, 2, 3, and so on.";
      key "termPointToSGWId";
      leaf termPointToSGWId {
        type leafref {
          path "../attributes/termPointToSGWId";
        }
      }
      container attributes {
        uses TermPointToSGW-attributes;
      }
    }
  }

  augment "/emael:ManagedElement/ENodeBFunction" {
    list AdditionalCoreNetwork {
      description "Additional definitions from MOM:min/max-elements:0/5; MO contains information of additional core network configuration.";
      key "additionalCoreNetworkId";
      leaf additionalCoreNetworkId {
        type leafref {
          path "../attributes/additionalCoreNetworkId";
        }
      }
      container attributes {
        uses AdditionalCoreNetwork-attributes;
      }
    }
  }

  augment "/emael:ManagedElement/ENodeBFunction" {
    list FastCoordinationGroup {
      description "Additional definitions from MOM:min/max-elements:2/2;systemCreated; FastCoordinationGroup MO class is automatically created for each Elastic RAN (ERAN) feature (DL CA and ULCOMP) for observability. It will serve as a grouping point of eNodeBs that are connected using Elastic Ran (ERAN) links. It has a list of RBS IDs which are active participants of FastCoordinationGroup (FCG) and a list of RBS IDs which are candidates to be active participants of FCG but were not configured due to exceeded number of maximum Elastic RAN (ERAN) connections. The RDNs of these MOs are FastCoordinationGroup=1 and FastCoordinationGroup=2.";
      key "fastCoordinationGroupId";
      leaf fastCoordinationGroupId {
        type leafref {
          path "../attributes/fastCoordinationGroupId";
        }
      }
      container attributes {
        uses FastCoordinationGroup-attributes;
      }
    }
  }

  augment "/emael:ManagedElement/ENodeBFunction" {
    list DynamicBlerTarget {
      description "Additional definitions from MOM:min/max-elements:1/1;systemCreated; Parameters for AI Powered Link Adaptation feature. The RDN of this MO is DynamicBlerTarget=1.";
      key "dynamicBlerTargetId";
      leaf dynamicBlerTargetId {
        type leafref {
          path "../attributes/dynamicBlerTargetId";
        }
      }
      container attributes {
        uses DynamicBlerTarget-attributes;
      }
    }
  }

  augment "/emael:ManagedElement/ENodeBFunction" {
    list EndcUserProfile {
      description "Additional definitions from MOM:min/max-elements:0/10; EN-DC user parameters to map towards different advanced subscriber groups.";
      key "endcUserProfileId";
      leaf endcUserProfileId {
        type leafref {
          path "../attributes/endcUserProfileId";
        }
      }
      container attributes {
        uses EndcUserProfile-attributes;
      }
    }
  }

  augment "/emael:ManagedElement/ENodeBFunction" {
    list CtsFunction {
      description "Additional definitions from MOM:min/max-elements:0/5; Centralized Training System (CTS) function. Contains information about supported machine learning features by CTS.";
      key "ctsFunctionId";
      leaf ctsFunctionId {
        type leafref {
          path "../attributes/ctsFunctionId";
        }
      }
      container attributes {
        uses CtsFunction-attributes;
      }
    }
  }

  augment "/emael:ManagedElement/ENodeBFunction" {
    list UeProfile {
      description "Additional definitions from MOM:min/max-elements:0/1; Contains sets of parameters applied to selected group of subscribers in selected cells.";
      key "ueProfileId";
      leaf ueProfileId {
        type leafref {
          path "../attributes/ueProfileId";
        }
      }
      container attributes {
        uses UeProfile-attributes;
      }
    }
  }

  augment "/emael:ManagedElement/ENodeBFunction" {
    list EndcDistrProfile {
      description "Additional definitions from MOM:min/max-elements:0/30; Set of parameters used to define model for distributing EN-DC users on NR frequencies. Only applicable if license for Optimized UE Distribution for EN-DC is present and feature is active.";
      key "endcDistrProfileId";
      leaf endcDistrProfileId {
        type leafref {
          path "../attributes/endcDistrProfileId";
        }
      }
      container attributes {
        uses EndcDistrProfile-attributes;
      }
    }
  }

  augment "/emael:ManagedElement/ENodeBFunction" {
    list RobustCallSetup {
      description "Additional definitions from MOM:min/max-elements:1/1;systemCreated; Contains parameters for LTE Delayed Mobility for Robust Call Setup feature. Parameters are common for all cells. RDN of this MO is RobustCallSetup=1.";
      key "robustCallSetupId";
      leaf robustCallSetupId {
        type leafref {
          path "../attributes/robustCallSetupId";
        }
      }
      container attributes {
        uses RobustCallSetup-attributes;
      }
    }
  }

  augment "/emael:ManagedElement/ENodeBFunction/UeProfile/EUtraFreqRelProfileSet" {
    list EUtraFreqRelProfile {
      description "Additional definitions from MOM:min/max-elements:0/16; Contains parameters applied to selected subscribers for selected frequency.";
      key "eUtraFreqRelProfileId";
      leaf eUtraFreqRelProfileId {
        type leafref {
          path "../attributes/eUtraFreqRelProfileId";
        }
      }
      container attributes {
        uses EUtraFreqRelProfile-attributes;
      }
    }
  }

  augment "/emael:ManagedElement/ENodeBFunction/EUtraNetwork" {
    list ExternalENodeBFunction {
      description "Additional definitions from MOM:min/max-elements:0/512; This managed object represents another ENodeB.";
      key "externalENodeBFunctionId";
      leaf externalENodeBFunctionId {
        type leafref {
          path "../attributes/externalENodeBFunctionId";
        }
      }
      container attributes {
        uses ExternalENodeBFunction-attributes;
      }
    }
  }

  augment "/emael:ManagedElement/ENodeBFunction/EUtraNetwork" {
    list EUtranFrequency {
      description "Additional definitions from MOM:min/max-elements:0/24; This Managed Object contains information of a specific EUtran frequency. MO is created manually, and when executing action changeFrequency in MO ExternalEUtranCellFDD/TDD. MO is also created automatically at X2 link setup with neighbor eNB. The RDNs of these MOs are EUtranFrequency=<number>, for example EUtranFrequency=2586. RDN must match attribute arfcnValueEUtranDl. If it does not match, automatic creation of MO can fail, leading to X2 link setup failure with neighbor eNB.";
      key "eUtranFrequencyId";
      leaf eUtranFrequencyId {
        type leafref {
          path "../attributes/eUtranFrequencyId";
        }
      }
      container attributes {
        uses EUtranFrequency-attributes;
      }
    }
  }

  augment "/emael:ManagedElement/ENodeBFunction/EUtraNetwork" {
    list UnlicensedBandProfile {
      description "Additional definitions from MOM:min/max-elements:0/24; Structure for regulatory requirements for unlicensed bands.";
      key "unlicensedBandProfileId";
      leaf unlicensedBandProfileId {
        type leafref {
          path "../attributes/unlicensedBandProfileId";
        }
      }
      container attributes {
        uses UnlicensedBandProfile-attributes;
      }
    }
  }

  augment "/emael:ManagedElement/ENodeBFunction/EUtranCellFDD" {
    list UeMeasControl {
      description "Additional definitions from MOM:min/max-elements:1/1;systemCreated; Models the manageable characteristics for UE measurements. The RDN of this MO is UeMeasControl=1.";
      key "ueMeasControlId";
      leaf ueMeasControlId {
        type leafref {
          path "../attributes/ueMeasControlId";
        }
      }
      container attributes {
        uses UeMeasControl-attributes;
      }
    }
  }

  augment "/emael:ManagedElement/ENodeBFunction/EUtranCellFDD" {
    list UtranFreqRelation {
      description "Additional definitions from MOM:min/max-elements:0/16; This Managed Object represents a UTRAN FDD mobility relation between a EUtranCellFDD or EUtranCellTDD and an UtranFrequency. It contains parameters that are specific for this relation. Deleting this MO while the parent EUtranCellFDD/EUtranCellTDD has operationalState set to ENABLED is not recommended as it may affect traffic.";
      key "utranFreqRelationId";
      leaf utranFreqRelationId {
        type leafref {
          path "../attributes/utranFreqRelationId";
        }
      }
      container attributes {
        uses UtranFreqRelation-attributes;
      }
    }
  }

  augment "/emael:ManagedElement/ENodeBFunction/EUtranCellFDD" {
    list GeranFreqGroupRelation {
      description "Additional definitions from MOM:min/max-elements:0/16; This Managed Object represents a mobility relation between an EUtranCellFDD or an EUtranCellTDD and a GeranFreqGroup. It contains parameters that are specific for this relation. Deleting this MO while the parent EUtranCellFDD/EUtranCellTDD has operationalState set to ENABLED is not recommended as it may affect traffic.";
      key "geranFreqGroupRelationId";
      leaf geranFreqGroupRelationId {
        type leafref {
          path "../attributes/geranFreqGroupRelationId";
        }
      }
      container attributes {
        uses GeranFreqGroupRelation-attributes;
      }
    }
  }

  augment "/emael:ManagedElement/ENodeBFunction/EUtranCellFDD" {
    list EUtranFreqRelation {
      description "Additional definitions from MOM:min/max-elements:0/16; This MO represents a mobility relation between a EUtranCellFDD and a EUtranFrequency. It contains parameters that are specific for this relation. To include SIB3 in System Information, one instance of this MO must be created which refers to a EUtranFrequency MO with the parameter arfcnValueEUtranDl set to the same value as the parent EUtranCellFDD/EUtranCellTDDs parameter earfcndl. It is only allowed to remove the EUtranFreqRelation, refering to the same frequency as the parent MO EUtranCellFDD/EUtranCellTDD has, when the EUtranCellFDD/EUtranCellTDD is locked. Deleting this MO while the parent EUtranCellFDD/EUtranCellTDD has operationalState set to ENABLED is not recommended as it may affect traffic.";
      key "eUtranFreqRelationId";
      leaf eUtranFreqRelationId {
        type leafref {
          path "../attributes/eUtranFreqRelationId";
        }
      }
      container attributes {
        uses EUtranFreqRelation-attributes;
      }
    }
  }

  augment "/emael:ManagedElement/ENodeBFunction/EUtranCellFDD" {
    list Cdma2000FreqBandRelation {
      description "Additional definitions from MOM:min/max-elements:0/32; This Managed Object represents a mobility relation between an EUtranCellFDD or an EUtranCellTDD and a Cdma2000FreqBand. It contains parameters that are specific for this relation. Deleting this MO while the parent EUtranCellFDD/EUtranCellTDD has operationalState set to ENABLED is not recommended as it may affect traffic.";
      key "cdma2000FreqBandRelationId";
      leaf cdma2000FreqBandRelationId {
        type leafref {
          path "../attributes/cdma2000FreqBandRelationId";
        }
      }
      container attributes {
        uses Cdma2000FreqBandRelation-attributes;
      }
    }
  }

  augment "/emael:ManagedElement/ENodeBFunction/EUtranCellFDD" {
    list UtranTDDFreqRelation {
      description "Additional definitions from MOM:min/max-elements:0/16; This Managed Object represents a UTRAN TDD mobility relation between a EUtranCellFDD or EUtranCellTDD and a UtranFrequency. It contains parameters that are specific for this relation. Deleting this MO while the parent EUtranCellFDD/EUtranCellTDD has operationalState set to ENABLED is not recommended as it may affect traffic.";
      key "utranTDDFreqRelationId";
      leaf utranTDDFreqRelationId {
        type leafref {
          path "../attributes/utranTDDFreqRelationId";
        }
      }
      container attributes {
        uses UtranTDDFreqRelation-attributes;
      }
    }
  }

  augment "/emael:ManagedElement/ENodeBFunction/EUtranCellFDD" {
    list Cdma20001xRttBandRelation {
      description "Additional definitions from MOM:min/max-elements:0/32; The MO represents a mobility relation between an EUtranCellFDD or an EUtranCellTDD and a Cdma20001xRTTFreqBand. It contains parameters that are specific for this relation.";
      key "cdma20001xRttBandRelationId";
      leaf cdma20001xRttBandRelationId {
        type leafref {
          path "../attributes/cdma20001xRttBandRelationId";
        }
      }
      container attributes {
        uses Cdma20001xRttBandRelation-attributes;
      }
    }
  }

  augment "/emael:ManagedElement/ENodeBFunction/EUtranCellFDD" {
    list Etws {
      description "Additional definitions from MOM:min/max-elements:1/1;systemCreated; Stores warning information for cell to be broadcast in SIB10 or SIB11. The RDN of this MO is Etws=1.";
      key "etwsId";
      leaf etwsId {
        type leafref {
          path "../attributes/etwsId";
        }
      }
      container attributes {
        uses Etws-attributes;
      }
    }
  }

  augment "/emael:ManagedElement/ENodeBFunction/EUtranCellFDD" {
    list MimoSleepFunction {
      description "Additional definitions from MOM:min/max-elements:1/1;systemCreated; Contains all MIMO sleep mode function configuration parameters of the in the cell. The RDN of this MO is MimoSleepFunction=1.";
      key "mimoSleepFunctionId";
      leaf mimoSleepFunctionId {
        type leafref {
          path "../attributes/mimoSleepFunctionId";
        }
      }
      container attributes {
        uses MimoSleepFunction-attributes;
      }
    }
  }

  augment "/emael:ManagedElement/ENodeBFunction/EUtranCellFDD" {
    list CellSleepFunction {
      description "Additional definitions from MOM:min/max-elements:1/1;systemCreated; Contains configuration parameters for function Cell Sleep Mode. The RDN of this MO is CellSleepFunction=1.";
      key "cellSleepFunctionId";
      leaf cellSleepFunctionId {
        type leafref {
          path "../attributes/cellSleepFunctionId";
        }
      }
      container attributes {
        uses CellSleepFunction-attributes;
      }
    }
  }

  augment "/emael:ManagedElement/ENodeBFunction/EUtranCellFDD" {
    list CellPortion {
      description "Additional definitions from MOM:min/max-elements:0/256; This MO represents the area within a Cell, which can be used for feature, e.g. UE Positioning.";
      key "cellPortionId";
      leaf cellPortionId {
        type leafref {
          path "../attributes/cellPortionId";
        }
      }
      container attributes {
        uses CellPortion-attributes;
      }
    }
  }

  augment "/emael:ManagedElement/ENodeBFunction/EUtranCellFDD" {
    list EUtranFreqRelationUnlicensed {
      description "Additional definitions from MOM:min/max-elements:0/1; MO represents mobility relation between EUtranCellFDD (or-TDD) and EUtranFrequencyUnlicensed. Contains parameters specific for this relation. One instance of this MO must refer to Band46UnlicensedProfile MO.";
      key "eUtranFreqRelationUnlicensedId";
      leaf eUtranFreqRelationUnlicensedId {
        type leafref {
          path "../attributes/eUtranFreqRelationUnlicensedId";
        }
      }
      container attributes {
        uses EUtranFreqRelationUnlicensed-attributes;
      }
    }
  }

  augment "/emael:ManagedElement/ENodeBFunction/EUtranCellFDD" {
    list PrefTrafficMgmt {
      description "Additional definitions from MOM:min/max-elements:0/1; Contains cell specific configuration for the preferential traffic management functionality.";
      key "prefTrafficMgmtId";
      status deprecated;
      leaf prefTrafficMgmtId {
        type leafref {
          path "../attributes/prefTrafficMgmtId";
        }
        status deprecated;
      }
      container attributes {
        uses PrefTrafficMgmt-attributes;
      }
    }
  }

  augment "/emael:ManagedElement/ENodeBFunction/EUtranCellFDD" {
    list CellPerformance {
      description "Additional definitions from MOM:min/max-elements:1/1;systemCreated; Contains parameters related to cell level performance improvement. The RDN of this MO is CellPerformance=1.";
      key "cellPerformanceId";
      leaf cellPerformanceId {
        type leafref {
          path "../attributes/cellPerformanceId";
        }
      }
      container attributes {
        uses CellPerformance-attributes;
      }
    }
  }

  augment "/emael:ManagedElement/ENodeBFunction/EUtranCellFDD" {
    list InstantUplinkAccess {
      description "Additional definitions from MOM:min/max-elements:1/1;systemCreated; Parameters for Instant Uplink Access feature for EUtranCellFDD/TDD. The RDN of this MO is InstantUplinkAccess=1.";
      key "instantUplinkAccessId";
      leaf instantUplinkAccessId {
        type leafref {
          path "../attributes/instantUplinkAccessId";
        }
      }
      container attributes {
        uses InstantUplinkAccess-attributes;
      }
    }
  }

  augment "/emael:ManagedElement/ENodeBFunction/EUtranCellFDD" {
    list GUtranFreqRelation {
      description "Additional definitions from MOM:min/max-elements:0/16; Mobility relation between an EUtranCellFDD or EUtranCellTDD and an NR Frequency. contains parameters specific for this relation.";
      key "gUtranFreqRelationId";
      leaf gUtranFreqRelationId {
        type leafref {
          path "../attributes/gUtranFreqRelationId";
        }
      }
      container attributes {
        uses GUtranFreqRelation-attributes;
      }
    }
  }

  augment "/emael:ManagedElement/ENodeBFunction/EUtranCellFDD" {
    list CIotEpsOptProfile {
      description "Additional definitions from MOM:min/max-elements:0/6; Activates CIoT EPS Optimization features in the cell for each PLMN.";
      key "cIotEpsOptProfileId";
      leaf cIotEpsOptProfileId {
        type leafref {
          path "../attributes/cIotEpsOptProfileId";
        }
      }
      container attributes {
        uses CIotEpsOptProfile-attributes;
      }
    }
  }

  augment "/emael:ManagedElement/ENodeBFunction/EUtranCellFDD" {
    list EabConfProfileBr {
      description "Additional definitions from MOM:min/max-elements:0/10; Extended Access Barring configuration profile for Cat-M. Attributes take effect only when EUtranCellFDD::eabPresenceBr is set to MANUAL or AUTO.";
      key "eabConfProfileBrId";
      leaf eabConfProfileBrId {
        type leafref {
          path "../attributes/eabConfProfileBrId";
        }
      }
      container attributes {
        uses EabConfProfileBr-attributes;
      }
    }
  }

  augment "/emael:ManagedElement/ENodeBFunction/EUtranCellFDD" {
    list CellPortionRd {
      description "Additional definitions from MOM:min/max-elements:0/192;systemCreated; Area within an RD cell, which can be used by RDS Location Support. Created by system when cell is unlocked. Deleted by system when cell is locked. Precondition for MO creation is that license for RDS Location Support is present and the feature is active. Attributes are updated only if license for RDS Location Support is present and the feature is active. The RDNs of these MOs are \"CellPortionRd=1\" to \"CellPortionRd=192\".";
      key "cellPortionRdId";
      leaf cellPortionRdId {
        type leafref {
          path "../attributes/cellPortionRdId";
        }
      }
      container attributes {
        uses CellPortionRd-attributes;
      }
    }
  }

  augment "/emael:ManagedElement/ENodeBFunction/EUtranCellFDD" {
    list ConnSuspendResume {
      description "Additional definitions from MOM:min/max-elements:0/6; Parameters for features: - LTE Connection Suspend and Resume - Category M Connection Suspend and Resume Each MO instance represents one PLMN in a cell.";
      key "connSuspendResumeId";
      leaf connSuspendResumeId {
        type leafref {
          path "../attributes/connSuspendResumeId";
        }
      }
      container attributes {
        uses ConnSuspendResume-attributes;
      }
    }
  }

  augment "/emael:ManagedElement/ENodeBFunction/EUtranCellTDD" {
    list UeMeasControl {
      description "Additional definitions from MOM:min/max-elements:1/1;systemCreated; Models the manageable characteristics for UE measurements. The RDN of this MO is UeMeasControl=1.";
      key "ueMeasControlId";
      leaf ueMeasControlId {
        type leafref {
          path "../attributes/ueMeasControlId";
        }
      }
      container attributes {
        uses UeMeasControl-attributes;
      }
    }
  }

  augment "/emael:ManagedElement/ENodeBFunction/EUtranCellTDD" {
    list UtranFreqRelation {
      description "Additional definitions from MOM:min/max-elements:0/16; This Managed Object represents a UTRAN FDD mobility relation between a EUtranCellFDD or EUtranCellTDD and an UtranFrequency. It contains parameters that are specific for this relation. Deleting this MO while the parent EUtranCellFDD/EUtranCellTDD has operationalState set to ENABLED is not recommended as it may affect traffic.";
      key "utranFreqRelationId";
      leaf utranFreqRelationId {
        type leafref {
          path "../attributes/utranFreqRelationId";
        }
      }
      container attributes {
        uses UtranFreqRelation-attributes;
      }
    }
  }

  augment "/emael:ManagedElement/ENodeBFunction/EUtranCellTDD" {
    list GeranFreqGroupRelation {
      description "Additional definitions from MOM:min/max-elements:0/16; This Managed Object represents a mobility relation between an EUtranCellFDD or an EUtranCellTDD and a GeranFreqGroup. It contains parameters that are specific for this relation. Deleting this MO while the parent EUtranCellFDD/EUtranCellTDD has operationalState set to ENABLED is not recommended as it may affect traffic.";
      key "geranFreqGroupRelationId";
      leaf geranFreqGroupRelationId {
        type leafref {
          path "../attributes/geranFreqGroupRelationId";
        }
      }
      container attributes {
        uses GeranFreqGroupRelation-attributes;
      }
    }
  }

  augment "/emael:ManagedElement/ENodeBFunction/EUtranCellTDD" {
    list EUtranFreqRelation {
      description "Additional definitions from MOM:min/max-elements:0/16; This MO represents a mobility relation between a EUtranCellFDD and a EUtranFrequency. It contains parameters that are specific for this relation. To include SIB3 in System Information, one instance of this MO must be created which refers to a EUtranFrequency MO with the parameter arfcnValueEUtranDl set to the same value as the parent EUtranCellFDD/EUtranCellTDDs parameter earfcndl. It is only allowed to remove the EUtranFreqRelation, refering to the same frequency as the parent MO EUtranCellFDD/EUtranCellTDD has, when the EUtranCellFDD/EUtranCellTDD is locked. Deleting this MO while the parent EUtranCellFDD/EUtranCellTDD has operationalState set to ENABLED is not recommended as it may affect traffic.";
      key "eUtranFreqRelationId";
      leaf eUtranFreqRelationId {
        type leafref {
          path "../attributes/eUtranFreqRelationId";
        }
      }
      container attributes {
        uses EUtranFreqRelation-attributes;
      }
    }
  }

  augment "/emael:ManagedElement/ENodeBFunction/EUtranCellTDD" {
    list Cdma2000FreqBandRelation {
      description "Additional definitions from MOM:min/max-elements:0/16; This Managed Object represents a mobility relation between an EUtranCellFDD or an EUtranCellTDD and a Cdma2000FreqBand. It contains parameters that are specific for this relation. Deleting this MO while the parent EUtranCellFDD/EUtranCellTDD has operationalState set to ENABLED is not recommended as it may affect traffic.";
      key "cdma2000FreqBandRelationId";
      leaf cdma2000FreqBandRelationId {
        type leafref {
          path "../attributes/cdma2000FreqBandRelationId";
        }
      }
      container attributes {
        uses Cdma2000FreqBandRelation-attributes;
      }
    }
  }

  augment "/emael:ManagedElement/ENodeBFunction/EUtranCellTDD" {
    list UtranTDDFreqRelation {
      description "Additional definitions from MOM:min/max-elements:0/16; This Managed Object represents a UTRAN TDD mobility relation between a EUtranCellFDD or EUtranCellTDD and a UtranFrequency. It contains parameters that are specific for this relation. Deleting this MO while the parent EUtranCellFDD/EUtranCellTDD has operationalState set to ENABLED is not recommended as it may affect traffic.";
      key "utranTDDFreqRelationId";
      leaf utranTDDFreqRelationId {
        type leafref {
          path "../attributes/utranTDDFreqRelationId";
        }
      }
      container attributes {
        uses UtranTDDFreqRelation-attributes;
      }
    }
  }

  augment "/emael:ManagedElement/ENodeBFunction/EUtranCellTDD" {
    list Cdma20001xRttBandRelation {
      description "Additional definitions from MOM:min/max-elements:0/32; The MO represents a mobility relation between an EUtranCellFDD or an EUtranCellTDD and a Cdma20001xRTTFreqBand. It contains parameters that are specific for this relation.";
      key "cdma20001xRttBandRelationId";
      leaf cdma20001xRttBandRelationId {
        type leafref {
          path "../attributes/cdma20001xRttBandRelationId";
        }
      }
      container attributes {
        uses Cdma20001xRttBandRelation-attributes;
      }
    }
  }

  augment "/emael:ManagedElement/ENodeBFunction/EUtranCellTDD" {
    list Etws {
      description "Additional definitions from MOM:min/max-elements:1/1;systemCreated; Stores warning information for cell to be broadcast in SIB10 or SIB11. The RDN of this MO is Etws=1.";
      key "etwsId";
      leaf etwsId {
        type leafref {
          path "../attributes/etwsId";
        }
      }
      container attributes {
        uses Etws-attributes;
      }
    }
  }

  augment "/emael:ManagedElement/ENodeBFunction/EUtranCellTDD" {
    list MimoSleepFunction {
      description "Additional definitions from MOM:min/max-elements:1/1;systemCreated; Contains all MIMO sleep mode function configuration parameters of the in the cell. The RDN of this MO is MimoSleepFunction=1.";
      key "mimoSleepFunctionId";
      leaf mimoSleepFunctionId {
        type leafref {
          path "../attributes/mimoSleepFunctionId";
        }
      }
      container attributes {
        uses MimoSleepFunction-attributes;
      }
    }
  }

  augment "/emael:ManagedElement/ENodeBFunction/EUtranCellTDD" {
    list CellSleepFunction {
      description "Additional definitions from MOM:min/max-elements:1/1;systemCreated; Contains configuration parameters for function Cell Sleep Mode. The RDN of this MO is CellSleepFunction=1.";
      key "cellSleepFunctionId";
      leaf cellSleepFunctionId {
        type leafref {
          path "../attributes/cellSleepFunctionId";
        }
      }
      container attributes {
        uses CellSleepFunction-attributes;
      }
    }
  }

  augment "/emael:ManagedElement/ENodeBFunction/EUtranCellTDD" {
    list EUtranFreqRelationUnlicensed {
      description "Additional definitions from MOM:min/max-elements:0/1; MO represents mobility relation between EUtranCellFDD (or-TDD) and EUtranFrequencyUnlicensed. Contains parameters specific for this relation. One instance of this MO must refer to Band46UnlicensedProfile MO.";
      key "eUtranFreqRelationUnlicensedId";
      leaf eUtranFreqRelationUnlicensedId {
        type leafref {
          path "../attributes/eUtranFreqRelationUnlicensedId";
        }
      }
      container attributes {
        uses EUtranFreqRelationUnlicensed-attributes;
      }
    }
  }

  augment "/emael:ManagedElement/ENodeBFunction/EUtranCellTDD" {
    list PrefTrafficMgmt {
      description "Additional definitions from MOM:min/max-elements:0/1; Contains cell specific configuration for the preferential traffic management functionality.";
      key "prefTrafficMgmtId";
      status deprecated;
      leaf prefTrafficMgmtId {
        type leafref {
          path "../attributes/prefTrafficMgmtId";
        }
        status deprecated;
      }
      container attributes {
        uses PrefTrafficMgmt-attributes;
      }
    }
  }

  augment "/emael:ManagedElement/ENodeBFunction/EUtranCellTDD" {
    list CellPerformance {
      description "Additional definitions from MOM:min/max-elements:1/1;systemCreated; Contains parameters related to cell level performance improvement. The RDN of this MO is CellPerformance=1.";
      key "cellPerformanceId";
      leaf cellPerformanceId {
        type leafref {
          path "../attributes/cellPerformanceId";
        }
      }
      container attributes {
        uses CellPerformance-attributes;
      }
    }
  }

  augment "/emael:ManagedElement/ENodeBFunction/EUtranCellTDD" {
    list InstantUplinkAccess {
      description "Additional definitions from MOM:min/max-elements:1/1;systemCreated; Parameters for Instant Uplink Access feature for EUtranCellFDD/TDD. The RDN of this MO is InstantUplinkAccess=1.";
      key "instantUplinkAccessId";
      leaf instantUplinkAccessId {
        type leafref {
          path "../attributes/instantUplinkAccessId";
        }
      }
      container attributes {
        uses InstantUplinkAccess-attributes;
      }
    }
  }

  augment "/emael:ManagedElement/ENodeBFunction/EUtranCellTDD" {
    list GUtranFreqRelation {
      description "Additional definitions from MOM:min/max-elements:0/16; Mobility relation between an EUtranCellFDD or EUtranCellTDD and an NR Frequency. contains parameters specific for this relation.";
      key "gUtranFreqRelationId";
      leaf gUtranFreqRelationId {
        type leafref {
          path "../attributes/gUtranFreqRelationId";
        }
      }
      container attributes {
        uses GUtranFreqRelation-attributes;
      }
    }
  }

  augment "/emael:ManagedElement/ENodeBFunction/EUtranCellTDD" {
    list CellPortionRd {
      description "Additional definitions from MOM:min/max-elements:0/192;systemCreated; Area within an RD cell, which can be used by RDS Location Support. Created by system when cell is unlocked. Deleted by system when cell is locked. Precondition for MO creation is that license for RDS Location Support is present and the feature is active. Attributes are updated only if license for RDS Location Support is present and the feature is active. The RDNs of these MOs are \"CellPortionRd=1\" to \"CellPortionRd=192\".";
      key "cellPortionRdId";
      leaf cellPortionRdId {
        type leafref {
          path "../attributes/cellPortionRdId";
        }
      }
      container attributes {
        uses CellPortionRd-attributes;
      }
    }
  }

  augment "/emael:ManagedElement/ENodeBFunction/EUtranCellTDD" {
    list ConnSuspendResume {
      description "Additional definitions from MOM:min/max-elements:0/6; Parameters for features: - LTE Connection Suspend and Resume - Category M Connection Suspend and Resume Each MO instance represents one PLMN in a cell.";
      key "connSuspendResumeId";
      leaf connSuspendResumeId {
        type leafref {
          path "../attributes/connSuspendResumeId";
        }
      }
      container attributes {
        uses ConnSuspendResume-attributes;
      }
    }
  }

  augment "/emael:ManagedElement/ENodeBFunction/EUtranCellFDD/EUtranFreqRelation" {
    list EUtranCellRelation {
      description "Additional definitions from MOM:min/max-elements:0/128; This managed object represents the handover relationship between two neighboring EUTRAN cells.";
      key "eUtranCellRelationId";
      leaf eUtranCellRelationId {
        type leafref {
          path "../attributes/eUtranCellRelationId";
        }
      }
      container attributes {
        uses EUtranCellRelation-attributes;
      }
    }
  }

  augment "/emael:ManagedElement/ENodeBFunction/EUtranCellFDD/EUtranFreqRelationUnlicensed" {
    list EUtranCellRelationUnlicensed {
      description "Additional definitions from MOM:min/max-elements:0/24; Handles relationship between two neighboring cells, EUTRAN FDD cell and LAA cell.";
      key "eUtranCellRelationUnlicensedId";
      leaf eUtranCellRelationUnlicensedId {
        type leafref {
          path "../attributes/eUtranCellRelationUnlicensedId";
        }
      }
      container attributes {
        uses EUtranCellRelationUnlicensed-attributes;
      }
    }
  }

  augment "/emael:ManagedElement/ENodeBFunction/EUtraNetwork/ExternalENodeBFunction/EranInterMeLink" {
    list BbLink {
      description "Additional definitions from MOM:min/max-elements:0/8;systemCreated; Models an eRAN application link between the Basebands of the eNodeB and a neighboring eNodeB. The RDNs of these MOs are BbLink=1 to BbLink=8. The BbLink MO under ExternalENodeBFunction is deprecated since L17A and removed. The new parent MO is EranInterMeLink.";
      key "bbLinkId";
      leaf bbLinkId {
        type leafref {
          path "../attributes/bbLinkId";
        }
      }
      container attributes {
        uses BbLink-attributes;
      }
    }
  }

  augment "/emael:ManagedElement/ENodeBFunction/EUtraNetwork/ExternalENodeBFunction" {
    list ExternalEUtranCellFDD {
      description "Additional definitions from MOM:min/max-elements:0/48; This managed object represents a neighbor EUTRAN cell (FDD) in another ENodeB in any MME pool.";
      key "externalEUtranCellFDDId";
      leaf externalEUtranCellFDDId {
        type leafref {
          path "../attributes/externalEUtranCellFDDId";
        }
      }
      container attributes {
        uses ExternalEUtranCellFDD-attributes;
      }
    }
  }

  augment "/emael:ManagedElement/ENodeBFunction/EUtraNetwork/ExternalENodeBFunction" {
    list ExternalEUtranCellTDD {
      description "Additional definitions from MOM:min/max-elements:0/48; This managed object represents a neighbor EUTRAN cell (TDD) in another ENodeB in any MME pool.";
      key "externalEUtranCellTDDId";
      leaf externalEUtranCellTDDId {
        type leafref {
          path "../attributes/externalEUtranCellTDDId";
        }
      }
      container attributes {
        uses ExternalEUtranCellTDD-attributes;
      }
    }
  }

  augment "/emael:ManagedElement/ENodeBFunction/EUtraNetwork/ExternalENodeBFunction" {
    list EranInterMeLink {
      description "Additional definitions from MOM:min/max-elements:0/6;systemCreated; Models an eRAN link between ME and a neighboring ME. The RDNs of these MOs are EranInterMeLink=1-1 to 1-4 for Elastic RAN Carrier Aggregation, EranInterMeLink=2 for Uplink Coordinated Multi-Point Reception, or EranInterMeLink=3 for Passive Inter Modulation Avoidance.";
      key "eranInterMeLinkId";
      leaf eranInterMeLinkId {
        type leafref {
          path "../attributes/eranInterMeLinkId";
        }
      }
      container attributes {
        uses EranInterMeLink-attributes;
      }
    }
  }

  augment "/emael:ManagedElement/ENodeBFunction/EUtraNetwork/ExternalENodeBFunction" {
    list ExternalEUtranCellUnlicensed {
      description "Additional definitions from MOM:min/max-elements:0/48; Represents a neighbor LAA cell in another eNodeB.";
      key "externalEUtranCellUnlicensedId";
      leaf externalEUtranCellUnlicensedId {
        type leafref {
          path "../attributes/externalEUtranCellUnlicensedId";
        }
      }
      container attributes {
        uses ExternalEUtranCellUnlicensed-attributes;
      }
    }
  }

  augment "/emael:ManagedElement/ENodeBFunction/EUtraNetwork/ExternalENodeBFunction" {
    list TermPointToENB {
      description "Additional definitions from MOM:min/max-elements:0/3; Models the local eNB termination point of an X2 link between the eNB and a neighbour eNB.";
      key "termPointToENBId";
      leaf termPointToENBId {
        type leafref {
          path "../attributes/termPointToENBId";
        }
      }
      container attributes {
        uses TermPointToENB-attributes;
      }
    }
  }

  augment "/emael:ManagedElement/ENodeBFunction/EUtraNetwork/ExternalENodeBFunction/ExternalEUtranCellFDD" {
    list ExternalPimFunction {
      description "Additional definitions from MOM:min/max-elements:0/1; Represents PIM function for a remote aggressor.";
      key "externalPimFunctionId";
      status deprecated;
      leaf externalPimFunctionId {
        type leafref {
          path "../attributes/externalPimFunctionId";
        }
        status deprecated;
      }
      container attributes {
        uses ExternalPimFunction-attributes;
      }
    }
  }

  augment "/emael:ManagedElement/ENodeBFunction/GUtraNetwork/ExternalGNodeBFunction/ExternalGNodeBDuPartner" {
    list InterMeLink {
      description "Additional definitions from MOM:min/max-elements:1/1;systemCreated; Models an inter-ME link between ME and partner ME. Created at E5 tunnel setup. The RDN of this MO is \"interMeLink=1\".";
      key "interMeLinkId";
      leaf interMeLinkId {
        type leafref {
          path "../attributes/interMeLinkId";
        }
      }
      container attributes {
        uses InterMeLink-attributes;
      }
    }
  }

  augment "/emael:ManagedElement/ENodeBFunction/GUtraNetwork/ExternalGNodeBFunction" {
    list ExternalGUtranCell {
      description "Additional definitions from MOM:min/max-elements:0/512; This managed object contains a GUtran cell.";
      key "externalGUtranCellId";
      leaf externalGUtranCellId {
        type leafref {
          path "../attributes/externalGUtranCellId";
        }
      }
      container attributes {
        uses ExternalGUtranCell-attributes;
      }
    }
  }

  augment "/emael:ManagedElement/ENodeBFunction/GUtraNetwork/ExternalGNodeBFunction" {
    list TermPointToGNB {
      description "Additional definitions from MOM:min/max-elements:0/3; Models the local eNB termination point of an X2 link between the gNB and an eNB. Precondition: Manual creation of TermPointToGNB instances, to gNodeBs listed in ENodeBFunction::blockedGNodeBList, is blocked.";
      key "termPointToGNBId";
      leaf termPointToGNBId {
        type leafref {
          path "../attributes/termPointToGNBId";
        }
      }
      container attributes {
        uses TermPointToGNB-attributes;
      }
    }
  }

  augment "/emael:ManagedElement/ENodeBFunction/GUtraNetwork/ExternalGNodeBFunction" {
    list ExternalGNodeBDuPartner {
      description "Additional definitions from MOM:min/max-elements:0/26;systemCreated; Models grouping point of inter-ME links to partner gNodeB-DU. Created at E5 tunnel setup. The RDN of this MO are \"ExtGNodeBDUPartnerFunction=1\" to \"ExtGNodeBDUPartnerFunction=26\".";
      key "externalGNodeBDuPartnerId";
      leaf externalGNodeBDuPartnerId {
        type leafref {
          path "../attributes/externalGNodeBDuPartnerId";
        }
      }
      container attributes {
        uses ExternalGNodeBDuPartner-attributes;
      }
    }
  }

  augment "/emael:ManagedElement/ENodeBFunction/GUtraNetwork/ExternalGNodeBFunction/ExternalGUtranCell" {
    list ExternalBroadcastPLMNInfo {
      description "Additional definitions from MOM:min/max-elements:0/12; PLMN-related information that is served by neighbor NR cell. Created and updated automatically through X2 interface or NCGI report. Deleted automatically. When created automatically, the RDNs of these MOs are ExternalBroadcastPLMNInfo=1 to ExternalBroadcastPLMNInfo=12. RDN value is assigned based on order of Broadcast PLMN Identify Info List NR entries in X2 message or PLMN-IdentityInfoListNR entries in NCGI report. Can also be created and deleted manually.";
      key "externalBroadcastPLMNInfoId";
      leaf externalBroadcastPLMNInfoId {
        type leafref {
          path "../attributes/externalBroadcastPLMNInfoId";
        }
      }
      container attributes {
        uses ExternalBroadcastPLMNInfo-attributes;
      }
    }
  }

  augment "/emael:ManagedElement/ENodeBFunction/FlexibleQoSFunction" {
    list FlexibleQoSGroup {
      description "Additional definitions from MOM:min/max-elements:0/18; Group of members to assign a bearer certain SCI profile. Multiple members in the same group must not be applicable to the same bearer.";
      key "flexibleQoSGroupId";
      leaf flexibleQoSGroupId {
        type leafref {
          path "../attributes/flexibleQoSGroupId";
        }
      }
      container attributes {
        uses FlexibleQoSGroup-attributes;
      }
    }
  }

  augment "/emael:ManagedElement/ENodeBFunction/FlexibleQoSFunction" {
    list UserProfile {
      description "Additional definitions from MOM:min/max-elements:0/50; A combination of attributes specifies which SCI profile a given bearer should be assigned.";
      key "userProfileId";
      leaf userProfileId {
        type leafref {
          path "../attributes/userProfileId";
        }
      }
      container attributes {
        uses UserProfile-attributes;
      }
    }
  }

  augment "/emael:ManagedElement/ENodeBFunction/FlexibleQoSFunction/FlexibleQoSGroup" {
    list FlexibleQoSGroupMember {
      description "Additional definitions from MOM:min/max-elements:0/6; Specifies a mapping configuration to decide what SciProfile should be assigned to a bearer.";
      key "flexibleQoSGroupMemberId";
      leaf flexibleQoSGroupMemberId {
        type leafref {
          path "../attributes/flexibleQoSGroupMemberId";
        }
      }
      container attributes {
        uses FlexibleQoSGroupMember-attributes;
      }
    }
  }

  augment "/emael:ManagedElement/ENodeBFunction/UeProfile/GUtraFreqRelProfileSet" {
    list GUtraFreqRelProfile {
      description "Additional definitions from MOM:min/max-elements:0/16; Contains parameters applied to selected subscribers for selected frequency.";
      key "gUtraFreqRelProfileId";
      leaf gUtraFreqRelProfileId {
        type leafref {
          path "../attributes/gUtraFreqRelProfileId";
        }
      }
      container attributes {
        uses GUtraFreqRelProfile-attributes;
      }
    }
  }

  augment "/emael:ManagedElement/ENodeBFunction/GUtraNetwork" {
    list ExternalGNodeBFunction {
      description "Additional definitions from MOM:min/max-elements:0/256; This managed object represents an GNodeB.";
      key "externalGNodeBFunctionId";
      leaf externalGNodeBFunctionId {
        type leafref {
          path "../attributes/externalGNodeBFunctionId";
        }
      }
      container attributes {
        uses ExternalGNodeBFunction-attributes;
      }
    }
  }

  augment "/emael:ManagedElement/ENodeBFunction/GUtraNetwork" {
    list GUtranSyncSignalFrequency {
      description "Additional definitions from MOM:min/max-elements:0/24; GUTRAN Synchronization Signal Frequency and related measurement parameters. The RDN of this MO is GUtranSyncSignalFrequency=arfcn-smtcScs. Example: GUtranSyncSignalFrequency=630000-30.";
      key "gUtranSyncSignalFrequencyId";
      leaf gUtranSyncSignalFrequencyId {
        type leafref {
          path "../attributes/gUtranSyncSignalFrequencyId";
        }
      }
      container attributes {
        uses GUtranSyncSignalFrequency-attributes;
      }
    }
  }

  augment "/emael:ManagedElement/ENodeBFunction/EUtranCellFDD/GUtranFreqRelation" {
    list GUtranCellRelation {
      description "Additional definitions from MOM:min/max-elements:0/128; Represents the relationship between an EUTRAN cell and a GUTRAN cell. It contains parameters that are specific for this relation.";
      key "gUtranCellRelationId";
      leaf gUtranCellRelationId {
        type leafref {
          path "../attributes/gUtranCellRelationId";
        }
      }
      container attributes {
        uses GUtranCellRelation-attributes;
      }
    }
  }

  augment "/emael:ManagedElement/ENodeBFunction/GeraNetwork" {
    list GeranFreqGroup {
      description "Additional definitions from MOM:min/max-elements:0/192; This managed object contains information about a set of Geran ARFCN values, which represent a group of Geran frequencies. It is not possible to include Geran frequencies from both band 1800 and 1900 within the same GeranFreqGroup.";
      key "geranFreqGroupId";
      leaf geranFreqGroupId {
        type leafref {
          path "../attributes/geranFreqGroupId";
        }
      }
      container attributes {
        uses GeranFreqGroup-attributes;
      }
    }
  }

  augment "/emael:ManagedElement/ENodeBFunction/GeraNetwork" {
    list GeranFrequency {
      description "Additional definitions from MOM:min/max-elements:0/512; This Managed Object contains information of a specific Geran frequency.";
      key "geranFrequencyId";
      leaf geranFrequencyId {
        type leafref {
          path "../attributes/geranFrequencyId";
        }
      }
      container attributes {
        uses GeranFrequency-attributes;
      }
    }
  }

  augment "/emael:ManagedElement/ENodeBFunction/GeraNetwork" {
    list ExternalGeranCell {
      description "Additional definitions from MOM:min/max-elements:0/8192; This Managed Object contains a GERAN cell.";
      key "externalGeranCellId";
      leaf externalGeranCellId {
        type leafref {
          path "../attributes/externalGeranCellId";
        }
      }
      container attributes {
        uses ExternalGeranCell-attributes;
      }
    }
  }

  augment "/emael:ManagedElement/ENodeBFunction/EUtranCellFDD/GeranFreqGroupRelation" {
    list GeranCellRelation {
      description "Additional definitions from MOM:min/max-elements:0/64; This Managed Object represents a mobility relation between an EUtranCellFDD or an EUtranCellTDD and a GeranCell. It contains parameters that are specific for this relation";
      key "geranCellRelationId";
      leaf geranCellRelationId {
        type leafref {
          path "../attributes/geranCellRelationId";
        }
      }
      container attributes {
        uses GeranCellRelation-attributes;
      }
    }
  }

  augment "/emael:ManagedElement/ENodeBFunction/ImeisvTable" {
    list ImeisvProfile {
      description "Additional definitions from MOM:min/max-elements:0/150; Contains UE IMEISV configuration used for feature Differentiated UE Handling. Instances of this class are created on demand by the operator. The instances can be created and configured independent of the serviceState for DifferentiatedUeHandling. But the IMEISV profiles cannot be used unless the service state is OPERABLE.";
      key "imeisvProfileId";
      leaf imeisvProfileId {
        type leafref {
          path "../attributes/imeisvProfileId";
        }
      }
      container attributes {
        uses ImeisvProfile-attributes;
      }
    }
  }

  augment "/emael:ManagedElement/ENodeBFunction/ImeisvTable" {
    list UnsupportedFreqProfile {
      description "Additional definitions from MOM:min/max-elements:0/20; Contains list of frequencies unsupported by UE. Used for Device-Based Frequency Filtering feature. MO instances are created on demand by the operator. Can be created and configured independent of serviceState license for Device-Based Frequency Filtering feature. However, UnsupportedFreq profiles cannot be used unless this license is activated.";
      key "unsupportedFreqProfileId";
      leaf unsupportedFreqProfileId {
        type leafref {
          path "../attributes/unsupportedFreqProfileId";
        }
      }
      container attributes {
        uses UnsupportedFreqProfile-attributes;
      }
    }
  }

  augment "/emael:ManagedElement/ENodeBFunction/LoadBalancingFunction" {
    list IdleModePrioAtRelease {
      description "Additional definitions from MOM:min/max-elements:0/24; Contains distribution model data for Load-Based Distribution at Release feature. This feature controls priority of frequencies in IdleModeMobilityControlInfo in RRC Connection Release message.";
      key "idleModePrioAtReleaseId";
      leaf idleModePrioAtReleaseId {
        type leafref {
          path "../attributes/idleModePrioAtReleaseId";
        }
      }
      container attributes {
        uses IdleModePrioAtRelease-attributes;
      }
    }
  }

  augment "/emael:ManagedElement/ENodeBFunction/Mbms" {
    list MbsfnArea {
      description "Additional definitions from MOM:min/max-elements:0/48; This MO represents a MBMS Single Frequence Network (MBSFN) area and contains MBSFN area related parameters.";
      key "mbsfnAreaId";
      leaf mbsfnAreaId {
        type leafref {
          path "../attributes/mbsfnAreaId";
        }
      }
      container attributes {
        uses MbsfnArea-attributes;
      }
    }
  }

  augment "/emael:ManagedElement/ENodeBFunction/Mbms/MbsfnArea" {
    list PmchMch {
      description "Additional definitions from MOM:min/max-elements:0/15; This MO represents configuration related to the Uu physical and transport layers for Multimedia Broadcast Multicast Service (MBMS).";
      key "pmchMchId";
      leaf pmchMchId {
        type leafref {
          path "../attributes/pmchMchId";
        }
      }
      container attributes {
        uses PmchMch-attributes;
      }
    }
  }

  augment "/emael:ManagedElement/ENodeBFunction/Mbms/MbsfnArea" {
    list MbsfnAreaCellRelation {
      description "Additional definitions from MOM:min/max-elements:0/24; This managed object represents the relationship between a MBSFN Area and a EUTRAN cell.";
      key "mbsfnAreaCellRelationId";
      leaf mbsfnAreaCellRelationId {
        type leafref {
          path "../attributes/mbsfnAreaCellRelationId";
        }
      }
      container attributes {
        uses MbsfnAreaCellRelation-attributes;
      }
    }
  }

  augment "/emael:ManagedElement/ENodeBFunction/MdtConfiguration" {
    list LoggedMdt {
      description "Additional definitions from MOM:min/max-elements:1/1;systemCreated; Contains parameters for Logged Area Based MDT. The RDN of this MO is LoggedMdt=1.";
      key "loggedMdtId";
      leaf loggedMdtId {
        type leafref {
          path "../attributes/loggedMdtId";
        }
      }
      container attributes {
        uses LoggedMdt-attributes;
      }
    }
  }

  augment "/emael:ManagedElement/ENodeBFunction/NbIotCell" {
    list AbConfProfile {
      description "Additional definitions from MOM:min/max-elements:0/10; Access barring configuration profile for NB-IoT. Attributes take effect only when abPresence is set to AUTO.";
      key "abConfProfileId";
      leaf abConfProfileId {
        type leafref {
          path "../attributes/abConfProfileId";
        }
      }
      container attributes {
        uses AbConfProfile-attributes;
      }
    }
  }

  augment "/emael:ManagedElement/ENodeBFunction/Mbms/MbsfnArea/PmchMch" {
    list MbmsService {
      description "Additional definitions from MOM:min/max-elements:0/28; MO represents configuration related to MBMS bearer service. If Autoconfiguration of LTE Broadcast Subframes is used, this MO will be created by the system.";
      key "mbmsServiceId";
      leaf mbmsServiceId {
        type leafref {
          path "../attributes/mbmsServiceId";
        }
      }
      container attributes {
        uses MbmsService-attributes;
      }
    }
  }

  augment "/emael:ManagedElement/ENodeBFunction/PtmFunction/PtmCellProfile" {
    list PtmIflbConfig {
      description "Additional definitions from MOM:min/max-elements:1/1;systemCreated; Contains PTM specific parameters affecting Inter-Frequency Load Balancing feature. The RDN of this MO is PtmIflbConfig=1.";
      key "ptmIflbConfigId";
      leaf ptmIflbConfigId {
        type leafref {
          path "../attributes/ptmIflbConfigId";
        }
      }
      container attributes {
        uses PtmIflbConfig-attributes;
      }
    }
  }

  augment "/emael:ManagedElement/ENodeBFunction/PtmFunction/PtmCellProfile" {
    list PtmIfoConfig {
      description "Additional definitions from MOM:min/max-elements:1/1;systemCreated; Contains PTM specific parameters affecting Inter-Frequency Offload feature. The RDN of this MO is PtmIfoConfig=1.";
      key "ptmIfoConfigId";
      leaf ptmIfoConfigId {
        type leafref {
          path "../attributes/ptmIfoConfigId";
        }
      }
      container attributes {
        uses PtmIfoConfig-attributes;
      }
    }
  }

  augment "/emael:ManagedElement/ENodeBFunction/PtmFunction/PtmCellProfile" {
    list PtmAtoConfig {
      description "Additional definitions from MOM:min/max-elements:1/1;systemCreated; Contains PTM specific parameters affecting Admission Triggered Offload feature. The RDN of this MO is PtmAtoConfig=1.";
      key "ptmAtoConfigId";
      leaf ptmAtoConfigId {
        type leafref {
          path "../attributes/ptmAtoConfigId";
        }
      }
      container attributes {
        uses PtmAtoConfig-attributes;
      }
    }
  }

  augment "/emael:ManagedElement/ENodeBFunction/PtmFunction/PtmCellProfile" {
    list PtmResOpUseConfig {
      description "Additional definitions from MOM:min/max-elements:1/1;systemCreated; Contains PTM specific parameters affecting Cell Reserved For Operator Use functionality. The RDN of this MO is PtmResOpUseConfig=1.";
      key "ptmResOpUseConfigId";
      leaf ptmResOpUseConfigId {
        type leafref {
          path "../attributes/ptmResOpUseConfigId";
        }
      }
      container attributes {
        uses PtmResOpUseConfig-attributes;
      }
    }
  }

  augment "/emael:ManagedElement/ENodeBFunction/PtmFunction/PtmCellProfile" {
    list PtmStmConfig {
      description "Additional definitions from MOM:min/max-elements:1/1;systemCreated; Contains PTM specific parameters affecting Subscriber Triggered Mobility feature. The RDN of this MO is PtmStmConfig=1.";
      key "ptmStmConfigId";
      leaf ptmStmConfigId {
        type leafref {
          path "../attributes/ptmStmConfigId";
        }
      }
      container attributes {
        uses PtmStmConfig-attributes;
      }
    }
  }

  augment "/emael:ManagedElement/ENodeBFunction/PtmFunction" {
    list PtmSubscriberGroup {
      description "Additional definitions from MOM:min/max-elements:0/12; PTM Subscriber Group that can be used in PtmCellProfile configuration. Groups can be referenced from structures IfoConfig, AtoConfig, ResOpUseConfig, and StmConfig in PtmCellProfile.";
      key "ptmSubscriberGroupId";
      leaf ptmSubscriberGroupId {
        type leafref {
          path "../attributes/ptmSubscriberGroupId";
        }
      }
      container attributes {
        uses PtmSubscriberGroup-attributes;
      }
    }
  }

  augment "/emael:ManagedElement/ENodeBFunction/PtmFunction" {
    list PtmCellProfile {
      description "Additional definitions from MOM:min/max-elements:0/4; Parameters that can be used to define a PTM Cell Profile, describing per cell configuration of Preferential Traffic Management. PtmCellProfile can be referenced from multiple cells on the eNodeB by using EUtranCellFDD.PtmCellProfileRef or EUtranCellTDD.PtmCellProfileRef.";
      key "ptmCellProfileId";
      leaf ptmCellProfileId {
        type leafref {
          path "../attributes/ptmCellProfileId";
        }
      }
      container attributes {
        uses PtmCellProfile-attributes;
      }
    }
  }

  augment "/emael:ManagedElement/ENodeBFunction/QciTable" {
    list LogicalChannelGroup {
      description "Additional definitions from MOM:min/max-elements:4/4;systemCreated; Represents QoS configuration related to a Logical Channel group. The RDNs of these MOs are LogicalChannelGroup=0 to LogicalChannelGroup=3.";
      key "logicalChannelGroupId";
      leaf logicalChannelGroupId {
        type leafref {
          path "../attributes/logicalChannelGroupId";
        }
      }
      container attributes {
        uses LogicalChannelGroup-attributes;
      }
    }
  }

  augment "/emael:ManagedElement/ENodeBFunction/QciTable" {
    list QciProfilePredefined {
      description "Additional definitions from MOM:min/max-elements:14/14;systemCreated; Bearer-level QoS configuration. Not possible to create or remove instances of this MO. Each QciProfilePredefined corresponds to a standardized QCI as described in 3GPP TS 23.203. If a profile related to a specific QCI is not defined, a default QCI profile is used. If a profile related to a specific QCI in S1AP E-RAB Setup Request or S1AP E-RAB Modify Request during an ongoing S1 or X2 handover procedure is not defined, profile related to specific QCI is used. RDNs of these MOs are QciProfilePredefined=qci1 to QciProfilePredefined=qci9, QciProfilePredefined=qci65, QciProfilePredefined=qci66, QciProfilePredefined=qci69, QciProfilePredefined=qci70, and QciProfilePredefined=default.";
      key "qciProfilePredefinedId";
      leaf qciProfilePredefinedId {
        type leafref {
          path "../attributes/qciProfilePredefinedId";
        }
      }
      container attributes {
        uses QciProfilePredefined-attributes;
      }
    }
  }

  augment "/emael:ManagedElement/ENodeBFunction/QciTable" {
    list QciProfileOperatorDefined {
      description "Additional definitions from MOM:min/max-elements:0/17; Contains bearer-level QoS configuration. Instances of this class are created on demand by the operator. Each QciProfileOperatorDefined instance corresponds to a unique operator defined QCI number within the range 10-255. The instances can be created and configured independent of the serviceStateOperatorDefinedQci. However the configured QCI profiles can not be used at bearer setup / modify unless the service state is OPERABLE.";
      key "qciProfileOperatorDefinedId";
      leaf qciProfileOperatorDefinedId {
        type leafref {
          path "../attributes/qciProfileOperatorDefinedId";
        }
      }
      container attributes {
        uses QciProfileOperatorDefined-attributes;
      }
    }
  }

  augment "/emael:ManagedElement/ENodeBFunction/QciTable" {
    list SciProfile {
      description "Additional definitions from MOM:min/max-elements:19/19;systemCreated; Contains bearer-level eNB specific QoS configuration used for feature FlexibleQoS. SCI profile can be used only when FlexibleQoS is activated. The RDNs of these MOs are SciProfile=sci1 to SciProfile=sci18, SciProfile=default.";
      key "sciProfileId";
      leaf sciProfileId {
        type leafref {
          path "../attributes/sciProfileId";
        }
      }
      container attributes {
        uses SciProfile-attributes;
      }
    }
  }

  augment "/emael:ManagedElement/ENodeBFunction/SubscriberProfileID/RATFreqPrio" {
    list FreqPrioNR {
      description "Additional definitions from MOM:min/max-elements:0/24; Prioritizes NR frequencies among all frequencies related to cell for UE cell reselection procedure and for UEs in connected mode.";
      key "freqPrioNRId";
      leaf freqPrioNRId {
        type leafref {
          path "../attributes/freqPrioNRId";
        }
      }
      container attributes {
        uses FreqPrioNR-attributes;
      }
    }
  }

  augment "/emael:ManagedElement/ENodeBFunction/SubscriberProfileID/RATFreqPrio" {
    list FreqPrioEUtra {
      description "Additional definitions from MOM:min/max-elements:0/24; Prioritizes EUtra frequencies among all frequencies related to cell for selected UEs.";
      key "freqPrioEUtraId";
      leaf freqPrioEUtraId {
        type leafref {
          path "../attributes/freqPrioEUtraId";
        }
      }
      container attributes {
        uses FreqPrioEUtra-attributes;
      }
    }
  }

  augment "/emael:ManagedElement/ENodeBFunction/RadioBearerTable" {
    list DataRadioBearer {
      description "Additional definitions from MOM:min/max-elements:1/1;systemCreated; Radio Bearer configuration. The RDN of this MO is DataRadioBearer=1.";
      key "dataRadioBearerId";
      leaf dataRadioBearerId {
        type leafref {
          path "../attributes/dataRadioBearerId";
        }
      }
      container attributes {
        uses DataRadioBearer-attributes;
      }
    }
  }

  augment "/emael:ManagedElement/ENodeBFunction/RadioBearerTable" {
    list MACConfiguration {
      description "Additional definitions from MOM:min/max-elements:1/1;systemCreated; MAC configuration. The RDN of this MO is MACConfiguration=1.";
      key "mACConfigurationId";
      leaf mACConfigurationId {
        type leafref {
          path "../attributes/mACConfigurationId";
        }
      }
      container attributes {
        uses MACConfiguration-attributes;
      }
    }
  }

  augment "/emael:ManagedElement/ENodeBFunction/RadioBearerTable" {
    list SignalingRadioBearer {
      description "Additional definitions from MOM:min/max-elements:1/1;systemCreated; Signaling Radio Bearer configuration. The RDN of this MO is SignalingRadioBearer=1.";
      key "signalingRadioBearerId";
      leaf signalingRadioBearerId {
        type leafref {
          path "../attributes/signalingRadioBearerId";
        }
      }
      container attributes {
        uses SignalingRadioBearer-attributes;
      }
    }
  }

  augment "/emael:ManagedElement/ENodeBFunction/RadioBearerTable" {
    list RlcConfiguration {
      description "Additional definitions from MOM:min/max-elements:1/1;systemCreated; Radio Link Control configuration. The RDN of this MO is RLCConfiguration=1.";
      key "rlcConfigurationId";
      leaf rlcConfigurationId {
        type leafref {
          path "../attributes/rlcConfigurationId";
        }
      }
      container attributes {
        uses RlcConfiguration-attributes;
      }
    }
  }

  augment "/emael:ManagedElement/ENodeBFunction/EUtranCellFDD/UeMeasControl/ReportConfigA5" {
    list ReportConfigA5Anr {
      description "Additional definitions from MOM:min/max-elements:1/1;systemCreated; The Automated Neighbor Relations (ANR) delta report configuration settings for the A5 event measurements as compared to mobility provided in the parent MO class. The RDN of this MO is ReportConfigA5Anr=1.";
      key "reportConfigA5AnrId";
      leaf reportConfigA5AnrId {
        type leafref {
          path "../attributes/reportConfigA5AnrId";
        }
      }
      container attributes {
        uses ReportConfigA5Anr-attributes;
      }
    }
  }

  augment "/emael:ManagedElement/ENodeBFunction/EUtranCellFDD/UeMeasControl/ReportConfigEUtraBestCell" {
    list ReportConfigEUtraBestCellAnr {
      description "Additional definitions from MOM:min/max-elements:1/1;systemCreated; The ANR delta report configuration settings for the A3 event measurements as compared to mobility provided in the parent MO class. The RDN of this MO is ReportConfigEUtraBestCellAnr=1.";
      key "reportConfigEUtraBestCellAnrId";
      leaf reportConfigEUtraBestCellAnrId {
        type leafref {
          path "../attributes/reportConfigEUtraBestCellAnrId";
        }
      }
      container attributes {
        uses ReportConfigEUtraBestCellAnr-attributes;
      }
    }
  }

  augment "/emael:ManagedElement/ENodeBFunction/ResourcePartitionGroup" {
    list ResourcePartitionGroupMember {
      description "Additional definitions from MOM:min/max-elements:0/6; Specifies a resource partition configuration and the share of resources it should be granted in the cell.";
      key "resourcePartitionGroupMemberId";
      leaf resourcePartitionGroupMemberId {
        type leafref {
          path "../attributes/resourcePartitionGroupMemberId";
        }
      }
      container attributes {
        uses ResourcePartitionGroupMember-attributes;
      }
    }
  }

  augment "/emael:ManagedElement/ENodeBFunction/ResourcePartitions" {
    list ResourcePartition {
      description "Additional definitions from MOM:min/max-elements:0/24; A combination of attributes which specify the resource partition a given UE should be included in.";
      key "resourcePartitionId";
      leaf resourcePartitionId {
        type leafref {
          path "../attributes/resourcePartitionId";
        }
      }
      container attributes {
        uses ResourcePartition-attributes;
      }
    }
  }

  augment "/emael:ManagedElement/ENodeBFunction/SectorCarrier" {
    list PmUlInterferenceReport {
      description "Additional definitions from MOM:min/max-elements:0/8;systemCreated; Contains RF branch information used for the feature Uplink Interference Reporting. Created when the feature license is activated. The RDNs of these MOs are PmUlInterferenceReport=1 to PmUlInterferenceReport=8.";
      key "pmUlInterferenceReportId";
      leaf pmUlInterferenceReportId {
        type leafref {
          path "../attributes/pmUlInterferenceReportId";
        }
      }
      container attributes {
        uses PmUlInterferenceReport-attributes;
      }
    }
  }

  augment "/emael:ManagedElement/ENodeBFunction/SectorCarrier" {
    list PimCancellationConfig {
      description "Additional definitions from MOM:min/max-elements:0/72; PIM cancellation configuration data of SectorCarrier participating in PIM cancellation function. This MO can be created and deleted automatically. Can also be created and deleted manually. When created automatically, the RDNs of these MOs have prefix 'auto_'. Only one PimCancellationConfig MO can refer to same PimCancellationFunction. Only one PimCancellationConfig MO among PimCancellationConfig MOs having same createdBy value can have other ulPimCancellationMode value than EXCLUDED. When createdBy is set to SYSTEM, attributes should not be changed by operator. Only takes effect for CPRI-based radio equipment that does not support AAS functions.";
      key "pimCancellationConfigId";
      leaf pimCancellationConfigId {
        type leafref {
          path "../attributes/pimCancellationConfigId";
        }
      }
      container attributes {
        uses PimCancellationConfig-attributes;
      }
    }
  }

  augment "/emael:ManagedElement/ENodeBFunction/SectorCarrier" {
    list PowerBackoff {
      description "Additional definitions from MOM:min/max-elements:0/1; Contains configuration parameters related to EMF Exposure Power Back-off. The feature intends to reduce radio safety distance in classic and AAS products with MIMO.";
      key "powerBackoffId";
      leaf powerBackoffId {
        type leafref {
          path "../attributes/powerBackoffId";
        }
      }
      container attributes {
        uses PowerBackoff-attributes;
      }
    }
  }

  augment "/emael:ManagedElement/ENodeBFunction/CellSleepNodeFunction/SleepModeCovProfile" {
    list WakeUpFreqPriority {
      description "Additional definitions from MOM:min/max-elements:0/24; Contains reference to frequency and priority used for sequential wake-up. For LTE CBRS frequencies, following apply: - MO instance can be created automatically by changeFrequency action from EUtranCellTDD or ExternalEUtranCellTDD instance. - MO instance can be deleted by periodic clean-up of empty CBRS MO instances. When created automatically, the RDN of this MO is WakeUpFreqPriority=auto<arfcnValueEUtranDl>, where arfcnValueEUtranDl = value of arfcnValueEutranDl attribute of referenced EUtranFrequency MO instance. Length of RDN value is up to 10 characters for automatically created instance. Instance can be created without a preceding user-initiated transaction.";
      key "wakeUpFreqPriorityId";
      leaf wakeUpFreqPriorityId {
        type leafref {
          path "../attributes/wakeUpFreqPriorityId";
        }
      }
      container attributes {
        uses WakeUpFreqPriority-attributes;
      }
    }
  }

  augment "/emael:ManagedElement/ENodeBFunction/SpectrumSharingFunction" {
    list SharingGroup {
      description "Additional definitions from MOM:min/max-elements:0/24; Represents a sharing group.";
      key "sharingGroupId";
      leaf sharingGroupId {
        type leafref {
          path "../attributes/sharingGroupId";
        }
      }
      container attributes {
        uses SharingGroup-attributes;
      }
    }
  }

  augment "/emael:ManagedElement/ENodeBFunction/SubscriberProfileID" {
    list HoWhiteList {
      description "Additional definitions from MOM:min/max-elements:0/1; Contains a whitelist of SPID values that are allowed to perform a incoming handover requests when the cell is in the mode \"reserved for operator use\"";
      key "hoWhiteListId";
      leaf hoWhiteListId {
        type leafref {
          path "../attributes/hoWhiteListId";
        }
      }
      container attributes {
        uses HoWhiteList-attributes;
      }
    }
  }

  augment "/emael:ManagedElement/ENodeBFunction/SubscriberProfileID" {
    list RATFreqPrio {
      description "Additional definitions from MOM:min/max-elements:0/8; Contains data that overrides information in the IdleModeMobilityControlInfo and RedirectedCarrierInfo (sent to UE in RRC Connection Release) that is configured for the cell. It also contains attributes that control load balancing and offloading. Only UEs that have a SPID value matching the list in this MOC are affected.";
      key "rATFreqPrioId";
      leaf rATFreqPrioId {
        type leafref {
          path "../attributes/rATFreqPrioId";
        }
      }
      container attributes {
        uses RATFreqPrio-attributes;
      }
    }
  }

  augment "/emael:ManagedElement/ENodeBFunction/EUtraNetwork/ExternalENodeBFunction/TermPointToENB" {
    list TermPointToLbm {
      description "Additional definitions from MOM:min/max-elements:0/27;systemCreated; Designates endpoints from a baseband unit on the local eNodeB to reach a particular baseband unit on the remote eNodeB indicated by TermPointToENB. The RDNs of these MOs are TermPointToLbm = LocalToRemoteLbmId<lbmIdLocal>-<lbmIdRemote>.";
      key "termPointToLbmId";
      leaf termPointToLbmId {
        type leafref {
          path "../attributes/termPointToLbmId";
        }
      }
      container attributes {
        uses TermPointToLbm-attributes;
      }
    }
  }

  augment "/emael:ManagedElement/ENodeBFunction/EUtraNetwork/ExternalENodeBFunction/TermPointToENB" {
    list GtpPath {
      description "Additional definitions from MOM:min/max-elements:0/1;systemCreated; Models GTP-U path between RBS and another node, either SGW or neighbor RBS. The RDNs of these MOs are GtpPath = <local ip address> to SGW nodes. The RDN of this MO is GtpPath = 1 to neighbor RBS.";
      key "gtpPathId";
      leaf gtpPathId {
        type leafref {
          path "../attributes/gtpPathId";
        }
      }
      container attributes {
        uses GtpPath-attributes;
      }
    }
  }

  augment "/emael:ManagedElement/ENodeBFunction/EUtraNetwork/ExternalENodeBFunction/TermPointToENB/TermPointToLbm" {
    list GtpuApplicationTunnel {
      description "Additional definitions from MOM:min/max-elements:2/2;systemCreated; Designates a GTP-U tunnel used to support a baseband-to-baseband application. The RDNs of these MOs are GtpuApplicationTunnel=0 to GtpuApplicationTunnel=1.";
      key "gtpuApplicationTunnelId";
      leaf gtpuApplicationTunnelId {
        type leafref {
          path "../attributes/gtpuApplicationTunnelId";
        }
      }
      container attributes {
        uses GtpuApplicationTunnel-attributes;
      }
    }
  }

  augment "/emael:ManagedElement/ENodeBFunction/TermPointToSGW" {
    list GtpPath {
      description "Additional definitions from MOM:min/max-elements:0/unbounded;systemCreated; Models GTP-U path between RBS and another node, either SGW or neighbor RBS. The RDNs of these MOs are GtpPath = <local ip address> to SGW nodes. The RDN of this MO is GtpPath = 1 to neighbor RBS.";
      key "gtpPathId";
      leaf gtpPathId {
        type leafref {
          path "../attributes/gtpPathId";
        }
      }
      container attributes {
        uses GtpPath-attributes;
      }
    }
  }

  augment "/emael:ManagedElement/ENodeBFunction/EUtranCellFDD/UeMeasControl" {
    list PmUeMeasControl {
      description "Additional definitions from MOM:min/max-elements:0/1; This managed object contains the settings for PM Initiated UE Measurements.";
      key "pmUeMeasControlId";
      leaf pmUeMeasControlId {
        type leafref {
          path "../attributes/pmUeMeasControlId";
        }
      }
      container attributes {
        uses PmUeMeasControl-attributes;
      }
    }
  }

  augment "/emael:ManagedElement/ENodeBFunction/EUtranCellFDD/UeMeasControl" {
    list ReportConfigEUtraBadCovPrim {
      description "Additional definitions from MOM:min/max-elements:1/1;systemCreated; This managed object contains the Report Configuration settings for primary bad coverage UE measurements. The RDN of this MO is ReportConfigEUtraBadCovPrim=1.";
      key "reportConfigEUtraBadCovPrimId";
      leaf reportConfigEUtraBadCovPrimId {
        type leafref {
          path "../attributes/reportConfigEUtraBadCovPrimId";
        }
      }
      container attributes {
        uses ReportConfigEUtraBadCovPrim-attributes;
      }
    }
  }

  augment "/emael:ManagedElement/ENodeBFunction/EUtranCellFDD/UeMeasControl" {
    list ReportConfigEUtraBadCovSec {
      description "Additional definitions from MOM:min/max-elements:1/1;systemCreated; This managed object contains the Report Configuration settings for secondary bad coverage UE measurements. The RDN of this MO is ReportConfigEUtraBadCovSec=1.";
      key "reportConfigEUtraBadCovSecId";
      leaf reportConfigEUtraBadCovSecId {
        type leafref {
          path "../attributes/reportConfigEUtraBadCovSecId";
        }
      }
      container attributes {
        uses ReportConfigEUtraBadCovSec-attributes;
      }
    }
  }

  augment "/emael:ManagedElement/ENodeBFunction/EUtranCellFDD/UeMeasControl" {
    list ReportConfigEUtraBestCell {
      description "Additional definitions from MOM:min/max-elements:1/1;systemCreated; This managed object contains the Report Configuration settings for best cell UE measurements. The RDN of this MO is ReportConfigEUtraBestCell=1.";
      key "reportConfigEUtraBestCellId";
      leaf reportConfigEUtraBestCellId {
        type leafref {
          path "../attributes/reportConfigEUtraBestCellId";
        }
      }
      container attributes {
        uses ReportConfigEUtraBestCell-attributes;
      }
    }
  }

  augment "/emael:ManagedElement/ENodeBFunction/EUtranCellFDD/UeMeasControl" {
    list ReportConfigEUtraIntraFreqPm {
      description "Additional definitions from MOM:min/max-elements:0/2; This managed object contains the Report Configuration settings for UE measurements on EUTRA intra frequencies initiated by PM.";
      key "reportConfigEUtraIntraFreqPmId";
      leaf reportConfigEUtraIntraFreqPmId {
        type leafref {
          path "../attributes/reportConfigEUtraIntraFreqPmId";
        }
      }
      container attributes {
        uses ReportConfigEUtraIntraFreqPm-attributes;
      }
    }
  }

  augment "/emael:ManagedElement/ENodeBFunction/EUtranCellFDD/UeMeasControl" {
    list ReportConfigA1Prim {
      description "Additional definitions from MOM:min/max-elements:1/1;systemCreated; This managed object contains report configuration settings for the primary A1 event measurements. The A1 event is used to detect the Bad Coverage Cease condition. Primary and secondary reporting configuration MOs refer to the option to use different settings for two simultaneous measurements for the event A1. The RDN of this MO is ReportConfigA1Prim=1.";
      key "reportConfigA1PrimId";
      leaf reportConfigA1PrimId {
        type leafref {
          path "../attributes/reportConfigA1PrimId";
        }
      }
      container attributes {
        uses ReportConfigA1Prim-attributes;
      }
    }
  }

  augment "/emael:ManagedElement/ENodeBFunction/EUtranCellFDD/UeMeasControl" {
    list ReportConfigA1Sec {
      description "Additional definitions from MOM:min/max-elements:1/1;systemCreated; This managed object contains report configuration settings for the secondary A1 event measurements. The A1 event is used to the detect traffic-related Bad Coverage Cease condition. Primary and secondary reporting configuration MOs refer to the option to use different settings for two simultaneous measurements for the event A1. The RDN of this MO is ReportConfigA1Sec=1.";
      key "reportConfigA1SecId";
      leaf reportConfigA1SecId {
        type leafref {
          path "../attributes/reportConfigA1SecId";
        }
      }
      container attributes {
        uses ReportConfigA1Sec-attributes;
      }
    }
  }

  augment "/emael:ManagedElement/ENodeBFunction/EUtranCellFDD/UeMeasControl" {
    list ReportConfigA5 {
      description "Additional definitions from MOM:min/max-elements:1/1;systemCreated; This managed object contains report configuration settings for the A5 event measurements. The A5 event is used to detect when serving cell becomes worse than threshold1, and neighbor cell becomes better than threshold2. The actual threshold values used can be adjusted by frequency relation related offsets if the feature Multi-Layer Service-Triggered Mobility (MLSTM) is enabled. The RDN of this MO is ReportConfigA5=1.";
      key "reportConfigA5Id";
      leaf reportConfigA5Id {
        type leafref {
          path "../attributes/reportConfigA5Id";
        }
      }
      container attributes {
        uses ReportConfigA5-attributes;
      }
    }
  }

  augment "/emael:ManagedElement/ENodeBFunction/EUtranCellFDD/UeMeasControl" {
    list ReportConfigB2Utra {
      description "Additional definitions from MOM:min/max-elements:1/1;systemCreated; This managed object contains report configuration settings for the B2 event for UTRA measurements. The B2 event is used to detect when a UTRAN cell becomes better than threshold2, and serving cell becomes worse than threshold1. The actual threshold values used can be adjusted by frequency relation related offsets if the feature Multi-Layer Service-Triggered Mobility (MLSTM) is enabled. The RDN of this MO is ReportConfigB2Utra=1.";
      key "reportConfigB2UtraId";
      leaf reportConfigB2UtraId {
        type leafref {
          path "../attributes/reportConfigB2UtraId";
        }
      }
      container attributes {
        uses ReportConfigB2Utra-attributes;
      }
    }
  }

  augment "/emael:ManagedElement/ENodeBFunction/EUtranCellFDD/UeMeasControl" {
    list ReportConfigB2Geran {
      description "Additional definitions from MOM:min/max-elements:1/1;systemCreated; This managed object contains report configuration settings for the B2 event for GERAN measurements. The B2 event is used to detect when a GERAN cell becomes better than threshold2, and serving cell becomes worse than threshold1. The actual threshold values used can be adjusted by frequency relation related offsets if the feature Multi-Layer Service-Triggered Mobility (MLSTM) is enabled. The RDN of this MO is ReportConfigB2Geran=1.";
      key "reportConfigB2GeranId";
      leaf reportConfigB2GeranId {
        type leafref {
          path "../attributes/reportConfigB2GeranId";
        }
      }
      container attributes {
        uses ReportConfigB2Geran-attributes;
      }
    }
  }

  augment "/emael:ManagedElement/ENodeBFunction/EUtranCellFDD/UeMeasControl" {
    list ReportConfigB2Cdma2000 {
      description "Additional definitions from MOM:min/max-elements:1/1;systemCreated; This managed object contains report configuration settings for the B2 event for CDMA2000 measurements. The B2 event is used to detect when a CDMA2000 cell becomes better than threshold2, and serving cell becomes worse than threshold1. The actual threshold values used can be adjusted by frequency relation related offsets if the feature Multi-Layer Service-Triggered Mobility (MLSTM) is enabled. The RDN of this MO is ReportConfigB2Cdma2000=1.";
      key "reportConfigB2Cdma2000Id";
      leaf reportConfigB2Cdma2000Id {
        type leafref {
          path "../attributes/reportConfigB2Cdma2000Id";
        }
      }
      container attributes {
        uses ReportConfigB2Cdma2000-attributes;
      }
    }
  }

  augment "/emael:ManagedElement/ENodeBFunction/EUtranCellFDD/UeMeasControl" {
    list ReportConfigA4 {
      description "Additional definitions from MOM:min/max-elements:1/1;systemCreated; This managed object contains report configuration settings for the A4 event measurements. The A4 event is used to detect when neighbor cell becomes better than threshold. The RDN of this MO is ReportConfigA4=1.";
      key "reportConfigA4Id";
      leaf reportConfigA4Id {
        type leafref {
          path "../attributes/reportConfigA4Id";
        }
      }
      container attributes {
        uses ReportConfigA4-attributes;
      }
    }
  }

  augment "/emael:ManagedElement/ENodeBFunction/EUtranCellFDD/UeMeasControl" {
    list ReportConfigB1Geran {
      description "Additional definitions from MOM:min/max-elements:1/1;systemCreated; This managed object contains report configuration settings for the B1 event for GERAN measurements. The B1 event is used to detect when a GERAN cell becomes better than threshold. The RDN of this MO is ReportConfigB1Geran=1.";
      key "reportConfigB1GeranId";
      leaf reportConfigB1GeranId {
        type leafref {
          path "../attributes/reportConfigB1GeranId";
        }
      }
      container attributes {
        uses ReportConfigB1Geran-attributes;
      }
    }
  }

  augment "/emael:ManagedElement/ENodeBFunction/EUtranCellFDD/UeMeasControl" {
    list ReportConfigB1Utra {
      description "Additional definitions from MOM:min/max-elements:1/1;systemCreated; This managed object contains report configuration settings for the B1 event for WCDMA measurements. The B1 event is used to detect when a WCDMA cell becomes better than threshold. The RDN of this MO is ReportConfigB1Utra=1.";
      key "reportConfigB1UtraId";
      leaf reportConfigB1UtraId {
        type leafref {
          path "../attributes/reportConfigB1UtraId";
        }
      }
      container attributes {
        uses ReportConfigB1Utra-attributes;
      }
    }
  }

  augment "/emael:ManagedElement/ENodeBFunction/EUtranCellFDD/UeMeasControl" {
    list ReportConfigEUtraInterFreqLb {
      description "Additional definitions from MOM:min/max-elements:1/1;systemCreated; Contains the Report Configuration settings for UE measurements initiated for EUTRA Inter-frequency Load Balancing. The RDN of this MO is ReportConfigEUtraInterFreqLb=1.";
      key "reportConfigEUtraInterFreqLbId";
      leaf reportConfigEUtraInterFreqLbId {
        type leafref {
          path "../attributes/reportConfigEUtraInterFreqLbId";
        }
      }
      container attributes {
        uses ReportConfigEUtraInterFreqLb-attributes;
      }
    }
  }

  augment "/emael:ManagedElement/ENodeBFunction/EUtranCellFDD/UeMeasControl" {
    list ReportConfigEUtraIFBestCell {
      description "Additional definitions from MOM:min/max-elements:1/1;systemCreated; This managed object contains the report configuration settings for best cell measurements on other LTE frequencies. The RDN of this MO is ReportConfigEUtraIFBestCell=1.";
      key "reportConfigEUtraIFBestCellId";
      leaf reportConfigEUtraIFBestCellId {
        type leafref {
          path "../attributes/reportConfigEUtraIFBestCellId";
        }
      }
      container attributes {
        uses ReportConfigEUtraIFBestCell-attributes;
      }
    }
  }

  augment "/emael:ManagedElement/ENodeBFunction/EUtranCellFDD/UeMeasControl" {
    list ReportConfigSearch {
      description "Additional definitions from MOM:min/max-elements:1/1;systemCreated; Contains report configuration settings for search area measurements that relate to features Mobility Control at Poor Coverage and Multi-Layer Service-Triggered Mobility (MLSTM). Corresponds to parameters needed for A2search, A1Search, A2OuterSearch and A2Critical events and QCI specific offsets to such parameters. The RDN of this MO is ReportConfigSearch=1.";
      key "reportConfigSearchId";
      leaf reportConfigSearchId {
        type leafref {
          path "../attributes/reportConfigSearchId";
        }
      }
      container attributes {
        uses ReportConfigSearch-attributes;
      }
    }
  }

  augment "/emael:ManagedElement/ENodeBFunction/EUtranCellFDD/UeMeasControl" {
    list ReportConfigInterRatLb {
      description "Additional definitions from MOM:min/max-elements:1/1;systemCreated; The MO contains the report configuration settings for UE measurements that are initiated for Inter-RAT load balancing actions. The RDN of this MO is ReportConfigInterRatLb=1.";
      key "reportConfigInterRatLbId";
      leaf reportConfigInterRatLbId {
        type leafref {
          path "../attributes/reportConfigInterRatLbId";
        }
      }
      container attributes {
        uses ReportConfigInterRatLb-attributes;
      }
    }
  }

  augment "/emael:ManagedElement/ENodeBFunction/EUtranCellFDD/UeMeasControl" {
    list ReportConfigCsfbCdma2000 {
      description "Additional definitions from MOM:min/max-elements:1/1;systemCreated; The MO contains report configuration settings for the B1 or B2 event for CDMA2000 1xRTT measurements, used when searching for a suitable target cell when CS Fallback is triggered for the UE. The RDN of this MO is ReportConfigCsfbCdma2000=1.";
      key "reportConfigCsfbCdma2000Id";
      leaf reportConfigCsfbCdma2000Id {
        type leafref {
          path "../attributes/reportConfigCsfbCdma2000Id";
        }
      }
      container attributes {
        uses ReportConfigCsfbCdma2000-attributes;
      }
    }
  }

  augment "/emael:ManagedElement/ENodeBFunction/EUtranCellFDD/UeMeasControl" {
    list ReportConfigEUtraInterFreqMbms {
      description "Additional definitions from MOM:min/max-elements:1/1;systemCreated; Contains the Report Configuration settings for UE measurements initiated for EUTRA Inter-frequency MBMS Interest. The RDN of this MO is ReportConfigEUtraInterFreqMbms=1.";
      key "reportConfigEUtraInterFreqMbmsId";
      leaf reportConfigEUtraInterFreqMbmsId {
        type leafref {
          path "../attributes/reportConfigEUtraInterFreqMbmsId";
        }
      }
      container attributes {
        uses ReportConfigEUtraInterFreqMbms-attributes;
      }
    }
  }

  augment "/emael:ManagedElement/ENodeBFunction/EUtranCellFDD/UeMeasControl" {
    list ReportConfigSCellA6 {
      description "Additional definitions from MOM:min/max-elements:1/1;systemCreated; This managed object contains the report configuration settings for A6 measurements on the frequency of any serving SCell when this cell is used as PCell. The RDN of this MO is ReportConfigSCellA6=1.";
      key "reportConfigSCellA6Id";
      leaf reportConfigSCellA6Id {
        type leafref {
          path "../attributes/reportConfigSCellA6Id";
        }
      }
      container attributes {
        uses ReportConfigSCellA6-attributes;
      }
    }
  }

  augment "/emael:ManagedElement/ENodeBFunction/EUtranCellFDD/UeMeasControl" {
    list ReportConfigSCellA1A2 {
      description "Additional definitions from MOM:min/max-elements:1/1;systemCreated; This managed object contains the report configuration settings for A2/A1 measurements on the frequency of any serving SCell when this cell is used as PCell. The RDN of this MO is ReportConfigSCellA1A2=1.";
      key "reportConfigSCellA1A2Id";
      leaf reportConfigSCellA1A2Id {
        type leafref {
          path "../attributes/reportConfigSCellA1A2Id";
        }
      }
      container attributes {
        uses ReportConfigSCellA1A2-attributes;
      }
    }
  }

  augment "/emael:ManagedElement/ENodeBFunction/EUtranCellFDD/UeMeasControl" {
    list ReportConfigSCellA4 {
      description "Additional definitions from MOM:min/max-elements:1/1;systemCreated; This managed object contains the report configuration settings for A4 measurements on the frequency of any non-serving SCell candidate when this cell is used as PCell. Note: This MO class is valid only for FDD cells. The RDN of this MO is ReportConfigSCellA4=1.";
      key "reportConfigSCellA4Id";
      leaf reportConfigSCellA4Id {
        type leafref {
          path "../attributes/reportConfigSCellA4Id";
        }
      }
      container attributes {
        uses ReportConfigSCellA4-attributes;
      }
    }
  }

  augment "/emael:ManagedElement/ENodeBFunction/EUtranCellFDD/UeMeasControl" {
    list ReportConfigCsfbUtra {
      description "Additional definitions from MOM:min/max-elements:1/1;systemCreated; Contains report configuration settings for the B1 or B2 event for UTRA measurements, used when searching for a suitable target cell when CS Fallback is triggered for the UE. The RDN of this MO is ReportConfigCsfbUtra=1.";
      key "reportConfigCsfbUtraId";
      leaf reportConfigCsfbUtraId {
        type leafref {
          path "../attributes/reportConfigCsfbUtraId";
        }
      }
      container attributes {
        uses ReportConfigCsfbUtra-attributes;
      }
    }
  }

  augment "/emael:ManagedElement/ENodeBFunction/EUtranCellFDD/UeMeasControl" {
    list ReportConfigCsfbGeran {
      description "Additional definitions from MOM:min/max-elements:1/1;systemCreated; Contains report configuration settings for the B1 or B2 event for GERAN measurements, used when searching for a suitable target cell when CS Fallback is triggered for the UE. The RDN of this MO is ReportConfigCsfbGeran=1.";
      key "reportConfigCsfbGeranId";
      leaf reportConfigCsfbGeranId {
        type leafref {
          path "../attributes/reportConfigCsfbGeranId";
        }
      }
      container attributes {
        uses ReportConfigCsfbGeran-attributes;
      }
    }
  }

  augment "/emael:ManagedElement/ENodeBFunction/EUtranCellFDD/UeMeasControl" {
    list ReportConfigB2Cdma20001xRtt {
      description "Additional definitions from MOM:min/max-elements:1/1;systemCreated; This managed object contains report configuration settings for the B2 event for CDMA2000 1xRTT measurements, used when searching for a suitable target cell when SRVCC is triggered for the UE. The B2 event is used to detect when a CDMA2000 1xRTT cell becomes better than threshold2, and serving cell becomes worse than threshold1. The actual threshold values used can be adjusted by frequency relation related offsets if the feature Multi-Layer Service-Triggered Mobility (MLSTM) is enabled. The RDN of this MO is ReportConfigB2Cdma20001xRtt=1.";
      key "reportConfigB2Cdma20001xRttId";
      leaf reportConfigB2Cdma20001xRttId {
        type leafref {
          path "../attributes/reportConfigB2Cdma20001xRttId";
        }
      }
      container attributes {
        uses ReportConfigB2Cdma20001xRtt-attributes;
      }
    }
  }

  augment "/emael:ManagedElement/ENodeBFunction/EUtranCellFDD/UeMeasControl" {
    list ReportConfigA5DlComp {
      description "Additional definitions from MOM:min/max-elements:1/1;systemCreated; This MO contains report configuration settings for the A5 event measurements that assist Downlink Coordinated Multi-Point. The A5 event is used to detect when serving cell becomes worse than threshold1, and neighbor cell becomes better than threshold2. The RDN of this MO is ReportConfigA5DlComp=1.";
      key "reportConfigA5DlCompId";
      leaf reportConfigA5DlCompId {
        type leafref {
          path "../attributes/reportConfigA5DlCompId";
        }
      }
      container attributes {
        uses ReportConfigA5DlComp-attributes;
      }
    }
  }

  augment "/emael:ManagedElement/ENodeBFunction/EUtranCellFDD/UeMeasControl" {
    list ReportConfigA5SoftLock {
      description "Additional definitions from MOM:min/max-elements:1/1;systemCreated; Contains the Report Configuration settings for the A5 event measurements initiated for Soft-Lock of Cell. The RDN of this MO is ReportConfigA5SoftLock=1.";
      key "reportConfigA5SoftLockId";
      leaf reportConfigA5SoftLockId {
        type leafref {
          path "../attributes/reportConfigA5SoftLockId";
        }
      }
      container attributes {
        uses ReportConfigA5SoftLock-attributes;
      }
    }
  }

  augment "/emael:ManagedElement/ENodeBFunction/EUtranCellFDD/UeMeasControl" {
    list ReportConfigEUtraIFA3UlTrig {
      description "Additional definitions from MOM:min/max-elements:1/1;systemCreated; Contains report configuration settings for the A3 event for inter-frequency LTE measurements initiated by Uplink-Triggered Inter-Frequency Mobility. The RDN of this MO is ReportConfigEUtraIFA3UlTrig=1.";
      key "reportConfigEUtraIFA3UlTrigId";
      leaf reportConfigEUtraIFA3UlTrigId {
        type leafref {
          path "../attributes/reportConfigEUtraIFA3UlTrigId";
        }
      }
      container attributes {
        uses ReportConfigEUtraIFA3UlTrig-attributes;
      }
    }
  }

  augment "/emael:ManagedElement/ENodeBFunction/EUtranCellFDD/UeMeasControl" {
    list ReportConfigA5UlTrig {
      description "Additional definitions from MOM:min/max-elements:1/1;systemCreated; Contains report configuration settings for the A5 event for inter-frequency LTE measurements initiated by Uplink-Triggered Inter-Frequency Mobility. The actual threshold values used can be adjusted by frequency relation or QCI related offsets if the feature Multi-Layer Service-Triggered Mobility (MLSTM) is enabled. The RDN of this MO is ReportConfigA5UlTrig=1.";
      key "reportConfigA5UlTrigId";
      leaf reportConfigA5UlTrigId {
        type leafref {
          path "../attributes/reportConfigA5UlTrigId";
        }
      }
      container attributes {
        uses ReportConfigA5UlTrig-attributes;
      }
    }
  }

  augment "/emael:ManagedElement/ENodeBFunction/EUtranCellFDD/UeMeasControl" {
    list ReportConfigB2UtraUlTrig {
      description "Additional definitions from MOM:min/max-elements:1/1;systemCreated; Contains report configuration settings for the B2 event for UTRA measurements initiated by Uplink-Triggered Inter-Frequency Mobility. The actual threshold values used can be adjusted by frequency relation or QCI related offsets if the feature Multi-Layer Service-Triggered Mobility (MLSTM) is enabled. The RDN of this MO is ReportConfigB2UtraUlTrig=1.";
      key "reportConfigB2UtraUlTrigId";
      leaf reportConfigB2UtraUlTrigId {
        type leafref {
          path "../attributes/reportConfigB2UtraUlTrigId";
        }
      }
      container attributes {
        uses ReportConfigB2UtraUlTrig-attributes;
      }
    }
  }

  augment "/emael:ManagedElement/ENodeBFunction/EUtranCellFDD/UeMeasControl" {
    list ReportConfigB2GeranUlTrig {
      description "Additional definitions from MOM:min/max-elements:1/1;systemCreated; Contains report configuration settings for the B2 event for GERAN measurements initiated by Uplink-Triggered Inter-Frequency Mobility. The actual threshold values used can be adjusted by frequency relation or QCI related offsets if the feature Multi-Layer Service-Triggered Mobility (MLSTM) is enabled. The RDN of this MO is ReportConfigB2GeranUlTrig=1.";
      key "reportConfigB2GeranUlTrigId";
      leaf reportConfigB2GeranUlTrigId {
        type leafref {
          path "../attributes/reportConfigB2GeranUlTrigId";
        }
      }
      container attributes {
        uses ReportConfigB2GeranUlTrig-attributes;
      }
    }
  }

  augment "/emael:ManagedElement/ENodeBFunction/EUtranCellFDD/UeMeasControl" {
    list ReportConfigB2CdmaUlTrig {
      description "Additional definitions from MOM:min/max-elements:1/1;systemCreated; Contains report configuration settings for the B2 event for CDMA2000 measurements initiated by Uplink-Triggered Inter-Frequency Mobility. The actual threshold values used can be adjusted by frequency relation or QCI related offsets if the feature Multi-Layer Service-Triggered Mobility (MLSTM) is enabled. The RDN of this MO is ReportConfigB2CdmaUlTrig=1.";
      key "reportConfigB2CdmaUlTrigId";
      status deprecated;
      leaf reportConfigB2CdmaUlTrigId {
        type leafref {
          path "../attributes/reportConfigB2CdmaUlTrigId";
        }
        status deprecated;
      }
      container attributes {
        uses ReportConfigB2CdmaUlTrig-attributes;
      }
    }
  }

  augment "/emael:ManagedElement/ENodeBFunction/EUtranCellFDD/UeMeasControl" {
    list ReportConfigB2CdmaRttUlTrig {
      description "Additional definitions from MOM:min/max-elements:1/1;systemCreated; Contains report configuration settings for the B2 event for CDMA2000 1xRTT measurements initiated by Uplink-Triggered Inter-Frequency Mobility. The actual threshold values used can be adjusted by frequency relation or QCI related offsets if the feature Multi-Layer Service-Triggered Mobility (MLSTM) is enabled. The RDN of this MO is ReportConfigB2CdmaRttUlTrig=1.";
      key "reportConfigB2CdmaRttUlTrigId";
      status deprecated;
      leaf reportConfigB2CdmaRttUlTrigId {
        type leafref {
          path "../attributes/reportConfigB2CdmaRttUlTrigId";
        }
        status deprecated;
      }
      container attributes {
        uses ReportConfigB2CdmaRttUlTrig-attributes;
      }
    }
  }

  augment "/emael:ManagedElement/ENodeBFunction/EUtranCellFDD/UeMeasControl" {
    list ReportConfigCsg {
      description "Additional definitions from MOM:min/max-elements:1/1;systemCreated; Report configuration setting for A5 measurement that assists UE to redirect another EUTRA Inter-frequency. Used for feature Mobility to CSG Cells. The RDN of this MO is ReportConfigCsg=1.";
      key "reportConfigCsgId";
      leaf reportConfigCsgId {
        type leafref {
          path "../attributes/reportConfigCsgId";
        }
      }
      container attributes {
        uses ReportConfigCsg-attributes;
      }
    }
  }

  augment "/emael:ManagedElement/ENodeBFunction/EUtranCellFDD/UeMeasControl" {
    list ReportConfigEUtraInterFreqPm {
      description "Additional definitions from MOM:min/max-elements:0/2; Contains Report Configuration settings for UE measurements on EUTRAN inter-frequencies initiated by PM.";
      key "reportConfigEUtraInterFreqPmId";
      leaf reportConfigEUtraInterFreqPmId {
        type leafref {
          path "../attributes/reportConfigEUtraInterFreqPmId";
        }
      }
      container attributes {
        uses ReportConfigEUtraInterFreqPm-attributes;
      }
    }
  }

  augment "/emael:ManagedElement/ENodeBFunction/EUtranCellFDD/UeMeasControl" {
    list ReportConfigInterRatPm {
      description "Additional definitions from MOM:min/max-elements:0/2; Contains Report Configuration settings for UE measurements on inter-Rat (GERAN or UTRAN) frequencies initiated by PM.";
      key "reportConfigInterRatPmId";
      leaf reportConfigInterRatPmId {
        type leafref {
          path "../attributes/reportConfigInterRatPmId";
        }
      }
      container attributes {
        uses ReportConfigInterRatPm-attributes;
      }
    }
  }

  augment "/emael:ManagedElement/ENodeBFunction/EUtranCellFDD/UeMeasControl" {
    list ReportConfigElcA1A2 {
      description "Additional definitions from MOM:min/max-elements:1/1;systemCreated; Contains the report configuration settings for A1/A2 measurements initiated by Ericsson Lean Carrier. The RDN of this MO is ReportConfigElcA1A2=1.";
      key "reportConfigElcA1A2Id";
      leaf reportConfigElcA1A2Id {
        type leafref {
          path "../attributes/reportConfigElcA1A2Id";
        }
      }
      container attributes {
        uses ReportConfigElcA1A2-attributes;
      }
    }
  }

  augment "/emael:ManagedElement/ENodeBFunction/EUtranCellFDD/UeMeasControl" {
    list ReportConfigInterEnbUlComp {
      description "Additional definitions from MOM:min/max-elements:1/1;systemCreated; Contains the Report Configuration settings for UE measurements initiated for Inter-eNB UL CoMP. The RDN of this MO is ReportConfigInterEnbUlComp=1.";
      key "reportConfigInterEnbUlCompId";
      leaf reportConfigInterEnbUlCompId {
        type leafref {
          path "../attributes/reportConfigInterEnbUlCompId";
        }
      }
      container attributes {
        uses ReportConfigInterEnbUlComp-attributes;
      }
    }
  }

  augment "/emael:ManagedElement/ENodeBFunction/EUtranCellFDD/UeMeasControl" {
    list ReportConfigB1GUtra {
      description "Additional definitions from MOM:min/max-elements:1/1;systemCreated; Default configuration settings for event B1 NR measurement for ENDC purposes. The RDN of this MO is ReportConfigB1GUtra=1.";
      key "reportConfigB1GUtraId";
      leaf reportConfigB1GUtraId {
        type leafref {
          path "../attributes/reportConfigB1GUtraId";
        }
      }
      container attributes {
        uses ReportConfigB1GUtra-attributes;
      }
    }
  }

  augment "/emael:ManagedElement/ENodeBFunction/EUtranCellFDD/UeMeasControl" {
    list ReportConfigA1A2Br {
      description "Additional definitions from MOM:min/max-elements:1/1;systemCreated; Contains report configuration settings for A1/A2 measurements for CAT-M UE. The RDN of this MO is ReportConfigA1A2Br=1.";
      key "reportConfigA1A2BrId";
      leaf reportConfigA1A2BrId {
        type leafref {
          path "../attributes/reportConfigA1A2BrId";
        }
      }
      container attributes {
        uses ReportConfigA1A2Br-attributes;
      }
    }
  }

  augment "/emael:ManagedElement/ENodeBFunction/EUtranCellFDD/UeMeasControl" {
    list ReportConfigB1NR {
      description "Additional definitions from MOM:min/max-elements:1/1;systemCreated; Default configuration settings for event B1 NR measurement. The RDN of this MO is ReportConfigB1NR=1.";
      key "reportConfigB1NRId";
      leaf reportConfigB1NRId {
        type leafref {
          path "../attributes/reportConfigB1NRId";
        }
      }
      container attributes {
        uses ReportConfigB1NR-attributes;
      }
    }
  }

  augment "/emael:ManagedElement/ENodeBFunction/EUtranCellFDD/UeMeasControl" {
    list ReportConfigA5UlTraffic {
      description "Additional definitions from MOM:min/max-elements:1/1;systemCreated; Report configuration settings for A5 event for inter-frequency LTE measurements initiated by Uplink-Traffic-Triggered Mobility. The RDN of this MO is ReportConfigA5UlTraffic = 1.";
      key "reportConfigA5UlTrafficId";
      leaf reportConfigA5UlTrafficId {
        type leafref {
          path "../attributes/reportConfigA5UlTrafficId";
        }
      }
      container attributes {
        uses ReportConfigA5UlTraffic-attributes;
      }
    }
  }

  augment "/emael:ManagedElement/ENodeBFunction/EUtranCellFDD/UeMeasControl" {
    list ReportConfigA5EndcHo {
      description "Additional definitions from MOM:min/max-elements:1/1;systemCreated; Report configuration settings for event A5 measurements initiated for EN-DC Triggered Handover during Setup. The RDN of this MO is ReportConfigA5EndcHo=1.";
      key "reportConfigA5EndcHoId";
      leaf reportConfigA5EndcHoId {
        type leafref {
          path "../attributes/reportConfigA5EndcHoId";
        }
      }
      container attributes {
        uses ReportConfigA5EndcHo-attributes;
      }
    }
  }

  augment "/emael:ManagedElement/ENodeBFunction/EUtranCellFDD/UeMeasControl" {
    list ReportConfigErabSetup {
      description "Additional definitions from MOM:min/max-elements:1/1;systemCreated; Contains report configuration settings for uplink quality measurements that relate to Coverage-Triggered Mobility at Setup feature. Corresponds to parameters needed for A1 UL SINR, A2 UL SINR, A1 UL pathloss, and A2 UL pathloss measurement events. The RDN of this MO is ReportConfigErabSetup=1.";
      key "reportConfigErabSetupId";
      leaf reportConfigErabSetupId {
        type leafref {
          path "../attributes/reportConfigErabSetupId";
        }
      }
      container attributes {
        uses ReportConfigErabSetup-attributes;
      }
    }
  }

  augment "/emael:ManagedElement/ENodeBFunction/EUtranCellFDD/UeMeasControl" {
    list ReportConfigA1A2Endc {
      description "Additional definitions from MOM:min/max-elements:1/1;systemCreated; Report configuration settings for Event A1 and A2 measurement offset initiated by Differentiate A2 Threshold function for EN-DC-capable UEs. The RDN of this MO is ReportConfigA1A2Endc=1.";
      key "reportConfigA1A2EndcId";
      leaf reportConfigA1A2EndcId {
        type leafref {
          path "../attributes/reportConfigA1A2EndcId";
        }
      }
      container attributes {
        uses ReportConfigA1A2Endc-attributes;
      }
    }
  }

  augment "/emael:ManagedElement/ENodeBFunction/EUtranCellFDD/UeMeasControl" {
    list ReportConfigA5Spifho {
      description "Additional definitions from MOM:min/max-elements:1/1;systemCreated; Service or Priority-Triggered Inter-Frequency Handover report configuration settings for A5. The RDN of this MO is ReportConfigA5Spifho=1.";
      key "reportConfigA5SpifhoId";
      leaf reportConfigA5SpifhoId {
        type leafref {
          path "../attributes/reportConfigA5SpifhoId";
        }
      }
      container attributes {
        uses ReportConfigA5Spifho-attributes;
      }
    }
  }

  augment "/emael:ManagedElement/ENodeBFunction/EUtranCellFDD/UeMeasControl" {
    list SecPmUeMeasControl {
      description "Additional definitions from MOM:min/max-elements:0/1; Settings for Security-Initiated UE Measurements feature.";
      key "secPmUeMeasControlId";
      leaf secPmUeMeasControlId {
        type leafref {
          path "../attributes/secPmUeMeasControlId";
        }
      }
      container attributes {
        uses SecPmUeMeasControl-attributes;
      }
    }
  }

  augment "/emael:ManagedElement/ENodeBFunction/EUtranCellFDD/UeMeasControl" {
    list ReportConfigEUtraInterFreqSec {
      description "Additional definitions from MOM:min/max-elements:0/1; Report configuration settings for inter-frequency UE measurements. Applicable for E-UTRAN inter-frequency measurements initiated by Security-Initiated UE Measurements feature.";
      key "reportConfigEUtraInterFreqSecId";
      leaf reportConfigEUtraInterFreqSecId {
        type leafref {
          path "../attributes/reportConfigEUtraInterFreqSecId";
        }
      }
      container attributes {
        uses ReportConfigEUtraInterFreqSec-attributes;
      }
    }
  }

  augment "/emael:ManagedElement/ENodeBFunction/EUtranCellFDD/UeMeasControl" {
    list ReportConfigEUtraIntraFreqSec {
      description "Additional definitions from MOM:min/max-elements:0/1; Report configuration settings for intra-frequency UE measurements. Applicable for E-UTRAN intra-frequency measurements initiated by Security-Initiated UE Measurements feature.";
      key "reportConfigEUtraIntraFreqSecId";
      leaf reportConfigEUtraIntraFreqSecId {
        type leafref {
          path "../attributes/reportConfigEUtraIntraFreqSecId";
        }
      }
      container attributes {
        uses ReportConfigEUtraIntraFreqSec-attributes;
      }
    }
  }

  augment "/emael:ManagedElement/ENodeBFunction/EUtranCellFDD/UeMeasControl" {
    list ReportConfigInterRatSec {
      description "Additional definitions from MOM:min/max-elements:0/1; Report Configuration settings for inter-RAT UE measurements. Applicable for GERAN or UTRAN inter-RAT frequency measurements initiated by Security-Initiated UE Measurements feature.";
      key "reportConfigInterRatSecId";
      leaf reportConfigInterRatSecId {
        type leafref {
          path "../attributes/reportConfigInterRatSecId";
        }
      }
      container attributes {
        uses ReportConfigInterRatSec-attributes;
      }
    }
  }

  augment "/emael:ManagedElement/ENodeBFunction/EUtranCellFDD/UeMeasControl" {
    list ReportConfigA5UlVolte {
      description "Additional definitions from MOM:min/max-elements:1/1;systemCreated; Configuration settings for event A5 for inter-frequency LTE measurements. Event A5 is initiated by Uplink-Triggered VoLTE Mobility feature or Downlink-Triggered VoLTE Mobility feature. RDN of MO is ReportConfigA5UlVolte=1.";
      key "reportConfigA5UlVolteId";
      leaf reportConfigA5UlVolteId {
        type leafref {
          path "../attributes/reportConfigA5UlVolteId";
        }
      }
      container attributes {
        uses ReportConfigA5UlVolte-attributes;
      }
    }
  }

  augment "/emael:ManagedElement/ENodeBFunction/EUtranCellFDD/UeMeasControl" {
    list ReportConfigB2NR {
      description "Additional definitions from MOM:min/max-elements:1/1;systemCreated; Default configuration settings for event B2 for NR measurements. Event B2 for NR measurements are used to detect when serving cell becomes worse than threshold 1 and GUTRAN cell becomes better than threshold 2. The RDN of this MO is ReportConfigB2NR=1.";
      key "reportConfigB2NRId";
      leaf reportConfigB2NRId {
        type leafref {
          path "../attributes/reportConfigB2NRId";
        }
      }
      container attributes {
        uses ReportConfigB2NR-attributes;
      }
    }
  }

  augment "/emael:ManagedElement/ENodeBFunction/EUtranCellFDD/UeMeasControl" {
    list ReportConfigA5InterFreqHigherPrio {
      description "Additional definitions from MOM:min/max-elements:1/1;systemCreated; A5 report configuration settings for LTE Inter-Frequency Handover to Higher Priority feature. The RDN of this MO must be ReportConfigA5InterFreqHigherPrio=1.";
      key "reportConfigA5InterFreqHigherPrioId";
      leaf reportConfigA5InterFreqHigherPrioId {
        type leafref {
          path "../attributes/reportConfigA5InterFreqHigherPrioId";
        }
      }
      container attributes {
        uses ReportConfigA5InterFreqHigherPrio-attributes;
      }
    }
  }

  augment "/emael:ManagedElement/ENodeBFunction/EUtranCellFDD/UeMeasControl" {
    list ReportConfigA1A2HigherPrio {
      description "Additional definitions from MOM:min/max-elements:1/1;systemCreated; A1 and A2 report configuration settings for LTE Inter-Frequency Handover to Higher Priority. The RDN of this MO must be ReportConfigA1A2HigherPrio=1.";
      key "reportConfigA1A2HigherPrioId";
      leaf reportConfigA1A2HigherPrioId {
        type leafref {
          path "../attributes/reportConfigA1A2HigherPrioId";
        }
      }
      container attributes {
        uses ReportConfigA1A2HigherPrio-attributes;
      }
    }
  }

  augment "/emael:ManagedElement/ENodeBFunction/UeMeasControlCommon" {
    list ReportConfigB1NRCommon {
      description "Additional definitions from MOM:min/max-elements:0/16; Event B1 NR measurement configuration settings. GUtranFreqRelation must be configured to use these settings. Otherwise, ReportConfigB1NR or ReportConfigB1GUtra in UeMeasControl in cell is used by default.";
      key "reportConfigB1NRCommonId";
      status deprecated;
      leaf reportConfigB1NRCommonId {
        type leafref {
          path "../attributes/reportConfigB1NRCommonId";
        }
        status deprecated;
      }
      container attributes {
        uses ReportConfigB1NRCommon-attributes;
      }
    }
  }

  augment "/emael:ManagedElement/ENodeBFunction/UeProfile" {
    list UeProfileFilter {
      description "Additional definitions from MOM:min/max-elements:0/16; Contains sets of filters applied to selected subset of subscribers.";
      key "ueProfileFilterId";
      leaf ueProfileFilterId {
        type leafref {
          path "../attributes/ueProfileFilterId";
        }
      }
      container attributes {
        uses UeProfileFilter-attributes;
      }
    }
  }

  augment "/emael:ManagedElement/ENodeBFunction/UeProfile" {
    list EUtraFreqRelProfileSet {
      description "Additional definitions from MOM:min/max-elements:0/16; Contains sets of parameters applied to selected subscribers for selected frequency.";
      key "eUtraFreqRelProfileSetId";
      leaf eUtraFreqRelProfileSetId {
        type leafref {
          path "../attributes/eUtraFreqRelProfileSetId";
        }
      }
      container attributes {
        uses EUtraFreqRelProfileSet-attributes;
      }
    }
  }

  augment "/emael:ManagedElement/ENodeBFunction/UeProfile" {
    list GUtraFreqRelProfileSet {
      description "Additional definitions from MOM:min/max-elements:0/16; Contains sets of parameters applied to selected subscribers for selected frequency.";
      key "gUtraFreqRelProfileSetId";
      leaf gUtraFreqRelProfileSetId {
        type leafref {
          path "../attributes/gUtraFreqRelProfileSetId";
        }
      }
      container attributes {
        uses GUtraFreqRelProfileSet-attributes;
      }
    }
  }

  augment "/emael:ManagedElement/ENodeBFunction/UtraNetwork" {
    list UtranFrequency {
      description "Additional definitions from MOM:min/max-elements:0/64; This Managed Object contains information of a specific Utran frequency.";
      key "utranFrequencyId";
      leaf utranFrequencyId {
        type leafref {
          path "../attributes/utranFrequencyId";
        }
      }
      container attributes {
        uses UtranFrequency-attributes;
      }
    }
  }

  augment "/emael:ManagedElement/ENodeBFunction/EUtranCellFDD/UtranFreqRelation" {
    list UtranCellRelation {
      description "Additional definitions from MOM:min/max-elements:0/64; This Managed Object represents a mobility relation between an EUtranCellFDD or an EUtranCellTDD and an UtranCell. It contains parameters that are specific for this relation";
      key "utranCellRelationId";
      leaf utranCellRelationId {
        type leafref {
          path "../attributes/utranCellRelationId";
        }
      }
      container attributes {
        uses UtranCellRelation-attributes;
      }
    }
  }

  augment "/emael:ManagedElement/ENodeBFunction/UtraNetwork/UtranFrequency" {
    list ExternalUtranCellFDD {
      description "Additional definitions from MOM:min/max-elements:0/392; This Managed Object contains a UTRAN cell for Frequency Division Duplex (FDD).";
      key "externalUtranCellFDDId";
      leaf externalUtranCellFDDId {
        type leafref {
          path "../attributes/externalUtranCellFDDId";
        }
      }
      container attributes {
        uses ExternalUtranCellFDD-attributes;
      }
    }
  }

  augment "/emael:ManagedElement/ENodeBFunction/UtraNetwork/UtranFrequency" {
    list ExternalUtranCellTDD {
      description "Additional definitions from MOM:min/max-elements:0/392; This Managed Object contains a UTRAN cell for TDD (Time Division Duplex).";
      key "externalUtranCellTDDId";
      leaf externalUtranCellTDDId {
        type leafref {
          path "../attributes/externalUtranCellTDDId";
        }
      }
      container attributes {
        uses ExternalUtranCellTDD-attributes;
      }
    }
  }

  augment "/emael:ManagedElement/ENodeBFunction/EUtranCellFDD/UtranTDDFreqRelation" {
    list UtranCellRelation {
      description "Additional definitions from MOM:min/max-elements:0/64; This Managed Object represents a mobility relation between an EUtranCellFDD or an EUtranCellTDD and an UtranCell. It contains parameters that are specific for this relation";
      key "utranCellRelationId";
      leaf utranCellRelationId {
        type leafref {
          path "../attributes/utranCellRelationId";
        }
      }
      container attributes {
        uses UtranCellRelation-attributes;
      }
    }
  }
  typedef AQMMode {
    type enumeration {
      enum OFF;
      enum MODE1;
      enum MODE2;
    }
  }
  typedef AbCategory {
    type enumeration {
      enum CATEGORY_A;
      enum CATEGORY_B;
      enum CATEGORY_C;
      enum OFF;
    }
  }
  typedef AbException {
    type enumeration {
      enum FALSE;
      enum TRUE;
      enum OFF;
    }
  }
  typedef AbPerNrsrp {
    type enumeration {
      enum OFF;
      enum THRESH1;
      enum THRESH2;
    }
  }
  typedef AbPresence {
    type enumeration {
      enum OFF;
      enum AUTO;
      enum MANUAL;
    }
  }
  typedef AbsPrioOverride {
    type enumeration {
      enum NO_OVERRIDE;
      enum HI_PRIO_OVERRIDE;
    }
  }
  typedef AcBarringMode {
    type enumeration {
      enum OFF;
      enum MANUAL;
      enum AUTO;
    }
  }
  typedef AcBarringModeEm {
    type enumeration {
      enum MANUAL;
      enum AUTO;
    }
  }
  typedef AcBarringPlmnPriorityLevel {
    type enumeration {
      enum PRIORITY0;
      enum PRIORITY1;
      enum PRIORITY2;
    }
  }
  typedef AcBarringPriorityLevel {
    type enumeration {
      enum PRIORITY0;
      enum PRIORITY1;
      enum PRIORITY2;
      enum PRIORITY3;
      enum PRIORITY4;
    }
  }
  typedef ActivationVals {
    type enumeration {
      enum ACTIVATED;
      enum DEACTIVATED;
    }
  }
  typedef AdaptiveCfiHoProhibitMode {
    type enumeration {
      enum NO_HO_PROHIBIT_CFI;
      enum HO_PROHIBIT_CFI_1;
      enum HO_PROHIBIT_CFI_1_AND_2;
    }
  }
  typedef AdmState {
    type enumeration {
      enum LOCKED;
      enum UNLOCKED;
      enum SHUTTINGDOWN;
    }
  }
  typedef AdvCellSupActions {
    type enumeration {
      enum NO_ACTION;
      enum CELL_RESTART;
      enum CELL_AND_NODE_RESTART;
    }
  }
  typedef AggressorNodeType {
    type enumeration {
      enum LOCAL_NODE;
      enum EXTERNAL_ENODEB;
      enum EXTERNAL_GNODEB;
    }
  }
  typedef AiAdvCellSupActions {
    type enumeration {
      enum NO_ACTION;
      enum CELL_RESTART;
    }
  }
  typedef AiAdvCellSupModelState {
    type enumeration {
      enum __UNDEFINED__;
    }
  }
  typedef AiAdvCellSupModes {
    type enumeration {
      enum OFF;
      enum OBSERVATION;
      enum NORMAL;
    }
  }
  typedef AiSrsAllocStrategy {
    type enumeration {
      enum OFF;
      enum EVENT_TRIGGER;
      enum RECURRENT;
    }
  }
  typedef AilgLoadType {
    type enumeration {
      enum PDSCH_NO_BF;
      enum PDSCH_BF_TYPE1;
      enum PDSCH_NO_BF_AND_PDCCH;
      enum PDSCH_BF_TYPE1_AND_PDCCH;
      enum PDSCH_BF_TYPE2;
      enum PDSCH_BF_TYPE2_AND_PDCCH;
      enum PDCCH_ONLY;
    }
  }
  typedef AltMmeInfo {
    type enumeration {
      enum DEFAULT_DCN;
      enum SENT_NAS_REQUEST;
    }
  }
  typedef AmoStateVals {
    type enumeration {
      enum DISABLED;
      enum ENABLED;
    }
  }
  typedef AnchorPowerBoostIndex {
    type enumeration {
      enum ANCHOR_POWER_RATIO_1_1;
      enum ANCHOR_POWER_RATIO_2_1;
      enum ANCHOR_POWER_RATIO_3_1;
      enum ANCHOR_POWER_RATIO_4_1;
    }
  }
  typedef AreaScopeType {
    type enumeration {
      enum NOT_PRESENT;
      enum TYPE_CGI;
      enum TYPE_TAC;
    }
  }
  typedef AsmSCellDetection {
    type enumeration {
      enum OFF;
      enum LOCAL;
      enum EXTERNAL;
      enum EXTERNAL_AND_LOCAL;
    }
  }
  typedef AsmSCellDlOnlyAllowed {
    type enumeration {
      enum DL_ONLY;
      enum DL_UL;
    }
  }
  typedef AsmStatus {
    type enumeration {
      enum NOT_ALLOWED;
      enum CANDIDATE;
      enum ALLOWED;
      enum ONLY_ALLOWED_FOR_DL;
    }
  }
  typedef AtoQciProfileHandling {
    type enumeration {
      enum ALLOWED;
      enum FORBIDDEN;
    }
  }
  typedef AttachWithoutPDN {
    type enumeration {
      enum OFF;
      enum CATM1;
    }
  }
  typedef AvailStatus {
    type enumeration {
      enum IN_TEST;
      enum FAILED;
      enum POWER_OFF;
      enum OFF_LINE;
      enum OFF_DUTY;
      enum DEPENDENCY;
      enum DEGRADED;
      enum NOT_INSTALLED;
      enum LOG_FULL;
      enum DEPENDENCY_LOCKED;
      enum DEPENDENCY_FAILED;
      enum DEPENDENCY_SHUTTINGDOWN;
      enum DEPENDENCY_RECOVERY;
      enum DEPENDENCY_HOLDING;
    }
  }
  typedef B46ChannelUsage {
    type enumeration {
      enum CHANNEL_DISABLED;
      enum CHANNEL_ENABLED;
    }
  }
  typedef BandIndicator {
    type enumeration {
      enum DCS_1800;
      enum PCS_1900;
    }
  }
  typedef CaBandwidthClass {
    type enumeration {
      enum CA_BANDWIDTH_CLASS_A;
      enum CA_BANDWIDTH_CLASS_B;
      enum CA_BANDWIDTH_CLASS_C;
      enum CA_BANDWIDTH_CLASS_D;
      enum CA_BANDWIDTH_CLASS_E;
      enum CA_BANDWIDTH_CLASS_F;
      enum UNDEFINED_VALUE;
    }
  }
  typedef CaOffloadingMode {
    type enumeration {
      enum DISABLED;
      enum ENABLED_LAA_SCELLS;
      enum ENABLED_SDL_SCELLS;
      enum ENABLED_SDL_AND_LAA_SCELLS;
      enum ENABLED_SELECTED_SCELLS;
    }
  }
  typedef CaPreference {
    type enumeration {
      enum NONE;
      enum DL;
      enum UL;
    }
  }
  typedef CapabilityEnquirySteps {
    type enumeration {
      enum ONE_STEP;
      enum TWO_STEP;
      enum THREE_STEP;
    }
  }
  typedef CauseCodeOffload {
    type enumeration {
      enum REDUCE_LOAD_IN_SERVING_CELL;
      enum RESOURCE_OPTIMSATION_HANDOVER;
      enum LOAD_BALANCING;
      enum TEMPORARY1;
      enum TEMPORARY2;
    }
  }
  typedef CbrsPriorityE {
    type enumeration {
      enum NORMAL;
      enum HIGH;
    }
  }
  typedef Cdma2000SysTimeVals {
    type enumeration {
      enum NONE;
      enum SYNCHRONOUS;
      enum ASYNCHRONOUS;
    }
  }
  typedef CdmaMsIdType {
    type enumeration {
      enum EMSIS_ESN;
      enum IMSI_OR_TMSI;
      enum IMSI_ESN_OR_TMSI;
    }
  }
  typedef CeLevel {
    type enumeration {
      enum CE_LEVEL_0;
      enum CE_LEVEL_1;
      enum CE_LEVEL_2;
      enum CE_LEVEL_3;
    }
  }
  typedef CeLevelNbIot {
    type enumeration {
      enum CE_0;
      enum CE_1;
      enum CE_2;
    }
  }
  typedef CellBarred {
    type enumeration {
      enum BARRED;
      enum NOT_BARRED;
    }
  }
  typedef CellCaOffsetType {
    type enumeration {
      enum AUTO;
      enum ONLY_ALLOWED_FOR_ADJACENT;
      enum NOT_ALLOWED;
    }
  }
  typedef CfiMode {
    type enumeration {
      enum CFI_STATIC_BY_BW;
      enum CFI_STATIC_1;
      enum CFI_STATIC_2;
      enum CFI_STATIC_3;
      enum CFI_AUTO_MAXIMUM_2;
      enum CFI_AUTO_MAXIMUM_3;
    }
  }
  typedef ChanQualityMode {
    type enumeration {
      enum NORMAL;
      enum COMPENSATED;
    }
  }
  typedef ChannelCharacteristicList {
    type enumeration {
      enum CHANNEL_DISABLED;
      enum CHANNEL_ENABLED;
    }
  }
  typedef ChannelSelectionType {
    type enumeration {
      enum STATIC_CHANNEL_SELECTION;
      enum DYNAMIC_CHANNEL_SELECTION;
    }
  }
  typedef CipheringAlgorithmID {
    type enumeration {
      enum EEA0;
      enum EEA1;
      enum EEA2;
      enum EEA3;
    }
  }
  typedef ConnectedModeDrxBr {
    type enumeration {
      enum DISABLED;
      enum CE_LEVEL_0;
      enum CE_LEVEL_1;
      enum CE_LEVEL_0_AND_1;
    }
  }
  typedef ConnectionPurpose {
    type enumeration {
      enum ENDC;
      enum ESS;
      enum ENDC_ESS;
    }
  }
  typedef CovCellCandidate {
    type enumeration {
      enum NOT_ALLOWED;
      enum ALLOWED;
      enum AUTO;
    }
  }
  typedef CovTrigMobErabSetupConfig {
    type enumeration {
      enum DISABLED;
      enum CSFB_TRIGGERED;
    }
  }
  typedef CreatedBy {
    type enumeration {
      enum SYSTEM;
      enum OPERATOR;
    }
  }
  typedef CreatedByEutran {
    type enumeration {
      enum ANR;
      enum X2;
      enum OPERATOR;
    }
  }
  typedef CreatedByIrat {
    type enumeration {
      enum OPERATOR;
      enum ANR;
    }
  }
  typedef CsfbTargetRat {
    type enumeration {
      enum GERAN_UTRAN;
      enum CDMA_1XRTT;
    }
  }
  typedef CsiRsConfigType8TxFDD {
    type enumeration {
      enum NZP_CSIRS;
      enum NZP_ZP_CSIRS;
    }
  }
  typedef CsiRsConfigType8TxTDD {
    type enumeration {
      enum NZP_CSIRS;
      enum NZP_ZP_CSIRS;
      enum NZP_CSIRS_TDD;
      enum NZP_ZP_CSIRS_TDD;
    }
  }
  typedef CsiRsConfigTypeFDD {
    type enumeration {
      enum NZP_CSIRS;
      enum NZP_ZP_CSIRS;
    }
  }
  typedef CsiRsConfigTypeTDD {
    type enumeration {
      enum NZP_CSIRS;
      enum NZP_ZP_CSIRS;
      enum NZP_CSIRS_TDD;
      enum NZP_ZP_CSIRS_TDD;
      enum NZP_CSIRS_RE_CFG_IDX_20_TDD;
    }
  }
  typedef CustomTriggerType {
    type enumeration {
      enum TRIGGER_NOT_USED;
      enum TRIGGER_TYPE_1;
      enum TRIGGER_TYPE_2;
      enum TRIGGER_TYPE_3;
      enum TRIGGER_TYPE_4;
      enum TRIGGER_TYPE_5;
      enum TRIGGER_TYPE_6;
      enum TRIGGER_TYPE_7;
      enum TRIGGER_TYPE_8;
      enum TRIGGER_TYPE_9;
      enum TRIGGER_TYPE_10;
    }
  }
  typedef DataModSchemes {
    type enumeration {
      enum QPSK_MOD_SCH;
      enum QAM_16_MOD_SCH;
      enum QAM_64_MOD_SCH;
    }
  }
  typedef DcnType {
    type enumeration {
      enum DEFAULT;
      enum SPECIFIC;
    }
  }
  typedef DisabledMobilityModeBackToNr {
    type enumeration {
      enum NO_RESTRICTION;
      enum CONNECTED_MODE_MOBILITY;
      enum CONNECTED_IDLE_MODE_MOBILITY;
    }
  }
  typedef Dl256QamSupport {
    type enumeration {
      enum NOT_SUPPORTED;
      enum SUPPORTED;
    }
  }
  typedef DlCalibrationMethod {
    type enumeration {
      enum NONE;
      enum INTERNAL;
    }
  }
  typedef DlCalibrationStatus {
    type enumeration {
      enum INACTIVE;
      enum CONVERGING;
      enum CALIBRATED;
      enum FAILED;
    }
  }
  typedef DlMuTransmissionMode {
    type enumeration {
      enum TRANSMISSION_MODE_8;
      enum TRANSMISSION_MODE_7;
    }
  }
  typedef DlPowerState {
    type enumeration {
      enum INVALID;
      enum STABLE;
      enum CHANGING;
    }
  }
  typedef DnsLookup {
    type enumeration {
      enum OFF;
      enum ON;
    }
  }
  typedef DrxInactivityTimer {
    type enumeration {
      enum PSF1;
      enum PSF2;
      enum PSF3;
      enum PSF4;
      enum PSF5;
      enum PSF6;
      enum PSF8;
      enum PSF10;
      enum PSF20;
      enum PSF30;
      enum PSF40;
      enum PSF50;
      enum PSF60;
      enum PSF80;
      enum PSF100;
      enum PSF200;
      enum PSF300;
      enum PSF500;
      enum PSF750;
      enum PSF1280;
      enum PSF1920;
      enum PSF2560;
      enum PSF0;
    }
  }
  typedef DrxMode {
    type enumeration {
      enum NO_OVERRIDE;
      enum DISABLE_DRX;
      enum RESERVED_FOR_FUTURE_USE;
    }
  }
  typedef DrxOperVals {
    type enumeration {
      enum DISABLED;
      enum ENABLED;
      enum ENABLED_COVERAGE_OPTIMIZED;
    }
  }
  typedef DrxRetransmissionTimer {
    type enumeration {
      enum PSF1;
      enum PSF2;
      enum PSF4;
      enum PSF6;
      enum PSF8;
      enum PSF16;
      enum PSF24;
      enum PSF33;
    }
  }
  typedef DtmSupport {
    type enumeration {
      enum NO_DTM_SUPPORT;
      enum DTM_SUPPORT;
    }
  }
  typedef DtvmUeDetect {
    type enumeration {
      enum DISABLED;
      enum MEASBASEDHO;
      enum BLINDHO;
    }
  }
  typedef DuctIntCharInfoScheme {
    type enumeration {
      enum GENERIC;
      enum EXTENDED;
      enum CELL_SPECIFIC;
    }
  }
  typedef DuctIntCrsMutingMode {
    type enumeration {
      enum NOT_MUTING;
      enum PARTIAL_MUTING;
      enum FULL_MUTING;
    }
  }
  typedef DuctIntOpMode {
    type enumeration {
      enum DISABLED;
      enum DETECTION;
      enum LOCATION;
      enum REDUCTION;
    }
  }
  typedef DynamicCellStatusOutput {
    type enumeration {
      enum UNFORMATTED_TEXT;
      enum FORMATTED_TEXT;
    }
  }
  typedef DynamicSCellSelectionMethod {
    type enumeration {
      enum ROUND_ROBIN;
      enum PRIORITIZED;
      enum PRIORITIZED_AUTOMATIC;
      enum GLOBAL_EVALUATION;
    }
  }
  typedef EScellState {
    type enumeration {
      enum DISABLED;
      enum ENABLED;
      enum NOT_APPLICABLE;
      enum ENABLED_ERAN;
      enum EANBLED_IENB;
      enum DISABLED_CELLSTATE;
      enum DISABLED_LICENSE;
      enum DISABLED_BB_COMPATABILITY;
      enum DISABLED_LINK;
      enum DISABLED_MISMATCHED_MODE;
      enum ENABLED_IENB;
      enum DISABLED_BB_COMPATIBILITY;
      enum LINK_REMOVED_BY_REMOTE_ENB;
      enum ESCELL_LIMIT_EXCEEDED;
      enum CPRI_LATENCY_EXCEEDED;
      enum VLAN_MISMATCH;
      enum TERMPOINT_TO_ENB_DISABLED;
      enum PCELL_DISABLED;
      enum ESCELL_DISABLED;
      enum MAX_PARTNERS_ON_REMOTE_ENB;
      enum MAX_PARTNERS_ON_LOCAL_ENB;
    }
  }
  typedef EUtranLbBnrPolicyVals {
    type enumeration {
      enum NOT_ALLOWED;
      enum AUTO;
      enum LB_ONLY;
      enum OFFLOAD_ONLY;
      enum IFO_AND_IFLB;
    }
  }
  typedef EUtranProbCellPolicyVals {
    type enumeration {
      enum OFF;
      enum AUTO_DETECT;
      enum AUTO_DETECT_AND_BAR;
    }
  }
  typedef EabCategory {
    type enumeration {
      enum CATEGORY_A;
      enum CATEGORY_B;
      enum CATEGORY_C;
      enum OFF;
    }
  }
  typedef EabPresence {
    type enumeration {
      enum OFF;
      enum MANUAL;
      enum AUTO;
    }
  }
  typedef EdrxUeType {
    type enumeration {
      enum LTE_CATM;
      enum LTE;
      enum CATM;
    }
  }
  typedef ElcLongDrxCycle {
    type enumeration {
      enum SF40;
      enum SF320;
    }
  }
  typedef EndcAwareImc {
    type enumeration {
      enum DEACTIVATED;
      enum MODE_1;
      enum MODE_2;
    }
  }
  typedef EndcB1MeasGapEnabledMode {
    type enumeration {
      enum NO_OVERRIDE;
      enum ENABLED;
      enum DISABLED;
    }
  }
  typedef EndcB1MeasGapMode {
    type enumeration {
      enum ENABLED;
      enum DISABLED;
      enum DISABLED_FR1;
      enum DISABLED_FR2;
    }
  }
  typedef EndcB1MeasGapOverrideMode {
    type enumeration {
      enum NO_OVERRIDE;
      enum ENABLED;
      enum DISABLED;
      enum DISABLED_FR1;
      enum DISABLED_FR2;
    }
  }
  typedef EndcCaPolicy {
    type enumeration {
      enum LTE_PREFERRED;
      enum NR_PREFERRED;
    }
  }
  typedef EndcStage {
    type enumeration {
      enum ENDC_NR_CAPABLE;
      enum ENDC_NR_MATCHED;
      enum ENDC_NR_ACTIVE;
      enum ENDC_UE_RELEASED;
    }
  }
  typedef EranExternalUlCompGroupAvail {
    type enumeration {
      enum DISABLED;
      enum ENABLED;
    }
  }
  typedef EranFeatureName {
    type enumeration {
      enum ULCOMP;
      enum DL_CA;
    }
  }
  typedef EssResourceAllocationMode {
    type enumeration {
      enum SCHED_POLICY;
      enum DEMAND_WEIGHTED_RP;
    }
  }
  typedef ExtendInactEmMode {
    type enumeration {
      enum INACTIVE;
      enum QCI1_EM;
      enum QCI1_QCI5_EM;
      enum QCI5_EM;
    }
  }
  typedef ExternalUlCompGroupAvail {
    type enumeration {
      enum DISABLED;
      enum ENABLED;
    }
  }
  typedef ExternalUlTrigHoSupport {
    type enumeration {
      enum NO_ULTRIG_HO;
      enum ULTRIG_HO_NO_UL_EVAL;
    }
  }
  typedef FeatureName {
    type enumeration {
      enum FEATURE_NAME1;
      enum FEATURE_NAME2;
      enum FEATURE_NAME3;
      enum FEATURE_NAME4;
      enum FEATURE_NAME5;
      enum FEATURE_NAME6;
      enum FEATURE_NAME7;
      enum FEATURE_NAME8;
      enum FEATURE_NAME9;
      enum FEATURE_NAME10;
      enum FEATURE_NAME11;
      enum FEATURE_NAME12;
      enum FEATURE_NAME13;
      enum FEATURE_NAME14;
      enum FEATURE_NAME15;
    }
  }
  typedef FrequencyBiasType {
    type enumeration {
      enum FBT_LOWER;
      enum FBT_UPPER;
    }
  }
  typedef GeranProbCellPolicyVals {
    type enumeration {
      enum OFF;
      enum AUTO_DETECT;
      enum AUTO_DETECT_AND_BAR;
    }
  }
  typedef GtpuEchoEnable {
    type enumeration {
      enum DISABLED;
      enum PERIODIC;
    }
  }
  typedef GtpuEchoFailureAction {
    type enumeration {
      enum NONE;
      enum RESET;
    }
  }
  typedef HoControl {
    type enumeration {
      enum PRIO_ENDC;
      enum PRIO_LTE;
    }
  }
  typedef HoNotAllowedMpLoadLevel {
    type enumeration {
      enum NOT_HIGH_LOAD;
      enum HIGH_LOAD;
      enum VERY_HIGH_LOAD;
    }
  }
  typedef HoStatisticsStatus {
    type enumeration {
      enum OFF;
      enum HIGH;
      enum MEDIUM;
      enum LOW;
    }
  }
  typedef HrpdBandClass {
    type enumeration {
      enum BAND_CLASS_0;
      enum BAND_CLASS_1;
      enum BAND_CLASS_2;
      enum BAND_CLASS_3;
      enum BAND_CLASS_4;
      enum BAND_CLASS_5;
      enum BAND_CLASS_6;
      enum BAND_CLASS_7;
      enum BAND_CLASS_8;
      enum BAND_CLASS_9;
      enum BAND_CLASS_10;
      enum BAND_CLASS_11;
      enum BAND_CLASS_12;
      enum BAND_CLASS_13;
      enum BAND_CLASS_14;
      enum BAND_CLASS_15;
      enum BAND_CLASS_16;
      enum BAND_CLASS_17;
      enum BAND_CLASS_18;
      enum BAND_CLASS_19;
      enum BAND_CLASS_20;
      enum BAND_CLASS_21;
      enum UNDEFINED_VALUE;
    }
  }
  typedef InhibitA2SearchConfig {
    type enumeration {
      enum NOT_INHIBIT;
      enum INHIBIT_A2SEARCH_RSRQ;
      enum INHIBIT_A2SEARCH_RSRP;
    }
  }
  typedef InitPreschedulingControl {
    type enumeration {
      enum NO_CONTROL;
      enum SINR;
      enum PATHLOSS;
    }
  }
  typedef InstantDl256QamMode {
    type enumeration {
      enum OFF;
      enum STATIC_HOM_MODE;
      enum DYNAMIC_HOM_MODE;
    }
  }
  typedef IntegrityProtectionAlgorithmID {
    type enumeration {
      enum EIA1;
      enum EIA2;
      enum EIA3;
    }
  }
  typedef InterENodeBCAInteractionMode {
    type enumeration {
      enum NONE;
      enum ERAN;
      enum IENBCA;
    }
  }
  typedef InterEnbSwCompatibilityState {
    type enumeration {
      enum UNKNOWN;
      enum COMPATIBLE;
      enum INCOMPATIBLE;
      enum RELEASE_COMPATIBLE;
    }
  }
  typedef InterFreqMeasType {
    type enumeration {
      enum EVENT_A5;
      enum EVENT_A3;
    }
  }
  typedef IuaIntervalSelection {
    type enumeration {
      enum LOAD_BASED_SELECTION;
      enum INTERVAL_1MS;
      enum INTERVAL_2MS;
      enum INTERVAL_4MS;
      enum INTERVAL_5MS;
    }
  }
  typedef IuaIntervalSelectionFdd {
    type enumeration {
      enum LOAD_BASED_SELECTION;
      enum INTERVAL_1MS;
      enum INTERVAL_2MS;
      enum INTERVAL_4MS;
    }
  }
  typedef IuaIntervalSelectionTdd {
    type enumeration {
      enum LOAD_BASED_SELECTION;
      enum INTERVAL_1MS;
      enum INTERVAL_5MS;
    }
  }
  typedef IuaMode {
    type enumeration {
      enum NO_OVERRIDE;
      enum DISABLE_IUA;
      enum USE_SPECIFIC_IUA;
    }
  }
  typedef LastModificationEutran {
    type enumeration {
      enum ANR_MODIFICATION;
      enum X2_MODIFICATION;
      enum OPERATOR_MODIFICATION;
      enum ANR_DELETE;
      enum X2_DELETE;
      enum OPERATOR_DELETE;
      enum NOT_MODIFIED;
      enum MRO_MODIFICATION;
      enum PCI_MODIFICATION;
      enum MLB_MODIFICATION;
      enum RACH_OPT_MODIFICATION;
      enum LM_MODIFICATION;
    }
  }
  typedef LastModificationGeran {
    type enumeration {
      enum ANR_MODIFICATION;
      enum OPERATOR_MODIFICATION;
      enum NOT_MODIFIED;
      enum ANR_DELETE;
      enum OPERATOR_DELETE;
    }
  }
  typedef LastModificationSourceCell {
    type enumeration {
      enum OPERATOR;
      enum PCI_MODIFICATION;
      enum RACH_OPT_MODIFICATION;
      enum OSS_PCI_MODIFICATION;
    }
  }
  typedef LastModificationUtran {
    type enumeration {
      enum ANR_MODIFICATION;
      enum OPERATOR_MODIFICATION;
      enum NOT_MODIFIED;
      enum ANR_DELETE;
      enum OPERATOR_DELETE;
      enum LM_MODIFICATION;
    }
  }
  typedef LastSchedLinkAdaptMode {
    type enumeration {
      enum NO_OVERRIDE;
      enum DISABLE;
      enum ENABLE;
    }
  }
  typedef LayerState {
    type enumeration {
      enum OFF;
      enum ON;
    }
  }
  typedef LbAllowedEndcUE {
    type enumeration {
      enum NOT_ALLOWED;
      enum ENDC_CAPABLE_NOT_CONFIGURED;
      enum ENDC_CAPABLE_ALL;
    }
  }
  typedef LbAllowedPerSpid {
    type enumeration {
      enum LB_AND_OFFLOAD_ALLOWED;
      enum OFFLOAD_ALLOWED;
      enum NOT_ALLOWED;
      enum KEEP_OTHER_CONFIGURATION;
    }
  }
  typedef LbQciProfileHandling {
    type enumeration {
      enum ALLOWED;
      enum FORBIDDEN;
      enum REQUIRED;
    }
  }
  typedef LicCapDistrMethod {
    type enumeration {
      enum SYSTEM;
      enum OPERATOR;
    }
  }
  typedef LiteMcsReductionMode {
    type enumeration {
      enum OFF;
      enum ON;
      enum ON_WHEN_NO_ELC;
    }
  }
  typedef LoadBalancingVals {
    type enumeration {
      enum NOT_ALLOWED;
      enum ALLOWED;
      enum OFFLOAD;
      enum IFO_AND_IFLB;
    }
  }
  typedef LoggingDuration {
    type enumeration {
      enum MIN_10;
      enum MIN_20;
      enum MIN_40;
      enum MIN_60;
      enum MIN_90;
      enum MIN_120;
    }
  }
  typedef LoggingInterval {
    type enumeration {
      enum MS_1280;
      enum MS_2560;
      enum MS_5120;
      enum MS_10240;
      enum MS_20480;
      enum MS_30720;
      enum MS_40960;
      enum MS_61440;
    }
  }
  typedef LongDrxCycle {
    type enumeration {
      enum SF10;
      enum SF20;
      enum SF32;
      enum SF40;
      enum SF64;
      enum SF80;
      enum SF128;
      enum SF160;
      enum SF256;
      enum SF320;
      enum SF512;
      enum SF640;
      enum SF1024;
      enum SF1280;
      enum SF2048;
      enum SF2560;
    }
  }
  typedef LoopingEndcProtectionOverride {
    type enumeration {
      enum NO_OVERRIDE;
      enum ENABLED;
      enum DISABLED;
    }
  }
  typedef LtePowerBackoffMode {
    type enumeration {
      enum AUTO;
      enum OFF;
      enum STATIC;
    }
  }
  typedef MacConResTimerBrConfig {
    type enumeration {
      enum SF80;
      enum SF100;
      enum SF120;
      enum SF160;
      enum SF200;
      enum SF240;
      enum SF480;
      enum SF960;
    }
  }
  typedef MappingInfo {
    type enumeration {
      enum NOT_MAPPED;
      enum MAPPED_SI_1;
      enum MAPPED_SI_2;
      enum MAPPED_SI_3;
      enum MAPPED_SI_4;
      enum MAPPED_SI_5;
      enum MAPPED_SI_6;
      enum MAPPED_SI_7;
      enum MAPPED_SI_8;
      enum MAPPED_SI_9;
      enum MAPPED_SI_10;
    }
  }
  typedef MaxNumPreambleAttBrConfig {
    type enumeration {
      enum N3;
      enum N4;
      enum N5;
      enum N6;
      enum N7;
      enum N8;
      enum N10;
    }
  }
  typedef MbsfnAreaCellStatus {
    type enumeration {
      enum NOT_ACTIVATED;
      enum ACTIVATED;
      enum FAILED;
      enum CELL_DISABLED;
      enum RESERVED;
    }
  }
  typedef MbsfnSubframesForTm9 {
    type enumeration {
      enum DISABLED;
      enum ENABLED_10_PERCENT;
      enum ENABLED_20_PERCENT;
      enum ENABLED_30_PERCENT;
      enum ENABLED_40_PERCENT;
      enum ENABLED_50_PERCENT;
      enum ENABLED_60_PERCENT;
    }
  }
  typedef MdtReportingTrigger {
    type enumeration {
      enum PERIODICAL;
      enum EVENT_A2;
      enum EVENT_A2_PERIODIC;
    }
  }
  typedef MeasGapPattEndcRestriction {
    type enumeration {
      enum NO_RESTRICTION;
      enum FDD;
      enum ESS_SA;
    }
  }
  typedef MeasGapShareScheme {
    type enumeration {
      enum SCHEME_ZERO;
      enum SCHEME_ONE;
      enum SCHEME_TWO;
      enum SCHEME_THREE;
    }
  }
  typedef MeasSelectionEUtra {
    type enumeration {
      enum PERIODICAL;
      enum EVENT_A1;
      enum EVENT_A2;
      enum EVENT_A3;
      enum EVENT_A4;
      enum EVENT_A5;
      enum EVENT_A6;
    }
  }
  typedef MeasSelectionIrat {
    type enumeration {
      enum PERIODICAL;
      enum EVENT_B1;
      enum EVENT_B2;
    }
  }
  typedef MeasureModeBr {
    type enumeration {
      enum DEFAULT_MEASUREMENT;
      enum PUSCH_SINR_BASED;
    }
  }
  typedef MfbiFreqBandIndPrioExt {
    type enumeration {
      enum NOT_BROADCASTED;
      enum BROADCASTED;
      enum NOT_SUPPORTED;
      enum UNDEFINED_VALUE;
    }
  }
  typedef MiEndcIdleModeControl {
    type enumeration {
      enum DEACTIVATED;
      enum OBSERVABILITY_MODE;
      enum OPERATIONAL_MODE;
    }
  }
  typedef MibContentScheduling {
    type enumeration {
      enum OFF;
      enum MODE_1_SCHEDULING;
      enum MODE_2_SCHEDULING;
    }
  }
  typedef MimoSleep4TxOpMode {
    type enumeration {
      enum OP_MODE_4TX_TO_2TX;
      enum OP_MODE_4TX_TO_2TX_TO_1TX;
    }
  }
  typedef MimoSleepStatus {
    type enumeration {
      enum OFF;
      enum DETECTION;
      enum SOFT_SWITCH;
      enum SWITCH;
      enum ADVANCED_SWITCH;
      enum MI_DETECTION;
      enum MI_SWITCH;
    }
  }
  typedef MobilityActionCsfbGeran {
    type enumeration {
      enum RELEASE_WITH_REDIRECT;
      enum RELEASE_WITH_REDIRECT_NACC;
    }
  }
  typedef MobilityActionCsfbUtranFDD {
    type enumeration {
      enum RELEASE_WITH_REDIRECT;
      enum RELEASE_WITH_REDIRECT_NACC;
      enum HANDOVER;
    }
  }
  typedef MobilityActionCsfbUtranTDD {
    type enumeration {
      enum RELEASE_WITH_REDIRECT;
      enum RELEASE_WITH_REDIRECT_NACC;
      enum HANDOVER;
    }
  }
  typedef MobilityActionEUtran {
    type enumeration {
      enum RELEASE_WITH_REDIRECT;
      enum HANDOVER;
    }
  }
  typedef MobilityActionGUtran {
    type enumeration {
      enum RELEASE_WITH_REDIRECT;
      enum HANDOVER;
    }
  }
  typedef MobilityActionGeran {
    type enumeration {
      enum RELEASE_WITH_REDIRECT;
      enum RELEASE_WITH_REDIRECT_NACC;
    }
  }
  typedef MobilityActionUtran {
    type enumeration {
      enum RELEASE_WITH_REDIRECT;
      enum RELEASE_WITH_REDIRECT_NACC;
      enum HANDOVER;
    }
  }
  typedef NBValue {
    type enumeration {
      enum T4;
      enum T2;
      enum T;
      enum T1_2;
      enum T1_4;
      enum T1_8;
      enum T1_16;
      enum T1_32;
    }
  }
  typedef NBValueBr {
    type enumeration {
      enum NOT_PRESENT;
      enum T1_64;
      enum T1_128;
      enum T1_256;
      enum T;
      enum T1_2T;
      enum T1_4T;
      enum T1_8T;
      enum T1_16T;
      enum T1_32T;
    }
  }
  typedef NRCellServiceStatus {
    type enumeration {
      enum OUT_OF_SERVICE;
      enum IN_SERVICE;
    }
  }
  typedef NRCellState {
    type enumeration {
      enum IDLE;
      enum INACTIVE;
      enum ACTIVE;
    }
  }
  typedef NRCoordinationPattern {
    type enumeration {
      enum DEFAULT;
      enum PATTERN_1;
      enum PATTERN_2;
      enum PATTERN_3;
    }
  }
  typedef NbIotAcPresence {
    type enumeration {
      enum OFF;
      enum ON;
    }
  }
  typedef NbIotCellType {
    type enumeration {
      enum NBIOT_INBAND;
      enum NBIOT_GUARDBAND;
      enum NBIOT_STANDALONE;
      enum NBIOT_INBAND_NOT_SAME_PCI;
    }
  }
  typedef NbIotFrequencyOffset {
    type enumeration {
      enum V_10;
      enum V_9;
      enum V_8;
      enum V_7;
      enum V_6;
      enum V_5;
      enum V_4;
      enum V_3;
      enum V_2;
      enum V_1;
      enum V_05;
      enum V0;
      enum V05;
      enum V1;
      enum V2;
      enum V3;
      enum V4;
      enum V5;
      enum V6;
      enum V7;
      enum V8;
      enum V9;
    }
  }
  typedef NbValueNbIot {
    type enumeration {
      enum T4;
      enum T2;
      enum T;
      enum T1_2;
      enum T1_4;
      enum T1_8;
      enum T1_16;
      enum T1_32;
      enum T1_64;
      enum T1_128;
      enum T1_256;
      enum T1_512;
      enum T1_1024;
    }
  }
  typedef NeighCellConfig {
    type enumeration {
      enum DIFF_MBSFN_SUBFRAMES;
      enum SAME_MBSFN_SUBFRAMES;
      enum NO_MBSFN_SUBFRAMES;
      enum DIFF_UL_DL_ALLOCATION;
    }
  }
  typedef NetworkSignallingValue {
    type enumeration {
      enum NS_01;
      enum NS_03;
      enum NS_04;
      enum NS_05;
      enum NS_06;
      enum NS_07;
      enum NS_08;
      enum NS_09;
      enum NS_10;
      enum NS_11;
      enum NS_12;
      enum NS_13;
      enum NS_14;
      enum NS_15;
      enum NS_16;
      enum NS_17;
      enum NS_18;
      enum NS_19;
      enum NS_20;
      enum NS_21;
      enum NS_22;
      enum NS_23;
      enum NS_24;
      enum NS_25;
      enum NS_26;
      enum NS_27;
      enum NS_28;
      enum NS_29;
      enum NS_30;
      enum NS_31;
      enum NS_32;
      enum NS_35;
    }
  }
  typedef NetworkSignallingValueCa {
    type enumeration {
      enum CA_NS_01;
      enum CA_NS_02;
      enum CA_NS_03;
      enum CA_NS_04;
      enum CA_NS_05;
      enum CA_NS_06;
      enum CA_NS_07;
      enum CA_NS_08;
      enum CA_NS_31;
    }
  }
  typedef NnsfModeVals {
    type enumeration {
      enum SPLMN;
      enum RPLMN_IF_SAME_AS_SPLMN;
      enum RPLMN_IF_MME_SERVES_SPLMN;
    }
  }
  typedef NoOfSubframesVals {
    type enumeration {
      enum SF1;
      enum SF2;
      enum SF4;
      enum SF6;
    }
  }
  typedef NonPlannedPciTargetIdType {
    type enumeration {
      enum MACRO_ENODEB_ID;
      enum HOME_ENODEB_ID;
    }
  }
  typedef NonPolledReleaseCfg {
    type enumeration {
      enum OFF_FOR_ALL_UE;
      enum ON_FOR_ALL_UE;
      enum ON_FOR_REL14_AND_LATER_UE;
    }
  }
  typedef NprachAllocationConfig {
    type enumeration {
      enum BASIC_CONFIG;
      enum OPTIMIZED_CONFIG_1;
      enum OPTIMIZED_CONFIG_2;
    }
  }
  typedef NprachSubcarrierForStMsg3 {
    type enumeration {
      enum ZERO;
      enum ONE_THIRD;
      enum TWO_THIRD;
      enum ONE;
    }
  }
  typedef NpuschGroupHopConfig {
    type enumeration {
      enum GROUP_HOP_DISABLED;
      enum GROUP_HOP_ENABLED;
    }
  }
  typedef Ns05LBSchedMode {
    type enumeration {
      enum ALWAYS_PROHIBIT;
      enum ALWAYS_AVAILABLE;
      enum ADAPTIVE_AVAILABLE_BY_REPEATER_DETECTION;
    }
  }
  typedef ObsMode {
    type enumeration {
      enum NORMAL;
      enum COUNTER_AND_PM_EVENT;
      enum COUNTER;
      enum KPI;
      enum INTERNAL_SUPERVISOR;
      enum AUTO;
    }
  }
  typedef ObsProtectionAutoTargetMode {
    type enumeration {
      enum COUNTER_AND_PM_EVENT;
      enum COUNTER;
      enum KPI;
      enum INTERNAL_SUPERVISOR;
    }
  }
  typedef ObsStatus {
    type enumeration {
      enum NORMAL;
      enum COUNTER_AND_PM_EVENT;
      enum COUNTER;
      enum KPI;
      enum INTERNAL_SUPERVISOR;
    }
  }
  typedef OnDurationTimer {
    type enumeration {
      enum PSF1;
      enum PSF2;
      enum PSF3;
      enum PSF4;
      enum PSF5;
      enum PSF6;
      enum PSF8;
      enum PSF10;
      enum PSF20;
      enum PSF30;
      enum PSF40;
      enum PSF50;
      enum PSF60;
      enum PSF80;
      enum PSF100;
      enum PSF200;
    }
  }
  typedef OperState {
    type enumeration {
      enum DISABLED;
      enum ENABLED;
    }
  }
  typedef OrderCode {
    type enumeration {
      enum RETAIN_EXISTING;
      enum RENEW_ALL_EXISTING;
    }
  }
  typedef PWSRestartHandling {
    type enumeration {
      enum DISABLED;
      enum ENABLED;
    }
  }
  typedef Pa {
    type enumeration {
      enum DB_MINUS_6;
      enum DB_MINUS_4_DOT_77;
      enum DB_MINUS_3;
      enum DB_MINUS_1_DOT_77;
      enum DB_0;
      enum DB_1;
      enum DB_2;
      enum DB_3;
    }
  }
  typedef PagingAssistDataBr {
    type enumeration {
      enum NOT_SUPPORTED;
      enum ASSISTANCE_DATA_CELL_ID;
    }
  }
  typedef PagingPriority {
    type enumeration {
      enum OFF;
      enum PRIO_LEVEL_1;
      enum PRIO_LEVEL_2;
      enum PRIO_LEVEL_3;
      enum PRIO_LEVEL_4;
      enum PRIO_LEVEL_5;
      enum PRIO_LEVEL_6;
      enum PRIO_LEVEL_7;
      enum PRIO_LEVEL_8;
    }
  }
  typedef ParameterChangeCause {
    type enumeration {
      enum INITIAL;
      enum MRO;
      enum MLB;
      enum RACH;
    }
  }
  typedef ParameterChangeState {
    type enumeration {
      enum INITIAL;
      enum PENDING;
      enum APPROVED;
      enum REJECTED;
      enum CANCELLED;
    }
  }
  typedef PciConflict {
    type enumeration {
      enum NO;
      enum NO_CONFLICTING_CELL;
      enum YES;
      enum YES_CONFLICTING_CELL;
    }
  }
  typedef PciConflictCellSelectVals {
    type enumeration {
      enum OFF;
      enum MANUAL_SELECT;
      enum MANUAL_SELECT_AND_AUTO_DETECT;
      enum AUTO_SELECT_OVER_MANUAL;
    }
  }
  typedef PciConflictDetectionType {
    type enumeration {
      enum NO;
      enum FR1;
      enum FR2;
      enum BOTH;
    }
  }
  typedef PciConflictReportType {
    type enumeration {
      enum LTE;
      enum NR;
      enum BOTH;
    }
  }
  typedef PdcchFlexibleBlerMode {
    type enumeration {
      enum NO_OVERRIDE;
      enum DISABLED;
      enum ENABLED;
    }
  }
  typedef PeerStatus {
    type enumeration {
      enum UNKNOWN;
      enum REACHABLE;
      enum UNREACHABLE;
    }
  }
  typedef PersistentStorage {
    type enumeration {
      enum OFF;
      enum ON;
    }
  }
  typedef PimAvoidanceModeStatus {
    type enumeration {
      enum AGGRESSOR;
      enum VICTIM;
      enum AGGRESSOR_VICTIM;
    }
  }
  typedef PimDetectionRole {
    type enumeration {
      enum AGGRESSOR;
      enum VICTIM;
      enum VICTIM_AND_AGGRESSOR;
    }
  }
  typedef PimDetectionStatus {
    type enumeration {
      enum NOT_APPLICABLE;
      enum NO_PIM_DETECTED;
      enum PIM_DETECTED;
    }
  }
  typedef PimMitigAggressiveness {
    type enumeration {
      enum LOW;
      enum MEDIUM;
      enum HIGH;
    }
  }
  typedef PimMitigLevel {
    type enumeration {
      enum LOW;
      enum MEDIUM;
      enum HIGH;
    }
  }
  typedef PimMitigStatus {
    type enumeration {
      enum PIM_MITIG_STATUS_UNKNOWN;
      enum PIM_MITIG_STATUS_ACTIVE;
      enum PIM_MITIG_STATUS_FAILED;
      enum PIM_MITIG_STATUS_FINISHED;
    }
  }
  typedef PimMutingStartPoint {
    type enumeration {
      enum DOWNMOST;
      enum UPMOST;
    }
  }
  typedef PimType {
    type enumeration {
      enum CLEAR;
      enum LIKELY;
    }
  }
  typedef PlmnServiceAlarmLevel {
    type enumeration {
      enum ENODEB;
      enum CELL;
    }
  }
  typedef PmEventGroup {
    type enumeration {
      enum S1_PAGING;
    }
  }
  typedef PortMerging4TxOpMode {
    type enumeration {
      enum PORT_MERGING_4TX_TO_1TX;
      enum PORT_MERGING_4TX_TO_2TX;
    }
  }
  typedef PortMergingOptionFor4TxTo2Tx {
    type enumeration {
      enum MUTE_ANT_1_AND_3;
      enum MUTE_ANT_2_AND_3;
    }
  }
  typedef PositioningMethod {
    type enumeration {
      enum NONE;
      enum GNSS;
    }
  }
  typedef PowerClass {
    type enumeration {
      enum PC_1;
      enum PC_2;
    }
  }
  typedef PrbPatternModel {
    type enumeration {
      enum OCNG;
      enum TRAFFIC_MODEL;
      enum NO_HIGH_PRIO_LOAD;
    }
  }
  typedef PreambleTransMaxCeBrConfig {
    type enumeration {
      enum N3;
      enum N4;
      enum N5;
      enum N6;
      enum N7;
      enum N8;
      enum N10;
      enum N20;
      enum N50;
      enum N100;
      enum N200;
    }
  }
  typedef PreemptionCapability {
    type enumeration {
      enum SHALL_NOT_TRIGGER_PREEMPTION;
      enum MAY_TRIGGER_PREEMPTION;
    }
  }
  typedef PreemptionVulnerability {
    type enumeration {
      enum NOT_PREEMPTABLE;
      enum PREEMPTABLE;
    }
  }
  typedef PreschedulingMode {
    type enumeration {
      enum NO_OVERRIDE;
      enum DISABLE_PRESCHEDULING;
      enum USE_SPECIFIC_PRESCHEDULING;
    }
  }
  typedef PrioHpueCapability {
    type enumeration {
      enum NO_PRIORITIZATION;
      enum PRIORITIZE_IN_CA;
    }
  }
  typedef PrsPerVals {
    type enumeration {
      enum PP160;
      enum PP320;
      enum PP640;
      enum PP1280;
    }
  }
  typedef PtmCellType {
    type enumeration {
      enum PRIORITY;
      enum NON_PRIORITY;
    }
  }
  typedef PuschChannelEstWindowSize {
    type enumeration {
      enum NORMAL_SIZE;
      enum LARGE_SIZE;
    }
  }
  typedef RIMAssociationStatus {
    type enumeration {
      enum RIM_ACTIVE;
      enum RIM_INACTIVE;
      enum RIM_STOPPED;
    }
  }
  typedef RIMCapability {
    type enumeration {
      enum RIM_CAPABLE;
      enum RIM_INCAPABLE;
      enum RIM_CAPABILITY_UNKNOWN;
    }
  }
  typedef RaBackoffBrConfig {
    type enumeration {
      enum NO_BACKOFF;
      enum STATIC_BACKOFF_10MS;
      enum STATIC_BACKOFF_20MS;
      enum STATIC_BACKOFF_30MS;
      enum STATIC_BACKOFF_40MS;
      enum STATIC_BACKOFF_60MS;
      enum STATIC_BACKOFF_80MS;
      enum STATIC_BACKOFF_120MS;
      enum STATIC_BACKOFF_160MS;
      enum STATIC_BACKOFF_240MS;
      enum STATIC_BACKOFF_320MS;
      enum STATIC_BACKOFF_480MS;
      enum STATIC_BACKOFF_960MS;
      enum DYNAMIC_BACKOFF;
    }
  }
  typedef RaBackoffNbConfig {
    type enumeration {
      enum NO_BACKOFF;
      enum STATIC_BACKOFF_256MS;
      enum STATIC_BACKOFF_512MS;
      enum STATIC_BACKOFF_1024MS;
      enum STATIC_BACKOFF_2048MS;
      enum STATIC_BACKOFF_4096MS;
      enum STATIC_BACKOFF_8192MS;
      enum STATIC_BACKOFF_16384MS;
      enum STATIC_BACKOFF_32768MS;
      enum STATIC_BACKOFF_65536MS;
      enum STATIC_BACKOFF_131072MS;
      enum STATIC_BACKOFF_262144MS;
      enum STATIC_BACKOFF_524288MS;
      enum DYNAMIC_BACKOFF;
    }
  }
  typedef RaResWinSizeBrConfig {
    type enumeration {
      enum SF20;
      enum SF50;
      enum SF80;
      enum SF120;
      enum SF180;
      enum SF240;
      enum SF320;
      enum SF400;
    }
  }
  typedef RadioOperatingMode {
    type enumeration {
      enum DEFAULT;
      enum QAM_64_BOOST;
      enum QAM_256_BOOST;
      enum MAX_POWER_CLASS;
    }
  }
  typedef RadioOperatingModeEnhanced {
    type enumeration {
      enum COVERAGE;
      enum CAPACITY;
      enum COVERAGE_GREEN;
      enum CAPACITY_GREEN;
    }
  }
  typedef Rat {
    type enumeration {
      enum UTRAN;
      enum GERAN;
    }
  }
  typedef Reason {
    type enumeration {
      enum NONE;
      enum PROBLEMATIC_CELL;
      enum PLMN_NOT_SUPPORTED;
      enum PLMN_BLOCKLISTED;
    }
  }
  typedef ReasonIrat {
    type enumeration {
      enum NONE;
      enum PLMN_NOT_SUPPORTED;
      enum PROBLEMATIC_CELL;
    }
  }
  typedef ReasonNR {
    type enumeration {
      enum NONE;
      enum NO_NR_TAC;
    }
  }
  typedef ReportDlActivity {
    type enumeration {
      enum DISABLED;
      enum AUTO;
      enum ENABLED_1;
      enum ENABLED_2;
      enum ENABLED_3;
      enum ENABLED_4;
      enum ENABLED_5;
      enum ENABLED_6;
    }
  }
  typedef ReportInterval {
    type enumeration {
      enum MS_120;
      enum MS_240;
      enum MS_480;
      enum MS_640;
      enum MS_1024;
      enum MS_5120;
      enum MS_10240;
      enum MIN_1;
      enum MIN_6;
      enum MIN_12;
      enum MIN_30;
      enum MIN_60;
      enum MS_2048;
    }
  }
  typedef ReportQuantity {
    type enumeration {
      enum SAME_AS_TRIGGER_QUANTITY;
      enum BOTH;
    }
  }
  typedef RequestReducedFormat {
    type enumeration {
      enum DISABLED;
      enum ENABLED;
    }
  }
  typedef RequestReducedIntNonContComb {
    type enumeration {
      enum DISABLED;
      enum ENABLED;
    }
  }
  typedef RequestSkipFallbackCombinations {
    type enumeration {
      enum DISABLED;
      enum ENABLED;
    }
  }
  typedef RequestedBandCombCompression {
    type enumeration {
      enum OFF;
      enum R11_REQUESTED_BAND_COMBO;
      enum R13_BAND_COMPRESSION;
      enum R14_DIFF_FALLBACK;
    }
  }
  typedef ResourceAllocationStrategy {
    type enumeration {
      enum RESOURCE_FAIR;
      enum FREQUENCY_SELECTIVE;
    }
  }
  typedef ResourceSharingType {
    type enumeration {
      enum DYNAMIC;
      enum STATIC;
    }
  }
  typedef ResourceType {
    type enumeration {
      enum NON_GBR;
      enum GBR;
    }
  }
  typedef RlcBufferStatus {
    type enumeration {
      enum HALF_BUFFER;
      enum FULL_BUFFER;
    }
  }
  typedef RlcDlDeliveryFailAction {
    type enumeration {
      enum UE_CONTEXT_RELEASE;
      enum RETAIN_CONNECTION_IF_OTHER_DRB_WITH_HIGHER_ARP;
      enum RETAIN_CONNECTION_IF_OTHER_DRB_WITH_HIGHER_OR_EQUAL_ARP;
    }
  }
  typedef RlcMode {
    type enumeration {
      enum AM;
      enum UM;
      enum TM;
    }
  }
  typedef SCellCandidate {
    type enumeration {
      enum NOT_ALLOWED;
      enum ALLOWED;
      enum AUTO;
      enum ONLY_ALLOWED_FOR_DL;
    }
  }
  typedef SCellEvaluationLevel {
    type enumeration {
      enum EFFECTIVE;
      enum HIGH;
    }
  }
  typedef SCellHandlingWithVolte {
    type enumeration {
      enum KEEP_SCELLS;
      enum DECONF_SCELLS;
      enum DECONF_UL_SUPPRESS_DL_SCELLS;
      enum DECONF_UL_SCELLS;
    }
  }
  typedef SCellPriority {
    type enumeration {
      enum NONE;
      enum TDD;
      enum FDD;
    }
  }
  typedef SCellSelectionMode {
    type enumeration {
      enum ACK_SEQUENTIAL_SCELL_SELECTION;
      enum UN_ACK_SIMULTANEOUS_SCELL_SELECTION;
      enum ACK_SIMULTANEOUS_SCELL_SELECTION;
      enum AI_ACK_SIMULT_SCELL_SELECT;
      enum AI_UNACK_SIMULT_SCELL_SELECT;
    }
  }
  typedef SCellState {
    type enumeration {
      enum DISABLED;
      enum ENABLED_LOCAL;
      enum ENABLED_ERAN;
      enum ENABLED_IENB;
      enum DISABLED_LICENSE;
      enum DISABLED_BB_COMPATIBILITY;
      enum DISABLED_LINK;
      enum DISABLED_MISMATCHED_MODE;
      enum LINK_REMOVED_BY_REMOTE_ENB;
      enum ESCELL_LIMIT_EXCEEDED;
      enum CANDIDATE_LIMIT_EXCEEDED;
      enum CPRI_LATENCY_EXCEEDED;
      enum VLAN_MISMATCH;
      enum TERMPOINT_TO_ENB_DISABLED;
      enum PCELL_DISABLED;
      enum ESCELL_DISABLED;
      enum LOCAL_SCELL_DISABLED;
      enum MAX_PARTNERS_ON_REMOTE_ENB;
      enum MAX_PARTNERS_ON_LOCAL_ENB;
      enum ERAN_MAX_RTT_DELAY_MISMATCH;
      enum ENABLED_ICM;
      enum CM_SCELL_DISABLED;
      enum ICM_SCELL_DISABLED;
    }
  }
  typedef ScheduledPolicy {
    type enumeration {
      enum FAIR;
      enum LTE_BIASED;
      enum NR_BIASED;
    }
  }
  typedef SchedulingAlgorithm {
    type enumeration {
      enum RESOURCE_FAIR;
      enum EQUAL_RATE;
      enum PROPORTIONAL_FAIR_HIGH;
      enum PROPORTIONAL_FAIR_MEDIUM;
      enum PROPORTIONAL_FAIR_LOW;
      enum MAXIMUM_C_OVER_I;
      enum DELAY_BASED;
    }
  }
  typedef SectorShape {
    type enumeration {
      enum MACRO;
      enum HIGHRISE;
      enum HOTSPOT;
      enum MACRO_NARROW;
      enum MACRO_WIDE;
      enum MACRO_2LOBE;
      enum MACRO_NARROW_H33;
    }
  }
  typedef SectorType {
    type enumeration {
      enum NORMAL_SECTOR;
      enum LEFT_DIGITAL_SECTOR;
      enum RIGHT_DIGITAL_SECTOR;
      enum LEFT_DIGITAL_SECTOR_3DS;
      enum RIGHT_DIGITAL_SECTOR_3DS;
      enum MIDDLE_DIGITAL_SECTOR_3DS;
      enum A1_DIGITAL_SECTOR_4DS;
      enum B1_DIGITAL_SECTOR_4DS;
      enum C1_DIGITAL_SECTOR_4DS;
      enum D1_DIGITAL_SECTOR_4DS;
      enum A2_DIGITAL_SECTOR_4DS;
      enum B2_DIGITAL_SECTOR_4DS;
      enum C2_DIGITAL_SECTOR_4DS;
      enum D2_DIGITAL_SECTOR_4DS;
    }
  }
  typedef ServOrPrioTriggeredErabActionType {
    type enumeration {
      enum SETUP;
      enum REJECT;
    }
  }
  typedef ServOrPrioTriggeredIFHoType {
    type enumeration {
      enum QCI;
      enum ARP;
      enum NOT_ACTIVATED;
    }
  }
  typedef ServiceType {
    type enumeration {
      enum UNDEFINED;
      enum VOIP;
      enum IMS_SIGNALING;
      enum PTT;
      enum MC_SIGNALING;
    }
  }
  typedef ShortDrxCycle {
    type enumeration {
      enum SF2;
      enum SF5;
      enum SF8;
      enum SF10;
      enum SF16;
      enum SF20;
      enum SF32;
      enum SF40;
      enum SF64;
      enum SF80;
      enum SF128;
      enum SF160;
      enum SF256;
      enum SF320;
      enum SF512;
      enum SF640;
    }
  }
  typedef SiSib1RepetitionBrType {
    type enumeration {
      enum NORMAL;
      enum MEDIUM;
      enum LARGE;
    }
  }
  typedef SleepCellDataCollect {
    type enumeration {
      enum COLLECTION_DISABLED;
      enum COLLECTION_ENABLED;
    }
  }
  typedef SleepPowerControlType {
    type enumeration {
      enum USE_MAX_POWER;
      enum RETAIN_SAME_POWER;
    }
  }
  typedef SonBasedMeasFeatureName {
    type enumeration {
      enum ANR;
      enum PM_INIT_UE_MEAS;
      enum MDT;
      enum BNR_INTRA_LTE_LM;
      enum ASM;
    }
  }
  typedef SrProcessingLevel {
    type enumeration {
      enum NO_ADDITIONAL_SR_NEEDED;
      enum TWO_SR_FOR_LOW_THRESHOLD_SR_PROCESSING;
      enum TWO_SR_FOR_ALL_SR_PROCESSING;
    }
  }
  typedef SrsAllocationStrategy {
    type enumeration {
      enum DEACTIVATED;
      enum ACTIVATED;
    }
  }
  typedef SrsBandwidth {
    type enumeration {
      enum FULL_BAND_FOR_ALL;
      enum HALF_AND_THIRD_BAND;
      enum QUARTER_BAND_AND_NA;
    }
  }
  typedef SrvccCapability {
    type enumeration {
      enum NOT_SUPPORTED;
      enum CS_ONLY_SUPPORTED;
      enum PS_AND_CS_SUPPORTED;
    }
  }
  typedef SupportNrFreqChange {
    type enumeration {
      enum OFF;
      enum ADD_FREQREL;
      enum ADD_FREQREL_IF_CELLREL_EXIST;
    }
  }
  typedef SupportedCoverage {
    type enumeration {
      enum NONE;
      enum COVERS;
      enum OVERLAP;
      enum CONTAINED_IN;
    }
  }
  typedef T300BrConfig {
    type enumeration {
      enum T300_100MS;
      enum T300_200MS;
      enum T300_300MS;
      enum T300_400MS;
      enum T300_600MS;
      enum T300_1000MS;
      enum T300_1500MS;
      enum T300_2000MS;
    }
  }
  typedef TaperType {
    type enumeration {
      enum NO_TAPERING;
      enum TYPE1;
      enum TYPE2;
      enum TYPE3;
      enum TYPE4;
      enum TYPE5;
    }
  }
  typedef ThpFilterDlVolume {
    type enumeration {
      enum FILTER_THRESH_0;
      enum FILTER_THRESH_1;
      enum FILTER_THRESH_10;
      enum FILTER_THRESH_15;
      enum FILTER_THRESH_22;
      enum FILTER_THRESH_45;
      enum FILTER_THRESH_70;
      enum FILTER_THRESH_100;
      enum FILTER_THRESH_150;
      enum FILTER_THRESH_220;
      enum FILTER_THRESH_450;
      enum FILTER_THRESH_700;
      enum FILTER_THRESH_1000;
      enum FILTER_THRESH_1500;
      enum FILTER_THRESH_2200;
      enum FILTER_THRESH_4500;
      enum FILTER_THRESH_7000;
      enum FILTER_THRESH_10000;
      enum FILTER_THRESH_15000;
      enum FILTER_THRESH_22000;
      enum FILTER_THRESH_45000;
      enum FILTER_THRESH_70000;
      enum FILTER_THRESH_100000;
      enum FILTER_THRESH_150000;
      enum FILTER_THRESH_220000;
      enum FILTER_THRESH_450000;
    }
  }
  typedef ThresholdUtra {
    type enumeration {
      enum RSCP;
      enum ECNO;
    }
  }
  typedef TimePhaseMaxDeviationTddIndex {
    type enumeration {
      enum TIME_PHASE_MAX_DEVIATION_TDD_IDX0;
      enum TIME_PHASE_MAX_DEVIATION_TDD_IDX1;
      enum TIME_PHASE_MAX_DEVIATION_TDD_IDX2;
      enum TIME_PHASE_MAX_DEVIATION_TDD_IDX3;
      enum TIME_PHASE_MAX_DEVIATION_TDD_IDX4;
      enum TIME_PHASE_MAX_DEVIATION_TDD_IDX5;
      enum TIME_PHASE_MAX_DEVIATION_TDD_IDX6;
      enum TIME_PHASE_MAX_DEVIATION_TDD_IDX7;
    }
  }
  typedef TracePmFileStatusEnum {
    type enumeration {
      enum INACTIVE;
      enum ACTIVE;
      enum FILECLOSED;
      enum LOAD_INHIBITED;
    }
  }
  typedef TracePmStreamStatusEnum {
    type enumeration {
      enum INACTIVE;
      enum ACTIVE;
      enum CONNECTING;
      enum RECONNECTING;
      enum ERROR;
      enum NOT_LICENSED;
      enum LOAD_INHIBITED;
      enum STREAM_REPORT_OFF;
    }
  }
  typedef TrafficConditionType {
    type enumeration {
      enum RRC_AND_DL_PRB;
      enum RRC_OR_DL_PRB;
      enum RRC_ONLY;
      enum DL_PRB_ONLY;
    }
  }
  typedef TransmissionMode {
    type enumeration {
      enum TRANSMISSION_MODE_2;
      enum TRANSMISSION_MODE_3;
      enum TRANSMISSION_MODE_4;
      enum TRANSMISSION_MODE_7;
      enum TRANSMISSION_MODE_8;
      enum TRANSMISSION_MODE_9;
    }
  }
  typedef TransmissionModeFDD {
    type enumeration {
      enum TRANSMISSION_MODE_2;
      enum TRANSMISSION_MODE_3;
      enum TRANSMISSION_MODE_4;
      enum TRANSMISSION_MODE_9;
    }
  }
  typedef TransmissionScheme {
    type enumeration {
      enum ANTENNA_SWITCHING;
      enum PRECODER_SWITCHING;
    }
  }
  typedef TriggerQuantity {
    type enumeration {
      enum RSRP;
      enum RSRQ;
    }
  }
  typedef TriggerQuantityGUtra {
    type enumeration {
      enum SS_RSRP;
      enum SS_RSRQ;
    }
  }
  typedef TriggerQuantityGUtraOverride {
    type enumeration {
      enum NO_OVERRIDE;
      enum SS_RSRP;
      enum SS_RSRQ;
    }
  }
  typedef TriggerQuantityNR {
    type enumeration {
      enum SS_RSRP;
      enum SS_RSRQ;
    }
  }
  typedef TtiBundTriggerAlignment {
    type enumeration {
      enum OFF;
      enum ULTRIG;
    }
  }
  typedef TtiBundlingAtSetup {
    type enumeration {
      enum OFF;
      enum ACT_TTIB_IMM;
    }
  }
  typedef TtiBundlingModeAfterHandover {
    type enumeration {
      enum NO_TTI_BUNDLING;
      enum TTI_BUNDLING_ALL_HO_CASES;
      enum TTI_BUNDLING_INTRA_FREQ_HO_ONLY;
    }
  }
  typedef TtiBundlingModeAfterReestablishment {
    type enumeration {
      enum NO_TTI_BUNDLING;
      enum TTI_BUNDLING_ALL_REEST_CASES;
      enum TTI_BUNDLING_SOURCE_REEST_ONLY;
    }
  }
  typedef TxPattern {
    type enumeration {
      enum ALL_ANTENNAS_ON;
      enum MAX_TWO_ANTENNAS_ON;
    }
  }
  typedef UeCapability {
    type enumeration {
      enum ENDC;
      enum TM9;
    }
  }
  typedef UeCategory {
    type enumeration {
      enum UE_CATEGORY_DL_M1_UL_M1;
      enum UE_CATEGORY_DL_0_UL_0;
      enum UE_CATEGORY_1;
      enum UE_CATEGORY_2;
      enum UE_CATEGORY_3;
      enum UE_CATEGORY_4;
      enum UE_CATEGORY_5;
      enum UE_CATEGORY_6;
      enum UE_CATEGORY_7;
      enum UE_CATEGORY_8;
      enum UE_CATEGORY_9;
      enum UE_CATEGORY_10;
      enum UE_CATEGORY_11;
      enum UE_CATEGORY_12;
      enum UE_CATEGORY_DL_6_UL_5;
      enum UE_CATEGORY_DL_7_UL_13;
      enum UE_CATEGORY_DL_9_UL_5;
      enum UE_CATEGORY_DL_10_UL_13;
      enum UE_CATEGORY_DL_11_UL_5;
      enum UE_CATEGORY_DL_12_UL_13;
      enum UE_CATEGORY_DL_13_UL_3;
      enum UE_CATEGORY_DL_13_UL_5;
      enum UE_CATEGORY_DL_13_UL_7;
      enum UE_CATEGORY_DL_13_UL_13;
      enum UE_CATEGORY_DL_14_UL_8;
      enum UE_CATEGORY_DL_15_UL_3;
      enum UE_CATEGORY_DL_15_UL_5;
      enum UE_CATEGORY_DL_15_UL_7;
      enum UE_CATEGORY_DL_15_UL_13;
      enum UE_CATEGORY_DL_16_UL_3;
      enum UE_CATEGORY_DL_16_UL_5;
      enum UE_CATEGORY_DL_16_UL_7;
      enum UE_CATEGORY_DL_16_UL_13;
      enum UE_CATEGORY_DL_17_UL_14;
      enum UE_CATEGORY_DL_18_UL_3;
      enum UE_CATEGORY_DL_18_UL_5;
      enum UE_CATEGORY_DL_18_UL_7;
      enum UE_CATEGORY_DL_18_UL_13;
      enum UE_CATEGORY_DL_19_UL_3;
      enum UE_CATEGORY_DL_19_UL_5;
      enum UE_CATEGORY_DL_19_UL_7;
      enum UE_CATEGORY_DL_19_UL_13;
      enum UE_CATEGORY_DL_20_UL_3;
      enum UE_CATEGORY_DL_20_UL_5;
      enum UE_CATEGORY_DL_20_UL_7;
      enum UE_CATEGORY_DL_20_UL_13;
      enum UE_CATEGORY_DL_4_UL_5;
      enum UE_CATEGORY_DL_6_UL_16;
      enum UE_CATEGORY_DL_7_UL_18;
      enum UE_CATEGORY_DL_9_UL_16;
      enum UE_CATEGORY_DL_10_UL_18;
      enum UE_CATEGORY_DL_11_UL_16;
      enum UE_CATEGORY_DL_12_UL_18;
      enum UE_CATEGORY_DL_13_UL_16;
      enum UE_CATEGORY_DL_13_UL_18;
      enum UE_CATEGORY_DL_15_UL_16;
      enum UE_CATEGORY_DL_15_UL_18;
      enum UE_CATEGORY_DL_16_UL_16;
      enum UE_CATEGORY_DL_16_UL_18;
      enum UE_CATEGORY_DL_18_UL_16;
      enum UE_CATEGORY_DL_18_UL_18;
      enum UE_CATEGORY_DL_19_UL_16;
      enum UE_CATEGORY_DL_19_UL_18;
      enum UE_CATEGORY_DL_20_UL_16;
      enum UE_CATEGORY_DL_20_UL_18;
      enum UE_CATEGORY_DL_12_UL_20;
      enum UE_CATEGORY_DL_16_UL_20;
      enum UE_CATEGORY_DL_18_UL_20;
      enum UE_CATEGORY_DL_19_UL_20;
      enum UE_CATEGORY_DL_20_UL_20;
      enum UE_CATEGORY_DL_22_UL_20;
    }
  }
  typedef UlCalibrationMethod {
    type enumeration {
      enum NONE;
      enum INTERNAL;
    }
  }
  typedef UlCalibrationStatus {
    type enumeration {
      enum INACTIVE;
      enum CONVERGING;
      enum CALIBRATED;
      enum FAILED;
    }
  }
  typedef UlHeavyCaReconfMode {
    type enumeration {
      enum RANDOM;
      enum ULPRIORITY;
    }
  }
  typedef UlHeavyExitCaMode {
    type enumeration {
      enum BACK_TO_DLCA;
      enum KEEP_ULCA;
    }
  }
  typedef UlPimCancellationMode {
    type enumeration {
      enum EXCLUDED;
      enum DEACTIVATED;
      enum ACTIVATED;
    }
  }
  typedef UnlicensedBandList {
    type enumeration {
      enum NONE;
      enum BAND_46A;
      enum BAND_46B;
      enum BAND_46C;
      enum BAND_46D;
    }
  }
  typedef UnlicensedEarfcnList {
    type enumeration {
      enum NONE;
      enum EARFCN_46890;
      enum EARFCN_47090;
      enum EARFCN_47290;
      enum EARFCN_47490;
      enum EARFCN_47690;
      enum EARFCN_47890;
      enum EARFCN_48090;
      enum EARFCN_48290;
      enum EARFCN_48490;
      enum EARFCN_48690;
      enum EARFCN_50090;
      enum EARFCN_50290;
      enum EARFCN_50490;
      enum EARFCN_50690;
      enum EARFCN_50890;
      enum EARFCN_51090;
      enum EARFCN_51290;
      enum EARFCN_51490;
      enum EARFCN_51690;
      enum EARFCN_51890;
      enum EARFCN_52090;
      enum EARFCN_52290;
      enum EARFCN_52490;
      enum EARFCN_52740;
      enum EARFCN_52940;
      enum EARFCN_53140;
      enum EARFCN_53340;
      enum EARFCN_53540;
      enum EARFCN_53740;
      enum EARFCN_53940;
      enum EARFCN_54140;
      enum EARFCN_54340;
    }
  }
  typedef UpIpAddress2Mode {
    type enumeration {
      enum LOAD_SHARING;
      enum BACKUP;
    }
  }
  typedef UtranLbBnrPolicyVals {
    type enumeration {
      enum NOT_ALLOWED;
      enum OFFLOAD_ONLY;
    }
  }
  typedef UtranLoadBalancingVals {
    type enumeration {
      enum NOT_ALLOWED;
      enum OFFLOAD;
    }
  }
  typedef UttmCtrlForEndcUe {
    type enumeration {
      enum ENABLED_FOR_ALL_ENDC_UE;
      enum DISABLED_FOR_ENDC_ALLOWED_UE;
      enum DISABLED_FOR_ENDC_CONFIG_UE;
    }
  }
  typedef UtvmUeDetect {
    type enumeration {
      enum DISABLED;
      enum MEASBASEDHO;
      enum BLINDHO;
    }
  }
  typedef ValidityTime {
    type enumeration {
      enum VALIDITY_TIME_3H;
      enum VALIDITY_TIME_24H;
    }
  }
  grouping AbConfProfile-attributes {
    leaf abCategory {
      type enumeration {
        enum CATEGORY_A;
        enum CATEGORY_B;
        enum CATEGORY_C;
        enum OFF;
      }
    }
    leaf abBarringBitmap {
      type eytypes:int32_range_0-1023-23;
      default "0";
      description "range 0..1023; Default value: 0.";
    }
    leaf abBarringBitmapSpec {
      type eytypes:int32_range_0-31-13;
      default "0";
      description "range 0..31; Default value: 0.";
    }
    leaf abException {
      type boolean;
      default "false";
      description "Default value: false.";
    }
    leaf abBarringTime {
      type int32 {
        range "20..4095";
      }
      default "60";
      description "range 20..4095; Default value: 60.";
    }
    leaf abPerNrsrp {
      type enumeration {
        enum OFF;
        enum THRESH1;
        enum THRESH2;
      }
    }
    leaf-list reservedBy {
      type string;
    }
    leaf abConfProfileId {
      type string;
      mandatory true;
    }
  }
  grouping AdditionalCoreNetwork-attributes {
    list plmnList {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf sctpS1Ref {
      type string;
    }
    leaf upS1IpAddressRef {
      type ietfinet:ip-address;
    }
    leaf upX2IpAddressRef {
      type ietfinet:ip-address;
    }
    leaf dnsSelectionS1Ref {
      type string;
    }
    leaf additionalCoreNetworkId {
      type string;
      mandatory true;
    }
    leaf-list reservedBy {
      type string;
    }
    leaf upEndcX2IpAddressRef {
      type ietfinet:ip-address;
      status deprecated;
      description "Takes effect: Node restart; MOM flags: isNillable=true; Status info: Since 19.Q2. Has no functional behavior. Planned to be removed..";
      reference "Takes effect: Node restart.";
    }
    leaf sctpX2Ref {
      type string;
    }
    leaf sctpEndcX2Ref {
      type string;
    }
    leaf upX2EndcIpAddressRef {
      type ietfinet:ip-address;
    }
    leaf ipsecEpAddressRef {
      type ietfinet:ip-address;
    }
    leaf ipsecEndcEpAddressRef {
      type ietfinet:ip-address;
    }
  }
  grouping AdmissionControl-attributes {
    leaf paArpOverride {
      type eytypes:int32_range_0-15;
      default "7";
      description "range 0..15; Default value: 7.";
    }
    leaf admissionControlId {
      type string;
      mandatory true;
    }
    leaf dlTransNwBandwidth {
      type int32 {
        range "0..20000";
      }
      default "1000";
      units "Mbps";
      description "range 0..20000; Default value: 1000.";
    }
    leaf ulTransNwBandwidth {
      type int32 {
        range "0..20000";
      }
      default "1000";
      units "Mbps";
      description "range 0..20000; Default value: 1000.";
    }
    leaf arpBasedPreEmptionState {
      type enumeration {
        enum ACTIVATED;
        enum DEACTIVATED;
      }
    }
    leaf resourceReservationForPAState {
      type enumeration {
        enum ACTIVATED;
        enum DEACTIVATED;
      }
    }
    leaf zzzTemporary1 {
      type string;
    }
    leaf zzzTemporary2 {
      type string;
    }
    leaf zzzTemporary3 {
      type string;
    }
    leaf zzzTemporary4 {
      type string;
    }
    leaf zzzTemporary5 {
      type int32;
      default "-2000000000";
      description "Default value: -2000000000.";
    }
    leaf zzzTemporary6 {
      type int32;
      default "-2000000000";
      description "Default value: -2000000000.";
    }
    leaf zzzTemporary7 {
      type int32;
      default "-2000000000";
      description "Default value: -2000000000.";
    }
    leaf zzzTemp1 {
      type eytypes:int32_range_-1-10000;
      default "-1";
      description "range -1..10000; Default value: -1.";
    }
    leaf zzzTemp2 {
      type eytypes:int32_range_-1-10000;
      default "-1";
      description "range -1..10000; Default value: -1.";
    }
    leaf zzzTemp3 {
      type eytypes:int32_range_-1-20000;
      default "-1";
      description "range -1..20000; Default value: -1.";
    }
    leaf zzzTemp4 {
      type eytypes:int32_range_-1-20000;
      default "-1";
      description "range -1..20000; Default value: -1.";
    }
    leaf zzzTemp5 {
      type eytypes:int32_range_-1-20000;
      default "-1";
      description "range -1..20000; Default value: -1.";
    }
    leaf zzzTemp6 {
      type eytypes:int32_range_0-1000-2;
      default "1000";
      description "range 0..1000; Default value: 1000.";
    }
    leaf zzzTemp7 {
      type eytypes:int32_range_0-1000-2;
      default "1000";
      description "range 0..1000; Default value: 1000.";
    }
    leaf zzzTemp8 {
      type eytypes:int32_range_0-1000-2;
      default "1000";
      description "range 0..1000; Default value: 1000.";
    }
    leaf zzzTemp9 {
      type eytypes:int32_range_0-1000-2;
      default "1000";
      description "range 0..1000; Default value: 1000.";
    }
    leaf zzzTemp10 {
      type eytypes:int32_range_0-1000-2;
      default "1000";
      description "range 0..1000; Default value: 1000.";
    }
    leaf zzzTemp11 {
      type eytypes:int32_range_0-1000-2;
      default "1000";
      description "range 0..1000; Default value: 1000.";
    }
    leaf zzzTemp12 {
      type eytypes:int32_range_0-1000-2;
      default "1000";
      description "range 0..1000; Default value: 1000.";
    }
    leaf zzzTemp13 {
      type eytypes:int32_range_0-1000-2;
      default "1000";
      description "range 0..1000; Default value: 1000.";
    }
    leaf zzzTemp14 {
      type eytypes:int32_range_0-1000-2;
      default "1000";
      description "range 0..1000; Default value: 1000.";
    }
    leaf zzzTemp15 {
      type eytypes:int32_range_0-1000-2;
      default "1000";
      description "range 0..1000; Default value: 1000.";
    }
    leaf zzzTemp16 {
      type eytypes:int32_range_0-1000-2;
      default "1000";
      description "range 0..1000; Default value: 1000.";
    }
    leaf zzzTemp17 {
      type eytypes:int32_range_0-1000-2;
      default "1000";
      description "range 0..1000; Default value: 1000.";
    }
    leaf zzzTemp18 {
      type eytypes:int32_range_0-1000-2;
      default "1000";
      description "range 0..1000; Default value: 1000.";
    }
    leaf zzzTemp19 {
      type eytypes:int32_range_0-1000-2;
      default "1000";
      description "range 0..1000; Default value: 1000.";
    }
    leaf zzzTemp20 {
      type eytypes:int32_range_0-1000-2;
      status deprecated;
      default "1000";
      description "range 0..1000; Default value: 1000; Takes effect: Cell lock/unlock; Status info: Since 19.Q3. Replaced by dlNonPaGbrTn. Planned to be removed..";
      reference "Takes effect: Cell lock/unlock.";
    }
    leaf zzzTemp21 {
      type eytypes:int32_range_0-1000-2;
      status deprecated;
      default "1000";
      description "range 0..1000; Default value: 1000; Takes effect: Cell lock/unlock; Status info: Since 19.Q3. Replaced by ulNonPaGbrTn. Planned to be removed..";
      reference "Takes effect: Cell lock/unlock.";
    }
    leaf dlMbmsGbrRatio {
      type eytypes:int32_range_0-1000-2;
      default "200";
      description "range 0..1000; Default value: 200.";
    }
    leaf resourceReservationForDifferentiation {
      type eytypes:int32_range_0-30-41;
      default "5";
      description "range 0..30; Default value: 5.";
    }
    leaf dlAdmOverloadThr {
      type eytypes:int32_range_0-1000-2;
      default "950";
      description "range 0..1000; Default value: 950.";
    }
    leaf ulAdmOverloadThr {
      type eytypes:int32_range_0-1000-2;
      default "950";
      description "range 0..1000; Default value: 950.";
    }
    leaf dlAdmDifferentiationThr {
      type eytypes:int32_range_0-1000-2;
      default "500";
      description "range 0..1000; Default value: 500.";
    }
    leaf ulAdmDifferentiationThr {
      type eytypes:int32_range_0-1000-2;
      default "500";
      description "range 0..1000; Default value: 500.";
    }
    leaf admNrRrcDifferentiationThr {
      type eytypes:int32_range_0-1000-2;
      default "750";
      description "range 0..1000; Default value: 750.";
    }
    leaf admNrRbDifferentiationThr {
      type eytypes:int32_range_0-1000-2;
      default "750";
      description "range 0..1000; Default value: 750.";
    }
    leaf nrOfPaConnReservationsPerCell {
      type eytypes:int32_range_0-20;
      default "1";
      description "range 0..20; Default value: 1.";
    }
    leaf nrOfRbReservationsPerPaConn {
      type eytypes:int32_range_0-10;
      status deprecated;
      default "4";
      description "range 0..10; Default value: 4; Takes effect: Cell lock/unlock; Status info: Since 23.Q4. Planned to be removed..";
      reference "Takes effect: Cell lock/unlock.";
    }
    leaf admResourceMinQciPrio {
      type ietfinet:ip-address;
      description "range 0..14; Default value: 5.";
    }
    leaf zzzTemporary22 {
      type int32;
      default "-2000000000";
      description "Default value: -2000000000.";
    }
    leaf zzzTemporary23 {
      type int32;
      default "-2000000000";
      description "Default value: -2000000000.";
    }
    leaf zzzTemporary24 {
      type int32;
      default "-2000000000";
      description "Default value: -2000000000.";
    }
    leaf zzzTemporary25 {
      type int32;
      default "-2000000000";
      description "Default value: -2000000000.";
    }
    leaf zzzTemporary26 {
      type int32;
      default "-2000000000";
      description "Default value: -2000000000.";
    }
    leaf lbAtoThresholdLevel1 {
      type eytypes:int32_range_0-100-3;
      default "30";
      description "range 0..100; Default value: 30.";
    }
    leaf lbAtoThresholdLevel2 {
      type eytypes:int32_range_0-100-3;
      default "45";
      description "range 0..100; Default value: 45.";
    }
    leaf diffAdmCtrlFilteringEnabled {
      type boolean;
      default "false";
      description "Default value: false.";
    }
    leaf nrOfPrevPreempPaRbReservation {
      type eytypes:int32_range_0-3;
      default "0";
      description "range 0..3; Default value: 0.";
    }
    leaf srBbmPaUsersPreallocation {
      type boolean;
      default "true";
      description "Default value: true.";
    }
    leaf limitSrNonPa {
      type eytypes:int32_range_0-20;
      default "0";
      description "range 0..20; Default value: 0.";
    }
    leaf nrOfPaConnHpaReservPerCell {
      type eytypes:int32_range_0-20;
      default "0";
      description "range 0..20; Default value: 0.";
    }
    leaf paArpOverrideHpa {
      type eytypes:int32_range_0-15;
      default "0";
      description "range 0..15; Default value: 0.";
    }
    leaf dlNonPaGbrTn {
      type eytypes:int32_range_0-1000-2;
      default "750";
      description "range 0..1000; Default value: 750.";
    }
    leaf ulNonPaGbrTn {
      type eytypes:int32_range_0-1000-2;
      default "750";
      description "range 0..1000; Default value: 750.";
    }
    leaf zzzTemporary27 {
      type int32;
      default "-2000000000";
      description "Default value: -2000000000.";
    }
    leaf zzzTemporary28 {
      type int32;
      default "-2000000000";
      description "Default value: -2000000000.";
    }
    leaf preemptInactTimerMin {
      type int32 {
        range "2..86400";
      }
      default "4";
      units "s";
      description "range 2..86400; Default value: 4.";
    }
    leaf enhPttAdmCtrlRejPaReqOvlGbr {
      type boolean;
      default "true";
      description "Default value: true.";
    }
    leaf recalcPreemptableUeTimer {
      type eytypes:int32_range_1-60;
      default "1";
      units "s";
      description "range 1..60; Default value: 1.";
    }
    leaf paArpOverrideEc {
      type int32 {
        range "-1 | 1..15";
      }
      default "-1";
      description "Default value: -1.";
    }
    leaf-list pmAdmNrRrcUnknownArpRatio {
      type uint32;
    }
  }
  grouping AirIfLoadProfile-attributes {
    leaf-list reservedBy {
      type string;
    }
    leaf userLabel {
      type string {
        length "1..128";
      }
      description "length 1..128.";
    }
    leaf airIfLoadProfileId {
      type string;
      mandatory true;
    }
    leaf dlPrbLoadLevel {
      type eytypes:int32_range_0-100;
      default "0";
      units "percent";
      description "range 0..100; Default value: 0.";
    }
    leaf ailgLowPrioModType {
      type enumeration {
        enum QPSK_MOD_SCH;
        enum QAM_16_MOD_SCH;
        enum QAM_64_MOD_SCH;
      }
    }
    leaf noOfOcngPrbSeries {
      type eytypes:int32_range_1-10;
      default "1";
      description "range 1..10; Default value: 1.";
    }
    list ocngPrbSerie {
      key "id";
      leaf id {
        type uint32;
        description "Synthetic key for struct sequence entry.";
      }
      container attributes {
      leaf pdschModType {
        type enumeration {
          enum QPSK_MOD_SCH;
          enum QAM_16_MOD_SCH;
          enum QAM_64_MOD_SCH;
        }
      }
      leaf prbFirst {
        type eytypes:int32_range_0-99;
        default "0";
        description "range 0..99; Default value: 0.";
      }
      leaf prbLast {
        type eytypes:int32_range_0-99;
        default "0";
        description "range 0..99; Default value: 0.";
      }
      leaf usedSubFrameNo {
        type string;
      }
      }
    }
    list trafficModelPrb {
      key "id";
      leaf id {
        type uint32;
        description "Synthetic key for struct entry.";
      }
      container attributes {
      leaf bufferStatus {
        type enumeration {
          enum HALF_BUFFER;
          enum FULL_BUFFER;
        }
      }
      leaf noOfArtificialUsers {
        type int32 {
          range "0..400";
        }
        default "0";
        description "range 0..400; Default value: 0.";
      }
      leaf qciDistSinrHigh {
        type string;
      }
      leaf qciDistSinrMedium {
        type string;
      }
      leaf qciDistSinrLow {
        type string;
      }
      leaf ulDlRatioPerQci {
        type string;
      }
      leaf bitRatePerQci {
        type string;
      }
      }
    }
    leaf ailgHighPrio {
      type enumeration {
        enum OCNG;
        enum TRAFFIC_MODEL;
        enum NO_HIGH_PRIO_LOAD;
      }
    }
    leaf zzzTemporary1 {
      type string;
    }
    leaf zzzTemporary2 {
      type string;
    }
    leaf zzzTemporary3 {
      type string;
    }
    leaf zzzTemporary4 {
      type string;
    }
    leaf zzzTemporary5 {
      type int32;
      default "-2000000000";
      description "Default value: -2000000000.";
    }
    leaf zzzTemporary6 {
      type int32;
      default "-2000000000";
      description "Default value: -2000000000.";
    }
    leaf zzzTemporary7 {
      type int32;
      default "-2000000000";
      description "Default value: -2000000000.";
    }
    leaf ailgChangePeriod {
      type int32 {
        range "1 | 5 | 10";
      }
      default "1";
      units "ms";
      description "Default value: 1.";
    }
    leaf minLoadLevelPdcch {
      type eytypes:int32_range_0-100;
      default "0";
      units "percent";
      description "range 0..100; Default value: 0.";
    }
    leaf ailgLoadType {
      type enumeration {
        enum PDSCH_NO_BF;
        enum PDSCH_BF_TYPE1;
        enum PDSCH_NO_BF_AND_PDCCH;
        enum PDSCH_BF_TYPE1_AND_PDCCH;
        enum PDSCH_BF_TYPE2;
        enum PDSCH_BF_TYPE2_AND_PDCCH;
        enum PDCCH_ONLY;
      }
    }
    leaf zzzTemporary8 {
      type int32;
      default "-2000000000";
      description "Default value: -2000000000.";
    }
    leaf zzzTemporary9 {
      type int32;
      default "-2000000000";
      description "Default value: -2000000000.";
    }
  }
  grouping AmoFunction-attributes {
    leaf amoFunctionId {
      type string;
      mandatory true;
    }
    leaf amoAllowedInterVendor {
      type boolean;
      default "true";
      description "Default value: true.";
    }
    leaf allowInterVendorX2Signal {
      type boolean;
      default "true";
      description "Default value: true.";
    }
  }
  grouping AnrFunction-attributes {
    leaf anrFunctionId {
      type string;
      mandatory true;
    }
    leaf removeNcellTime {
      type eytypes:int32_range_1-1000;
      default "30";
      units "day";
      description "range 1..1000; Default value: 30.";
    }
    leaf removeNenbTime {
      type eytypes:int32_range_1-1000;
      default "7";
      units "day";
      description "range 1..1000; Default value: 7.";
    }
    leaf removeNrelTime {
      type eytypes:int32_range_1-1000;
      default "7";
      units "day";
      description "range 1..1000; Default value: 7.";
    }
    leaf zzzTemporary1 {
      type string;
    }
    leaf zzzTemporary2 {
      type string;
    }
    leaf zzzTemporary3 {
      type string;
    }
    leaf zzzTemporary4 {
      type string;
    }
    leaf zzzTemporary5 {
      type int32;
      default "-2000000000";
      description "Default value: -2000000000.";
    }
    leaf zzzTemporary6 {
      type int32;
      default "-2000000000";
      description "Default value: -2000000000.";
    }
    leaf zzzTemporary7 {
      type int32;
      default "-2000000000";
      description "Default value: -2000000000.";
    }
    leaf prioTime {
      type eytypes:int32_range_0-100-3;
      default "100";
      description "range 0..100; Default value: 100.";
    }
    leaf prioHoSuccRate {
      type eytypes:int32_range_0-100-3;
      default "100";
      description "range 0..100; Default value: 100.";
    }
    leaf prioHoRate {
      type eytypes:int32_range_0-100-3;
      default "100";
      description "range 0..100; Default value: 100.";
    }
    leaf maxTimeEventBasedPciConf {
      type int32 {
        range "0..1440";
      }
      default "30";
      units "minutes";
      description "range 0..1440; Default value: 30.";
    }
    leaf maxNoPciReportsEvent {
      type ietfinet:port-number;
      default "15";
      units "number of messages";
      description "range 0..100; Default value: 15.";
    }
    leaf cellRelHoAttRateThreshold {
      type int32 {
        range "0..200";
      }
      default "0";
      description "range 0..200; Default value: 0.";
    }
    leaf zzzTemporary8 {
      type int32;
      status deprecated;
      default "-2000000000";
      description "Default value: -2000000000; Status info: Since 21.Q1. Planned to be removed..";
    }
    leaf zzzTemporary9 {
      type int32;
      default "-2000000000";
      description "Default value: -2000000000.";
    }
    leaf zzzTemporary10 {
      type int32;
      default "-2000000000";
      description "Default value: -2000000000.";
    }
    leaf zzzTemporary11 {
      type int32;
      default "-2000000000";
      description "Default value: -2000000000.";
    }
    leaf zzzTemporary12 {
      type int32;
      default "-2000000000";
      description "Default value: -2000000000.";
    }
    leaf problematicCellPolicy {
      type enumeration {
        enum OFF;
        enum AUTO_DETECT;
        enum AUTO_DETECT_AND_BAR;
      }
    }
    leaf probCellDetectMedHoSuccThres {
      type int32 {
        range "2..100";
      }
      default "50";
      description "range 2..100; Default value: 50.";
    }
    leaf probCellDetectMedHoSuccTime {
      type int32 {
        range "1..30";
      }
      default "4";
      units "Days";
      description "range 1..30; Default value: 4.";
    }
    leaf probCellDetectLowHoSuccThres {
      type eytypes:int32_range_1-99;
      default "10";
      description "range 1..99; Default value: 10.";
    }
    leaf probCellDetectLowHoSuccTime {
      type int32 {
        range "1..30";
      }
      default "10";
      units "Days";
      description "range 1..30; Default value: 10.";
    }
    leaf plmnWhiteListEnabled {
      type boolean;
      default "false";
      description "Default value: false.";
    }
    leaf perEcgiMeasPlmnWhiteList {
      type boolean;
      default "true";
      description "Default value: true.";
    }
    leaf pciConflictDetectionEcgiMeas {
      type boolean;
      default "false";
      description "Default value: false.";
    }
    leaf pciConflictMobilityEcgiMeas {
      type boolean;
      default "false";
      description "Default value: false.";
    }
    leaf perCgiMeasPlmnWhiteListGeran {
      type boolean;
      default "true";
      description "Default value: true.";
    }
    leaf perCgiMeasPlmnWhiteListUtran {
      type boolean;
      default "true";
      description "Default value: true.";
    }
    leaf plmnWhiteListUtranEnabled {
      type boolean;
      default "false";
      description "Default value: false.";
    }
    leaf plmnWhiteListGeranEnabled {
      type boolean;
      default "false";
      description "Default value: false.";
    }
    leaf detectObsoleteExtCellsEnabled {
      type boolean;
      default "false";
      description "Default value: false.";
    }
    leaf s1HoPrepConsFailThres {
      type int32 {
        range "20..800";
      }
      default "50";
      description "range 20..800; Default value: 50.";
    }
    leaf removeNgnbTime {
      type eytypes:int32_range_1-1000;
      default "7";
      units "day";
      description "range 1..1000; Default value: 7.";
    }
    leaf zzzTemporary13 {
      type int32;
      default "-2000000000";
      description "Default value: -2000000000.";
    }
    leaf removeFreqRelTime {
      type int32 {
        range "-1 | 10..10000";
      }
      default "-1";
      units "minute";
      description "Default value: -1.";
    }
    leaf cgiReportCountEval {
      type ietfinet:port-number;
      default "10";
      description "range 1..200; Default value: 10.";
    }
    leaf pciConflictSelectThreshPerc {
      type eytypes:int32_range_1-100;
      default "20";
      units "percent";
      description "range 1..100; Default value: 20.";
    }
    leaf pciConflictCellSelection {
      type enumeration {
        enum OFF;
        enum MANUAL_SELECT;
        enum MANUAL_SELECT_AND_AUTO_DETECT;
        enum AUTO_SELECT_OVER_MANUAL;
      }
    }
    leaf removeEUtranFreqRelTime {
      type int32 {
        range "-1 | 1..10000";
      }
      default "-1";
      units "minute";
      description "Default value: -1.";
    }
    leaf blockingPlmnEnabled {
      type boolean;
      default "false";
      description "Default value: false.";
    }
    list blockedPlmnList {
      key "id";
      leaf id {
        type uint32;
        description "Synthetic key for struct sequence entry.";
      }
      ordered-by user;
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
  }
  grouping AnrFunctionEUtran-attributes {
    leaf anrFunctionEUtranId {
      type string;
      mandatory true;
    }
    leaf anrUesThreshInterFMax {
      type eytypes:int32_range_0-100-16;
      default "0";
      units "UE";
      description "range 0..100; Default value: 0.";
    }
    leaf anrUesThreshInterFMin {
      type eytypes:int32_range_0-100-16;
      default "0";
      units "UE";
      description "range 0..100; Default value: 0.";
    }
    leaf anrUesThreshInterFDecr {
      type eytypes:int32_range_0-1000-17;
      default "10";
      units "centiUE";
      description "range 0..1000; Default value: 10.";
    }
    leaf anrUesThreshInterFIncrHo {
      type eytypes:int32_range_0-1000-17;
      default "100";
      units "centiUE";
      description "range 0..1000; Default value: 100.";
    }
    leaf anrUesThreshInterFIncrAnr {
      type eytypes:int32_range_0-1000-17;
      default "20";
      units "centiUE";
      description "range 0..1000; Default value: 20.";
    }
    leaf anrInterFreqState {
      type enumeration {
        enum ACTIVATED;
        enum DEACTIVATED;
      }
    }
    leaf anrIntraFreqState {
      type enumeration {
        enum ACTIVATED;
        enum DEACTIVATED;
      }
    }
    leaf anrUesEUtraIntraFDecr {
      type eytypes:int32_range_0-1000-17;
      default "10";
      units "centiUE";
      description "range 0..1000; Default value: 10.";
    }
    leaf cellAddRsrpThresholdEutran {
      type int32 {
        range "-1440..0";
      }
      default "-1150";
      units "dBm";
      description "range -1440..0; Default value: -1150.";
    }
    leaf anrUesEUtraIntraFIncrHo {
      type eytypes:int32_range_0-1000-17;
      default "100";
      units "centiUE";
      description "range 0..1000; Default value: 100.";
    }
    leaf x2SetupPolicy {
      type boolean;
      default "true";
      description "Default value: true.";
    }
    leaf cellAddRsrqThresholdEutran {
      type int32 {
        range "-1920..0";
      }
      default "-1530";
      units "dB";
      description "range -1920..0; Default value: -1530.";
    }
    leaf anrUesEUtraIntraFMin {
      type eytypes:int32_range_0-100-16;
      default "0";
      units "UE";
      description "range 0..100; Default value: 0.";
    }
    leaf anrUesEUtraIntraFMax {
      type eytypes:int32_range_0-100-16;
      default "0";
      units "UE";
      description "range 0..100; Default value: 0.";
    }
    leaf hoAllowedEutranPolicy {
      type boolean;
      default "true";
      description "Default value: true.";
    }
    leaf anrUesEUtraIntraFIncrAnr {
      type eytypes:int32_range_0-1000-17;
      default "20";
      units "centiUE";
      description "range 0..1000; Default value: 20.";
    }
    leaf lbCellOffloadCapacityPolicy {
      type eytypes:int32_range_0-1000000-18;
      default "1000";
      description "range 0..1000000; Default value: 1000.";
    }
    leaf anrEutranInterFMeasReportMax {
      type ietfinet:port-number;
      default "100";
      units "DecMeasurementReports";
      description "range 0..1000; Default value: 100.";
    }
    leaf anrEutranInterFMeasReportMin {
      type ietfinet:port-number;
      default "5";
      units "DecMeasurementReports";
      description "range 0..1000; Default value: 5.";
    }
    leaf anrEutranInterFMeasReportIncr {
      type ietfinet:port-number;
      default "10";
      units "DecMeasurementReports";
      description "range 0..1000; Default value: 10.";
    }
    leaf anrEutranInterFMeasReportDecr {
      type ietfinet:port-number;
      default "1";
      units "DecMeasurementReports";
      description "range 0..1000; Default value: 1.";
    }
    leaf acquirePlmnIdListEnabled {
      type boolean;
      default "false";
      description "Default value: false.";
    }
  }
  grouping AnrFunctionGeran-attributes {
    leaf anrStateGsm {
      type enumeration {
        enum ACTIVATED;
        enum DEACTIVATED;
      }
    }
    leaf anrFunctionGeranId {
      type string;
      mandatory true;
    }
    leaf anrGeranMeasReportMax {
      type ietfinet:port-number;
      default "100";
      units "DecMeasurementReports";
      description "range 0..1000; Default value: 100.";
    }
    leaf anrGeranMeasReportMin {
      type ietfinet:port-number;
      default "5";
      units "DecMeasurementReports";
      description "range 0..1000; Default value: 5.";
    }
    leaf anrGeranMeasReportDecr {
      type ietfinet:port-number;
      default "1";
      units "DecMeasurementReports";
      description "range 0..1000; Default value: 1.";
    }
    leaf anrGeranMeasReportIncr {
      type ietfinet:port-number;
      default "10";
      units "DecMeasurementReports";
      description "range 0..1000; Default value: 10.";
    }
    leaf rimIntegrationEnabled {
      type boolean;
      default "true";
      description "Default value: true.";
    }
    leaf anrGeranMeasReportRacIncr {
      type ietfinet:port-number;
      default "20";
      units "DecMeasurementReports";
      description "range 0..1000; Default value: 20.";
    }
    leaf anrGeranRacMeasOn {
      type boolean;
      default "true";
      description "Default value: true.";
    }
    leaf problematicCellPolicy {
      type enumeration {
        enum OFF;
        enum AUTO_DETECT;
        enum AUTO_DETECT_AND_BAR;
      }
    }
  }
  grouping AnrFunctionNR-attributes {
    leaf anrFunctionNRId {
      type string;
      mandatory true;
    }
    leaf anrStateNR {
      type enumeration {
        enum ACTIVATED;
        enum DEACTIVATED;
      }
    }
    leaf gNodebIdLength {
      type eytypes:int32_range_22-32;
      default "22";
      description "range 22..32; Default value: 22.";
    }
    leaf essNRNeighborCellInfoUsed {
      type boolean;
      default "true";
      description "Default value: true.";
    }
    leaf separateEnGnbForMoranEnabled {
      type boolean;
    }
    leaf endcRachFailThrPerUe {
      type eytypes:int32_range_0-100-3;
      default "0";
      description "range 0..100; Default value: 0.";
    }
    leaf maxNoOfUeForPciConflictDetect {
      type int32 {
        range "1..2000";
      }
      default "1000";
      description "range 1..2000; Default value: 1000.";
    }
    leaf scgSessTimeForEndcRachFail {
      type int32 {
        range "0..11000";
      }
      default "1500";
      units "ms";
      description "range 0..11000; Default value: 1500.";
    }
    leaf pciConflictDetectionType {
      type enumeration {
        enum NO;
        enum FR1;
        enum FR2;
        enum BOTH;
      }
    }
    leaf cellAddRsrpThresholdNR {
      type eytypes:int32_range_-156--29;
      default "-156";
      units "dBm";
      description "range -156..-29; Default value: -156.";
    }
    leaf cellAddRsrqThresholdNR {
      type eytypes:int32_range_-435-200;
      default "-435";
      units "dB";
      description "range -435..200; Default value: -435.";
    }
    leaf supportNrFreqChange {
      type ietfinet:port-number;
    }
  }
  grouping AnrFunctionUtran-attributes {
    leaf anrStateUtran {
      type enumeration {
        enum ACTIVATED;
        enum DEACTIVATED;
      }
    }
    leaf anrFunctionUtranId {
      type string;
      mandatory true;
    }
    leaf anrUtranMeasReportMax {
      type ietfinet:port-number;
      default "100";
      units "DecMeasurementReports";
      description "range 0..1000; Default value: 100.";
    }
    leaf anrUtranMeasReportMin {
      type ietfinet:port-number;
      default "5";
      units "DecMeasurementReports";
      description "range 0..1000; Default value: 5.";
    }
    leaf anrUtranMeasReportDecr {
      type ietfinet:port-number;
      default "1";
      units "DecMeasurementReports";
      description "range 0..1000; Default value: 1.";
    }
    leaf anrUtranMeasReportIncr {
      type ietfinet:port-number;
      default "10";
      units "DecMeasurementReports";
      description "range 0..1000; Default value: 10.";
    }
    leaf hoAllowedUtranPolicy {
      type boolean;
      default "true";
      description "Default value: true.";
    }
    leaf anrUtranMeasReportAcIncr {
      type ietfinet:port-number;
      default "20";
      units "DecMeasurementReports";
      description "range 0..1000; Default value: 20.";
    }
    leaf anrUtranAcMeasOn {
      type boolean;
      default "true";
      description "Default value: true.";
    }
    leaf rimIntegrationEnabled {
      type boolean;
      default "true";
      description "Default value: true.";
    }
    leaf cellAddRscpThresholdUtranDelta {
      type eytypes:int32_range_-10-10;
      default "-1";
      units "dB";
      description "range -10..10; Default value: -1.";
    }
    leaf cellAddEcNoThresholdUtranDelta {
      type eytypes:int32_range_-100-100;
      default "-10";
      units "dB";
      description "range -100..100; Default value: -10.";
    }
    leaf srvccPolicy {
      type enumeration {
        enum NOT_SUPPORTED;
        enum CS_ONLY_SUPPORTED;
        enum PS_AND_CS_SUPPORTED;
      }
    }
  }
  grouping AnrPciConflictDrxProfile-attributes {
    leaf anrPciConflictDrxProfileId {
      type string;
      mandatory true;
    }
    leaf anrPciConflictDrxInactivityTimer {
      type enumeration {
        enum PSF1;
        enum PSF2;
        enum PSF3;
        enum PSF4;
        enum PSF5;
        enum PSF6;
        enum PSF8;
        enum PSF10;
        enum PSF20;
        enum PSF30;
        enum PSF40;
        enum PSF50;
        enum PSF60;
        enum PSF80;
        enum PSF100;
        enum PSF200;
        enum PSF300;
        enum PSF500;
        enum PSF750;
        enum PSF1280;
        enum PSF1920;
        enum PSF2560;
        enum PSF0;
      }
    }
    leaf anrPciConflictLongDrxCycle {
      type enumeration {
        enum SF10;
        enum SF20;
        enum SF32;
        enum SF40;
        enum SF64;
        enum SF80;
        enum SF128;
        enum SF160;
        enum SF256;
        enum SF320;
        enum SF512;
        enum SF640;
        enum SF1024;
        enum SF1280;
        enum SF2048;
        enum SF2560;
      }
    }
    leaf anrPciConflictOnDurationTimer {
      type enumeration {
        enum PSF1;
        enum PSF2;
        enum PSF3;
        enum PSF4;
        enum PSF5;
        enum PSF6;
        enum PSF8;
        enum PSF10;
        enum PSF20;
        enum PSF30;
        enum PSF40;
        enum PSF50;
        enum PSF60;
        enum PSF80;
        enum PSF100;
        enum PSF200;
      }
    }
  }
  grouping AutoCellCapEstFunction-attributes {
    leaf useEstimatedCellCap {
      type boolean;
      default "false";
      description "Default value: false.";
    }
    leaf autoCellCapEstFunctionId {
      type string;
      mandatory true;
    }
  }
  grouping AutoSCellMgmFunction-attributes {
    leaf asmInterFMeasReportDecr {
      type ietfinet:port-number;
      default "1";
      units "decMeasurementReport";
      description "range 0..1000; Default value: 1.";
    }
    leaf asmInterFMeasReportIncr {
      type ietfinet:port-number;
      default "10";
      units "decMeasurementReport";
      description "range 0..1000; Default value: 10.";
    }
    leaf asmInterFMeasReportMax {
      type ietfinet:port-number;
      default "100";
      units "decMeasurementReport";
      description "range 0..1000; Default value: 100.";
    }
    leaf asmInterFMeasReportMin {
      type ietfinet:port-number;
      default "20";
      units "decMeasurementReport";
      description "range 0..1000; Default value: 20.";
    }
    leaf autoSCellMgmFunctionId {
      type string;
      mandatory true;
    }
    leaf freezeDisabledSCellsTimer {
      type int32 {
        range "0..200";
      }
      status deprecated;
      default "24";
      units "hour";
      description "range 0..200; Default value: 24; Status info: Since 21.Q2. Has no functional behavior. Planned to be removed..";
    }
    leaf sCellCandidateLimit {
      type int32 {
        range "10..150";
      }
      default "50";
      description "range 10..150; Default value: 50.";
    }
    leaf asmAlarmSuppression {
      type boolean;
      default "false";
      description "Default value: false.";
    }
  }
  grouping Band46UnlicensedProfile-attributes {
    leaf band46UnlicensedProfileId {
      type string;
      mandatory true;
    }
    leaf b46A46890Allowed {
      type enumeration {
        enum CHANNEL_DISABLED;
        enum CHANNEL_ENABLED;
      }
    }
    leaf b46A46890MaxPower {
      type eytypes:int32_range_0-30-41;
      description "range 0..30.";
    }
    leaf b46A47090Allowed {
      type enumeration {
        enum CHANNEL_DISABLED;
        enum CHANNEL_ENABLED;
      }
    }
    leaf b46A47090MaxPower {
      type eytypes:int32_range_0-30-41;
      description "range 0..30.";
    }
    leaf b46A47290Allowed {
      type enumeration {
        enum CHANNEL_DISABLED;
        enum CHANNEL_ENABLED;
      }
    }
    leaf b46A47290MaxPower {
      type eytypes:int32_range_0-30-41;
      description "range 0..30.";
    }
    leaf b46A47490Allowed {
      type enumeration {
        enum CHANNEL_DISABLED;
        enum CHANNEL_ENABLED;
      }
    }
    leaf b46A47490MaxPower {
      type eytypes:int32_range_0-30-41;
      description "range 0..30.";
    }
    leaf b46A47690Allowed {
      type enumeration {
        enum CHANNEL_DISABLED;
        enum CHANNEL_ENABLED;
      }
    }
    leaf b46A47690MaxPower {
      type eytypes:int32_range_0-30-41;
      description "range 0..30.";
    }
    leaf b46B47890Allowed {
      type enumeration {
        enum CHANNEL_DISABLED;
        enum CHANNEL_ENABLED;
      }
    }
    leaf b46B47890MaxPower {
      type eytypes:int32_range_0-30-41;
      description "range 0..30.";
    }
    leaf b46B48090Allowed {
      type enumeration {
        enum CHANNEL_DISABLED;
        enum CHANNEL_ENABLED;
      }
    }
    leaf b46B48090MaxPower {
      type eytypes:int32_range_0-30-41;
      description "range 0..30.";
    }
    leaf b46B48290Allowed {
      type enumeration {
        enum CHANNEL_DISABLED;
        enum CHANNEL_ENABLED;
      }
    }
    leaf b46B48290MaxPower {
      type eytypes:int32_range_0-30-41;
      description "range 0..30.";
    }
    leaf b46B48490Allowed {
      type enumeration {
        enum CHANNEL_DISABLED;
        enum CHANNEL_ENABLED;
      }
    }
    leaf b46B48490MaxPower {
      type eytypes:int32_range_0-30-41;
      description "range 0..30.";
    }
    leaf b46B48690Allowed {
      type enumeration {
        enum CHANNEL_DISABLED;
        enum CHANNEL_ENABLED;
      }
    }
    leaf b46B48690MaxPower {
      type eytypes:int32_range_0-30-41;
      description "range 0..30.";
    }
    leaf b46C50090Allowed {
      type enumeration {
        enum CHANNEL_DISABLED;
        enum CHANNEL_ENABLED;
      }
    }
    leaf b46C50090MaxPower {
      type eytypes:int32_range_0-30-41;
      description "range 0..30.";
    }
    leaf b46C50290Allowed {
      type enumeration {
        enum CHANNEL_DISABLED;
        enum CHANNEL_ENABLED;
      }
    }
    leaf b46C50290MaxPower {
      type eytypes:int32_range_0-30-41;
      description "range 0..30.";
    }
    leaf b46C50490Allowed {
      type enumeration {
        enum CHANNEL_DISABLED;
        enum CHANNEL_ENABLED;
      }
    }
    leaf b46C50490MaxPower {
      type eytypes:int32_range_0-30-41;
      description "range 0..30.";
    }
    leaf b46C50690Allowed {
      type enumeration {
        enum CHANNEL_DISABLED;
        enum CHANNEL_ENABLED;
      }
    }
    leaf b46C50690MaxPower {
      type eytypes:int32_range_0-30-41;
      description "range 0..30.";
    }
    leaf b46C50890Allowed {
      type enumeration {
        enum CHANNEL_DISABLED;
        enum CHANNEL_ENABLED;
      }
    }
    leaf b46C50890MaxPower {
      type eytypes:int32_range_0-30-41;
      description "range 0..30.";
    }
    leaf b46C51090Allowed {
      type enumeration {
        enum CHANNEL_DISABLED;
        enum CHANNEL_ENABLED;
      }
    }
    leaf b46C51090MaxPower {
      type eytypes:int32_range_0-30-41;
      description "range 0..30.";
    }
    leaf b46C51290Allowed {
      type enumeration {
        enum CHANNEL_DISABLED;
        enum CHANNEL_ENABLED;
      }
    }
    leaf b46C51290MaxPower {
      type eytypes:int32_range_0-30-41;
      description "range 0..30.";
    }
    leaf b46C51490Allowed {
      type enumeration {
        enum CHANNEL_DISABLED;
        enum CHANNEL_ENABLED;
      }
    }
    leaf b46C51490MaxPower {
      type eytypes:int32_range_0-30-41;
      description "range 0..30.";
    }
    leaf b46C51690Allowed {
      type enumeration {
        enum CHANNEL_DISABLED;
        enum CHANNEL_ENABLED;
      }
    }
    leaf b46C51690MaxPower {
      type eytypes:int32_range_0-30-41;
      description "range 0..30.";
    }
    leaf b46C51890Allowed {
      type enumeration {
        enum CHANNEL_DISABLED;
        enum CHANNEL_ENABLED;
      }
    }
    leaf b46C51890MaxPower {
      type eytypes:int32_range_0-30-41;
      description "range 0..30.";
    }
    leaf b46C52090Allowed {
      type enumeration {
        enum CHANNEL_DISABLED;
        enum CHANNEL_ENABLED;
      }
    }
    leaf b46C52090MaxPower {
      type eytypes:int32_range_0-30-41;
      description "range 0..30.";
    }
    leaf b46C52290Allowed {
      type enumeration {
        enum CHANNEL_DISABLED;
        enum CHANNEL_ENABLED;
      }
    }
    leaf b46C52290MaxPower {
      type eytypes:int32_range_0-30-41;
      description "range 0..30.";
    }
    leaf b46C52490Allowed {
      type enumeration {
        enum CHANNEL_DISABLED;
        enum CHANNEL_ENABLED;
      }
    }
    leaf b46C52490MaxPower {
      type eytypes:int32_range_0-30-41;
      description "range 0..30.";
    }
    leaf b46D52740Allowed {
      type enumeration {
        enum CHANNEL_DISABLED;
        enum CHANNEL_ENABLED;
      }
    }
    leaf b46D52740MaxPower {
      type eytypes:int32_range_0-30-41;
      description "range 0..30.";
    }
    leaf b46D52940Allowed {
      type enumeration {
        enum CHANNEL_DISABLED;
        enum CHANNEL_ENABLED;
      }
    }
    leaf b46D52940MaxPower {
      type eytypes:int32_range_0-30-41;
      description "range 0..30.";
    }
    leaf b46D53140Allowed {
      type enumeration {
        enum CHANNEL_DISABLED;
        enum CHANNEL_ENABLED;
      }
    }
    leaf b46D53140MaxPower {
      type eytypes:int32_range_0-30-41;
      description "range 0..30.";
    }
    leaf b46D53340Allowed {
      type enumeration {
        enum CHANNEL_DISABLED;
        enum CHANNEL_ENABLED;
      }
    }
    leaf b46D53340MaxPower {
      type eytypes:int32_range_0-30-41;
      description "range 0..30.";
    }
    leaf b46D53540Allowed {
      type enumeration {
        enum CHANNEL_DISABLED;
        enum CHANNEL_ENABLED;
      }
    }
    leaf b46D53540MaxPower {
      type eytypes:int32_range_0-30-41;
      description "range 0..30.";
    }
    leaf b46D53740Allowed {
      type enumeration {
        enum CHANNEL_DISABLED;
        enum CHANNEL_ENABLED;
      }
    }
    leaf b46D53740MaxPower {
      type eytypes:int32_range_0-30-41;
      description "range 0..30.";
    }
    leaf b46D53940Allowed {
      type enumeration {
        enum CHANNEL_DISABLED;
        enum CHANNEL_ENABLED;
      }
    }
    leaf b46D53940MaxPower {
      type eytypes:int32_range_0-30-41;
      description "range 0..30.";
    }
    leaf b46D54140Allowed {
      type enumeration {
        enum CHANNEL_DISABLED;
        enum CHANNEL_ENABLED;
      }
    }
    leaf b46D54140MaxPower {
      type eytypes:int32_range_0-30-41;
      description "range 0..30.";
    }
    leaf b46D54340Allowed {
      type enumeration {
        enum CHANNEL_DISABLED;
        enum CHANNEL_ENABLED;
      }
    }
    leaf b46D54340MaxPower {
      type eytypes:int32_range_0-30-41;
      description "range 0..30.";
    }
    leaf-list reservedBy {
      type string;
    }
  }
  grouping BandCombCompression-attributes {
    leaf requestedBandCombCompression {
      type enumeration {
        enum OFF;
        enum R11_REQUESTED_BAND_COMBO;
        enum R13_BAND_COMPRESSION;
        enum R14_DIFF_FALLBACK;
      }
    }
    leaf requestReducedFormat {
      type enumeration {
        enum DISABLED;
        enum ENABLED;
      }
    }
    leaf requestSkipFallbackComb {
      type ietfinet:ip-address;
    }
    leaf requestReducedIntNonContComb {
      type enumeration {
        enum DISABLED;
        enum ENABLED;
      }
    }
    leaf requestMaxCCsDL {
      type eytypes:int32_range_0-32;
      default "0";
      description "range 0..32; Default value: 0.";
    }
    leaf requestMaxCCsUL {
      type eytypes:int32_range_0-32;
      default "0";
      description "range 0..32; Default value: 0.";
    }
    leaf-list requestedFreqBandsFiltered {
      type int32 {
        range "0..1024";
      }
    }
    leaf bandCombCompressionId {
      type string;
      mandatory true;
    }
  }
  grouping BandCombination-attributes {
    leaf bandCombinationId {
      type string;
      mandatory true;
    }
  }
  grouping BandIndication-attributes {
    leaf bandIndicationId {
      type string;
      mandatory true;
    }
    leaf bandEUtra {
      type eytypes:int32_range_1-256;
      mandatory true;
      description "range 1..256.";
    }
    leaf caBandwidthClassDl {
      type enumeration {
        enum CA_BANDWIDTH_CLASS_A;
        enum CA_BANDWIDTH_CLASS_B;
        enum CA_BANDWIDTH_CLASS_C;
        enum CA_BANDWIDTH_CLASS_D;
        enum CA_BANDWIDTH_CLASS_E;
        enum CA_BANDWIDTH_CLASS_F;
        enum UNDEFINED_VALUE;
      }
      mandatory true;
    }
    leaf caBandwidthClassUl {
      type enumeration {
        enum CA_BANDWIDTH_CLASS_A;
        enum CA_BANDWIDTH_CLASS_B;
        enum CA_BANDWIDTH_CLASS_C;
        enum CA_BANDWIDTH_CLASS_D;
        enum CA_BANDWIDTH_CLASS_E;
        enum CA_BANDWIDTH_CLASS_F;
        enum UNDEFINED_VALUE;
      }
    }
  }
  grouping BbLink-attributes {
    leaf bbLinkId {
      type string;
      mandatory true;
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf operationalState {
      type enumeration {
        enum DISABLED;
        enum ENABLED;
      }
      config false;
    }
    leaf localAddress {
      type string;
      config false;
    }
    leaf remoteAddress {
      type string;
      config false;
    }
  }
  grouping CarrierAggregationFunction-attributes {
    leaf caUsageLimit {
      type int32 {
        range "0..65535";
      }
      default "65535";
      units "UE SCell instances";
      description "range 0..65535; Default value: 65535.";
    }
    leaf caPreemptionThreshold {
      type eytypes:int32_range_0-100-27;
      default "50";
      units "percent";
      description "range 0..100; Default value: 50.";
    }
    leaf sCellActDeactDataThres {
      type eytypes:int32_range_-1-5000;
      default "100";
      units "Number of DL subframes";
      description "range -1..5000; Default value: 100.";
    }
    leaf sCellActDeactDataThresHyst {
      type eytypes:int32_range_0-5000-42;
      default "90";
      units "Number of DL subframes";
      description "range 0..5000; Default value: 90.";
    }
    leaf sCellScheduleSinrThres {
      type int32 {
        range "-200..300";
      }
      default "0";
      units "dB";
      description "range -200..300; Default value: 0.";
    }
    leaf waitForCaOpportunity {
      type ietfinet:port-number;
      default "10000";
      units "ms";
      description "range -1..60000; Default value: 10000.";
    }
    leaf waitForBetterSCellRep {
      type eytypes:int32_range_-1-32000;
      default "1000";
      units "ms";
      description "range -1..32000; Default value: 1000.";
    }
    leaf carrierAggregationFunctionId {
      type string;
      mandatory true;
    }
    leaf waitForAdditionalSCellOpportunity {
      type ietfinet:port-number;
      default "10000";
      units "ms";
      description "range -1..60000; Default value: 10000.";
    }
    leaf caRateAdjustCoeff {
      type eytypes:int32_range_0-10;
      default "10";
      description "range 0..10; Default value: 10.";
    }
    leaf fddTddSCellPriority {
      type enumeration {
        enum NONE;
        enum TDD;
        enum FDD;
      }
    }
    leaf dlOnlySCellPriorityEnabled {
      type boolean;
      default "false";
      description "Default value: false.";
    }
    leaf sCellActDeactUlDataThresh {
      type int32 {
        range "0..5000";
      }
      default "100";
      units "Number of UL subframes";
      description "range 0..5000; Default value: 100.";
    }
    leaf sCellActDeactUlDataThreshHyst {
      type int32 {
        range "0..5000";
      }
      default "90";
      units "Number of UL subframes";
      description "range 0..5000; Default value: 90.";
    }
    leaf pdcchEnhancedLaForVolte {
      type boolean;
      default "false";
      description "Default value: false.";
    }
    leaf sCellSelectionMode {
      type enumeration {
        enum ACK_SEQUENTIAL_SCELL_SELECTION;
        enum UN_ACK_SIMULTANEOUS_SCELL_SELECTION;
        enum ACK_SIMULTANEOUS_SCELL_SELECTION;
        enum AI_ACK_SIMULT_SCELL_SELECT;
        enum AI_UNACK_SIMULT_SCELL_SELECT;
      }
    }
    leaf laaSCellActDeactDataThres {
      type eytypes:int32_range_0-5000-42;
      status deprecated;
      default "100";
      units "Number of DL subframes";
      description "range 0..5000; Default value: 100; Takes effect: Cell lock/unlock; Status info: Since 17.Q3. Replaced by UnlicensedAccessFunction::laaSCellActDeactDataThres. Planned to be removed..";
      reference "Takes effect: Cell lock/unlock.";
    }
    leaf laaSCellActDeactDataThresHyst {
      type eytypes:int32_range_0-5000-42;
      status deprecated;
      default "90";
      units "Number of DL subframes";
      description "range 0..5000; Default value: 90; Takes effect: Cell lock/unlock; Status info: Since 17.Q3. Replaced by UnlicensedAccessFunction::laaSCellActDeactDataThresHyst. Planned to be removed..";
      reference "Takes effect: Cell lock/unlock.";
    }
    leaf laaSCellActDeactProhibitTimer {
      type eytypes:int32_range_0-5000-5;
      status deprecated;
      default "200";
      units "ms";
      description "range 0..5000; Default value: 200; Takes effect: Cell lock/unlock; Status info: Since 17.Q1. Replaced by laaSCellActProhibitTimer and laaSCellDeactProhibitTimer. Planned to be removed..";
      reference "Takes effect: Cell lock/unlock.";
    }
    leaf laaSCellScheduleSinrThres {
      type int32 {
        range "-200..300";
      }
      status deprecated;
      default "0";
      units "dB";
      description "range -200..300; Default value: 0; Takes effect: Cell lock/unlock; Status info: Since 17.Q1. Has no functional behavior. Planned to be removed..";
      reference "Takes effect: Cell lock/unlock.";
    }
    leaf sCellActProhibitTimer {
      type eytypes:int32_range_0-5000-5;
      default "10";
      units "ms";
      description "range 0..5000; Default value: 10.";
    }
    leaf sCellDeactProhibitTimer {
      type eytypes:int32_range_0-5000-5;
      default "200";
      units "ms";
      description "range 0..5000; Default value: 200.";
    }
    leaf sCellDeactOutOfCoverageTimer {
      type int32 {
        range "-1..5000";
      }
      default "100";
      units "ms";
      description "range -1..5000; Default value: 100.";
    }
    leaf sCellDeactDelayTimer {
      type eytypes:int32_range_0-5000-5;
      default "50";
      units "ms";
      description "range 0..5000; Default value: 50.";
    }
    leaf dynamicSCellSelectionMethod {
      type enumeration {
        enum ROUND_ROBIN;
        enum PRIORITIZED;
        enum PRIORITIZED_AUTOMATIC;
        enum GLOBAL_EVALUATION;
      }
    }
    leaf zzzTemporary1 {
      type int32;
      status deprecated;
      default "-2000000000";
      description "Default value: -2000000000; Status info: Since 17.Q3. Replaced by sCellPdcchOuterLoopMargin. Planned to be removed..";
    }
    leaf zzzTemporary2 {
      type int32;
      default "-2000000000";
      description "Default value: -2000000000.";
    }
    leaf zzzTemporary3 {
      type int32;
      default "-2000000000";
      description "Default value: -2000000000.";
    }
    leaf caPreference {
      type enumeration {
        enum NONE;
        enum DL;
        enum UL;
      }
    }
    leaf sCellPdcchOuterLoopMargin {
      type eytypes:int32_range_-200-200;
      default "100";
      units "dB";
      description "range -200..200; Default value: 100.";
    }
    leaf enhancedSelectionOfMimoAndCa {
      type boolean;
      default "false";
      description "Default value: false.";
    }
    leaf fourLayerMimoPreferred {
      type boolean;
      default "false";
      description "Default value: false.";
    }
    leaf laaSCellActProhibitTimer {
      type eytypes:int32_range_0-5000-5;
      status deprecated;
      default "10";
      units "ms";
      description "range 0..5000; Default value: 10; Takes effect: Next cell unlock; Status info: Since 19.Q3. Replaced by UnlicensedAccessFunction::laaSCellActProhibitTimer. Planned to be removed..";
      reference "Takes effect: Next cell unlock.";
    }
    leaf laaSCellDeactProhibitTimer {
      type eytypes:int32_range_0-5000-5;
      status deprecated;
      default "200";
      units "ms";
      description "range 0..5000; Default value: 200; Takes effect: Next cell unlock; Status info: Since 19.Q3. Replaced by UnlicensedAccessFunction::laaSCellDeactProhibitTimer. Planned to be removed..";
      reference "Takes effect: Next cell unlock.";
    }
    leaf selectionPolicyUlWeighting {
      type eytypes:int32_range_-1-100;
      default "50";
      units "percent";
      description "range -1..100; Default value: 50.";
    }
    leaf selectionPolicyUlTargetRatio {
      type eytypes:int32_range_0-100-27;
      status deprecated;
      default "0";
      units "percent";
      description "range 0..100; Default value: 0; Takes effect: Takes effect on next SCell reconfiguration; Status info: Since 19.Q3. Has no functional behavior. Planned to be removed..";
      reference "Takes effect: Takes effect on next SCell reconfiguration.";
    }
    leaf effectiveBwImpactDl2Layer {
      type int32 {
        range "0..200";
      }
      default "180";
      units "ratio of throughput increase";
      description "range 0..200; Default value: 180.";
    }
    leaf effectiveBwImpactDl4Layer {
      type int32 {
        range "0..200";
      }
      default "150";
      units "ratio of throughput increase";
      description "range 0..200; Default value: 150.";
    }
    leaf zzzTemporary4 {
      type int32;
      default "-2000000000";
      description "Default value: -2000000000.";
    }
    leaf zzzTemporary5 {
      type int32;
      default "-2000000000";
      description "Default value: -2000000000.";
    }
    leaf waitForBlindSelSCellRepLessTtt {
      type eytypes:int32_range_0-10000;
      default "600";
      units "ms";
      description "range 0..10000; Default value: 600.";
    }
    leaf zzzTemporary6 {
      type int32;
      default "-2000000000";
      description "Default value: -2000000000.";
    }
    leaf useAbsolutePrioForCspEffBw {
      type boolean;
      default "false";
      description "Default value: false.";
    }
    leaf dcSCellActDeactDataThres {
      type eytypes:int32_range_-1-5000;
      default "30";
      units "Number of DL subframes";
      description "range -1..5000; Default value: 30.";
    }
    leaf dcSCellActDeactDataThresHyst {
      type eytypes:int32_range_0-5000-42;
      default "30";
      units "Number of DL subframes";
      description "range 0..5000; Default value: 30.";
    }
    leaf dcSCellDeactDelayTimer {
      type eytypes:int32_range_0-5000-5;
      default "200";
      units "ms";
      description "range 0..5000; Default value: 200.";
    }
    leaf a6TriggerSCellDeconfig {
      type boolean;
      default "true";
      description "Default value: true.";
    }
    leaf sCellEvaluationLevel {
      type enumeration {
        enum EFFECTIVE;
        enum HIGH;
      }
    }
    leaf zzzTemporary7 {
      type int32;
      default "-2000000000";
      description "Default value: -2000000000.";
    }
    leaf zzzTemporary8 {
      type int32;
      default "-2000000000";
      description "Default value: -2000000000.";
    }
    leaf endcCaPolicy {
      type enumeration {
        enum LTE_PREFERRED;
        enum NR_PREFERRED;
      }
    }
    leaf caOffloadingMode {
      type enumeration {
        enum DISABLED;
        enum ENABLED_LAA_SCELLS;
        enum ENABLED_SDL_SCELLS;
        enum ENABLED_SDL_AND_LAA_SCELLS;
        enum ENABLED_SELECTED_SCELLS;
      }
    }
    leaf offloadingDataThresh {
      type eytypes:int32_range_0-5000-5;
      default "100";
      units "ms";
      description "range 0..5000; Default value: 100.";
    }
    leaf caMaxSCellsPreemptionThres {
      type eytypes:int32_range_0-100;
      default "100";
      units "percent";
      description "range 0..100; Default value: 100.";
    }
    leaf caUpswitchPreemptionThres {
      type eytypes:int32_range_0-100;
      default "100";
      units "percent";
      description "range 0..100; Default value: 100.";
    }
    leaf maxNoInitSCells {
      type int32 {
        range "1..6";
      }
      default "2";
      description "range 1..6; Default value: 2.";
    }
    leaf sCellsUpswitchDataThres {
      type eytypes:int32_range_0-5000-5;
      default "100";
      units "ms";
      description "range 0..5000; Default value: 100.";
    }
    leaf sCellsUpswitchTimer {
      type eytypes:int32_range_0-1000;
      default "50";
      units "ms";
      description "range 0..1000; Default value: 50.";
    }
    leaf caPCellOnlyInitialSetup {
      type boolean;
      default "false";
      description "Default value: false.";
    }
    leaf sCellPdcchOutLoopMarginCong {
      type eytypes:int32_range_-200-200;
      default "100";
      units "dB";
      description "range -200..200; Default value: 100.";
    }
    leaf endcBcsValidation {
      type boolean;
      default "false";
      description "Default value: false.";
    }
  }
  grouping Cdma20001xRttBandRelation-attributes {
    leaf cdma2000FreqBandRef {
      type string;
      mandatory true;
    }
    leaf cdma20001xRttBandRelationId {
      type string;
      mandatory true;
    }
    leaf cellReselectionPriority {
      type eytypes:int32_range_0-7;
      default "6";
      description "range 0..7; Default value: 6.";
    }
    leaf threshXHigh1xRtt {
      type eytypes:int32_range_0-63;
      default "63";
      description "range 0..63; Default value: 63.";
    }
    leaf threshXLow1xRtt {
      type eytypes:int32_range_0-63;
      default "63";
      description "range 0..63; Default value: 63.";
    }
    leaf userLabel {
      type string {
        length "1..128";
      }
      description "length 1..128.";
    }
  }
  grouping Cdma20001xRttCellRelation-attributes {
    leaf externalCdma20001xRttCellRef {
      type string;
      mandatory true;
    }
    leaf cdma20001xRttCellRelationId {
      type string;
      mandatory true;
    }
    leaf includeInSystemInformation {
      type boolean;
      default "true";
      description "Default value: true.";
    }
    leaf includeInSystemInformationRel9 {
      type boolean;
      default "false";
      description "Default value: false.";
    }
    leaf userLabel {
      type string {
        length "1..128";
      }
      description "length 1..128.";
    }
    leaf pmHoPrepSuccCsfb {
      type uint32;
      config false;
    }
    leaf pmHoPrepAttCsfbEm {
      type uint32;
      config false;
    }
    leaf pmHoPrepAtt1xRttSrvcc {
      type uint32;
      config false;
    }
    leaf pmZtemporary97 {
      type uint32;
      config false;
    }
    leaf pmHoPrepAttCsfb {
      type uint32;
      config false;
    }
    leaf pmHoPrepSucc1xRttSrvcc {
      type uint32;
      config false;
    }
    leaf pmHoPrepSuccCsfbEm {
      type uint32;
      config false;
    }
    leaf pmZtemporary96 {
      type uint32;
      config false;
    }
  }
  grouping Cdma20001xRttFreqRelation-attributes {
    leaf cdma2000FreqRef {
      type string;
      mandatory true;
    }
    leaf cdma20001xRttFreqRelationId {
      type string;
      mandatory true;
    }
    leaf csFallbackPrio {
      type eytypes:int32_range_0-7;
      default "0";
      description "range 0..7; Default value: 0.";
    }
    leaf csFallbackPrioEC {
      type eytypes:int32_range_0-7;
      default "0";
      description "range 0..7; Default value: 0.";
    }
    leaf userLabel {
      type string {
        length "1..128";
      }
      description "length 1..128.";
    }
    leaf qOffsetFreq {
      type eytypes:int32_range_-15-15;
      default "0";
      units "dB";
      description "range -15..15; Default value: 0.";
    }
    leaf voicePrio {
      type eytypes:int32_range_-1-7;
      default "0";
      description "range -1..7; Default value: 0.";
    }
    leaf b2Thr1RsrpCdma20001xFreqOffset {
      type eytypes:int32_range_-100-100;
      default "0";
      units "dB";
      description "range -100..100; Default value: 0.";
    }
    leaf b2Thr1RsrqCdma20001xFreqOffset {
      type eytypes:int32_range_-240-240;
      default "0";
      units "dB";
      description "range -240..240; Default value: 0.";
    }
    leaf b2Thr2Cdma20001xFreqOffset {
      type int32 {
        range "-250..250";
      }
      default "0";
      units "dB";
      description "range -250..250; Default value: 0.";
    }
  }
  grouping Cdma2000CellRelation-attributes {
    leaf cdma2000CellRelationId {
      type string;
      mandatory true;
    }
    leaf userLabel {
      type string {
        length "1..128";
      }
      description "length 1..128.";
    }
    leaf externalCdma2000CellRef {
      type string;
      mandatory true;
    }
    leaf includeInSystemInformation {
      type boolean;
      default "true";
      description "Default value: true.";
    }
    leaf includeInSystemInformationRel9 {
      type boolean;
      default "false";
      description "Default value: false.";
    }
  }
  grouping Cdma2000Freq-attributes {
    leaf freqCdma {
      type int32 {
        range "0..2047";
      }
      mandatory true;
      description "range 0..2047.";
    }
    leaf cdma2000FreqId {
      type string;
      mandatory true;
    }
    leaf-list reservedBy {
      type string;
    }
    leaf userLabel {
      type string {
        length "1..128";
      }
      description "length 1..128.";
    }
  }
  grouping Cdma2000FreqBand-attributes {
    leaf cdma2000FreqBandId {
      type string;
      mandatory true;
    }
    leaf userLabel {
      type string {
        length "1..128";
      }
      description "length 1..128.";
    }
    leaf-list reservedBy {
      type string;
    }
    leaf cdmaBandClass {
      type enumeration {
        enum BAND_CLASS_0;
        enum BAND_CLASS_1;
        enum BAND_CLASS_2;
        enum BAND_CLASS_3;
        enum BAND_CLASS_4;
        enum BAND_CLASS_5;
        enum BAND_CLASS_6;
        enum BAND_CLASS_7;
        enum BAND_CLASS_8;
        enum BAND_CLASS_9;
        enum BAND_CLASS_10;
        enum BAND_CLASS_11;
        enum BAND_CLASS_12;
        enum BAND_CLASS_13;
        enum BAND_CLASS_14;
        enum BAND_CLASS_15;
        enum BAND_CLASS_16;
        enum BAND_CLASS_17;
        enum BAND_CLASS_18;
        enum BAND_CLASS_19;
        enum BAND_CLASS_20;
        enum BAND_CLASS_21;
        enum UNDEFINED_VALUE;
      }
    }
  }
  grouping Cdma2000FreqBandRelation-attributes {
    leaf cdma2000FreqBandRelationId {
      type string;
      mandatory true;
    }
    leaf userLabel {
      type string {
        length "1..128";
      }
      description "length 1..128.";
    }
    leaf cdma2000FreqBandRef {
      type string;
      mandatory true;
    }
    leaf threshXHighHrpd {
      type eytypes:int32_range_0-63;
      default "63";
      description "range 0..63; Default value: 63.";
    }
    leaf threshXLowHrpd {
      type eytypes:int32_range_0-63;
      default "63";
      description "range 0..63; Default value: 63.";
    }
    leaf cellReselectionPriority {
      type eytypes:int32_range_0-7;
      default "6";
      description "range 0..7; Default value: 6.";
    }
  }
  grouping Cdma2000FreqRelation-attributes {
    leaf cdma2000FreqRelationId {
      type string;
      mandatory true;
    }
    leaf userLabel {
      type string {
        length "1..128";
      }
      description "length 1..128.";
    }
    leaf connectedModeMobilityPrio {
      type eytypes:int32_range_-1-7;
      default "6";
      description "range -1..7; Default value: 6.";
    }
    leaf qOffsetFreq {
      type eytypes:int32_range_-15-15;
      default "0";
      units "dB";
      description "range -15..15; Default value: 0.";
    }
    leaf cdma2000FreqRef {
      type string;
      mandatory true;
    }
    leaf b2Thr1RsrpCdma2000FreqOffset {
      type eytypes:int32_range_-100-100;
      default "0";
      units "dB";
      description "range -100..100; Default value: 0.";
    }
    leaf b2Thr1RsrqCdma2000FreqOffset {
      type eytypes:int32_range_-240-240;
      default "0";
      units "dB";
      description "range -240..240; Default value: 0.";
    }
    leaf b2Thr2Cdma2000FreqOffset {
      type int32 {
        range "-250..250";
      }
      default "0";
      units "dB";
      description "range -250..250; Default value: 0.";
    }
    list qciB2ThrOffsets {
      key "id";
      leaf id {
        type uint32;
        description "Synthetic key for struct sequence entry.";
      }
      container attributes {
      leaf qciProfileRef {
        type ietfinet:ip-address;
      }
      leaf b2Thr1RsrpCdma2000FreqQciOffset {
        type eytypes:int32_range_-100-100;
        default "0";
        units "dB";
        description "range -100..100; Default value: 0.";
      }
      leaf b2Thr1RsrqCdma2000FreqQciOffset {
        type eytypes:int32_range_-240-240;
        default "0";
        units "dB";
        description "range -240..240; Default value: 0.";
      }
      leaf b2Thr2Cdma2000FreqQciOffset {
        type int32 {
          range "-250..250";
        }
        default "0";
        units "dB";
        description "range -250..250; Default value: 0.";
      }
      }
    }
    list b2Cdma2000OffsetPerPC {
      key "id";
      leaf id {
        type uint32;
        description "Synthetic key for struct sequence entry.";
      }
      container attributes {
      leaf powerClass {
        type enumeration {
          enum PC_1;
          enum PC_2;
        }
      }
      leaf b2Thr1RsrpCdma2000PCOffset {
        type eytypes:int32_range_-100-100;
        default "0";
        units "dB";
        description "range -100..100; Default value: 0.";
      }
      leaf b2Thr1RsrqCdma2000PCOffset {
        type eytypes:int32_range_-240-240;
        default "0";
        units "dB";
        description "range -240..240; Default value: 0.";
      }
      }
    }
  }
  grouping Cdma2000Network-attributes {
    leaf cdma2000NetworkId {
      type string;
      mandatory true;
    }
    leaf userLabel {
      type string {
        length "1..128";
      }
      description "length 1..128.";
    }
  }
  grouping CellPerformance-attributes {
    leaf cellPerformanceId {
      type string;
      mandatory true;
    }
    leaf zzzTemporary1 {
      type int32;
      default "-2000000000";
      description "Default value: -2000000000.";
    }
    leaf zzzTemporary2 {
      type int32;
      default "-2000000000";
      description "Default value: -2000000000.";
    }
    leaf zzzTemporary3 {
      type int32;
      default "-2000000000";
      description "Default value: -2000000000.";
    }
    leaf zzzTemporary4 {
      type int32;
      default "-2000000000";
      description "Default value: -2000000000.";
    }
    leaf zzzTemporary5 {
      type int32;
      default "-2000000000";
      description "Default value: -2000000000.";
    }
    leaf zzzTemporary6 {
      type int32;
      default "-2000000000";
      description "Default value: -2000000000.";
    }
    leaf zzzTemporary7 {
      type int32;
      default "-2000000000";
      description "Default value: -2000000000.";
    }
    leaf zzzTemporary8 {
      type int32;
      default "-2000000000";
      description "Default value: -2000000000.";
    }
  }
  grouping CellPortion-attributes {
    leaf altitude {
      type int32 {
        range "-32768..32767";
      }
      default "0";
      units "m";
      description "range -32768..32767; Default value: 0.";
    }
    list cellPortionCoverage {
      key "id";
      leaf id {
        type uint32;
        description "Synthetic key for struct entry.";
      }
      container attributes {
      leaf posCellRadius {
        type eytypes:int32_range_0-200000;
        default "0";
        units "meter";
        description "range 0..200000; Default value: 0.";
      }
      leaf posCellOpeningAngle {
        type eytypes:int32_range_-1-3599;
        default "-1";
        units "degrees";
        description "range -1..3599; Default value: -1.";
      }
      leaf posCellBearing {
        type eytypes:int32_range_-1-3599;
        default "-1";
        units "degrees";
        description "range -1..3599; Default value: -1.";
      }
      }
    }
    leaf cellPortionId {
      type ietfinet:port-number;
      mandatory true;
    }
    list cellPortionPolygon {
      key "id";
      leaf id {
        type uint32;
        description "Synthetic key for struct sequence entry.";
      }
      container attributes {
      leaf cornerLatitude {
        type eytypes:int32_range_-90000000-90000000;
        default "0";
        units "degrees";
        description "range -90000000..90000000; Default value: 0.";
      }
      leaf cornerLongitude {
        type eytypes:int32_range_-180000000-180000000;
        default "0";
        units "degrees";
        description "range -180000000..180000000; Default value: 0.";
      }
      }
    }
    leaf latitude {
      type eytypes:int32_range_-90000000-90000000;
      default "0";
      units "degrees";
      description "range -90000000..90000000; Default value: 0.";
    }
    leaf longitude {
      type eytypes:int32_range_-180000000-180000000;
      default "0";
      units "degrees";
      description "range -180000000..180000000; Default value: 0.";
    }
    leaf lppaCellPortionId {
      type ietfinet:port-number;
      default "0";
      description "range 0..255; Default value: 0.";
    }
    leaf sectorCarrierRef {
      type string;
    }
  }
  grouping CellPortionRd-attributes {
    leaf altitude {
      type int32 {
        range "-8388608..8388607";
      }
      config false;
      units "m";
      description "range -8388608..8388607.";
    }
    leaf cellPortionRdId {
      type ietfinet:port-number;
      mandatory true;
      description "length 0..40.";
    }
    leaf latitude {
      type eytypes:int32_range_-90000000-90000000;
      config false;
      units "degrees";
      description "range -90000000..90000000.";
    }
    leaf longitude {
      type eytypes:int32_range_-180000000-180000000;
      config false;
      units "degrees";
      description "range -180000000..180000000.";
    }
    leaf lppaCellPortionId {
      type ietfinet:port-number;
      config false;
      description "range 0..32767.";
    }
    list radioDotCoverage {
      config false;
      container attributes {
      leaf posCellRadius {
        type int32 {
          range "0..100000";
        }
        units "meter";
        description "range 0..100000.";
      }
      leaf posCellOpeningAngle {
        type eytypes:int32_range_-1-3599;
        units "degrees";
        description "range -1..3599.";
      }
      leaf posCellBearing {
        type eytypes:int32_range_-1-3599;
        units "degrees";
        description "range -1..3599.";
      }
      }
    }
    leaf fieldReplaceableUnitRef {
      type string;
      config false;
    }
    list floorInformation {
      config false;
      container attributes {
      leaf floorNumber {
        type int32 {
          range "-101..1000";
        }
        description "range -101..1000.";
      }
      leaf heightOfDot {
        type int32 {
          range "-1..500";
        }
        units "m";
        description "range -1..500.";
      }
      }
    }
  }
  grouping CellResource-attributes {
    leaf cellResourceId {
      type string;
      mandatory true;
      status deprecated;
      description "MOM flags: restricted, noNotification; Status info: Since 18.Q2. Has no functional behavior. Planned to be removed..";
    }
    leaf resourceId {
      type eytypes:int32_range_0-24;
      status deprecated;
      default "0";
      description "range 0..24; Default value: 0; Takes effect: Next cell unlock; Status info: Since 18.Q2. Has no functional behavior. Planned to be removed..";
      reference "Takes effect: Next cell unlock.";
    }
    list plmnList {
      key "id";
      leaf id {
        type uint32;
        description "Synthetic key for struct sequence entry.";
      }
      description "Takes effect: Next cell unlock; Status info: Since 18.Q2. Has no functional behavior. Planned to be removed..";
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf-list spidList {
      type eytypes:int32_range_0-256;
      description "Takes effect: Next cell unlock; Status info: Since 18.Q2. Has no functional behavior. Planned to be removed..";
    }
    leaf-list reservedBy {
      type string;
      description "Status info: Since 18.Q2. Has no functional behavior. Planned to be removed..";
    }
  }
  grouping CellResources-attributes {
    leaf cellResourcesId {
      type string;
      mandatory true;
      status deprecated;
      description "MOM flags: restricted, noNotification; Status info: Since 18.Q2. Has no functional behavior. Planned to be removed..";
    }
  }
  grouping CellSleepFunction-attributes {
    leaf cellSleepFunctionId {
      type string;
      mandatory true;
    }
    leaf sleepMode {
      type enumeration {
        enum ACTIVATED;
        enum DEACTIVATED;
      }
    }
    leaf sleepState {
      type enumeration {
        enum ACTIVATED;
        enum DEACTIVATED;
      }
      config false;
    }
    leaf sleepStartTime {
      type string {
        length "5";
      }
      default "02:00";
      description "length 5..5; Default value: 02:00.";
    }
    leaf sleepEndTime {
      type string {
        length "5";
      }
      default "05:00";
      description "length 5..5; Default value: 05:00.";
    }
    leaf capCellSleepMonitorDurTimer {
      type eytypes:int32_range_1-120;
      default "15";
      units "minutes";
      description "range 1..120; Default value: 15.";
    }
    leaf capCellDlPrbSleepThreshold {
      type eytypes:int32_range_0-100;
      default "10";
      units "percent";
      description "range 0..100; Default value: 10.";
    }
    leaf capCellRrcConnSleepThreshold {
      type eytypes:int32_range_0-3000-40;
      default "5";
      description "range 0..3000; Default value: 5.";
    }
    leaf covCellWakeUpMonitorDurTimer {
      type eytypes:int32_range_1-120;
      default "15";
      units "minutes";
      description "range 1..120; Default value: 15.";
    }
    leaf covCellDlPrbWakeUpThreshold {
      type eytypes:int32_range_0-100;
      default "25";
      units "percent";
      description "range 0..100; Default value: 25.";
    }
    leaf covCellRrcConnWakeUpThreshold {
      type eytypes:int32_range_0-3000-40;
      default "30";
      description "range 0..3000; Default value: 30.";
    }
    leaf coverageCellDiscovery {
      type boolean;
      default "false";
      description "Default value: false.";
    }
    leaf capCellMobReasNotSleepThr {
      type eytypes:int32_range_-1-10000;
      default "-1";
      description "range -1..10000; Default value: -1.";
    }
    leaf capCellSleepProhibitInterval {
      type int32 {
        range "0..10000";
      }
      default "24";
      units "hours";
      description "range 0..10000; Default value: 24.";
    }
    leaf sleepProhibitStartTime {
      type string {
        length "0..19";
      }
      config false;
      description "length 0..19.";
    }
    leaf isCleanupHitRateTable {
      type boolean;
      default "true";
      description "Default value: true.";
    }
    leaf covCellUeLostWakeUpThr {
      type eytypes:int32_range_0-100;
      default "100";
      units "percent";
      description "range 0..100; Default value: 100.";
    }
    leaf covCellRrcReestWakeUpThr {
      type eytypes:int32_range_0-100;
      default "100";
      units "percent";
      description "range 0..100; Default value: 100.";
    }
    leaf covCellUeCtxtRelMin {
      type int32 {
        range "0..100000";
      }
      default "200";
      description "range 0..100000; Default value: 200.";
    }
    leaf covCellRrcConnEstAttMin {
      type int32 {
        range "0..100000";
      }
      default "200";
      description "range 0..100000; Default value: 200.";
    }
    leaf covCellLatestStatsAdaRatio {
      type eytypes:int32_range_0-100;
      default "60";
      units "percent";
      description "range 0..100; Default value: 60.";
    }
    leaf isAllowedMsmOnCovCell {
      type boolean;
      default "true";
      description "Default value: true.";
    }
    leaf wakeUpLastHoTime {
      type int32 {
        range "1..1000";
      }
      default "2";
      units "days";
      description "range 1..1000; Default value: 2.";
    }
    leaf wakeUpWaitTimer {
      type eytypes:int32_range_0-120000;
      default "0";
      units "ms";
      description "range 0..120000; Default value: 0.";
    }
    leaf sleepStartTimeApplied {
      type string {
        length "0..5";
      }
      config false;
      description "length 0..5.";
    }
    leaf sleepEndTimeApplied {
      type string {
        length "0..5";
      }
      config false;
      description "length 0..5.";
    }
    leaf covCellDlPrbWakeUpThresHigh {
      type eytypes:int32_range_0-100;
      default "35";
      units "percent";
      description "range 0..100; Default value: 35.";
    }
    leaf covCellRrcConnWakeUpThresHigh {
      type eytypes:int32_range_0-3000-40;
      default "60";
      description "range 0..3000; Default value: 60.";
    }
    leaf covCellWakeUpMonitorDurTHigh {
      type int32 {
        range "0..15";
      }
      default "0";
      units "minute";
      description "range 0..15; Default value: 0.";
    }
    leaf movingAvgPeriod {
      type eytypes:int32_range_1-5-21;
      default "5";
      description "range 1..5; Default value: 5.";
    }
    leaf prbOffloadAdjust {
      type eytypes:int32_range_0-100;
      default "0";
      units "percent";
      description "range 0..100; Default value: 0.";
    }
    leaf rrcOffloadAdjust {
      type eytypes:int32_range_0-100;
      default "0";
      units "percent";
      description "range 0..100; Default value: 0.";
    }
    leaf covCellWakeUpSeqTimer {
      type int32 {
        range "1..120";
      }
      default "15";
      units "min";
      description "range 1..120; Default value: 15.";
    }
    leaf capCellWakeUpDlPrbOffset {
      type int32 {
        range "0..50";
      }
      default "30";
      units "percent";
      description "range 0..50; Default value: 30.";
    }
    leaf capCellWakeUpRrcOffset {
      type eytypes:int32_range_0-2000-31;
      default "50";
      description "range 0..2000; Default value: 50.";
    }
    leaf wakeUpTrafficCriteria {
      type enumeration {
        enum RRC_AND_DL_PRB;
        enum RRC_OR_DL_PRB;
        enum RRC_ONLY;
        enum DL_PRB_ONLY;
      }
    }
    leaf covCellProfileRef {
      type string;
    }
    leaf capCellRequiredActivationTime {
      type int32 {
        range "2..600";
      }
      default "2";
      units "s";
      description "range 2..600; Default value: 2.";
    }
    leaf capCellWakeUpIndInstMonitor {
      type boolean;
      default "false";
      description "Default value: false.";
    }
  }
  grouping CellSleepNodeFunction-attributes {
    leaf cellSleepNodeFunctionId {
      type string;
      mandatory true;
    }
    leaf csmEutranInterFMeasReportMax {
      type ietfinet:port-number;
      default "100";
      units "DecMeasurementReports";
      description "range 0..1000; Default value: 100.";
    }
    leaf csmEutranInterFMeasReportMin {
      type ietfinet:port-number;
      default "5";
      units "DecMeasurementReports";
      description "range 0..1000; Default value: 5.";
    }
    leaf csmEutranInterFMeasReportIncr {
      type ietfinet:port-number;
      default "10";
      units "DecMeasurementReports";
      description "range 0..1000; Default value: 10.";
    }
    leaf csmEutranInterFMeasReportDecr {
      type ietfinet:port-number;
      default "1";
      units "DecMeasurementReports";
      description "range 0..1000; Default value: 1.";
    }
    leaf csmMinHitRateForCovCell {
      type int32 {
        range "0..50";
      }
      default "50";
      description "range 0..50; Default value: 50.";
    }
    leaf seqWakeUpEnabled {
      type boolean;
      default "false";
      description "Default value: false.";
    }
  }
  grouping CIotEpsOptProfile-attributes {
    leaf attachWithoutPdn {
      type enumeration {
        enum OFF;
        enum CATM1;
      }
    }
    list cIotEpsOptPlmnIdentity {
      key "id";
      leaf id {
        type uint32;
        description "Synthetic key for struct entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf cIotEpsOptProfileId {
      type string;
      mandatory true;
    }
    leaf rrcSuspendResumeEnabled {
      type boolean;
      status deprecated;
      default "false";
      description "Default value: false; Status info: Since 20.Q2. Has no functional behavior. Planned to be removed.; Specification: TS 36.300, TS 23.401, TS 36.331, TS 36.413, TS 36.423.";
    }
    leaf rrcSuspendResumeEnabledBr {
      type boolean;
      status deprecated;
      default "false";
      description "Default value: false; Status info: Since 20.Q2. Has no functional behavior. Planned to be removed.; Specification: TS 36.300, TS 23.401, TS 36.331, TS 36.413, TS 36.423.";
    }
  }
  grouping ConnSuspendResume-attributes {
    leaf connSuspendResumeId {
      type string;
      mandatory true;
    }
    list suspResPlmnId {
      key "id";
      leaf id {
        type uint32;
        description "Synthetic key for struct entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf suspResEnabled {
      type boolean;
      default "false";
      description "Default value: false.";
    }
    leaf suspResEnabledBr {
      type boolean;
      default "false";
      description "Default value: false.";
    }
  }
  grouping CtsFunction-attributes {
    leaf ctsFunctionId {
      type string;
      mandatory true;
    }
    leaf ctsMlAcsEnabled {
      type boolean;
      default "false";
      description "Default value: false.";
    }
    leaf ctsMlAcsState {
      type enumeration {
        enum ACTIVATED;
        enum DEACTIVATED;
      }
      config false;
    }
    leaf ctsMlSCellSelEnabled {
      type boolean;
      default "false";
      description "Default value: false.";
    }
    leaf ctsMlSCellSelState {
      type enumeration {
        enum ACTIVATED;
        enum DEACTIVATED;
      }
      config false;
    }
    leaf mlTrainingServiceAlarmFilterTime {
      type int32 {
        range "0..1800";
      }
      default "300";
      units "s";
      description "range 0..1800; Default value: 300.";
    }
  }
  grouping DataRadioBearer-attributes {
    leaf dataRadioBearerId {
      type string;
      mandatory true;
    }
    leaf tPollRetransmitUl {
      type int32 {
        range "5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500";
      }
      default "80";
      units "ms";
      description "Default value: 80.";
    }
    leaf ulPollPDU {
      type int32 {
        range "0 | 4 | 8 | 16 | 32 | 64 | 128 | 256";
      }
      default "16";
      description "Default value: 16.";
    }
    leaf tPollRetransmitDl {
      type int32 {
        range "5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500";
      }
      default "80";
      units "ms";
      description "Default value: 80.";
    }
    leaf dlPollPDU {
      type int32 {
        range "0 | 4 | 8 | 16 | 32 | 64 | 128 | 256";
      }
      default "16";
      description "Default value: 16.";
    }
    leaf dlMaxRetxThreshold {
      type int32 {
        range "1..4 | 6 | 8 | 16 | 32";
      }
      default "8";
      description "Default value: 8.";
    }
    leaf ulMaxRetxThreshold {
      type int32 {
        range "1..4 | 6 | 8 | 16 | 32";
      }
      default "8";
      description "Default value: 8.";
    }
    leaf ulMaxRetxThresholdLow {
      type int32 {
        range "1..4 | 6 | 8 | 16 | 32";
      }
      default "8";
      description "Default value: 8.";
    }
    leaf tPollRetransmitDrbUlCatmCeLev0 {
      type int32 {
        range "5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 2000 | 4000";
      }
      default "400";
      units "ms";
      description "Default value: 400.";
    }
    leaf tPollRetransmitDrbDlCatmCeLev0 {
      type int32 {
        range "5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 2000 | 4000";
      }
      default "500";
      units "ms";
      description "Default value: 500.";
    }
  }
  grouping DiffAdmCtrlFilteringProfile-attributes {
    leaf diffAdmCtrlFilteringProfileId {
      type string;
      mandatory true;
    }
    leaf-list firstPreEmptionSpidSet {
      type int32 {
        range "-1 | 1..256";
      }
    }
    leaf-list reservedBy {
      type string;
    }
    leaf zzzTemporary1 {
      type int32;
      default "-2000000000";
      description "Default value: -2000000000.";
    }
    leaf zzzTemporary2 {
      type int32;
      default "-2000000000";
      description "Default value: -2000000000.";
    }
    leaf zzzTemporary3 {
      type string;
    }
  }
  grouping DiffFallback-attributes {
    leaf diffFallbackId {
      type string;
      mandatory true;
    }
  }
  grouping DlComp-attributes {
    leaf dlCompMeasRprtMinSinr {
      type int32 {
        range "-100..300";
      }
      default "-20";
      units "dB";
      description "range -100..300; Default value: -20.";
    }
    leaf dlCompMeasRprtMaxSinr {
      type int32 {
        range "-100..300";
      }
      default "60";
      units "dB";
      description "range -100..300; Default value: 60.";
    }
    leaf dlCompId {
      type string;
      mandatory true;
    }
  }
  grouping DrxProfile-attributes {
    leaf drxProfileId {
      type string;
      mandatory true;
    }
    leaf onDurationTimer {
      type enumeration {
        enum PSF1;
        enum PSF2;
        enum PSF3;
        enum PSF4;
        enum PSF5;
        enum PSF6;
        enum PSF8;
        enum PSF10;
        enum PSF20;
        enum PSF30;
        enum PSF40;
        enum PSF50;
        enum PSF60;
        enum PSF80;
        enum PSF100;
        enum PSF200;
      }
    }
    leaf drxInactivityTimer {
      type enumeration {
        enum PSF1;
        enum PSF2;
        enum PSF3;
        enum PSF4;
        enum PSF5;
        enum PSF6;
        enum PSF8;
        enum PSF10;
        enum PSF20;
        enum PSF30;
        enum PSF40;
        enum PSF50;
        enum PSF60;
        enum PSF80;
        enum PSF100;
        enum PSF200;
        enum PSF300;
        enum PSF500;
        enum PSF750;
        enum PSF1280;
        enum PSF1920;
        enum PSF2560;
        enum PSF0;
      }
    }
    leaf drxRetransmissionTimer {
      type enumeration {
        enum PSF1;
        enum PSF2;
        enum PSF4;
        enum PSF6;
        enum PSF8;
        enum PSF16;
        enum PSF24;
        enum PSF33;
      }
    }
    leaf shortDrxCycle {
      type enumeration {
        enum SF2;
        enum SF5;
        enum SF8;
        enum SF10;
        enum SF16;
        enum SF20;
        enum SF32;
        enum SF40;
        enum SF64;
        enum SF80;
        enum SF128;
        enum SF160;
        enum SF256;
        enum SF320;
        enum SF512;
        enum SF640;
      }
    }
    leaf shortDrxCycleTimer {
      type eytypes:int32_range_0-16;
      default "4";
      description "range 0..16; Default value: 4.";
    }
    leaf longDrxCycle {
      type enumeration {
        enum SF10;
        enum SF20;
        enum SF32;
        enum SF40;
        enum SF64;
        enum SF80;
        enum SF128;
        enum SF160;
        enum SF256;
        enum SF320;
        enum SF512;
        enum SF640;
        enum SF1024;
        enum SF1280;
        enum SF2048;
        enum SF2560;
      }
    }
    leaf longDrxCycleOnly {
      type enumeration {
        enum SF10;
        enum SF20;
        enum SF32;
        enum SF40;
        enum SF64;
        enum SF80;
        enum SF128;
        enum SF160;
        enum SF256;
        enum SF320;
        enum SF512;
        enum SF640;
        enum SF1024;
        enum SF1280;
        enum SF2048;
        enum SF2560;
      }
    }
    leaf drxState {
      type enumeration {
        enum DISABLED;
        enum ENABLED;
        enum ENABLED_COVERAGE_OPTIMIZED;
      }
    }
  }
  grouping DynamicBlerTarget-attributes {
    leaf dynamicBlerTargetId {
      type string;
      mandatory true;
    }
    leaf dlActivitySubscrDelay {
      type int32 {
        range "1..1440";
      }
      default "120";
      units "minute";
      description "range 1..1440; Default value: 120.";
    }
    leaf dlAiLaCellRankingUpdatePeriod {
      type int32 {
        range "1..1440";
      }
      default "120";
      units "min";
      description "range 1..1440; Default value: 120.";
    }
  }
  grouping EabConfProfileBr-attributes {
    leaf eabConfProfileBrId {
      type string;
      mandatory true;
    }
    leaf eabCategory {
      type enumeration {
        enum CATEGORY_A;
        enum CATEGORY_B;
        enum CATEGORY_C;
        enum OFF;
      }
    }
    leaf eabBarringBitmap {
      type eytypes:int32_range_0-1023-23;
      default "0";
      description "range 0..1023; Default value: 0.";
    }
    leaf eabBarringTime {
      type int32 {
        range "16..4095";
      }
      default "32";
      description "range 16..4095; Default value: 32.";
    }
    leaf-list reservedBy {
      type string;
    }
  }
  grouping EndcDistrProfile-attributes {
    leaf endcDistrProfileId {
      type string;
      mandatory true;
    }
    leaf endcUserThreshold {
      type int32 {
        range "-1..4000";
      }
      default "-1";
      description "range -1..4000; Default value: -1.";
    }
    leaf-list gUtranFreqDistribution {
      type eytypes:int32_range_1-100;
      ordered-by user;
    }
    leaf-list gUtranFreqRef {
      type string;
      ordered-by user;
    }
    leaf-list mandatoryGUtranFreqRef {
      type string;
      ordered-by user;
    }
    leaf-list reservedBy {
      type string;
    }
    leaf-list mandatoryHiPrioGUtranFreqRef {
      type ietfinet:ip-address;
      ordered-by user;
    }
  }
  grouping EndcProfile-attributes {
    leaf endcProfileId {
      type string;
      mandatory true;
    }
    leaf meNbS1TermReqArpLev {
      type eytypes:int32_range_0-15;
      default "7";
      description "range 0..15; Default value: 7.";
    }
    leaf userLabel {
      type string {
        length "1..128";
      }
      description "length 1..128.";
    }
    leaf-list reservedBy {
      type string;
    }
    leaf splitNotAllowedUeArpLev {
      type eytypes:int32_range_0-15;
      default "7";
      description "range 0..15; Default value: 7.";
    }
    leaf splitNotAllowedNonDynPwrSUe {
      type boolean;
      status deprecated;
      default "false";
      description "Default value: false; Takes effect: New connection; Status info: Since 19.Q1. Has no functional behavior. Planned to be removed..";
      reference "Takes effect: New connection.";
    }
    leaf-list meNbS1TermExclArpList {
      type eytypes:int32_range_1-15-8;
      ordered-by user;
    }
  }
  grouping EndcProfilePredefined-attributes {
    leaf endcProfilePredefinedId {
      type string;
      mandatory true;
    }
    leaf meNbS1TermReqArpLev {
      type eytypes:int32_range_0-15;
      config false;
      description "range 0..15.";
    }
    leaf userLabelPredefined {
      type string {
        length "1..128";
      }
      config false;
      description "length 1..128.";
    }
    leaf-list reservedBy {
      type string;
    }
    leaf splitNotAllowedUeArpLev {
      type eytypes:int32_range_0-15;
      config false;
      description "range 0..15.";
    }
    leaf splitNotAllowedNonDynPwrSUe {
      type boolean;
      config false;
      status deprecated;
      description "Status info: Since 19.Q1. Has no functional behavior. Planned to be removed..";
    }
  }
  grouping EndcUserProfile-attributes {
    leaf endcMeasTimeOverride {
      type int32 {
        range "-1 | 40..120000";
      }
      default "2000";
      units "ms";
      description "Default value: 2000.";
    }
    leaf endcMeasRestartTimeOverride {
      type int32 {
        range "-1..240000";
      }
      default "-1";
      units "ms";
      description "range -1..240000; Default value: -1.";
    }
    leaf-list reservedBy {
      type string;
    }
    leaf endcUserProfileId {
      type string;
      mandatory true;
    }
    leaf endcAllowedOverride {
      type boolean;
      default "true";
      description "Default value: true.";
    }
    leaf endcSetupDlPktAgeThrOverride {
      type int32 {
        range "0 | 10..1000";
      }
      default "0";
      units "ms";
      description "Default value: 0.";
    }
    leaf endcSetupDlPktVolThrOverride {
      type eytypes:int32_range_0-30000;
      default "0";
      units "kB";
      description "range 0..30000; Default value: 0.";
    }
    leaf endcB1MeasGapEnabledOverride {
      type enumeration {
        enum NO_OVERRIDE;
        enum ENABLED;
        enum DISABLED;
      }
      status deprecated;
      default "NO_OVERRIDE";
      description "Default value: NO_OVERRIDE; Takes effect: New connection; Status info: Since 23.Q1. Replaced by EndcUserProfile::endcB1MeasGapConfigOverride. Planned to be removed..";
      reference "Takes effect: New connection.";
    }
    leaf b1ThresholdRsrpOverride {
      type int32 {
        range "-1000 | -156..-29";
      }
      default "-1000";
      units "dBm";
      description "Default value: -1000.";
    }
    leaf b1ThresholdRsrqOverride {
      type int32 {
        range "-1000 | -435..200";
      }
      default "-1000";
      units "dB";
      description "Default value: -1000.";
    }
    leaf hysteresisB1Override {
      type int32 {
        range "-1000 | 0..30";
      }
      default "-1000";
      units "dB";
      description "Default value: -1000.";
    }
    leaf timeToTriggerB1Override {
      type int32 {
        range "-1000 | 0 | 40 | 64 | 80 | 100 | 128 | 160 | 256 | 320 | 480 | 512 | 640 | 1024 | 1280 | 2560 | 5120";
      }
      default "-1000";
      units "ms";
      description "Default value: -1000.";
    }
    leaf endcB1MeasGapConfigOverride {
      type enumeration {
        enum NO_OVERRIDE;
        enum ENABLED;
        enum DISABLED;
        enum DISABLED_FR1;
        enum DISABLED_FR2;
      }
    }
    leaf loopingEndcProtectionEnabledOverride {
      type enumeration {
        enum NO_OVERRIDE;
        enum ENABLED;
        enum DISABLED;
      }
    }
    leaf loopingEndcBackoffDurationOverride {
      type int32 {
        range "-1000 | 0..86400";
      }
      default "-1000";
      units "s";
      description "Default value: -1000.";
    }
    leaf loopingEndcShortScgSessTimeOverride {
      type int32 {
        range "-1000 | 0..30000";
      }
      default "-1000";
      units "ms";
      description "Default value: -1000.";
    }
    leaf loopingEndcConsecFailThrOverride {
      type int32 {
        range "-1000 | 1..100";
      }
      default "-1000";
      description "Default value: -1000.";
    }
    leaf endcInhibitTimeOverride {
      type int32 {
        range "-1000 | -1 | 100..240000";
      }
      default "-1000";
      units "ms";
      description "Default value: -1000.";
    }
    leaf endcSetupUlBsVolThrOverride {
      type int32 {
        range "-1000 | 0..150000";
      }
      default "-1000";
      units "bytes";
      description "Default value: -1000.";
    }
  }
  grouping ENodeBFunction-attributes {
    leaf ipsecEpAddress2Ref {
      type ietfinet:ip-address;
    }
    leaf timeAndPhaseSynchCritical {
      type boolean;
      default "false";
      description "Default value: false.";
    }
    leaf eNodeBFunctionId {
      type string;
      mandatory true;
    }
    leaf userLabel {
      type string {
        length "1..128";
      }
      description "length 1..128.";
    }
    leaf sctpRef {
      type string;
    }
    leaf dnsLookupOnTai {
      type enumeration {
        enum OFF;
        enum ON;
      }
    }
    leaf dnsLookupTimer {
      type int32 {
        range "0..1000";
      }
      default "0";
      units "Hour";
      description "range 0..1000; Default value: 0.";
    }
    leaf dscpLabel {
      type eytypes:int32_range_0-63;
      default "24";
      description "range 0..63; Default value: 24.";
    }
    leaf eNBId {
      type eytypes:int32_range_-1-1048575;
      default "-1";
      description "range -1..1048575; Default value: -1.";
    }
    list eNodeBPlmnId {
      key "id";
      leaf id {
        type uint32;
        description "Synthetic key for struct entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    list x2BlackList {
      key "id";
      leaf id {
        type uint32;
        description "Synthetic key for struct sequence entry.";
      }
      container attributes {
      leaf mcc {
        type eytypes:int32_range_0-999;
        default "1";
        description "range 0..999; Default value: 1.";
      }
      leaf mnc {
        type eytypes:int32_range_0-999;
        default "1";
        description "range 0..999; Default value: 1.";
      }
      leaf mncLength {
        type eytypes:int32_range_2-3;
        default "2";
        description "range 2..3; Default value: 2.";
      }
      leaf enbId {
        type eytypes:int32_range_-1-1048575;
        default "0";
        description "range -1..1048575; Default value: 0.";
      }
      }
    }
    leaf x2retryTimerMaxAuto {
      type int32 {
        range "0..60000";
      }
      default "1440";
      units "minute";
      description "range 0..60000; Default value: 1440.";
    }
    leaf x2retryTimerStart {
      type int32 {
        range "0..1000";
      }
      default "30";
      units "s";
      description "range 0..1000; Default value: 30.";
    }
    list x2WhiteList {
      key "id";
      leaf id {
        type uint32;
        description "Synthetic key for struct sequence entry.";
      }
      container attributes {
      leaf mcc {
        type eytypes:int32_range_0-999;
        default "1";
        description "range 0..999; Default value: 1.";
      }
      leaf mnc {
        type eytypes:int32_range_0-999;
        default "1";
        description "range 0..999; Default value: 1.";
      }
      leaf mncLength {
        type eytypes:int32_range_2-3;
        default "2";
        description "range 2..3; Default value: 2.";
      }
      leaf enbId {
        type eytypes:int32_range_-1-1048575;
        default "0";
        description "range -1..1048575; Default value: 0.";
      }
      }
    }
    leaf s1RetryTimer {
      type int32 {
        range "1..300";
      }
      default "30";
      units "s";
      description "range 1..300; Default value: 30.";
    }
    leaf ulSchedulerDynamicBWAllocationEnabled {
      type boolean;
      default "true";
      description "Default value: true.";
    }
    leaf x2IpAddrViaS1Active {
      type ietfinet:ip-address;
      description "Default value: true.";
    }
    leaf nnsfMode {
      type enumeration {
        enum SPLMN;
        enum RPLMN_IF_SAME_AS_SPLMN;
        enum RPLMN_IF_MME_SERVES_SPLMN;
      }
    }
    leaf rrcConnReestActive {
      type boolean;
      default "false";
      description "Default value: false.";
    }
    leaf zzzTemporary1 {
      type string;
    }
    leaf zzzTemporary2 {
      type string;
    }
    leaf zzzTemporary3 {
      type string;
    }
    leaf zzzTemporary5 {
      type string;
    }
    leaf zzzTemporary6 {
      type string;
    }
    leaf zzzTemporary7 {
      type string;
    }
    leaf zzzTemporary8 {
      type string;
    }
    leaf zzzTemporary9 {
      type int32;
      default "-2000000000";
      description "Default value: -2000000000.";
    }
    leaf zzzTemporary10 {
      type int32;
      default "-2000000000";
      description "Default value: -2000000000.";
    }
    leaf zzzTemporary11 {
      type int32;
      default "-2000000000";
      description "Default value: -2000000000.";
    }
    leaf zzzTemporary12 {
      type int32;
      default "-2000000000";
      description "Default value: -2000000000.";
    }
    leaf x2SetupTwoWayRelations {
      type boolean;
      default "true";
      description "Default value: true.";
    }
    leaf timePhaseMaxDeviation {
      type eytypes:int32_range_9-100;
      default "100";
      units "microseconds";
      description "range 9..100; Default value: 100.";
    }
    leaf licCapDistrMethod {
      type enumeration {
        enum SYSTEM;
        enum OPERATOR;
      }
    }
    leaf s1HODirDataPathAvail {
      type boolean;
      default "false";
      description "Default value: false.";
    }
    leaf minRandc {
      type int32 {
        range "1..254";
      }
      default "1";
      description "range 1..254; Default value: 1.";
    }
    leaf maxRandc {
      type int32 {
        range "2..255";
      }
      default "255";
      description "range 2..255; Default value: 255.";
    }
    leaf randUpdateInterval {
      type int32 {
        range "15..1440";
      }
      default "200";
      units "minutes";
      description "range 15..1440; Default value: 200.";
    }
    leaf zzzTemporary13 {
      type int32;
      default "-2000000000";
      description "Default value: -2000000000.";
    }
    leaf zzzTemporary16 {
      type int32;
      default "-2000000000";
      description "Default value: -2000000000.";
    }
    leaf mfbiSupport {
      type ietfinet:port-number;
      config false;
    }
    leaf upIpAddressRef {
      type ietfinet:ip-address;
    }
    leaf pwsPersistentStorage {
      type enumeration {
        enum OFF;
        enum ON;
      }
    }
    leaf csfbMeasFromIdleMode {
      type boolean;
      default "true";
      description "Default value: true.";
    }
    leaf maxNoCellsNaccCsfb {
      type eytypes:int32_range_0-16;
      default "4";
      description "range 0..16; Default value: 4.";
    }
    leaf maxNoCellsNaccSessionCont {
      type eytypes:int32_range_0-16;
      default "4";
      description "range 0..16; Default value: 4.";
    }
    leaf forcedSiTunnelingActive {
      type boolean;
      default "false";
      description "Default value: false.";
    }
    leaf initPreschedulingEnable {
      type boolean;
      default "true";
      description "Default value: true.";
    }
    leaf zzzTemporary18 {
      type int32;
      default "-2000000000";
      description "Default value: -2000000000.";
    }
    leaf zzzTemporary21 {
      type int32;
      default "-2000000000";
      description "Default value: -2000000000.";
    }
    leaf zzzTemporary22 {
      type int32;
      default "-2000000000";
      description "Default value: -2000000000.";
    }
    leaf zzzTemporary23 {
      type int32;
      default "-2000000000";
      description "Default value: -2000000000.";
    }
    leaf zzzTemporary24 {
      type int32;
      default "-2000000000";
      description "Default value: -2000000000.";
    }
    leaf zzzTemporary25 {
      type int32;
      default "-2000000000";
      description "Default value: -2000000000.";
    }
    leaf zzzTemporary26 {
      type int32;
      default "-2000000000";
      description "Default value: -2000000000.";
    }
    leaf tOutgoingHoExecCdma1xRtt {
      type int32 {
        range "1..32000";
      }
      default "5";
      units "s";
      description "range 1..32000; Default value: 5.";
    }
    leaf biasThpWifiMobility {
      type eytypes:int32_range_1-100-4;
      default "10";
      description "range 1..100; Default value: 10.";
    }
    leaf tS1HoCancelTimer {
      type eytypes:int32_range_1-30;
      default "3";
      units "s";
      description "range 1..30; Default value: 3.";
    }
    leaf dnsSelectionS1X2Ref {
      type string;
    }
    leaf releaseInactiveUesInactTime {
      type int32 {
        range "0..32767";
      }
      default "1";
      units "s";
      description "range 0..32767; Default value: 1.";
    }
    leaf releaseInactiveUesMpLoadLevel {
      type enumeration {
        enum NOT_HIGH_LOAD;
        enum HIGH_LOAD;
        enum VERY_HIGH_LOAD;
      }
    }
    leaf combCellSectorSelectThreshTx {
      type int32 {
        range "0..1800";
      }
      default "300";
      units "dB";
      description "range 0..1800; Default value: 300.";
    }
    leaf combCellSectorSelectThreshRx {
      type int32 {
        range "0..1800";
      }
      default "300";
      units "dB";
      description "range 0..1800; Default value: 300.";
    }
    leaf timePhaseMaxDeviationSib16 {
      type eytypes:int32_range_9-100;
      default "100";
      units "microseconds";
      description "range 9..100; Default value: 100.";
    }
    leaf timePhaseMaxDeviationMbms {
      type eytypes:int32_range_9-100;
      default "50";
      units "microseconds";
      description "range 9..100; Default value: 50.";
    }
    leaf timePhaseMaxDeviationOtdoa {
      type eytypes:int32_range_9-100;
      default "9";
      units "microseconds";
      description "range 9..100; Default value: 9.";
    }
    leaf timePhaseMaxDeviationCdma2000 {
      type eytypes:int32_range_9-100;
      default "100";
      units "microseconds";
      description "range 9..100; Default value: 100.";
    }
    leaf timePhaseMaxDeviationTdd {
      type eytypes:int32_range_9-100;
      default "15";
      units "microseconds";
      description "range 9..100; Default value: 15.";
    }
    leaf timePhaseSynchStateSib16 {
      type boolean;
      config false;
    }
    leaf timePhaseSynchStateMbms {
      type boolean;
      config false;
    }
    leaf timePhaseSynchStateOtdoa {
      type boolean;
      config false;
    }
    leaf timePhaseSynchStateCdma2000 {
      type boolean;
      config false;
    }
    leaf timeAndPhaseSynchAlignment {
      type boolean;
      default "false";
      description "Default value: false.";
    }
    leaf licConnectedUsersPercentileConf {
      type eytypes:int32_range_1-100;
      default "90";
      units "percent";
      description "range 1..100; Default value: 90.";
    }
    leaf licDlBbPercentileConf {
      type eytypes:int32_range_1-100;
      default "90";
      units "percent";
      description "range 1..100; Default value: 90.";
    }
    leaf licUlBbPercentileConf {
      type eytypes:int32_range_1-100;
      default "90";
      units "percent";
      description "range 1..100; Default value: 90.";
    }
    leaf licDlPrbPercentileConf {
      type eytypes:int32_range_1-100;
      default "90";
      units "percent";
      description "range 1..100; Default value: 90.";
    }
    leaf licUlPrbPercentileConf {
      type eytypes:int32_range_1-100;
      default "90";
      units "percent";
      description "range 1..100; Default value: 90.";
    }
    leaf mtRreWithoutNeighborActive {
      type boolean;
      default "true";
      description "Default value: true.";
    }
    leaf csmMinHighHitThreshold {
      type int32 {
        range "50..100";
      }
      default "70";
      units "percent";
      description "range 50..100; Default value: 70.";
    }
    leaf checkEmergencySoftLock {
      type boolean;
      default "false";
      description "Default value: false.";
    }
    leaf softLockRwRWaitTimerInternal {
      type int32 {
        range "20..80";
      }
      default "60";
      units "s";
      description "range 20..80; Default value: 60.";
    }
    leaf softLockRwRWaitTimerOperator {
      type int32 {
        range "20..80";
      }
      default "60";
      units "s";
      description "range 20..80; Default value: 60.";
    }
    leaf mfbiSupportPolicy {
      type ietfinet:port-number;
      description "Default value: false.";
    }
    leaf zzzTemporary28 {
      type int32;
      default "-2000000000";
      description "Default value: -2000000000.";
    }
    leaf zzzTemporary30 {
      type int32;
      status deprecated;
      default "-2000000000";
      description "Default value: -2000000000; Status info: Since 17.Q2. Replaced by attribute CarrierAggregationFunction::waitForBlindSelSCellRepLessTtt. Planned to be removed..";
    }
    leaf zzzTemporary32 {
      type int32;
      default "-2000000000";
      description "Default value: -2000000000.";
    }
    leaf zzzTemporary33 {
      type int32;
      status deprecated;
      default "-2000000000";
      description "Default value: -2000000000; Status info: Since 19.Q1. Has no functional behavior. Planned to be removed..";
    }
    leaf zzzTemporary34 {
      type int32;
      default "-2000000000";
      description "Default value: -2000000000.";
    }
    leaf tddVoipDrxProfileId {
      type ietfinet:ip-address;
      description "range -1..17; Default value: -1.";
    }
    leaf measuringEcgiWithAgActive {
      type boolean;
      default "false";
      description "Default value: false.";
    }
    leaf enabledUlTrigMeas {
      type boolean;
      default "false";
      description "Default value: false.";
    }
    leaf ulMaxWaitingTimeGlobal {
      type eytypes:int32_range_0-500;
      default "0";
      units "ms";
      description "range 0..500; Default value: 0.";
    }
    leaf dlMaxWaitingTimeGlobal {
      type eytypes:int32_range_0-500;
      default "0";
      units "ms";
      description "range 0..500; Default value: 0.";
    }
    leaf tRelocOverall {
      type eytypes:int32_range_1-20;
      default "5";
      units "s";
      description "range 1..20; Default value: 5.";
    }
    leaf alignTtiBundWUlTrigSinr {
      type enumeration {
        enum OFF;
        enum ULTRIG;
      }
    }
    leaf s1GtpuEchoEnable {
      type enumeration {
        enum DISABLED;
        enum PERIODIC;
      }
    }
    leaf x2GtpuEchoEnable {
      type enumeration {
        enum DISABLED;
        enum PERIODIC;
      }
    }
    leaf s1GtpuEchoDscp {
      type eytypes:int32_range_0-63;
      default "14";
      description "range 0..63; Default value: 14.";
    }
    leaf x2GtpuEchoDscp {
      type eytypes:int32_range_0-63;
      default "14";
      description "range 0..63; Default value: 14.";
    }
    leaf gtpuErrorIndicationDscp {
      type eytypes:int32_range_0-63;
      default "40";
      description "range 0..63; Default value: 40.";
    }
    leaf s1GtpuEchoFailureAction {
      type enumeration {
        enum NONE;
        enum RESET;
      }
    }
    leaf zzzTemporary35 {
      type int32;
      default "-2000000000";
      description "Default value: -2000000000.";
    }
    leaf zzzTemporary36 {
      type int32;
      default "-2000000000";
      description "Default value: -2000000000.";
    }
    leaf zzzTemporary37 {
      type int32;
      default "-2000000000";
      description "Default value: -2000000000.";
    }
    leaf zzzTemporary39 {
      type int32;
      default "-2000000000";
      description "Default value: -2000000000.";
    }
    leaf zzzTemporary40 {
      type int32;
      default "-2000000000";
      description "Default value: -2000000000.";
    }
    leaf caAwareMfbiIntraCellHo {
      type boolean;
      default "false";
      description "Default value: false.";
    }
    leaf prioritizeAdditionalBands {
      type boolean;
      default "false";
      description "Default value: false.";
    }
    leaf useBandPrioritiesInSCellEval {
      type boolean;
      default "false";
      description "Default value: false.";
    }
    leaf useBandPrioritiesInSib1 {
      type boolean;
      status deprecated;
      default "false";
      description "Default value: false; Status info: Since 18.Q2. Has no functional behavior. Planned to be removed.";
    }
    leaf ipsecEpAddressRef {
      type ietfinet:ip-address;
    }
    leaf upX2IpAddressRef {
      type ietfinet:ip-address;
    }
    leaf sctpX2Ref {
      type string;
    }
    leaf zzzTemporary43 {
      type string;
    }
    leaf eranVlanPortRef {
      type ietfinet:port-number;
    }
    leaf interEnbCaTunnelDscp {
      type eytypes:int32_range_0-63;
      default "14";
      description "range 0..63; Default value: 14.";
    }
    leaf timePhaseMaxDeviationIeNbCa {
      type eytypes:int32_range_9-100;
      default "30";
      units "microseconds";
      description "range 9..100; Default value: 30.";
    }
    leaf ulBbCapacityNet {
      type eytypes:int32_range_-1-65535;
      config false;
      units "Mbps";
      description "range -1..65535.";
    }
    leaf ulBbCapacityMaxLimit {
      type eytypes:int32_range_-1-65535;
      config false;
      units "Mbps";
      description "range -1..65535.";
    }
    leaf dlBbCapacityNet {
      type eytypes:int32_range_-1-65535;
      config false;
      units "Mbps";
      description "range -1..65535.";
    }
    leaf dlBbCapacityMaxLimit {
      type eytypes:int32_range_-1-65535;
      config false;
      units "Mbps";
      description "range -1..65535.";
    }
    leaf altNasBackTo {
      type enumeration {
        enum DEFAULT_DCN;
        enum SENT_NAS_REQUEST;
      }
    }
    leaf zzzTemporary41 {
      type int32;
      default "-2000000000";
      description "Default value: -2000000000.";
    }
    leaf zzzTemporary42 {
      type int32;
      default "-2000000000";
      description "Default value: -2000000000.";
    }
    leaf zzzTemporary54 {
      type int32;
      status deprecated;
      default "-2000000000";
      description "Default value: -2000000000; Status info: Since 19.Q4. Has no functional behavior. Planned to be removed..";
    }
    leaf zzzTemporary44 {
      type int32;
      status deprecated;
      default "-2000000000";
      description "Default value: -2000000000; Status info: Since 17.Q3. Replaced by inactivitySupervisionTimerNb. Planned to be removed..";
    }
    leaf zzzTemporary45 {
      type int32;
      status deprecated;
      default "-2000000000";
      description "Default value: -2000000000; Status info: Since 17.Q3. Replaced by inactivitySupervisionTimerNb. Planned to be removed..";
    }
    leaf zzzTemporary46 {
      type int32;
      status deprecated;
      default "-2000000000";
      description "Default value: -2000000000; Status info: Since 17.Q3. Replaced by inactivitySupervisionTimerNb. Planned to be removed..";
    }
    leaf zzzTemporary47 {
      type int32;
      default "-2000000000";
      description "Default value: -2000000000.";
    }
    leaf zzzTemporary48 {
      type int32;
      default "-2000000000";
      description "Default value: -2000000000.";
    }
    leaf zzzTemporary49 {
      type int32;
      default "-2000000000";
      description "Default value: -2000000000.";
    }
    leaf zzzTemporary50 {
      type int32;
      default "-2000000000";
      description "Default value: -2000000000.";
    }
    leaf zzzTemporary51 {
      type int32;
      default "-2000000000";
      description "Default value: -2000000000.";
    }
    leaf zzzTemporary52 {
      type int32;
      default "-2000000000";
      description "Default value: -2000000000.";
    }
    leaf zzzTemporary53 {
      type int32;
      status deprecated;
      default "-2000000000";
      description "Default value: -2000000000; Status info: Since 17.Q4. Replaced by Paging::pagingDiscardTimerEdrx. Planned to be removed..";
    }
    leaf timePhaseMaxDeviationEdrx {
      type int32 {
        range "1..200";
      }
      default "10";
      units "ms";
      description "range 1..200; Default value: 10.";
    }
    leaf timePhaseSyncStateEdrx {
      type boolean;
      config false;
    }
    leaf csfbUseRegisteredLai {
      type boolean;
      default "false";
      description "Default value: false.";
    }
    leaf timePhaseMaxDeviationTdd1 {
      type eytypes:int32_range_9-100;
      default "15";
      units "microseconds";
      description "range 9..100; Default value: 15.";
    }
    leaf timePhaseMaxDeviationTdd2 {
      type eytypes:int32_range_9-100;
      default "15";
      units "microseconds";
      description "range 9..100; Default value: 15.";
    }
    leaf timePhaseMaxDeviationTdd3 {
      type eytypes:int32_range_9-100;
      default "15";
      units "microseconds";
      description "range 9..100; Default value: 15.";
    }
    leaf timePhaseMaxDeviationTdd4 {
      type eytypes:int32_range_9-100;
      default "15";
      units "microseconds";
      description "range 9..100; Default value: 15.";
    }
    leaf timePhaseMaxDeviationTdd5 {
      type eytypes:int32_range_9-100;
      default "15";
      units "microseconds";
      description "range 9..100; Default value: 15.";
    }
    leaf timePhaseMaxDeviationTdd6 {
      type eytypes:int32_range_9-100;
      default "15";
      units "microseconds";
      description "range 9..100; Default value: 15.";
    }
    leaf timePhaseMaxDeviationTdd7 {
      type eytypes:int32_range_9-100;
      default "15";
      units "microseconds";
      description "range 9..100; Default value: 15.";
    }
    leaf timePhaseMaxDevIeNBUlComp {
      type eytypes:int32_range_9-100;
      default "30";
      units "microseconds";
      description "range 9..100; Default value: 30.";
    }
    leaf timePhaseSyncStateIeNBUlComp {
      type boolean;
      config false;
    }
    leaf interEnbUlCompTunnelDscp {
      type eytypes:int32_range_0-63;
      default "14";
      description "range 0..63; Default value: 14.";
    }
    leaf maxNrOfInterEnbUlCompLbm {
      type eytypes:int32_range_0-10;
      default "6";
      description "range 0..10; Default value: 6.";
    }
    leaf extendedWaitTimeNb {
      type int32 {
        range "0..1800";
      }
      default "0";
      units "s";
      description "range 0..1800; Default value: 0.";
    }
    leaf-list inactivitySupervisionTimerNb {
      type eytypes:int32_range_0-2000-24;
      description "Status info: Since 20.Q4. Replaced by NbIotCell::inactivitySupervisionTimer. Planned to be removed..";
    }
    leaf zzzTemporary55 {
      type int32;
      status deprecated;
      default "-2000000000";
      description "Default value: -2000000000; Status info: Since 20.Q3. Planned to be removed..";
    }
    leaf zzzTemporary56 {
      type int32;
      status deprecated;
      default "-2000000000";
      description "Default value: -2000000000; Status info: Since 19.Q2. Planned to be removed..";
    }
    leaf zzzTemporary57 {
      type int32;
      status deprecated;
      default "-2000000000";
      description "Default value: -2000000000; Status info: Since 25.Q2. Replaced by AnrFunction::removeEUtranFreqRelTime. Planned to be removed..";
    }
    leaf zzzTemporary58 {
      type int32;
      default "-2000000000";
      description "Default value: -2000000000.";
    }
    leaf intraRanIpAddressRef {
      type ietfinet:ip-address;
    }
    leaf rpUpIpAddressRef {
      type ietfinet:ip-address;
    }
    leaf zzzTemporary59 {
      type int32;
      status deprecated;
      default "-2000000000";
      description "Default value: -2000000000; Status info: Since 18.Q2. Has no functional behavior. Planned to be removed..";
    }
    leaf maxNrOfEnbPartnersEranUlComp {
      type eytypes:int32_range_0-20;
      default "6";
      description "range 0..20; Default value: 6.";
    }
    leaf eranUlCompReSelectLinkTime {
      type int32 {
        range "0..1000";
      }
      default "7";
      units "day";
      description "range 0..1000; Default value: 7.";
    }
    leaf eranUlCompVlanPortRef {
      type ietfinet:port-number;
    }
    leaf zzzTemporary60 {
      type int32;
      status deprecated;
      default "-2000000000";
      description "Default value: -2000000000; Status info: Since 18.Q3. Replaced by intraEnbHoNasNonDelIndCause. Planned to be removed..";
    }
    leaf zzzTemporary61 {
      type int32;
      default "-2000000000";
      description "Default value: -2000000000.";
    }
    leaf elasticRanUlCompSupport {
      type ietfinet:port-number;
      status deprecated;
      description "Default value: false; Status info: Since 18.Q2. Has no functional behavior. Planned to be removed..";
    }
    leaf iuaMaxResourcePerBbm {
      type eytypes:int32_range_0-100;
      status deprecated;
      default "20";
      units "percent";
      description "range 0..100; Default value: 20; Status info: Since 18.Q3. Replaced by iuaBbmResourceLimit. Planned to be removed..";
    }
    leaf s1GtpuEchoInterval {
      type int32 {
        range "100 | 1000";
      }
      status deprecated;
      default "1000";
      units "ms";
      description "Default value: 1000; Status info: Since 23.Q2. Planned to be removed..";
    }
    list interNodalProtVersions {
      config false;
      container attributes {
      leaf interEnbCaProtVerExact {
        type eytypes:int32_range_-1-2147483647;
        description "range -1..2147483647.";
      }
      leaf eRanCaProtVerExact {
        type eytypes:int32_range_-1-2147483647;
        description "range -1..2147483647.";
      }
      leaf interEnbUlCompProtVerExact {
        type eytypes:int32_range_-1-2147483647;
        description "range -1..2147483647.";
      }
      leaf eRanUlCompProtVerExact {
        type eytypes:int32_range_-1-2147483647;
        description "range -1..2147483647.";
      }
      leaf commonProtVerRel {
        type eytypes:int32_range_-1-2147483647;
        description "range -1..2147483647.";
      }
      leaf commonProtVerRelMinus1 {
        type eytypes:int32_range_-1-2147483647;
        description "range -1..2147483647.";
      }
      leaf commonProtVerRelMinus2 {
        type eytypes:int32_range_-1-2147483647;
        description "range -1..2147483647.";
      }
      leaf commonProtVerRelMinus3 {
        type eytypes:int32_range_-1-2147483647;
        description "range -1..2147483647.";
      }
      }
    }
    leaf zzzTemporary62 {
      type int32;
      status deprecated;
      default "-2000000000";
      description "Default value: -2000000000; Status info: Since 19.Q3. Planned to be removed..";
    }
    leaf intraEnbHoNasNonDelIndCause {
      type boolean;
      default "false";
      description "Default value: false.";
    }
    leaf zzzTemporary63 {
      type int32;
      status deprecated;
      default "-2000000000";
      description "Default value: -2000000000; Status info: Since 19.Q1. Replaced by caUnknownImeisvEnabled. Planned to be removed..";
    }
    leaf iuaBbmResourceLimit {
      type int32 {
        range "1..80";
      }
      default "20";
      units "percent";
      description "range 1..80; Default value: 20.";
    }
    leaf endcPowerOffsetLte {
      type int32 {
        range "0 | 3";
      }
      default "3";
      units "dB";
      description "Default value: 3.";
    }
    leaf upIpAddress2Ref {
      type ietfinet:ip-address;
    }
    leaf zzzTemporary64 {
      type boolean;
      default "false";
      description "Default value: false.";
    }
    leaf zzzTemporary65 {
      type int32;
      default "-2000000000";
      description "Default value: -2000000000.";
    }
    leaf ulPhyProcResTradingEnabled {
      type eytypes:int32_range_0-2;
      default "2";
      description "range 0..2; Default value: 2.";
    }
    leaf pdbMeasurementDelta {
      type int32 {
        range "-80..100";
      }
      default "0";
      units "ms";
      description "range -80..100; Default value: 0.";
    }
    leaf caUnknownImeisvEnabled {
      type boolean;
      default "false";
      description "Default value: false.";
    }
    leaf zzzTemporary66 {
      type int32;
      status deprecated;
      default "-2000000000";
      description "Default value: -2000000000; Status info: Since 22.Q3. Replaced by hoSrvccToWcdmaMocnEnabled. Planned to be removed..";
    }
    leaf sctpEndcX2Ref {
      type string;
    }
    leaf zzzTemporary67 {
      type int32;
      default "-2000000000";
      description "Default value: -2000000000.";
    }
    leaf endcSplitAllowedNonDynPwrShUe {
      type boolean;
      default "false";
      description "Default value: false.";
    }
    leaf upEndcX2IpAddressRef {
      type ietfinet:ip-address;
    }
    leaf zzzTemporary68 {
      type int32;
      status deprecated;
      default "-2000000000";
      description "Default value: -2000000000; Status info: Since 23.Q4. Replaced by interEnbCaTddPCellEnabled. Planned to be removed..";
    }
    leaf mfbiFbipOnX2Enabled {
      type ietfinet:ip-address;
      description "Default value: false.";
    }
    leaf nbRrcConnReestActive {
      type boolean;
      default "false";
      description "Default value: false.";
    }
    leaf tWaitForConnEstInd {
      type eytypes:int32_range_1-20;
      default "3";
      units "s";
      description "range 1..20; Default value: 3.";
    }
    leaf endcDataUsageReportEnabled {
      type ietfinet:port-number;
      description "Default value: false.";
    }
    leaf ulHeavyUeBsrThresh {
      type int32 {
        range "0..32767";
      }
      default "400";
      units "byte";
      description "range 0..32767; Default value: 400.";
    }
    leaf ulHeavyUeDetectTime {
      type eytypes:int32_range_0-1000;
      default "500";
      units "ms";
      description "range 0..1000; Default value: 500.";
    }
    leaf srsPeriodicityTdd {
      type int32 {
        range "5 | 10 | 20 | 40 | 80";
      }
      default "20";
      units "ms";
      description "Default value: 20.";
    }
    leaf zzzTemporary69 {
      type int32;
      default "-2000000000";
      description "Default value: -2000000000.";
    }
    leaf allowMocnCellLevelCommonTac {
      type boolean;
      default "false";
      description "Default value: false.";
    }
    leaf zzzTemporary70 {
      type int32;
      default "-2000000000";
      description "Default value: -2000000000.";
    }
    leaf zzzTemporary71 {
      type int32;
      default "-2000000000";
      description "Default value: -2000000000.";
    }
    leaf ulHeavyUeBsrHyst {
      type int32 {
        range "0..10000";
      }
      default "100";
      units "byte";
      description "range 0..10000; Default value: 100.";
    }
    leaf upX2IpAddress2Ref {
      type ietfinet:ip-address;
    }
    leaf endcSplitAllowedMoVoice {
      type boolean;
      default "false";
      description "Default value: false.";
    }
    leaf tMoVoiceBearerEstSupervision {
      type int32 {
        range "0..20000";
      }
      default "2000";
      units "ms";
      description "range 0..20000; Default value: 2000.";
    }
    leaf ulHeavyUeBsrThUlCaFactor {
      type int32 {
        range "2..10";
      }
      default "6";
      description "range 2..10; Default value: 6.";
    }
    leaf ulHeavyUeDetectTimeOffset {
      type eytypes:int32_range_0-1000;
      default "250";
      units "ms";
      description "range 0..1000; Default value: 250.";
    }
    leaf ipsecEndcEpAddressRef {
      type ietfinet:ip-address;
    }
    leaf useFullResumeId {
      type boolean;
      default "false";
      description "Default value: false.";
    }
    leaf zzzTemporary72 {
      type string;
    }
    leaf zzzTemporary73 {
      type string;
    }
    leaf zzzTemporary74 {
      type int32;
      default "-2000000000";
      description "Default value: -2000000000.";
    }
    leaf zzzTemporary75 {
      type int32;
      default "-2000000000";
      description "Default value: -2000000000.";
    }
    leaf zzzTemporary76 {
      type int32;
      default "-2000000000";
      description "Default value: -2000000000.";
    }
    leaf zzzTemporary77 {
      type int32;
      default "-2000000000";
      description "Default value: -2000000000.";
    }
    leaf ductIntCharInfoScheme {
      type enumeration {
        enum GENERIC;
        enum EXTENDED;
        enum CELL_SPECIFIC;
      }
    }
    leaf zzzTemporary78 {
      type string;
    }
    leaf endcX2IpAddrViaS1Active {
      type ietfinet:ip-address;
      description "Default value: false.";
    }
    leaf endcS1OverlapMode {
      type boolean;
      default "false";
      description "Default value: false.";
    }
    leaf release {
      type string;
      config false;
    }
    leaf zzzTemporary79 {
      type int32;
      default "-2000000000";
      description "Default value: -2000000000.";
    }
    leaf zzzTemporary80 {
      type int32;
      status deprecated;
      default "-2000000000";
      description "Default value: -2000000000; Status info: Since 25.Q3. Replaced by ENodeBFunction::eranPrioritizeDefaultEnabled. Planned to be removed..";
    }
    leaf zzzTemporary81 {
      type int32;
      default "-2000000000";
      description "Default value: -2000000000.";
    }
    leaf obsMode {
      type enumeration {
        enum NORMAL;
        enum COUNTER_AND_PM_EVENT;
        enum COUNTER;
        enum KPI;
        enum INTERNAL_SUPERVISOR;
        enum AUTO;
      }
    }
    leaf obsProtectionAutoTargetMode {
      type enumeration {
        enum COUNTER_AND_PM_EVENT;
        enum COUNTER;
        enum KPI;
        enum INTERNAL_SUPERVISOR;
      }
    }
    leaf obsStatus {
      type enumeration {
        enum NORMAL;
        enum COUNTER_AND_PM_EVENT;
        enum COUNTER;
        enum KPI;
        enum INTERNAL_SUPERVISOR;
      }
      config false;
    }
    leaf dlBbCapacityTarget {
      type int32 {
        range "-1 | 75..65535";
      }
      default "-1";
      units "Mbps";
      description "Default value: -1.";
    }
    leaf endcAwareMfbiIntraCellHo {
      type boolean;
      default "false";
      description "Default value: false.";
    }
    leaf srsAllocationV2TddAasEnabled {
      type boolean;
      default "false";
      description "Default value: false.";
    }
    leaf timePhaseSynchStateNR {
      type boolean;
      config false;
    }
    leaf endcIntraBandBlocked {
      type boolean;
      default "true";
      description "Default value: true.";
    }
    leaf ductIntFlexibleDetectionEnabled {
      type boolean;
      default "false";
      description "Default value: false.";
    }
    leaf prachConfigEnabled {
      type boolean;
      default "false";
      description "Default value: false.";
    }
    leaf endcAllowed {
      type boolean;
      default "true";
      description "Default value: true.";
    }
    leaf zzzTemporary82 {
      type int32;
      default "-2000000000";
      description "Default value: -2000000000.";
    }
    leaf inhibitEndcFr2Volte {
      type boolean;
      default "false";
      description "Default value: false.";
    }
    leaf externalLinkFailureFilterTime {
      type int32 {
        range "0..900";
      }
      default "490";
      units "s";
      description "range 0..900; Default value: 490.";
    }
    leaf externalLinkToGNodeBFailureFilterTime {
      type int32 {
        range "0..900";
      }
      default "490";
      units "s";
      description "range 0..900; Default value: 490.";
    }
    leaf plmnServiceAlarmFilterTime {
      type int32 {
        range "0..300";
      }
      default "0";
      units "s";
      description "range 0..300; Default value: 0.";
    }
    leaf plmnServiceAlarmLevel {
      type enumeration {
        enum ENODEB;
        enum CELL;
      }
    }
    leaf upIpAddress2Mode {
      type ietfinet:ip-address;
    }
    leaf ueCapabilityEnquirySteps {
      type enumeration {
        enum ONE_STEP;
        enum TWO_STEP;
        enum THREE_STEP;
      }
    }
    leaf sleepCellDataCollect {
      type enumeration {
        enum COLLECTION_DISABLED;
        enum COLLECTION_ENABLED;
      }
    }
    leaf pimCancAutoConfigEnabled {
      type boolean;
      default "false";
      description "Default value: false.";
    }
    leaf zzzTemporary83 {
      type int32;
      default "-2000000000";
      description "Default value: -2000000000.";
    }
    list drxCycleNb {
      key "id";
      leaf id {
        type uint32;
        description "Synthetic key for struct entry.";
      }
      container attributes {
      leaf drxCycleNb0 {
        type int32;
        default "256";
        description "Default value: 256.";
      }
      leaf drxCycleNb1 {
        type int32;
        default "2048";
        description "Default value: 2048.";
      }
      leaf drxCycleNb2 {
        type int32;
        default "8192";
        description "Default value: 8192.";
      }
      }
    }
    list onDurationTimerNb {
      key "id";
      leaf id {
        type uint32;
        description "Synthetic key for struct entry.";
      }
      container attributes {
      leaf onDurationTimerNb0 {
        type int32;
        default "4";
        description "Default value: 4.";
      }
      leaf onDurationTimerNb1 {
        type int32;
        default "4";
        description "Default value: 4.";
      }
      leaf onDurationTimerNb2 {
        type eytypes:int32_range_1-3;
        default "2";
        description "range 1..3; Default value: 2.";
      }
      }
    }
    list drxInactivityTimerNb {
      key "id";
      leaf id {
        type uint32;
        description "Synthetic key for struct entry.";
      }
      container attributes {
      leaf drxInactivityTimerNb0 {
        type int32;
        default "4";
        description "Default value: 4.";
      }
      leaf drxInactivityTimerNb1 {
        type int32;
        default "4";
        description "Default value: 4.";
      }
      leaf drxInactivityTimerNb2 {
        type eytypes:int32_range_1-3;
        default "2";
        description "range 1..3; Default value: 2.";
      }
      }
    }
    leaf zzzTemporary84 {
      type int32;
      status deprecated;
      default "-2000000000";
      description "Default value: -2000000000; Status info: Since 24.Q2. Replaced by diffX2CauseMisconfig. Planned to be removed..";
    }
    leaf locationReportForPSCell {
      type ietfinet:port-number;
      description "Default value: false.";
    }
    leaf mmeSupervisionTimerNb {
      type int32 {
        range "1..32000";
      }
      default "5";
      units "s";
      description "range 1..32000; Default value: 5.";
    }
    leaf extendedBandN77Supported {
      type ietfinet:port-number;
      description "Default value: false.";
    }
    leaf pimAutoDetectionEnabled {
      type boolean;
      status deprecated;
      default "false";
      description "Default value: false; Status info: Since 24.Q1. Replaced by ENodeBFunction::pimDetectionEnabled. Planned to be removed..";
    }
    leaf zzzTemporary85 {
      type int32;
      status deprecated;
      default "-2000000000";
      description "Default value: -2000000000; Status info: Since 24.Q3. Replaced by ueCapInfoReEnq. Planned to be removed..";
    }
    leaf endcOverheatingAssistance {
      type boolean;
      default "false";
      description "Default value: false.";
    }
    leaf overheatingIndProhibitTimer {
      type int32 {
        range "0 | 5 | 10 | 20 | 50 | 100 | 200 | 300 | 600 | 900 | 1200 | 3000 | 6000";
      }
      default "20";
      units "s";
      description "Default value: 20.";
    }
    leaf hoSrvccToWcdmaMocnEnabled {
      type boolean;
      default "false";
      description "Default value: false.";
    }
    leaf moranOnSingleBbEnabled {
      type boolean;
      default "false";
      description "Default value: false.";
    }
    leaf channelQualityMode {
      type enumeration {
        enum NORMAL;
        enum COMPENSATED;
      }
    }
    leaf mobilityBackToNrFreqDisabled {
      type enumeration {
        enum NO_RESTRICTION;
        enum CONNECTED_MODE_MOBILITY;
        enum CONNECTED_IDLE_MODE_MOBILITY;
      }
    }
    leaf zzzTemporary86 {
      type int32;
      status deprecated;
      default "-2000000000";
      description "Default value: -2000000000; Status info: Since 24.Q3. Replaced by measSCellReportKeepLast. Planned to be removed..";
    }
    leaf ipecPrbCycles {
      type ietfinet:ip-address;
      description "range 25..100; Default value: 25.";
    }
    leaf voiceHoToNrEnabled {
      type boolean;
      status deprecated;
      default "false";
      description "Default value: false; Status info: Since 23.Q4. Replaced by voiceMobilityToNrEnabled. Planned to be removed..";
    }
    leaf relativePriorityBrOverride {
      type boolean;
      default "false";
      description "Default value: false.";
    }
    leaf separateEnGnbForMoranEnabled {
      type boolean;
      default "false";
      description "Default value: false.";
    }
    leaf extendedBandN77TwoSupported {
      type ietfinet:port-number;
      description "Default value: false.";
    }
    leaf queueErabSetupDuringCgiMeas {
      type boolean;
      default "true";
      description "Default value: true.";
    }
    leaf pciConflictReportType {
      type ietfinet:port-number;
    }
    leaf nrMobilityForMcPttDisabled {
      type boolean;
      default "true";
      description "Default value: true.";
    }
    leaf nrCellOverloadBackoffTime {
      type eytypes:int32_range_0-10000-25;
      default "0";
      units "s";
      description "range 0..10000; Default value: 0.";
    }
    leaf rRCContSizeLimit {
      type int32 {
        range "1..8100";
      }
      default "1823";
      description "range 1..8100; Default value: 1823.";
    }
    leaf mobility2g3gForMcPttDisabled {
      type boolean;
      default "false";
      description "Default value: false.";
    }
    leaf extendMixedTxModeEnabled {
      type boolean;
      default "false";
      description "Default value: false.";
    }
    leaf interEnbCaTddPCellEnabled {
      type boolean;
      default "true";
      description "Default value: true.";
    }
    leaf zzzTemporary87 {
      type int32;
      default "-2000000000";
      description "Default value: -2000000000.";
    }
    leaf eranPimVlanPortRef {
      type ietfinet:port-number;
    }
    leaf voiceMobilityToNrEnabled {
      type boolean;
      default "false";
      description "Default value: false.";
    }
    leaf noOfUsedPimAvoidEranPartners {
      type int32 {
        range "0..6";
      }
      config false;
      description "range 0..6.";
    }
    leaf pimDetectionEnabled {
      type boolean;
      default "false";
      description "Default value: false.";
    }
    leaf csfbSkipSmcRrcFromIdleMode {
      type ietfinet:ip-address;
      description "Default value: true.";
    }
    leaf diffX2CauseMisconfig {
      type boolean;
      default "false";
      description "Default value: false.";
    }
    leaf zzzTemporary88 {
      type int32;
      default "-2000000000";
      description "Default value: -2000000000.";
    }
    leaf secUeMeasFraction {
      type eytypes:int32_range_0-100;
      default "0";
      units "percent";
      description "range 0..100; Default value: 0.";
    }
    leaf rxBranchImbalanceThreshold {
      type int32 {
        range "40..100";
      }
      default "80";
      units "dB";
      description "range 40..100; Default value: 80.";
    }
    leaf rxDiversityLostThreshold {
      type int32 {
        range "150..190";
      }
      default "170";
      units "dB";
      description "range 150..190; Default value: 170.";
    }
    leaf antSysMonitoringAlarmHandling {
      type boolean;
      default "true";
      description "Default value: true.";
    }
    leaf measSCellReportKeepLast {
      type ietfinet:port-number;
      description "Default value: false.";
    }
    leaf zzzTemporary89 {
      type int32;
      default "-2000000000";
      description "Default value: -2000000000.";
    }
    leaf ueCapInfoReEnq {
      type eytypes:int32_range_0-2;
      default "1";
      description "range 0..2; Default value: 1.";
    }
    leaf zzzTemporary90 {
      type int32;
      default "-2000000000";
      description "Default value: -2000000000.";
    }
    leaf interCapModLink {
      type boolean;
      default "true";
      description "Default value: true.";
    }
    leaf ulHeavyExitCaMode {
      type enumeration {
        enum BACK_TO_DLCA;
        enum KEEP_ULCA;
      }
    }
    leaf ulHeavyCaReconfMode {
      type enumeration {
        enum RANDOM;
        enum ULPRIORITY;
      }
    }
    list blockedGNodeBList {
      key "id";
      leaf id {
        type uint32;
        description "Synthetic key for struct sequence entry.";
      }
      ordered-by user;
      container attributes {
      leaf mcc {
        type eytypes:int32_range_0-999;
        default "1";
        description "range 0..999; Default value: 1.";
      }
      leaf mnc {
        type eytypes:int32_range_0-999;
        default "1";
        description "range 0..999; Default value: 1.";
      }
      leaf mncLength {
        type eytypes:int32_range_2-3;
        default "2";
        description "range 2..3; Default value: 2.";
      }
      leaf gNodeBId {
        type int64 {
          range "-1..4294967295";
        }
        default "0";
        description "range -1..4294967295; Default value: 0.";
      }
      leaf gNodeBIdLength {
        type eytypes:int32_range_22-32;
        default "22";
        description "range 22..32; Default value: 22.";
      }
      }
    }
    leaf pimaPlmnAgnostic {
      type boolean;
      default "false";
      description "Default value: false.";
    }
    leaf pwsSupportInCsmAndMsm {
      type ietfinet:port-number;
      description "Default value: true.";
    }
    leaf pwsCsmAndMsmInResponse {
      type boolean;
      default "false";
      description "Default value: false.";
    }
    leaf maxEUtranUeCapabilitiesSize {
      type int32 {
        range "0..12288";
      }
      default "0";
      units "byte";
      description "range 0..12288; Default value: 0.";
    }
    leaf zzzTemporary91 {
      type int32;
      default "-2000000000";
      description "Default value: -2000000000.";
    }
    leaf eranCaAutoRemoveLinkEnabled {
      type boolean;
      default "false";
      description "Default value: false.";
    }
    leaf eranCaAutoRemoveLinkTime {
      type int32 {
        range "0..720";
      }
      default "24";
      units "hour";
      description "range 0..720; Default value: 24.";
    }
    leaf eranPrioritizeDefaultEnabled {
      type boolean;
      default "true";
      description "Default value: true.";
    }
    leaf zzzTemporary92 {
      type int32;
      default "-2000000000";
      description "Default value: -2000000000.";
    }
    leaf zzzTemporary93 {
      type int32;
      default "-2000000000";
      description "Default value: -2000000000.";
    }
    leaf pmZtemporary35 {
      type uint32;
      config false;
    }
    leaf pmRimAssocMax {
      type int32;
      config false;
    }
    leaf-list pmPagS1RecDistr {
      type uint32;
    }
    leaf pmLicDlCapUsedSum {
      type uint32;
      config false;
    }
    leaf pmPagS1DiscAssistBr {
      type uint32;
      config false;
    }
    leaf pmPagS1DiscAssistNb {
      type uint32;
      config false;
    }
    leaf pmLicUlPrbCapLicense {
      type int32;
      config false;
    }
    leaf pmPagS1Discarded {
      type uint32;
      config false;
    }
    leaf pmLicConnectedUsersLicense {
      type int32;
      config false;
    }
    leaf pmLicDlPrbCapLicense {
      type int32;
      config false;
    }
    leaf pmRrcConnBrEnbMax {
      type int32;
      config false;
      status deprecated;
      description "MOM flags: noNotification.";
    }
    leaf pmObsLocalEventDiscPmLoad {
      type uint32;
      config false;
    }
    leaf pmLicUlCapActual {
      type int32;
      config false;
    }
    leaf pmLicConnectedUsersActual {
      type int32;
      config false;
    }
    leaf pmLicUlCapUsedSamp {
      type uint32;
      config false;
    }
    leaf pmLicDlCapUsedMax {
      type int32;
      config false;
    }
    leaf-list pmEranThpVolDlTransDistr {
      type uint32;
      description "MOM flags: noNotification.";
    }
    leaf pmLicUlCapUsedSum {
      type uint32;
      config false;
    }
    leaf pmLic5Plus5MHzScTddActual {
      type int32;
      config false;
    }
    leaf pmMoFootprintMax {
      type int32;
      config false;
    }
    leaf-list pmBbmDlBbCapacityUtilization {
      type uint32;
    }
    leaf pmLicDlCapActual {
      type int32;
      config false;
    }
    leaf-list pmBbmDlBbCapacityPttReservation {
      type uint32;
    }
    leaf pmLicDlCapUsedSamp {
      type uint32;
      config false;
    }
    leaf pmLicConnectedUsersLevSamp {
      type uint32;
      config false;
    }
    leaf pmLic10MHzBwHwacTddAas {
      type int32;
      config false;
    }
    leaf-list pmEranThpVolDlRecDistr {
      type uint32;
      description "MOM flags: noNotification.";
    }
    leaf pmLic10MHzBwHwacFddAas {
      type int32;
      config false;
    }
    leaf-list pmLicDlCapDistr {
      type uint32;
    }
    leaf pmRrcConnLevSamp {
      type uint32;
      config false;
    }
    leaf-list pmLicUlCapDistr {
      type uint32;
    }
    leaf pmLicConnectedUsersMax {
      type int32;
      config false;
    }
    leaf-list pmPagS1DiscDistr {
      type uint32;
    }
    leaf-list pmLicConnectedUsersDistr {
      type uint32;
    }
    leaf pmLicConnectedUsersLevSum {
      type uint32;
      config false;
    }
    leaf pmRimReportErr {
      type ietfinet:port-number;
      config false;
    }
    leaf pmZtemporary34 {
      type uint32;
      config false;
    }
    leaf pmRrcConnBrEnbLevSum {
      type uint32;
      config false;
      status deprecated;
      description "MOM flags: noNotification.";
    }
    leaf pmLicDlCapLicense {
      type int32;
      config false;
    }
    leaf pmPagS1EdrxReceived {
      type uint32;
      config false;
    }
    leaf pmLicConnectedUsersTimeCong {
      type uint32;
      config false;
    }
    leaf pmLic5MHzBwHwacNonAas {
      type int32;
      config false;
    }
    leaf-list pmBbmUlBbCapacityUtilization {
      type uint32;
    }
    leaf pmRrcConnMaxEndc {
      type int32;
      config false;
    }
    leaf pmLicUlCapLicense {
      type int32;
      config false;
    }
    leaf pmRrcConnLevSumEndc {
      type uint32;
      config false;
    }
    leaf pmLic5MHzSectorCarrierActual {
      type int32;
      config false;
    }
    leaf pmPagS1Received {
      type uint32;
      config false;
    }
    leaf pmLic5Plus5MHzScFddActual {
      type int32;
      config false;
    }
    leaf pmPagS1EdrxDiscarded {
      type uint32;
      config false;
    }
    leaf pmCellLoadStateInd {
      type uint32;
      config false;
    }
    leaf pmRrcConnBrEnbLevSamp {
      type uint32;
      config false;
      status deprecated;
      description "MOM flags: noNotification.";
    }
    leaf pmLicUlCapUsedMax {
      type int32;
      config false;
    }
  }
  grouping EranInterMeLink-attributes {
    leaf eranVlanPortRef {
      type ietfinet:port-number;
      config false;
    }
    leaf localPort {
      type ietfinet:port-number;
      config false;
      description "length 0..128.";
    }
    leaf remotePort {
      type ietfinet:port-number;
      config false;
      description "length 0..128.";
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf operationalState {
      type enumeration {
        enum DISABLED;
        enum ENABLED;
      }
      config false;
    }
    leaf eranInterMeLinkId {
      type string;
      mandatory true;
    }
    leaf linkLatency24hrsHWM {
      type eytypes:int32_range_-1-1000000;
      config false;
      units "microseconds";
      description "range -1..1000000.";
    }
    leaf linkLatency15minHWM {
      type eytypes:int32_range_-1-1000000;
      config false;
      units "microseconds";
      description "range -1..1000000.";
    }
    leaf linkLatency1minAvg {
      type eytypes:int32_range_-1-1000000;
      config false;
      units "microseconds";
      description "range -1..1000000.";
    }
    leaf administrativeState {
      type enumeration {
        enum LOCKED;
        enum UNLOCKED;
        enum SHUTTINGDOWN;
      }
      status deprecated;
      default "LOCKED";
      description "Default value: LOCKED; Status info: Since 19.Q4. Has no functional behavior. Planned to be removed.; Specification: ITU-T Rec. X.731.";
    }
    leaf pmEranCompUlServReceiveRsp {
      type uint32;
      config false;
      status deprecated;
      description "MOM flags: noNotification.";
    }
    leaf pmEranCompUlServSendReq {
      type uint32;
      config false;
      status deprecated;
      description "MOM flags: noNotification.";
    }
    leaf pmEranCompUlCoopReceiveReq {
      type uint32;
      config false;
      status deprecated;
      description "MOM flags: noNotification.";
    }
    leaf pmEranCompUlCoopSendRsp {
      type uint32;
      config false;
      status deprecated;
      description "MOM flags: noNotification.";
    }
  }
  grouping EricssonLeanCarrierFunction-attributes {
    leaf elcDrxOnDurationPreHeating {
      type int32 {
        range "0..38";
      }
      default "3";
      units "ms";
      description "range 0..38; Default value: 3.";
    }
    leaf elcDrxOnDurationPostHeating {
      type int32 {
        range "0..38";
      }
      default "4";
      units "ms";
      description "range 0..38; Default value: 4.";
    }
    leaf disableElcOnVolte {
      type boolean;
      default "false";
      description "Default value: false.";
    }
    leaf ericssonLeanCarrierFunctionId {
      type string;
      mandatory true;
    }
    leaf elcPdcchCrsMuting {
      type boolean;
      default "true";
      description "Default value: true.";
    }
    leaf disableElcOnPtt {
      type boolean;
      default "true";
      description "Default value: true.";
    }
  }
  grouping Etws-attributes {
    leaf etwsId {
      type string;
      mandatory true;
    }
  }
  grouping EUtraFreqRelProfile-attributes {
    leaf-list ueProfileFilterRefList {
      type string;
      ordered-by user;
    }
    leaf arpPrio {
      type int32 {
        range "-1000 | -1..7";
      }
      default "-1000";
      description "Default value: -1000.";
    }
    leaf cellReselectionPriority {
      type int32 {
        range "-1000 | -1..7";
      }
      default "-1000";
      description "Default value: -1000.";
    }
    leaf connectedModeMobilityPrio {
      type int32 {
        range "-1000 | -1..7";
      }
      default "-1000";
      description "Default value: -1000.";
    }
    leaf voicePrio {
      type int32 {
        range "-1000 | -1..7";
      }
      default "-1000";
      description "Default value: -1000.";
    }
    leaf endcHoFreqPriority {
      type int32 {
        range "-1000 | -1..7";
      }
      default "-1000";
      description "Default value: -1000.";
    }
    leaf loadBalancingAllowed {
      type enumeration {
        enum LB_AND_OFFLOAD_ALLOWED;
        enum OFFLOAD_ALLOWED;
        enum NOT_ALLOWED;
        enum KEEP_OTHER_CONFIGURATION;
      }
    }
    leaf eUtraFreqRelProfileId {
      type string;
      mandatory true;
    }
    leaf-list ueProfileFilterRef {
      type string;
      ordered-by user;
    }
    leaf interFreqHoHigherPrioAllowed {
      type boolean;
      default "false";
      description "Default value: false.";
    }
    leaf interFreqHoHigherPrioControl {
      type enumeration {
        enum PRIO_ENDC;
        enum PRIO_LTE;
      }
    }
  }
  grouping EUtraFreqRelProfileSet-attributes {
    leaf eUtraFreqRelProfileSetId {
      type string;
      mandatory true;
    }
    leaf-list reservedBy {
      type string;
    }
  }
  grouping EUtranCellFDD-attributes {
    leaf eUtranCellFDDId {
      type string;
      mandatory true;
    }
    leaf earfcndl {
      type int32 {
        range "0..17999 | 46590..262143";
      }
      mandatory true;
    }
    leaf earfcnul {
      type int32 {
        range "0 | 18000..35999 | 46590..262143";
      }
      mandatory true;
    }
    list frameStartOffset {
      key "id";
      leaf id {
        type uint32;
        description "Synthetic key for struct entry.";
      }
      container attributes {
      leaf subFrameOffset {
        type eytypes:int32_range_0-5;
        default "0";
        description "range 0..5; Default value: 0.";
      }
      }
    }
    leaf noOfPucchCqiUsers {
      type eytypes:int32_range_0-4000;
      default "160";
      description "range 0..4000; Default value: 160.";
    }
    leaf noOfPucchSrUsers {
      type eytypes:int32_range_0-4000;
      default "160";
      description "range 0..4000; Default value: 160.";
    }
    leaf dlChannelBandwidth {
      type int32 {
        range "1400 | 3000 | 5000 | 10000 | 15000 | 20000";
      }
      default "10000";
      units "kHz";
      description "Default value: 10000.";
    }
    leaf ulChannelBandwidth {
      type int32 {
        range "1400 | 3000 | 5000 | 10000 | 15000 | 20000";
      }
      default "10000";
      units "kHz";
      description "Default value: 10000.";
    }
    leaf cellRange {
      type int32 {
        range "1..200";
      }
      default "15";
      units "km";
      description "range 1..200; Default value: 15.";
    }
    leaf commonSrPeriodicity {
      type int32 {
        range "5 | 10 | 20";
      }
      default "10";
      units "ms";
      description "Default value: 10.";
    }
    leaf nrOfTransmissionsSib1 {
      type int32 {
        range "1..4";
      }
      default "4";
      description "range 1..4; Default value: 4.";
    }
    leaf transmissionMode {
      type enumeration {
        enum TRANSMISSION_MODE_2;
        enum TRANSMISSION_MODE_3;
        enum TRANSMISSION_MODE_4;
        enum TRANSMISSION_MODE_9;
      }
    }
    leaf isDlOnly {
      type boolean;
      default "false";
      description "Default value: false.";
    }
    leaf noOfChannelSelectionSets {
      type int32 {
        range "0 | 4..12";
      }
      default "4";
      units "CS sets";
      description "Default value: 4.";
    }
    leaf channelSelectionSetSize {
      type eytypes:int32_range_1-2;
      default "2";
      description "range 1..2; Default value: 2.";
    }
    leaf csiRsConfigType8TxFDD {
      type enumeration {
        enum NZP_CSIRS;
        enum NZP_ZP_CSIRS;
      }
    }
    leaf maxSentCrsAssistCells {
      type eytypes:int32_range_0-8;
      default "8";
      description "range 0..8; Default value: 8.";
    }
    leaf dlInternalChannelBandwidth {
      type int32 {
        range "0 | 4200 | 4400 | 4600 | 4800 | 7500 | 8800 | 9000";
      }
      default "0";
      units "kHz";
      description "Default value: 0.";
    }
    leaf ulInternalChannelBandwidth {
      type int32 {
        range "0 | 4200 | 4400 | 4600 | 4800 | 7500 | 8800 | 9000";
      }
      default "0";
      units "kHz";
      description "Default value: 0.";
    }
    leaf ttiBundlingSwitchThres {
      type eytypes:int32_range_-150-250;
      default "90";
      units "dB";
      description "range -150..250; Default value: 90.";
    }
    leaf ttiBundlingSwitchThresHyst {
      type eytypes:int32_range_0-50;
      default "10";
      units "dB";
      description "range 0..50; Default value: 10.";
    }
    leaf ttiBundlingAfterHo {
      type enumeration {
        enum NO_TTI_BUNDLING;
        enum TTI_BUNDLING_ALL_HO_CASES;
        enum TTI_BUNDLING_INTRA_FREQ_HO_ONLY;
      }
    }
    leaf ttiBundlingAfterReest {
      type enumeration {
        enum NO_TTI_BUNDLING;
        enum TTI_BUNDLING_ALL_REEST_CASES;
        enum TTI_BUNDLING_SOURCE_REEST_ONLY;
      }
    }
    leaf noOfPucchFormat3PrbPairs {
      type eytypes:int32_range_0-3;
      default "1";
      description "range 0..3; Default value: 1.";
    }
    list siPeriodicityBr {
      key "id";
      leaf id {
        type uint32;
        description "Synthetic key for struct entry.";
      }
      description "Takes effect: Next cell unlock; Status info: Since 24.Q3. Replaced by siPeriodicityCe. Planned to be removed..";
      container attributes {
      leaf siPeriodicitySI9 {
        type ietfinet:ip-address;
        units "rf (radio frames)";
        description "Default value: 64.";
      }
      leaf siPeriodicitySI8 {
        type ietfinet:ip-address;
        units "rf (radio frames)";
        description "Default value: 64.";
      }
      leaf siPeriodicitySI10 {
        type ietfinet:ip-address;
        units "rf (radio frames)";
        description "Default value: 64.";
      }
      leaf siPeriodicitySI2 {
        type ietfinet:ip-address;
        units "rf (radioframes)";
        description "Default value: 64.";
      }
      leaf siPeriodicitySI3 {
        type ietfinet:ip-address;
        units "rf (radioframes)";
        description "Default value: 64.";
      }
      leaf siPeriodicitySI4 {
        type ietfinet:ip-address;
        units "rf (radioframes)";
        description "Default value: 64.";
      }
      leaf siPeriodicitySI5 {
        type ietfinet:ip-address;
        units "rf (radioframes)";
        description "Default value: 64.";
      }
      leaf siPeriodicitySI6 {
        type ietfinet:ip-address;
        units "rf (radioframes)";
        description "Default value: 64.";
      }
      leaf siPeriodicitySI7 {
        type ietfinet:ip-address;
        units "rf (radioframes)";
        description "Default value: 64.";
      }
      leaf siPeriodicitySI1 {
        type ietfinet:ip-address;
        units "rf (radioframes)";
        description "Default value: 8.";
      }
      }
    }
    leaf maxValidSubframeDlBr {
      type int32 {
        range "50..100";
      }
      default "100";
      units "percent";
      description "range 50..100; Default value: 100.";
    }
    leaf highestSupportedCeLevelBr {
      type ietfinet:port-number;
      default "0";
      description "range 0..1; Default value: 0.";
    }
    leaf catm1SupportEnabled {
      type ietfinet:port-number;
      description "Default value: false.";
    }
    leaf beamWeightSet16Tr {
      type int32 {
        range "0..128";
      }
      default "0";
      description "range 0..128; Default value: 0.";
    }
    leaf beamWeightSet16TrTm9 {
      type int32 {
        range "0..128";
      }
      default "0";
      description "range 0..128; Default value: 0.";
    }
    leaf csiRsConfigType {
      type enumeration {
        enum NZP_CSIRS;
        enum NZP_ZP_CSIRS;
      }
    }
    leaf extGUtranCellRef {
      type string;
    }
    leaf schedulingInfoSib1BrMod {
      type enumeration {
        enum OFF;
        enum MODE_1_SCHEDULING;
        enum MODE_2_SCHEDULING;
      }
    }
    leaf tm9Tm4ModeSwitchingEnabled {
      type boolean;
      default "false";
      description "Default value: false.";
    }
    leaf mbsfnSubframesForTm9 {
      type enumeration {
        enum DISABLED;
        enum ENABLED_10_PERCENT;
        enum ENABLED_20_PERCENT;
        enum ENABLED_30_PERCENT;
        enum ENABLED_40_PERCENT;
        enum ENABLED_50_PERCENT;
        enum ENABLED_60_PERCENT;
      }
    }
    leaf ttiBundlingAtSetup {
      type enumeration {
        enum OFF;
        enum ACT_TTIB_IMM;
      }
    }
    leaf tm9Tm4ModeSwitchingThresh {
      type int32 {
        range "-1000..1000";
      }
      default "180";
      units "dB";
      description "range -1000..1000; Default value: 180.";
    }
    leaf prachFrequencyAllocation {
      type eytypes:int32_range_0-1;
      default "0";
      description "range 0..1; Default value: 0.";
    }
    leaf puschFrequencyAllocationBr {
      type eytypes:int32_range_0-1;
      default "0";
      description "range 0..1; Default value: 0.";
    }
    leaf msg3FrequencyAllocationBr {
      type eytypes:int32_range_0-1;
      default "1";
      description "range 0..1; Default value: 1.";
    }
    leaf eDrxUeType {
      type enumeration {
        enum LTE_CATM;
        enum LTE;
        enum CATM;
      }
    }
    leaf eabPresenceBr {
      type enumeration {
        enum OFF;
        enum MANUAL;
        enum AUTO;
      }
    }
    leaf activeEabCategory {
      type enumeration {
        enum CATEGORY_A;
        enum CATEGORY_B;
        enum CATEGORY_C;
        enum OFF;
      }
      config false;
    }
    leaf activeEabBitmap {
      type int32 {
        range "-1..1023";
      }
      config false;
      description "range -1..1023.";
    }
    leaf-list eabConfProfileBrRef {
      type string;
    }
    leaf noOfPucchFormat1PrbPairsPerFrameConf {
      type eytypes:int32_range_0-22;
      default "2";
      description "range 0..22; Default value: 2.";
    }
    leaf noOfPucchFormat2PrbPairsPerFrameConf {
      type eytypes:int32_range_0-22;
      default "1";
      description "range 0..22; Default value: 1.";
    }
    leaf noOfPucchSrUsersCalc {
      type eytypes:int32_range_0-4000;
      config false;
      description "range 0..4000.";
    }
    leaf noOfPucchCqiUsersCalc {
      type eytypes:int32_range_0-4000;
      config false;
      description "range 0..4000.";
    }
    leaf eabThreshRejRateLteHighBr {
      type eytypes:int32_range_0-1000-11;
      default "10";
      units "percent";
      description "range 0..1000; Default value: 10.";
    }
    leaf eabThreshRejRateLteLowBr {
      type eytypes:int32_range_0-1000-11;
      default "5";
      units "percent";
      description "range 0..1000; Default value: 5.";
    }
    leaf eabThreshRejRateCatmHighBr {
      type eytypes:int32_range_0-1000-11;
      default "10";
      units "percent";
      description "range 0..1000; Default value: 10.";
    }
    leaf eabThreshRejRateCatmLowBr {
      type eytypes:int32_range_0-1000-11;
      default "5";
      units "percent";
      description "range 0..1000; Default value: 5.";
    }
    leaf eabThreshTimeHigh {
      type eytypes:int32_range_1-4095;
      default "120";
      units "s";
      description "range 1..4095; Default value: 120.";
    }
    leaf eabThreshTimeLow {
      type eytypes:int32_range_1-4095;
      default "120";
      units "s";
      description "range 1..4095; Default value: 120.";
    }
    leaf noOfMpdcchUessBr {
      type eytypes:int32_range_1-8;
      default "1";
      description "range 1..8; Default value: 1.";
    }
    leaf dedicatedMpdcchCss2Br {
      type boolean;
      default "false";
      description "Default value: false.";
    }
    leaf noOfPuschNbBr {
      type eytypes:int32_range_1-16;
      default "2";
      description "range 1..16; Default value: 2.";
    }
    leaf ailgRef {
      type string;
    }
    leaf ailgActive {
      type boolean;
      config false;
    }
    list changeNotification {
      key "id";
      leaf id {
        type uint32;
        description "Synthetic key for struct entry.";
      }
      container attributes {
      leaf changeNotificationSIB2 {
        type boolean;
        default "true";
        description "Default value: true.";
      }
      leaf changeNotificationSIB3 {
        type boolean;
        default "true";
        description "Default value: true.";
      }
      leaf changeNotificationSIB4 {
        type boolean;
        default "true";
        description "Default value: true.";
      }
      leaf changeNotificationSIB5 {
        type boolean;
        default "true";
        description "Default value: true.";
      }
      leaf changeNotificationSIB6 {
        type boolean;
        default "true";
        description "Default value: true.";
      }
      leaf changeNotificationSIB7 {
        type boolean;
        default "true";
        description "Default value: true.";
      }
      leaf changeNotificationSIB8 {
        type boolean;
        default "true";
        description "Default value: true.";
      }
      leaf changeNotificationSIB1 {
        type boolean;
        default "true";
        description "Default value: true.";
      }
      leaf changeNotificationSIB15 {
        type boolean;
        default "true";
        description "Default value: true.";
      }
      leaf changeNotificationSIB16 {
        type boolean;
        default "true";
        description "Default value: true.";
      }
      leaf changeNotificationSIB13 {
        type boolean;
        default "true";
        description "Default value: true.";
      }
      leaf changeNotificationSIB24 {
        type boolean;
        default "true";
        description "Default value: true.";
      }
      }
    }
    list mappingInfo {
      key "id";
      leaf id {
        type uint32;
        description "Synthetic key for struct entry.";
      }
      container attributes {
      leaf mappingInfoSIB4 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB5 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB6 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB7 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB8 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB3 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB10 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB11 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB12 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB15 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB16 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB13 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB24 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      }
    }
    leaf modificationPeriodCoeff {
      type int32 {
        range "2 | 4 | 8 | 16";
      }
      default "2";
      description "Default value: 2.";
    }
    list siPeriodicity {
      key "id";
      leaf id {
        type uint32;
        description "Synthetic key for struct entry.";
      }
      container attributes {
      leaf siPeriodicitySI9 {
        type ietfinet:ip-address;
        units "rf (radio frames)";
        description "Default value: 64.";
      }
      leaf siPeriodicitySI8 {
        type ietfinet:ip-address;
        units "rf (radio frames)";
        description "Default value: 64.";
      }
      leaf siPeriodicitySI10 {
        type ietfinet:ip-address;
        units "rf (radio frames)";
        description "Default value: 64.";
      }
      leaf siPeriodicitySI2 {
        type ietfinet:ip-address;
        units "rf (radioframes)";
        description "Default value: 64.";
      }
      leaf siPeriodicitySI3 {
        type ietfinet:ip-address;
        units "rf (radioframes)";
        description "Default value: 64.";
      }
      leaf siPeriodicitySI4 {
        type ietfinet:ip-address;
        units "rf (radioframes)";
        description "Default value: 64.";
      }
      leaf siPeriodicitySI5 {
        type ietfinet:ip-address;
        units "rf (radioframes)";
        description "Default value: 64.";
      }
      leaf siPeriodicitySI6 {
        type ietfinet:ip-address;
        units "rf (radioframes)";
        description "Default value: 64.";
      }
      leaf siPeriodicitySI7 {
        type ietfinet:ip-address;
        units "rf (radioframes)";
        description "Default value: 64.";
      }
      leaf siPeriodicitySI1 {
        type ietfinet:ip-address;
        units "rf (radioframes)";
        description "Default value: 8.";
      }
      }
    }
    leaf siWindowLength {
      type int32 {
        range "1..2 | 5 | 10 | 15 | 20 | 40";
      }
      default "10";
      units "ms";
      description "Default value: 10.";
    }
    leaf qRxLevMin {
      type eytypes:int32_range_-140--44;
      default "-140";
      units "dBm";
      description "range -140..-44; Default value: -140.";
    }
    leaf minBestCellHoAttempts {
      type eytypes:int32_range_1-10;
      default "1";
      description "range 1..10; Default value: 1.";
    }
    list systemInformationBlock6 {
      key "id";
      leaf id {
        type uint32;
        description "Synthetic key for struct entry.";
      }
      container attributes {
      leaf tReselectionUtra {
        type eytypes:int32_range_0-7-9;
        default "2";
        units "s";
        description "range 0..7; Default value: 2.";
      }
      leaf tReselectionUtraSfMedium {
        type eytypes:int32_range_25-100-26;
        default "100";
        units "percent";
        description "range 25..100; Default value: 100.";
      }
      leaf tReselectionUtraSfHigh {
        type eytypes:int32_range_25-100-26;
        default "100";
        units "percent";
        description "range 25..100; Default value: 100.";
      }
      }
    }
    list systemInformationBlock7 {
      key "id";
      leaf id {
        type uint32;
        description "Synthetic key for struct entry.";
      }
      container attributes {
      leaf tReselectionGeran {
        type eytypes:int32_range_0-7;
        default "2";
        description "range 0..7; Default value: 2.";
      }
      leaf tReselectionGeranSfMedium {
        type eytypes:int32_range_25-100;
        default "100";
        description "range 25..100; Default value: 100.";
      }
      leaf tReselectionGeranSfHigh {
        type eytypes:int32_range_25-100;
        default "100";
        description "range 25..100; Default value: 100.";
      }
      }
    }
    list systemInformationBlock8 {
      key "id";
      leaf id {
        type uint32;
        description "Synthetic key for struct entry.";
      }
      container attributes {
      leaf searchWindowSizeCdma {
        type eytypes:int32_range_0-15;
        default "8";
        description "range 0..15; Default value: 8.";
      }
      leaf tReselectionCdmaHrpd {
        type eytypes:int32_range_0-7-9;
        default "2";
        units "s";
        description "range 0..7; Default value: 2.";
      }
      leaf tReselectionCdmaHrpdSfMedium {
        type eytypes:int32_range_25-100-26;
        default "100";
        units "percent";
        description "range 25..100; Default value: 100.";
      }
      leaf tReselectionCdmaHrpdSfHigh {
        type eytypes:int32_range_25-100-26;
        default "100";
        units "percent";
        description "range 25..100; Default value: 100.";
      }
      leaf tReselectionCdma1xRtt {
        type int32 {
          range "0..7";
        }
        default "2";
        units "second";
        description "range 0..7; Default value: 2.";
      }
      leaf tReselectionCdma1xRttSfHigh {
        type eytypes:int32_range_25-100-26;
        default "100";
        units "percent";
        description "range 25..100; Default value: 100.";
      }
      leaf tReselectionCdma1xRttSfMedium {
        type eytypes:int32_range_25-100-26;
        default "100";
        units "percent";
        description "range 25..100; Default value: 100.";
      }
      }
    }
    leaf-list reservedBy {
      type string;
    }
    list systemInformationBlock3 {
      key "id";
      leaf id {
        type uint32;
        description "Synthetic key for struct entry.";
      }
      container attributes {
      leaf qHyst {
        type int32;
        default "4";
        units "dB";
        description "Default value: 4.";
      }
      leaf tEvaluation {
        type int32;
        default "240";
        units "s";
        description "Default value: 240.";
      }
      leaf tHystNormal {
        type int32;
        default "240";
        units "s";
        description "Default value: 240.";
      }
      leaf nCellChangeMedium {
        type eytypes:int32_range_1-16;
        default "16";
        description "range 1..16; Default value: 16.";
      }
      leaf nCellChangeHigh {
        type eytypes:int32_range_1-16;
        default "16";
        description "range 1..16; Default value: 16.";
      }
      leaf qHystSfMedium {
        type eytypes:int32_range_-6-0;
        default "0";
        units "dB";
        description "range -6..0; Default value: 0.";
      }
      leaf qHystSfHigh {
        type eytypes:int32_range_-6-0;
        default "0";
        units "dB";
        description "range -6..0; Default value: 0.";
      }
      leaf sIntraSearch {
        type int32;
        default "1000";
        units "dB";
        description "Default value: 1000.";
      }
      leaf sNonIntraSearch {
        type int32;
        default "0";
        units "dB";
        description "Default value: 0.";
      }
      leaf sIntraSearchQ {
        type eytypes:int32_range_0-31;
        default "0";
        units "dB";
        description "range 0..31; Default value: 0.";
      }
      leaf sIntraSearchP {
        type eytypes:int32_range_0-62;
        default "62";
        units "dB";
        description "range 0..62; Default value: 62.";
      }
      leaf sNonIntraSearchQ {
        type eytypes:int32_range_0-31;
        default "0";
        units "dB";
        description "range 0..31; Default value: 0.";
      }
      leaf sNonIntraSearchP {
        type eytypes:int32_range_0-62;
        default "0";
        units "dB";
        description "range 0..62; Default value: 0.";
      }
      leaf threshServingLowQ {
        type int32;
        default "1000";
        units "dB";
        description "Default value: 1000.";
      }
      leaf sIntraSearchv920Active {
        type boolean;
        default "false";
        description "Default value: false.";
      }
      leaf sNonIntraSearchv920Active {
        type boolean;
        default "false";
        description "Default value: false.";
      }
      }
    }
    leaf ulInterferenceManagementActive {
      type boolean;
      default "true";
      description "Default value: true.";
    }
    leaf ulInterferenceManagementDuration {
      type eytypes:int32_range_0-10000-25;
      default "5000";
      units "s";
      description "range 0..10000; Default value: 5000.";
    }
    leaf-list activeMtdMeasurements {
      type eytypes:int32_range_0-255;
    }
    leaf cellBarred {
      type enumeration {
        enum BARRED;
        enum NOT_BARRED;
      }
    }
    leaf dlInterferenceManagementActive {
      type boolean;
      default "false";
      description "Default value: false.";
    }
    leaf dlInterferenceManagementDuration {
      type eytypes:int32_range_0-10000-25;
      default "100";
      units "s";
      description "range 0..10000; Default value: 100.";
    }
    leaf pMaxServingCell {
      type int32 {
        range "-30..33 | 1000";
      }
      default "1000";
      description "Default value: 1000.";
    }
    leaf pZeroNominalPucch {
      type eytypes:int32_range_-127--96;
      default "-117";
      units "dBm";
      description "range -127..-96; Default value: -117.";
    }
    leaf pZeroNominalPusch {
      type eytypes:int32_range_-126-24;
      default "-103";
      units "dBm";
      description "range -126..24; Default value: -103.";
    }
    leaf qciTableRef {
      type string;
    }
    leaf rachNoOfAllocationsPerFrame {
      type int32 {
        range "5 | 10 | 20 | 30 | 50 | 100";
      }
      default "10";
      description "Default value: 10.";
    }
    leaf rachPreambleRepetition {
      type boolean;
      default "false";
      description "Default value: false.";
    }
    leaf rachRootSequence {
      type eytypes:int32_range_0-837;
      default "386";
      description "range 0..837; Default value: 386.";
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf operationalState {
      type enumeration {
        enum DISABLED;
        enum ENABLED;
      }
      config false;
    }
    leaf administrativeState {
      type enumeration {
        enum LOCKED;
        enum UNLOCKED;
        enum SHUTTINGDOWN;
      }
    }
    leaf cellId {
      type eytypes:int32_range_0-255;
      mandatory true;
      description "range 0..255.";
    }
    leaf physicalLayerCellIdGroup {
      type eytypes:int32_range_0-167;
      mandatory true;
      description "range 0..167.";
    }
    leaf physicalLayerSubCellId {
      type eytypes:int32_range_0-2;
      mandatory true;
      description "range 0..2.";
    }
    leaf userLabel {
      type string {
        length "1..128";
      }
      description "length 1..128.";
    }
    leaf tac {
      type eytypes:int32_range_0-65535-10;
      mandatory true;
      description "range 0..65535.";
    }
    leaf drxActive {
      type boolean;
      default "false";
      description "Default value: false.";
    }
    leaf networkSignallingValue {
      type enumeration {
        enum NS_01;
        enum NS_03;
        enum NS_04;
        enum NS_05;
        enum NS_06;
        enum NS_07;
        enum NS_08;
        enum NS_09;
        enum NS_10;
        enum NS_11;
        enum NS_12;
        enum NS_13;
        enum NS_14;
        enum NS_15;
        enum NS_16;
        enum NS_17;
        enum NS_18;
        enum NS_19;
        enum NS_20;
        enum NS_21;
        enum NS_22;
        enum NS_23;
        enum NS_24;
        enum NS_25;
        enum NS_26;
        enum NS_27;
        enum NS_28;
        enum NS_29;
        enum NS_30;
        enum NS_31;
        enum NS_32;
        enum NS_35;
      }
    }
    leaf initCdma2000SysTimeType {
      type enumeration {
        enum NONE;
        enum SYNCHRONOUS;
        enum ASYNCHRONOUS;
      }
    }
    leaf bcCdma2000SysTimeType {
      type enumeration {
        enum NONE;
        enum SYNCHRONOUS;
        enum ASYNCHRONOUS;
      }
      config false;
    }
    leaf pucchOverdimensioning {
      type int32 {
        range "0..49";
      }
      default "0";
      units "Resource Block";
      description "range 0..49; Default value: 0.";
    }
    leaf qRxLevMinOffset {
      type int32 {
        range "2..16 | 1000";
      }
      default "1000";
      units "dB";
      description "Default value: 1000.";
    }
    leaf estimatedE2ERTT {
      type int32 {
        range "0..2048";
      }
      default "100";
      units "ms";
      description "range 0..2048; Default value: 100.";
    }
    leaf otdoaSuplActive {
      type boolean;
      default "false";
      description "Default value: false.";
    }
    leaf prsConfigIndex {
      type int32 {
        range "-1..4095";
      }
      default "-1";
      description "range -1..4095; Default value: -1.";
    }
    leaf noConsecutiveSubframes {
      type enumeration {
        enum SF1;
        enum SF2;
        enum SF4;
        enum SF6;
      }
    }
    leaf latitude {
      type eytypes:int32_range_-90000000-90000000;
      default "0";
      units "degrees";
      description "range -90000000..90000000; Default value: 0.";
    }
    leaf longitude {
      type eytypes:int32_range_-180000000-180000000;
      default "0";
      units "degrees";
      description "range -180000000..180000000; Default value: 0.";
    }
    leaf altitude {
      type int32 {
        range "-32768..32767";
      }
      default "0";
      units "meter";
      description "range -32768..32767; Default value: 0.";
    }
    leaf uncertSemiMajor {
      type eytypes:int32_range_0-127;
      default "0";
      description "range 0..127; Default value: 0.";
    }
    leaf uncertSemiMinor {
      type eytypes:int32_range_0-127;
      default "0";
      description "range 0..127; Default value: 0.";
    }
    leaf orientMajorAxis {
      type int32 {
        range "0..179";
      }
      default "0";
      units "degrees";
      description "range 0..179; Default value: 0.";
    }
    leaf uncertAltitude {
      type eytypes:int32_range_0-127;
      default "0";
      description "range 0..127; Default value: 0.";
    }
    leaf confidence {
      type eytypes:int32_range_0-100-27;
      default "100";
      units "percent";
      description "range 0..100; Default value: 100.";
    }
    leaf gpsTimeSFN0DecimalSecond {
      type eytypes:int64_range_0-4294967295;
      config false;
      description "range 0..4294967295.";
    }
    leaf primaryPlmnReserved {
      type boolean;
      default "false";
      description "Default value: false.";
    }
    leaf-list additionalPlmnReservedList {
      type boolean;
    }
    list additionalPlmnList {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    list activePlmnList {
      config false;
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf gpsTimeSFN0Seconds {
      type int64 {
        range "0..4294967295";
      }
      config false;
      units "seconds";
      description "range 0..4294967295.";
    }
    leaf prsPeriod {
      type enumeration {
        enum PP160;
        enum PP320;
        enum PP640;
        enum PP1280;
      }
    }
    leaf covTriggerdBlindHoAllowed {
      type boolean;
      default "true";
      description "Default value: true.";
    }
    leaf dlConfigurableFrequencyStart {
      type eytypes:int32_range_0-100-27;
      default "0";
      units "percent";
      description "range 0..100; Default value: 0.";
    }
    leaf ulConfigurableFrequencyStart {
      type eytypes:int32_range_0-100-27;
      default "0";
      units "percent";
      description "range 0..100; Default value: 0.";
    }
    leaf dlFrequencyAllocationProportion {
      type ietfinet:port-number;
      default "100";
      units "percent";
      description "range 1..100; Default value: 100.";
    }
    leaf ulFrequencyAllocationProportion {
      type ietfinet:port-number;
      default "100";
      units "percent";
      description "range 1..100; Default value: 100.";
    }
    list eutranCellPolygon {
      key "id";
      leaf id {
        type uint32;
        description "Synthetic key for struct sequence entry.";
      }
      container attributes {
      leaf cornerLatitude {
        type eytypes:int32_range_-90000000-90000000;
        default "0";
        units "degrees";
        description "range -90000000..90000000; Default value: 0.";
      }
      leaf cornerLongitude {
        type eytypes:int32_range_-180000000-180000000;
        default "0";
        units "degrees";
        description "range -180000000..180000000; Default value: 0.";
      }
      }
    }
    leaf prsConfigIndexMapped {
      type eytypes:int32_range_0-4095;
      config false;
      description "range 0..4095.";
    }
    list eutranCellCoverage {
      key "id";
      leaf id {
        type uint32;
        description "Synthetic key for struct entry.";
      }
      container attributes {
      leaf posCellRadius {
        type eytypes:int32_range_0-200000;
        default "0";
        units "meter";
        description "range 0..200000; Default value: 0.";
      }
      leaf posCellOpeningAngle {
        type eytypes:int32_range_-1-3599;
        default "-1";
        units "degrees";
        description "range -1..3599; Default value: -1.";
      }
      leaf posCellBearing {
        type eytypes:int32_range_-1-3599;
        default "-1";
        units "degrees";
        description "range -1..3599; Default value: -1.";
      }
      }
    }
    leaf qQualMin {
      type int32 {
        range "-34..-3 | 0";
      }
      default "0";
      units "dB";
      description "Default value: 0.";
    }
    leaf qQualMinOffset {
      type eytypes:int32_range_0-8-28;
      default "0";
      units "dB";
      description "range 0..8; Default value: 0.";
    }
    leaf pdcchCfiMode {
      type enumeration {
        enum CFI_STATIC_BY_BW;
        enum CFI_STATIC_1;
        enum CFI_STATIC_2;
        enum CFI_STATIC_3;
        enum CFI_AUTO_MAXIMUM_2;
        enum CFI_AUTO_MAXIMUM_3;
      }
    }
    leaf ulSrsEnable {
      type boolean;
      default "false";
      description "Default value: false.";
    }
    leaf rateShapingActive {
      type boolean;
      default "false";
      description "Default value: false.";
    }
    leaf cellSubscriptionCapacity {
      type ietfinet:ip-address;
      description "range 0..1000000; Default value: 1000.";
    }
    leaf threshServingLow {
      type eytypes:int32_range_0-62;
      default "0";
      units "dB";
      description "range 0..62; Default value: 0.";
    }
    leaf-list pciConflict {
      type enumeration {
        enum NO;
        enum NO_CONFLICTING_CELL;
        enum YES;
        enum YES_CONFLICTING_CELL;
      }
    }
    leaf lastModification {
      type enumeration {
        enum OPERATOR;
        enum PCI_MODIFICATION;
        enum RACH_OPT_MODIFICATION;
        enum OSS_PCI_MODIFICATION;
      }
    }
    list pciConflictCell {
      key "id";
      leaf id {
        type uint32;
        description "Synthetic key for struct sequence entry.";
      }
      container attributes {
      leaf enbId {
        type eytypes:int32_range_0-1048575;
        default "0";
        description "range 0..1048575; Default value: 0.";
      }
      leaf cellId {
        type eytypes:int32_range_0-255;
        default "0";
        description "range 0..255; Default value: 0.";
      }
      leaf mcc {
        type eytypes:int32_range_0-999;
        default "1";
        description "range 0..999; Default value: 1.";
      }
      leaf mnc {
        type eytypes:int32_range_0-999;
        default "1";
        description "range 0..999; Default value: 1.";
      }
      leaf mncLength {
        type eytypes:int32_range_2-3;
        default "2";
        description "range 2..3; Default value: 2.";
      }
      }
    }
    leaf timeOfLastModification {
      type string {
        length "0..19";
      }
      description "length 0..19.";
    }
    leaf cfraEnable {
      type boolean;
      default "false";
      description "Default value: false.";
    }
    leaf acBarringInfoPresent {
      type boolean;
      default "false";
      description "Default value: false.";
    }
    list acBarringForMoSignalling {
      key "id";
      leaf id {
        type uint32;
        description "Synthetic key for struct entry.";
      }
      container attributes {
      leaf acBarringFactor {
        type int32;
        default "95";
        units "percent";
        description "Default value: 95.";
      }
      leaf acBarringTime {
        type int32;
        default "64";
        units "s";
        description "Default value: 64.";
      }
      leaf acBarringForSpecialAC {
        type string;
      }
      }
    }
    list acBarringForMoData {
      key "id";
      leaf id {
        type uint32;
        description "Synthetic key for struct entry.";
      }
      container attributes {
      leaf acBarringFactor {
        type int32;
        default "95";
        units "percent";
        description "Default value: 95.";
      }
      leaf acBarringTime {
        type int32;
        default "64";
        units "s";
        description "Default value: 64.";
      }
      leaf acBarringForSpecialAC {
        type string;
      }
      }
    }
    leaf ssacBarringForMMTELVoicePresent {
      type boolean;
      status deprecated;
      default "false";
      description "Default value: false; Status info: Since 17.Q3. Replaced by AcBarringPresence.acBarringForMmtelVoicePresence in EUtranCellFDD/EUtranCellTDD::acBarringPresence. Planned to be removed..";
    }
    leaf ssacBarringForMMTELVideoPresent {
      type boolean;
      status deprecated;
      default "false";
      description "Default value: false; Status info: Since 17.Q3. Replaced by AcBarringPresence.acBarringForMmtelVideoPresence in EUtranCellFDD/EUtranCellTDD::acBarringPresence. Planned to be removed..";
    }
    list ssacBarringForMMTELVoice {
      key "id";
      leaf id {
        type uint32;
        description "Synthetic key for struct entry.";
      }
      container attributes {
      leaf acBarringFactor {
        type int32;
        default "95";
        units "percent";
        description "Default value: 95.";
      }
      leaf acBarringTime {
        type int32;
        default "64";
        units "s";
        description "Default value: 64.";
      }
      leaf acBarringForSpecialAC {
        type string;
      }
      }
    }
    list ssacBarringForMMTELVideo {
      key "id";
      leaf id {
        type uint32;
        description "Synthetic key for struct entry.";
      }
      container attributes {
      leaf acBarringFactor {
        type int32;
        default "95";
        units "percent";
        description "Default value: 95.";
      }
      leaf acBarringTime {
        type int32;
        default "64";
        units "s";
        description "Default value: 64.";
      }
      leaf acBarringForSpecialAC {
        type string;
      }
      }
    }
    leaf acBarringForEmergency {
      type boolean;
      default "false";
      description "Default value: false.";
    }
    list pciDetectingCell {
      key "id";
      leaf id {
        type uint32;
        description "Synthetic key for struct sequence entry.";
      }
      container attributes {
      leaf enbId {
        type eytypes:int32_range_0-1048575;
        default "0";
        description "range 0..1048575; Default value: 0.";
      }
      leaf cellId {
        type eytypes:int32_range_0-255;
        default "0";
        description "range 0..255; Default value: 0.";
      }
      leaf mcc {
        type eytypes:int32_range_0-999;
        default "1";
        description "range 0..999; Default value: 1.";
      }
      leaf mnc {
        type eytypes:int32_range_0-999;
        default "1";
        description "range 0..999; Default value: 1.";
      }
      leaf mncLength {
        type eytypes:int32_range_2-3;
        default "2";
        description "range 2..3; Default value: 2.";
      }
      }
    }
    leaf-list emergencyAreaId {
      type eytypes:int32_range_-1-16777215;
    }
    leaf hostingDigitalUnit {
      type string;
      config false;
    }
    leaf highSpeedUEActive {
      type boolean;
      default "false";
      description "Default value: false.";
    }
    leaf advCellSupSensitivity {
      type eytypes:int32_range_0-100-3;
      default "0";
      description "range 0..100; Default value: 0.";
    }
    leaf advCellSupAction {
      type enumeration {
        enum NO_ACTION;
        enum CELL_RESTART;
        enum CELL_AND_NODE_RESTART;
      }
    }
    leaf hoOptStatTime {
      type int32 {
        range "1..32767";
      }
      default "24";
      units "hour";
      description "range 1..32767; Default value: 24.";
    }
    leaf hoOptStatNum {
      type eytypes:int32_range_1-32767;
      default "200";
      description "range 1..32767; Default value: 200.";
    }
    leaf mobCtrlAtPoorCovActive {
      type boolean;
      default "false";
      description "Default value: false.";
    }
    leaf sdmActive {
      type ietfyang:mac-address;
      description "Default value: false.";
    }
    leaf-list sectorCarrierRef {
      type string;
    }
    leaf lbUtranOffloadThreshold {
      type int32 {
        range "0..1600";
      }
      default "100";
      description "range 0..1600; Default value: 100.";
    }
    leaf externalCdma20001xRttCellRef {
      type string;
    }
    list acBarringForCsfb {
      key "id";
      leaf id {
        type uint32;
        description "Synthetic key for struct entry.";
      }
      container attributes {
      leaf acBarringFactor {
        type int32;
        default "95";
        units "percent";
        description "Default value: 95.";
      }
      leaf acBarringTime {
        type int32;
        default "64";
        units "s";
        description "Default value: 64.";
      }
      leaf acBarringForSpecialAC {
        type string;
      }
      }
    }
    leaf zzzTemporary14 {
      type int32;
      status deprecated;
      default "-2000000000";
      description "Default value: -2000000000; Status info: Since 20.Q1. Has no functional behavior. Planned to be removed..";
    }
    leaf zzzTemporary17 {
      type int32;
      default "-2000000000";
      description "Default value: -2000000000.";
    }
    leaf-list activeServiceAreaId {
      type eytypes:int32_range_0-65535-10;
    }
    leaf pdcchPowerBoostMax {
      type eytypes:int32_range_0-6;
      default "0";
      units "dB";
      description "range 0..6; Default value: 0.";
    }
    leaf alpha {
      type int32 {
        range "0 | 4..10";
      }
      default "10";
      units ".";
      description "Default value: 10.";
    }
    leaf lbEUtranTriggerOffloadThreshold {
      type eytypes:int32_range_0-1600;
      default "100";
      units ".";
      description "range 0..1600; Default value: 100.";
    }
    leaf lbEUtranAcceptOffloadThreshold {
      type eytypes:int32_range_0-1600;
      default "50";
      units ".";
      description "range 0..1600; Default value: 50.";
    }
    leaf lbEUtranCellOffloadCapacity {
      type eytypes:int32_range_0-1000000-18;
      default "1000";
      description "range 0..1000000; Default value: 1000.";
    }
    leaf-list additionalFreqBandList {
      type eytypes:int32_range_1-256;
    }
    leaf freqBand {
      type eytypes:int32_range_1-256;
      config false;
      description "range 1..256.";
    }
    leaf hoOptAdjThresholdAbs {
      type eytypes:int32_range_0-32767;
      default "5";
      description "range 0..32767; Default value: 5.";
    }
    leaf hoOptAdjThresholdPerc {
      type eytypes:int32_range_0-1000-11;
      default "50";
      units "percent";
      description "range 0..1000; Default value: 50.";
    }
    leaf crsGain {
      type int32 {
        range "-300 | -200 | -100 | 0 | 177 | 300 | 477 | 600";
      }
      default "0";
      units "dB";
      description "Default value: 0.";
    }
    leaf dynCellSubscrCap {
      type eytypes:int32_range_0-1000000;
      config false;
      units "kbps";
      description "range 0..1000000.";
    }
    leaf cellCapMinCellSubCap {
      type eytypes:int32_range_0-1000000;
      default "500";
      units "kbps";
      description "range 0..1000000; Default value: 500.";
    }
    leaf cellCapMaxCellSubCap {
      type eytypes:int32_range_0-1000000;
      default "1500";
      units "kbps";
      description "range 0..1000000; Default value: 1500.";
    }
    leaf-list additionalSpectrumEmissionValues {
      type enumeration {
        enum NS_01;
        enum NS_03;
        enum NS_04;
        enum NS_05;
        enum NS_06;
        enum NS_07;
        enum NS_08;
        enum NS_09;
        enum NS_10;
        enum NS_11;
        enum NS_12;
        enum NS_13;
        enum NS_14;
        enum NS_15;
        enum NS_16;
        enum NS_17;
        enum NS_18;
        enum NS_19;
        enum NS_20;
        enum NS_21;
        enum NS_22;
        enum NS_23;
        enum NS_24;
        enum NS_25;
        enum NS_26;
        enum NS_27;
        enum NS_28;
        enum NS_29;
        enum NS_30;
        enum NS_31;
        enum NS_32;
        enum NS_35;
      }
    }
    list spectrumEmissionReqMapping {
      key "id";
      leaf id {
        type uint32;
        description "Synthetic key for struct sequence entry.";
      }
      container attributes {
      leaf freqBand {
        type eytypes:int32_range_1-256;
        default "1";
        description "range 1..256; Default value: 1.";
      }
      leaf spectrumEmissionReq {
        type enumeration {
          enum NS_01;
          enum NS_03;
          enum NS_04;
          enum NS_05;
          enum NS_06;
          enum NS_07;
          enum NS_08;
          enum NS_09;
          enum NS_10;
          enum NS_11;
          enum NS_12;
          enum NS_13;
          enum NS_14;
          enum NS_15;
          enum NS_16;
          enum NS_17;
          enum NS_18;
          enum NS_19;
          enum NS_20;
          enum NS_21;
          enum NS_22;
          enum NS_23;
          enum NS_24;
          enum NS_25;
          enum NS_26;
          enum NS_27;
          enum NS_28;
          enum NS_29;
          enum NS_30;
          enum NS_31;
          enum NS_32;
          enum NS_35;
        }
      }
      }
    }
    leaf expectedMaxNoOfUsersInCell {
      type int32 {
        range "-1..32768";
      }
      default "-1";
      description "range -1..32768; Default value: -1.";
    }
    leaf measuredMaxNoOfUsersInCell {
      type eytypes:int32_range_0-32768;
      config false;
      description "range 0..32768.";
    }
    leaf pdcchLaGinrMargin {
      type int32 {
        range "-50..150";
      }
      default "100";
      units "dB";
      description "range -50..150; Default value: 100.";
    }
    leaf initialBufferSizeDefault {
      type eytypes:int32_range_1-10000;
      default "86";
      units "bytes";
      description "range 1..10000; Default value: 86.";
    }
    leaf cioUpperLimitAdjBySon {
      type eytypes:int32_range_0-24-29;
      default "4";
      units "dB";
      description "range 0..24; Default value: 4.";
    }
    leaf cioLowerLimitAdjBySon {
      type eytypes:int32_range_-24-0;
      default "-3";
      units "dB";
      description "range -24..0; Default value: -3.";
    }
    leaf servOrPrioTriggeredIFHo {
      type enumeration {
        enum QCI;
        enum ARP;
        enum NOT_ACTIVATED;
      }
    }
    leaf otdoaCheckEnabled {
      type boolean;
      default "false";
      description "Default value: false.";
    }
    leaf servOrPrioRedirectEnabled {
      type boolean;
      default "true";
      description "Default value: true.";
    }
    leaf-list arpPriorityLevelForSPIFHo {
      type boolean;
    }
    leaf lbabIncr {
      type eytypes:int32_range_5-100;
      default "5";
      units "percent";
      description "range 5..100; Default value: 5.";
    }
    list acBarringPresence {
      key "id";
      leaf id {
        type uint32;
        description "Synthetic key for struct entry.";
      }
      container attributes {
      leaf acBarringForMoDataPresence {
        type enumeration {
          enum OFF;
          enum MANUAL;
          enum AUTO;
        }
      }
      leaf acBarringForMoSignPresence {
        type enumeration {
          enum OFF;
          enum MANUAL;
          enum AUTO;
        }
      }
      leaf acBarringForCsfbPresence {
        type enumeration {
          enum OFF;
          enum MANUAL;
          enum AUTO;
        }
      }
      leaf acBarringForMmtelVoicePresence {
        type enumeration {
          enum OFF;
          enum MANUAL;
          enum AUTO;
        }
      }
      leaf acBarringForMmtelVideoPresence {
        type enumeration {
          enum OFF;
          enum MANUAL;
          enum AUTO;
        }
      }
      leaf acBarringPriorityCsfb {
        type enumeration {
          enum PRIORITY0;
          enum PRIORITY1;
          enum PRIORITY2;
          enum PRIORITY3;
          enum PRIORITY4;
        }
      }
      leaf acBarringPriorityMoData {
        type enumeration {
          enum PRIORITY0;
          enum PRIORITY1;
          enum PRIORITY2;
          enum PRIORITY3;
          enum PRIORITY4;
        }
      }
      leaf acBarringPriorityMoSignaling {
        type enumeration {
          enum PRIORITY0;
          enum PRIORITY1;
          enum PRIORITY2;
          enum PRIORITY3;
          enum PRIORITY4;
        }
      }
      leaf acBarringPriorityMmtelVoice {
        type enumeration {
          enum PRIORITY0;
          enum PRIORITY1;
          enum PRIORITY2;
          enum PRIORITY3;
          enum PRIORITY4;
        }
      }
      leaf acBarringPriorityMmtelVideo {
        type enumeration {
          enum PRIORITY0;
          enum PRIORITY1;
          enum PRIORITY2;
          enum PRIORITY3;
          enum PRIORITY4;
        }
      }
      leaf acBarringForEmergencySpecAcPres {
        type enumeration {
          enum MANUAL;
          enum AUTO;
        }
      }
      leaf acBarringPrioCsfbSpecAc {
        type string;
      }
      leaf acBarringPrioMmtelVideoSpecAc {
        type string;
      }
      leaf acBarringPrioMmtelVoiceSpecAc {
        type string;
      }
      leaf acBarringPrioMoDataSpecAc {
        type string;
      }
      leaf acBarringPrioMoSignalingSpecAc {
        type string;
      }
      leaf acBarringPrioEmergencySpecAc {
        type enumeration {
          enum PRIORITY0;
          enum PRIORITY1;
          enum PRIORITY2;
          enum PRIORITY3;
          enum PRIORITY4;
        }
      }
      }
    }
    leaf lbabThreshTimeHigh {
      type eytypes:int32_range_0-4095-30;
      default "30";
      units "s";
      description "range 0..4095; Default value: 30.";
    }
    leaf lbabThreshTimeLow {
      type eytypes:int32_range_0-4095-30;
      default "30";
      units "s";
      description "range 0..4095; Default value: 30.";
    }
    leaf lbabThreshRejectRateHigh {
      type eytypes:int32_range_0-1000-11;
      default "200";
      units "percent";
      description "range 0..1000; Default value: 200.";
    }
    leaf lbabThreshRejectRateLow {
      type eytypes:int32_range_0-1000-11;
      default "20";
      units "percent";
      description "range 0..1000; Default value: 20.";
    }
    leaf lbabDecr {
      type eytypes:int32_range_5-100;
      default "5";
      units "percent";
      description "range 5..100; Default value: 5.";
    }
    leaf lbabPeriod {
      type eytypes:int32_range_0-4095-30;
      default "120";
      units "s";
      description "range 0..4095; Default value: 120.";
    }
    leaf loadBasedBarringFactor {
      type eytypes:int32_range_0-100;
      config false;
      units "percent";
      description "range 0..100.";
    }
    leaf prsTransmisScheme {
      type enumeration {
        enum ANTENNA_SWITCHING;
        enum PRECODER_SWITCHING;
      }
    }
    leaf prsPowerBoosting {
      type eytypes:int32_range_0-3;
      default "0";
      description "range 0..3; Default value: 0.";
    }
    leaf prsMutingPatternLen {
      type int32 {
        range "1..2 | 4 | 8 | 16";
      }
      default "1";
      units "bits";
      description "Default value: 1.";
    }
    leaf prsMutingPattern {
      type string {
        length "1..16";
      }
      config false;
      description "length 1..16.";
    }
    leaf preambleInitialReceivedTargetPower {
      type eytypes:int32_range_-120--90;
      default "-110";
      units "dBm";
      description "range -120..-90; Default value: -110.";
    }
    leaf initialBufferSizeMsg5Default {
      type eytypes:int32_range_1-10000;
      default "86";
      units "bytes";
      description "range 1..10000; Default value: 86.";
    }
    leaf assumedUePowerMsg3 {
      type int32 {
        range "230 | 260 | 310 | 1000";
      }
      default "1000";
      units "dBm";
      description "Default value: 1000.";
    }
    leaf servOrPrioTriggeredErabAction {
      type enumeration {
        enum SETUP;
        enum REJECT;
      }
    }
    leaf pdschTypeBGain {
      type eytypes:int32_range_0-3;
      default "0";
      description "range 0..3; Default value: 0.";
    }
    leaf zzzTemporary21 {
      type int32;
      status deprecated;
      default "-2000000000";
      description "Default value: -2000000000; Status info: Since 20.Q1. Has no functional behavior. Planned to be removed..";
    }
    leaf zzzTemporary22 {
      type int32;
      default "-2000000000";
      description "Default value: -2000000000.";
    }
    leaf zzzTemporary23 {
      type int32;
      default "-2000000000";
      description "Default value: -2000000000.";
    }
    leaf zzzTemporary24 {
      type int32;
      default "-2000000000";
      description "Default value: -2000000000.";
    }
    leaf incrPrioServingFreqActive {
      type boolean;
      status deprecated;
      default "false";
      description "Default value: false; Status info: Since 17.Q3. Has no functional behavior. Planned to be removed..";
    }
    leaf puschMaxNrOfPrbsPerUe {
      type int32 {
        range "1..100";
      }
      default "100";
      units "Resource Block";
      description "range 1..100; Default value: 100.";
    }
    leaf dummyCdmaBandClass {
      type enumeration {
        enum BAND_CLASS_0;
        enum BAND_CLASS_1;
        enum BAND_CLASS_2;
        enum BAND_CLASS_3;
        enum BAND_CLASS_4;
        enum BAND_CLASS_5;
        enum BAND_CLASS_6;
        enum BAND_CLASS_7;
        enum BAND_CLASS_8;
        enum BAND_CLASS_9;
        enum BAND_CLASS_10;
        enum BAND_CLASS_11;
        enum BAND_CLASS_12;
        enum BAND_CLASS_13;
        enum BAND_CLASS_14;
        enum BAND_CLASS_15;
        enum BAND_CLASS_16;
        enum BAND_CLASS_17;
        enum BAND_CLASS_18;
        enum BAND_CLASS_19;
        enum BAND_CLASS_20;
        enum BAND_CLASS_21;
        enum UNDEFINED_VALUE;
      }
    }
    leaf loadCtrlPrioOfMta {
      type boolean;
      default "false";
      description "Default value: false.";
    }
    leaf ulHarqVolteBlerTarget {
      type int32 {
        range "0..10";
      }
      default "5";
      units "percent";
      description "range 0..10; Default value: 5.";
    }
    leaf tTimeAlignmentTimer {
      type int32 {
        range "0 | 500 | 750 | 1280 | 1920 | 2560 | 5120 | 10240";
      }
      default "0";
      units "ms";
      description "Default value: 0.";
    }
    leaf cellCapMinMaxWriProt {
      type ietfinet:ip-address;
      description "Default value: false.";
    }
    leaf noOfPucchFormat1PrbPairsPerFrame {
      type int32 {
        range "0..1000 | 65535";
      }
      config false;
      units "PRB";
    }
    leaf noOfPucchFormat2PrbPairsPerFrame {
      type int32 {
        range "0..1000 | 65535";
      }
      config false;
      units "PRB";
    }
    leaf noOfPucchFormat3PrbPairsPerFrame {
      type int32 {
        range "0..1000 | 65535";
      }
      config false;
      units "PRB";
    }
    leaf lbTpNonQualFraction {
      type int32 {
        range "0 | 20..80";
      }
      default "35";
      description "Default value: 35.";
    }
    leaf lbTpRankThreshMin {
      type int32 {
        range "-100 | -60..60";
      }
      default "-20";
      description "Default value: -20.";
    }
    leaf primaryPlmnAlarmSuppr {
      type boolean;
      default "false";
      description "Default value: false.";
    }
    leaf-list additionalPlmnAlarmSupprList {
      type boolean;
    }
    leaf zzzTemporary29 {
      type int32;
      default "-2000000000";
      description "Default value: -2000000000.";
    }
    leaf zzzTemporary30 {
      type int32;
      default "-2000000000";
      description "Default value: -2000000000.";
    }
    leaf zzzTemporary31 {
      type int32;
      default "-2000000000";
      description "Default value: -2000000000.";
    }
    leaf zzzTemporary32 {
      type int32;
      default "-2000000000";
      description "Default value: -2000000000.";
    }
    leaf zzzTemporary33 {
      type int32;
      default "-2000000000";
      description "Default value: -2000000000.";
    }
    leaf zzzTemporary34 {
      type int32;
      status deprecated;
      default "-2000000000";
      description "Default value: -2000000000; Status info: Since 17.Q1. Replaced by transmissionMode. Planned to be removed..";
    }
    leaf idleModePrioAtReleaseRef {
      type string;
    }
    leaf-list includeLcgInMacUeThp {
      type ietfyang:mac-address;
    }
    leaf acBarringSkipForMmtelVoice {
      type ietfinet:ip-address;
      description "Default value: false.";
    }
    leaf acBarringSkipForMmtelVideo {
      type ietfinet:ip-address;
      description "Default value: false.";
    }
    leaf acBarringSkipForSms {
      type ietfinet:ip-address;
      description "Default value: false.";
    }
    leaf puschPwrOffset64qam {
      type eytypes:int32_range_0-8-28;
      default "0";
      units "dB";
      description "range 0..8; Default value: 0.";
    }
    leaf ul64qamEnabled {
      type boolean;
      default "true";
      description "Default value: true.";
    }
    leaf ulDynUeAdmCtrlOverloadThr {
      type eytypes:int32_range_0-1000-2;
      default "600";
      description "range 0..1000; Default value: 600.";
    }
    leaf dlDynUeAdmCtrlOverloadThr {
      type eytypes:int32_range_0-1000-2;
      default "600";
      description "range 0..1000; Default value: 600.";
    }
    leaf cceDynUeAdmCtrlOverloadThr {
      type eytypes:int32_range_0-1000-2;
      default "600";
      description "range 0..1000; Default value: 600.";
    }
    leaf ulDynUeAdmCtrlRetDiffThr {
      type eytypes:int32_range_0-1000-2;
      default "500";
      description "range 0..1000; Default value: 500.";
    }
    leaf dlDynUeAdmCtrlRetDiffThr {
      type eytypes:int32_range_0-1000-2;
      default "500";
      description "range 0..1000; Default value: 500.";
    }
    leaf cceDynUeAdmCtrlRetDiffThr {
      type eytypes:int32_range_0-1000-2;
      default "500";
      description "range 0..1000; Default value: 500.";
    }
    leaf dynUeAdmCtrlFilterConst {
      type eytypes:int32_range_0-10000;
      default "3000";
      units "ms";
      description "range 0..10000; Default value: 3000.";
    }
    leaf dynUeAdmCtrlEnabled {
      type boolean;
      default "false";
      description "Default value: false.";
    }
    leaf servOrPrioIFHoSetupBearer {
      type boolean;
      default "true";
      description "Default value: true.";
    }
    leaf networkSignallingValueCa {
      type enumeration {
        enum CA_NS_01;
        enum CA_NS_02;
        enum CA_NS_03;
        enum CA_NS_04;
        enum CA_NS_05;
        enum CA_NS_06;
        enum CA_NS_07;
        enum CA_NS_08;
        enum CA_NS_31;
      }
    }
    leaf elcEnabled {
      type boolean;
      default "false";
      description "Default value: false.";
    }
    leaf cellDownlinkCaCapacity {
      type eytypes:int32_range_0-1000000-18;
      default "0";
      description "range 0..1000000; Default value: 0.";
    }
    leaf estCellCapUsableFraction {
      type int32 {
        range "0..100";
      }
      default "100";
      units "Percent";
      description "range 0..100; Default value: 100.";
    }
    leaf maxSoftLockBackoffTime {
      type int32 {
        range "10..90";
      }
      default "90";
      units "s";
      description "range 10..90; Default value: 90.";
    }
    leaf ailgAutoRestartEnabled {
      type boolean;
      default "false";
      description "Default value: false.";
    }
    leaf ulBlerTargetEnabled {
      type boolean;
      default "false";
      description "Default value: false.";
    }
    leaf rtpTimeout {
      type int32 {
        range "1..15";
      }
      default "10";
      units "seconds";
      description "range 1..15; Default value: 10.";
    }
    leaf dl256QamEnabled {
      type boolean;
      default "true";
      description "Default value: true.";
    }
    leaf dl256QamStatus {
      type enumeration {
        enum NOT_SUPPORTED;
        enum SUPPORTED;
      }
      config false;
    }
    leaf zzzTemporary41 {
      type int32;
      default "-2000000000";
      description "Default value: -2000000000.";
    }
    leaf zzzTemporary42 {
      type int32;
      default "-2000000000";
      description "Default value: -2000000000.";
    }
    leaf zzzTemporary43 {
      type int32;
      default "-2000000000";
      description "Default value: -2000000000.";
    }
    leaf zzzTemporary44 {
      type int32;
      status deprecated;
      default "-2000000000";
      description "Default value: -2000000000; Status info: Since 17.Q2. Replaced by dlBlerTargetEnabled. Planned to be removed..";
    }
    leaf zzzTemporary45 {
      type int32;
      status deprecated;
      default "-2000000000";
      description "Default value: -2000000000; Status info: Since 17.Q2. Replaced by dlHarqVoLTEBlerTarget. Planned to be removed..";
    }
    leaf zzzTemporary46 {
      type int32;
    }
    leaf zzzTemporary47 {
      type int32;
    }
    leaf maxNoClusteredPuschAlloc {
      type eytypes:int32_range_0-5;
      default "0";
      description "range 0..5; Default value: 0.";
    }
    leaf clusteredPuschMprFactor {
      type int32 {
        range "0..200";
      }
      default "100";
      units "percent";
      description "range 0..200; Default value: 100.";
    }
    leaf enableUeAssistedAdaptiveDrx {
      type boolean;
      default "true";
      description "Default value: true.";
    }
    leaf enableUeAssistedSigReduction {
      type boolean;
      default "true";
      description "Default value: true.";
    }
    leaf spifhoSetupBearerAtInitialCtxtSetup {
      type boolean;
      default "false";
      description "Default value: false.";
    }
    leaf allocThrPucchFormat1 {
      type eytypes:int32_range_0-2000-31;
      default "50";
      description "range 0..2000; Default value: 50.";
    }
    leaf allocTimerPucchFormat1 {
      type eytypes:int32_range_0-36000;
      default "50";
      units "ms";
      description "range 0..36000; Default value: 50.";
    }
    leaf deallocThrPucchFormat1 {
      type eytypes:int32_range_0-2000-31;
      default "100";
      description "range 0..2000; Default value: 100.";
    }
    leaf deallocTimerPucchFormat1 {
      type eytypes:int32_range_0-36000;
      default "6000";
      units "ms";
      description "range 0..36000; Default value: 6000.";
    }
    leaf primaryPsdOffset {
      type eytypes:int32_range_0-31;
      default "0";
      units "dB";
      description "range 0..31; Default value: 0.";
    }
    leaf outOfCoverageThreshold {
      type eytypes:int32_range_1-63;
      default "20";
      description "range 1..63; Default value: 20.";
    }
    leaf outOfCoverageDepth {
      type eytypes:int32_range_0-20;
      default "1";
      description "range 0..20; Default value: 1.";
    }
    leaf outOfCoverageSparseGrantingBsr {
      type int32 {
        range "1..1000";
      }
      default "4";
      units "byte";
      description "range 1..1000; Default value: 4.";
    }
    leaf outOfCoverageSrTimerPeriodicity {
      type int32 {
        range "40 | 80 | 160 | 320 | 640 | 960 | 1280";
      }
      default "320";
      units "ms";
      description "Default value: 320.";
    }
    leaf ulSchedCtrlForOocUesEnabled {
      type boolean;
      default "true";
      description "Default value: true.";
    }
    leaf resourcePartitionGroupRef {
      type string;
    }
    leaf zzzTemporary48 {
      type int32;
    }
    leaf zzzTemporary49 {
      type int32;
    }
    leaf zzzTemporary50 {
      type int32;
      default "-2000000000";
      description "Default value: -2000000000.";
    }
    leaf ulTrigActive {
      type boolean;
      default "true";
      description "Default value: true.";
    }
    leaf pdcchCovImproveSrb {
      type boolean;
      default "false";
      description "Default value: false.";
    }
    leaf pdcchCovImproveQci1 {
      type boolean;
      default "false";
      description "Default value: false.";
    }
    leaf pdcchCovImproveDtx {
      type boolean;
      default "false";
      description "Default value: false.";
    }
    leaf ulSCellPriority {
      type eytypes:int32_range_0-5;
      default "5";
      description "range 0..5; Default value: 5.";
    }
    leaf-list prioAdditionalFreqBandList {
      type eytypes:int32_range_1-256;
    }
    leaf srDetectHighThres {
      type eytypes:int32_range_0-300;
      default "70";
      units "dB";
      description "range 0..300; Default value: 70.";
    }
    leaf srProcessingLevel {
      type enumeration {
        enum NO_ADDITIONAL_SR_NEEDED;
        enum TWO_SR_FOR_LOW_THRESHOLD_SR_PROCESSING;
        enum TWO_SR_FOR_ALL_SR_PROCESSING;
      }
    }
    leaf adaptiveCfiHoProhibit {
      type enumeration {
        enum NO_HO_PROHIBIT_CFI;
        enum HO_PROHIBIT_CFI_1;
        enum HO_PROHIBIT_CFI_1_AND_2;
      }
    }
    leaf lastSchedLinkAdaptEnabled {
      type boolean;
      default "true";
      description "Default value: true.";
    }
    leaf pdschMaxNrOfPrbsPerUe {
      type eytypes:int32_range_1-100-4;
      default "100";
      description "range 1..100; Default value: 100.";
    }
    list mappingInfoBr {
      key "id";
      leaf id {
        type uint32;
        description "Synthetic key for struct sequence entry.";
      }
      description "Takes effect: Object unlocked; Status info: Since 17.Q4. Planned to be removed.; Specification: 3GPP 36331_CR2069r3_(Rel-13).";
      container attributes {
      leaf mappingInfoSIB10 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB11 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB12 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB13 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB15 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB16 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB3 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB4 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB5 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB6 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB7 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB8 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB14 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      }
    }
    leaf siValidityTimeBr {
      type enumeration {
        enum VALIDITY_TIME_3H;
        enum VALIDITY_TIME_24H;
      }
    }
    leaf qRxLevMinCe {
      type eytypes:int32_range_-140--44;
      default "-140";
      units "dBm";
      description "range -140..-44; Default value: -140.";
    }
    leaf qQualMinRsrqCe {
      type int32 {
        range "-34..-3 | 0";
      }
      default "0";
      units "dB";
      description "Default value: 0.";
    }
    leaf dynUlResourceAllocEnabled {
      type boolean;
      default "false";
      description "Default value: false.";
    }
    leaf enableSinrUplinkClpc {
      type boolean;
      default "false";
      description "Default value: false.";
    }
    leaf rxSinrTargetClpc {
      type eytypes:int32_range_-50-50;
      default "25";
      units "dB";
      description "range -50..50; Default value: 25.";
    }
    leaf interferenceThresholdSinrClpc {
      type int32 {
        range "-125..-60";
      }
      default "-105";
      units "dBm";
      description "range -125..-60; Default value: -105.";
    }
    leaf ulPsdLoadThresholdSinrClpc {
      type eytypes:int32_range_-126-24;
      default "2";
      units "dBm";
      description "range -126..24; Default value: 2.";
    }
    leaf zzzTemporary51 {
      type int32;
      status deprecated;
      default "-2000000000";
      description "Default value: -2000000000; Status info: Since 18.Q1. Replaced by ns05FullBandSchedEnabled. Planned to be removed..";
    }
    leaf zzzTemporary52 {
      type int32;
      status deprecated;
      default "-2000000000";
      description "Default value: -2000000000; Status info: Since 18.Q1. Replaced by ns05FullBandUsersInCellThres. Planned to be removed..";
    }
    leaf caPrioThreshold {
      type eytypes:int32_range_0-65535-10;
      default "300";
      description "range 0..65535; Default value: 300.";
    }
    leaf measBasedElcControl {
      type boolean;
      default "false";
      description "Default value: false.";
    }
    leaf pdcchOuterLoopInitialAdj {
      type eytypes:int32_range_-200-200;
      default "-70";
      units "dB";
      description "range -200..200; Default value: -70.";
    }
    leaf pdcchOuterLoopInitialAdjVolte {
      type eytypes:int32_range_-200-200;
      default "-70";
      units "dB";
      description "range -200..200; Default value: -70.";
    }
    leaf pdcchOuterLoopInitialAdjPCell {
      type eytypes:int32_range_-200-200;
      default "-70";
      units "dB";
      description "range -200..200; Default value: -70.";
    }
    leaf pdcchOuterLoopUpStep {
      type eytypes:int32_range_0-100-6;
      default "8";
      units "dB";
      description "range 0..100; Default value: 8.";
    }
    leaf pdcchOuterLoopUpStepVolte {
      type eytypes:int32_range_0-100-6;
      default "6";
      units "dB";
      description "range 0..100; Default value: 6.";
    }
    leaf pdcchOuterLoopUpStepPCell {
      type eytypes:int32_range_0-100-6;
      default "6";
      units "dB";
      description "range 0..100; Default value: 6.";
    }
    leaf pdcchTargetBler {
      type eytypes:int32_range_1-200;
      default "24";
      units "percent";
      description "range 1..200; Default value: 24.";
    }
    leaf pdcchTargetBlerVolte {
      type eytypes:int32_range_1-200;
      default "22";
      units "percent";
      description "range 1..200; Default value: 22.";
    }
    leaf pdcchTargetBlerPCell {
      type eytypes:int32_range_1-200;
      default "22";
      units "percent";
      description "range 1..200; Default value: 22.";
    }
    leaf eDrxAllowed {
      type boolean;
      default "false";
      description "Default value: false.";
    }
    leaf elcLongDrxCycle {
      type enumeration {
        enum SF40;
        enum SF320;
      }
    }
    leaf zzzTemporary53 {
      type int32;
      status deprecated;
      default "-2000000000";
      description "Default value: -2000000000; Status info: Since 18.Q1. Replaced by ns05LowBandSchedMode. Planned to be removed..";
    }
    leaf zzzTemporary54 {
      type int32;
      status deprecated;
      default "-2000000000";
      description "Default value: -2000000000; Status info: Since 18.Q1. Replaced by ns05PathlossOffsetThres. Planned to be removed..";
    }
    leaf zzzTemporary55 {
      type int32;
      status deprecated;
      default "-2000000000";
      description "Default value: -2000000000; Status info: Since 18.Q1. Replaced by liteMcsReduction. Planned to be removed..";
    }
    leaf zzzTemporary56 {
      type int32;
      status deprecated;
      default "-2000000000";
      description "Default value: -2000000000; Status info: Since 18.Q3. Has no functional behavior. Planned to be removed..";
    }
    leaf zzzTemporary57 {
      type int32;
      default "-2000000000";
      description "Default value: -2000000000.";
    }
    leaf zzzTemporary58 {
      type int32;
      status deprecated;
      default "-2000000000";
      description "Default value: -2000000000; Status info: Since 18.Q2. Has no functional behavior. Planned to be removed..";
    }
    leaf zzzTemporary59 {
      type int32;
    }
    leaf zzzTemporary60 {
      type int32;
      default "-2000000000";
      description "Default value: -2000000000.";
    }
    leaf zzzTemporary61 {
      type int32;
      status deprecated;
      default "-2000000000";
      description "Default value: -2000000000; Status info: Since 20.Q1. Replaced by eranHighThpEnabled. Planned to be removed..";
    }
    leaf zzzTemporary62 {
      type int32;
    }
    leaf tReorderingAutoConfiguration {
      type boolean;
      default "false";
      description "Default value: false.";
    }
    leaf harqOffsetDl {
      type eytypes:int32_range_-20-20;
      default "3";
      units "ms";
      description "range -20..20; Default value: 3.";
    }
    leaf harqOffsetUl {
      type eytypes:int32_range_-20-20;
      default "3";
      units "ms";
      description "range -20..20; Default value: 3.";
    }
    leaf enableDrxAwareRlcArq {
      type boolean;
      default "false";
      description "Default value: false.";
    }
    leaf enableServiceSpecificHARQ {
      type boolean;
      default "false";
      description "Default value: false.";
    }
    leaf lessPrbUsageThreshold {
      type eytypes:int32_range_0-100;
      default "90";
      units "percent";
      description "range 0..100; Default value: 90.";
    }
    leaf dlBlerTargetEnabled {
      type boolean;
      default "false";
      description "Default value: false.";
    }
    leaf interEnbUlCompUserSelSinrThr {
      type eytypes:int32_range_-150-250;
      default "100";
      units "dB";
      description "range -150..250; Default value: 100.";
    }
    leaf interEnbUlCompUserSelSinrHys {
      type eytypes:int32_range_10-50;
      default "10";
      units "dB";
      description "range 10..50; Default value: 10.";
    }
    leaf ulTxPsdDistrThr {
      type eytypes:int32_range_0-100-3;
      default "40";
      description "range 0..100; Default value: 40.";
    }
    list commonSFAllocList {
      config false;
      container attributes {
      leaf radioframeAllocationPeriod {
        type int32;
      }
      leaf radioframeAllocationOffset {
        type eytypes:int32_range_0-7;
        description "range 0..7.";
      }
      leaf subframeAllocation {
        type int32;
      }
      leaf subframeAllocationOneFrame {
        type string;
      }
      leaf subframeAllocationFourFrame {
        type string;
      }
      leaf sfAllocationFourFrame {
        type eytypes:int32_range_0-16777215;
        description "range 0..16777215.";
      }
      leaf sfAllocationOneFrame {
        type eytypes:int32_range_0-63;
        description "range 0..63.";
      }
      }
    }
    leaf ulImprovedUeSchedLastEnabled {
      type boolean;
      default "true";
      description "Default value: true.";
    }
    leaf noOfUlImprovedUe {
      type eytypes:int32_range_0-5;
      default "1";
      description "range 0..5; Default value: 1.";
    }
    leaf ulImprovedUeAdapRetransEnabled {
      type boolean;
      status deprecated;
      default "true";
      description "Default value: true; Status info: Since 17.Q3. Has no functional behavior. Planned to be removed..";
    }
    leaf bsrThreshold {
      type int32 {
        range "0..32767";
      }
      default "0";
      units "Bytes";
      description "range 0..32767; Default value: 0.";
    }
    leaf tUeBlockingTimer {
      type int32 {
        range "50..200";
      }
      default "200";
      units "s";
      description "range 50..200; Default value: 200.";
    }
    leaf sCellHpueEnabled {
      type boolean;
      status deprecated;
      default "true";
      description "Default value: true; Status info: Since 17.Q3. Has no functional behavior. Planned to be removed..";
    }
    leaf zzzTemporary63 {
      type int32;
    }
    leaf zzzTemporary64 {
      type int32;
      default "-2000000000";
      description "Default value: -2000000000.";
    }
    leaf zzzTemporary65 {
      type int32;
      default "-2000000000";
      description "Default value: -2000000000.";
    }
    leaf zzzTemporary66 {
      type int32;
      default "-2000000000";
      description "Default value: -2000000000.";
    }
    leaf lbabBarringPriorityLevel {
      type enumeration {
        enum PRIORITY0;
        enum PRIORITY1;
        enum PRIORITY2;
        enum PRIORITY3;
        enum PRIORITY4;
      }
      config false;
    }
    leaf lbabMinBarringFactor {
      type eytypes:int32_range_0-100;
      default "0";
      units "percent";
      description "range 0..100; Default value: 0.";
    }
    leaf lbabMinBarringFactorPrio1 {
      type eytypes:int32_range_0-100;
      default "0";
      units "percent";
      description "range 0..100; Default value: 0.";
    }
    leaf lbabMinBarringFactorPrio2 {
      type eytypes:int32_range_0-100;
      default "0";
      units "percent";
      description "range 0..100; Default value: 0.";
    }
    leaf physicalLayerCellId {
      type eytypes:int32_range_0-503;
      config false;
      description "range 0..503.";
    }
    leaf prioHpueCapability {
      type enumeration {
        enum NO_PRIORITIZATION;
        enum PRIORITIZE_IN_CA;
      }
    }
    leaf noOfEnhAdptReTxCand {
      type int32 {
        range "-1..5";
      }
      default "0";
      description "range -1..5; Default value: 0.";
    }
    list mappingInfoCe {
      key "id";
      leaf id {
        type uint32;
        description "Synthetic key for struct entry.";
      }
      container attributes {
      leaf mappingInfoSIB10 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB11 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB12 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB13 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB15 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB16 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB3 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB4 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB5 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB6 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB7 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB8 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB14 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      }
    }
    leaf prescheduling {
      type boolean;
      default "true";
      description "Default value: true.";
    }
    leaf eranUlCompUserSelSinrThr {
      type eytypes:int32_range_-150-400;
      default "150";
      units "dB";
      description "range -150..400; Default value: 150.";
    }
    leaf eranUlCompUserSelSinrHys {
      type eytypes:int32_range_10-50;
      default "10";
      units "dB";
      description "range 10..50; Default value: 10.";
    }
    leaf-list cellResourceRef {
      type string;
      description "Takes effect: Next cell unlock; Status info: Since 18.Q2. Has no functional behavior. Planned to be removed..";
    }
    leaf liteMcsReduction {
      type enumeration {
        enum OFF;
        enum ON;
        enum ON_WHEN_NO_ELC;
      }
    }
    leaf zzzTemporary67 {
      type int32;
      status deprecated;
      default "-2000000000";
      description "Default value: -2000000000; Status info: Since 20.Q3. Planned to be removed..";
    }
    leaf measCellGroupCellRef {
      type string;
    }
    leaf iuaEnabled {
      type boolean;
      status deprecated;
      default "false";
      description "Default value: false; Status info: Since 18.Q3. Replaced by InstantUplinkAccess::iuaEnabled. Planned to be removed..";
    }
    leaf iuaInterval {
      type eytypes:int32_range_0-5-32;
      status deprecated;
      default "1";
      units "ms";
      description "range 0..5; Default value: 1; Status info: Since 18.Q3. Replaced by InstantUplinkAccess::iuaInterval. Planned to be removed.; Specification: 3GPP 36.331.";
    }
    leaf iuaMaxResourcePerCell {
      type eytypes:int32_range_0-100;
      status deprecated;
      default "20";
      units "percent";
      description "range 0..100; Default value: 20; Status info: Since 18.Q3. Replaced by InstantUplinkAccess::iuaCellResourceLimit. Planned to be removed..";
    }
    leaf iuaMaxPrbsPerUe {
      type eytypes:int32_range_0-100;
      status deprecated;
      default "20";
      units "percent";
      description "range 0..100; Default value: 20; Status info: Since 18.Q3. Replaced by InstantUplinkAccess::iuaUePrbLimit. Planned to be removed..";
    }
    leaf ns05FullBandSchedEnabled {
      type boolean;
      default "false";
      description "Default value: false.";
    }
    leaf ns05FullBandUsersInCellThres {
      type eytypes:int32_range_1-100-4;
      default "10";
      description "range 1..100; Default value: 10.";
    }
    leaf ns05LowBandSchedMode {
      type enumeration {
        enum ALWAYS_PROHIBIT;
        enum ALWAYS_AVAILABLE;
        enum ADAPTIVE_AVAILABLE_BY_REPEATER_DETECTION;
      }
    }
    leaf ns05PathlossOffsetThres {
      type int32 {
        range "0..1000";
      }
      default "50";
      units "dB";
      description "range 0..1000; Default value: 50.";
    }
    leaf zzzTemporary68 {
      type int32;
      status deprecated;
      default "-2000000000";
      description "Default value: -2000000000; Status info: Since 20.Q3. Planned to be removed..";
    }
    leaf zzzTemporary69 {
      type int32;
      status deprecated;
      default "-2000000000";
      description "Default value: -2000000000; Status info: Since 20.Q3. Planned to be removed..";
    }
    leaf zzzTemporary70 {
      type int32;
      status deprecated;
      default "-2000000000";
      description "Default value: -2000000000; Status info: Since 21.Q1. Replaced by UeMeasControl::endcCheckForRwrToNRDisabled. Planned to be removed..";
    }
    leaf zzzTemporary71 {
      type int32;
      default "-2000000000";
      description "Default value: -2000000000.";
    }
    leaf srvccDelayTimer {
      type eytypes:int32_range_0-30000-33;
      default "0";
      units "ms";
      description "range 0..30000; Default value: 0.";
    }
    leaf voiceMeasAccEnabled {
      type boolean;
      status deprecated;
      default "false";
      description "Default value: false; Takes effect: New connection; Status info: Since 18.Q2. Has no functional behavior. Planned to be removed..";
      reference "Takes effect: New connection.";
    }
    leaf hpueCaSwitchThres {
      type eytypes:int32_range_-150-450;
      default "-150";
      units "dB";
      description "range -150..450; Default value: -150.";
    }
    leaf hpueCaSwitchHyst {
      type eytypes:int32_range_0-150;
      default "20";
      units "dB";
      description "range 0..150; Default value: 20.";
    }
    leaf hpueCaSwitchTimeToTrigger {
      type int32 {
        range "0 | 40 | 64 | 80 | 100 | 128 | 160 | 256 | 320 | 480 | 512 | 640 | 1024 | 1280 | 2560 | 5120";
      }
      default "40";
      units "ms";
      description "Default value: 40.";
    }
    list additionalMultipleNSPmax {
      config false;
      container attributes {
      leaf multiplePmax {
        type ietfinet:ip-address;
      }
      leaf multipleNSvalue {
        type ietfinet:ip-address;
      }
      }
    }
    list multipleNSPmaxReqMapping {
      key "id";
      leaf id {
        type uint32;
        description "Synthetic key for struct sequence entry.";
      }
      container attributes {
      leaf additionalFreqBand {
        type eytypes:int32_range_1-256;
        default "1";
        description "range 1..256; Default value: 1.";
      }
      leaf additionalPMax {
        type int32;
        default "1000";
        description "Default value: 1000.";
      }
      leaf additionalNSvalue {
        type enumeration {
          enum NS_01;
          enum NS_03;
          enum NS_04;
          enum NS_05;
          enum NS_06;
          enum NS_07;
          enum NS_08;
          enum NS_09;
          enum NS_10;
          enum NS_11;
          enum NS_12;
          enum NS_13;
          enum NS_14;
          enum NS_15;
          enum NS_16;
          enum NS_17;
          enum NS_18;
          enum NS_19;
          enum NS_20;
          enum NS_21;
          enum NS_22;
          enum NS_23;
          enum NS_24;
          enum NS_25;
          enum NS_26;
          enum NS_27;
          enum NS_28;
          enum NS_29;
          enum NS_30;
          enum NS_31;
          enum NS_32;
          enum NS_35;
        }
      }
      }
    }
    leaf dlPowerRampUpInitialRatio {
      type eytypes:int32_range_10-100;
      status deprecated;
      default "100";
      units "percent";
      description "range 10..100; Default value: 100; Takes effect: Cell lock/unlock; Status info: Since 18.Q4. Planned to be removed..";
      reference "Takes effect: Cell lock/unlock.";
    }
    leaf dlPowerRampUpRate {
      type eytypes:int32_range_1-10-34;
      default "1";
      units "%/second";
      description "range 1..10; Default value: 1.";
    }
    leaf puschNcpChannelEstWindowSize {
      type enumeration {
        enum NORMAL_SIZE;
        enum LARGE_SIZE;
      }
    }
    leaf useBandPrioritiesInSib1 {
      type boolean;
      status deprecated;
      default "false";
      description "Default value: false; Takes effect: New connection; Status info: Since 18.Q4. Replaced by mfbiFreqBandIndPrio. Planned to be removed..";
      reference "Takes effect: New connection.";
    }
    leaf-list measCellGroupUeRef {
      type string;
    }
    leaf catmMbmsDlSubframes {
      type eytypes:int32_range_0-2;
      default "0";
      description "range 0..2; Default value: 0.";
    }
    leaf-list validDlBrSubframes {
      type eytypes:int32_range_0-1023-23;
    }
    leaf zzzTemporary72 {
      type int32;
      default "-2000000000";
      description "Default value: -2000000000.";
    }
    leaf zzzTemporary82 {
      type int32;
      default "-2000000000";
      description "Default value: -2000000000.";
    }
    leaf zzzTemporary73 {
      type int32;
      default "-2000000000";
      description "Default value: -2000000000.";
    }
    leaf zzzTemporary74 {
      type int32;
      default "-2000000000";
      description "Default value: -2000000000.";
    }
    leaf zzzTemporary75 {
      type string;
    }
    leaf zzzTemporary76 {
      type string;
    }
    leaf zzzTemporary77 {
      type string;
    }
    leaf zzzTemporary78 {
      type int32;
      status deprecated;
      default "-2000000000";
      description "Default value: -2000000000; Status info: Since 23.Q2. Replaced by paConnCellUeReservations. Planned to be removed..";
    }
    leaf zzzTemporary79 {
      type int32;
      default "-2000000000";
      description "Default value: -2000000000.";
    }
    leaf zzzTemporary80 {
      type int32;
      default "-2000000000";
      description "Default value: -2000000000.";
    }
    leaf zzzTemporary81 {
      type int32;
      default "-2000000000";
      description "Default value: -2000000000.";
    }
    leaf hoOptStatNumQci1 {
      type eytypes:int32_range_1-32767;
      default "200";
      description "range 1..32767; Default value: 200.";
    }
    leaf hoOptAdjThresholdPercQci1 {
      type eytypes:int32_range_0-1000-11;
      default "50";
      units "percent";
      description "range 0..1000; Default value: 50.";
    }
    leaf hoOptAdjThresholdAbsQci1 {
      type eytypes:int32_range_0-32767;
      default "5";
      description "range 0..32767; Default value: 5.";
    }
    leaf diffAdmCtrlFilteringProfRef {
      type string;
    }
    leaf sCellHandlingAtVolteCall {
      type enumeration {
        enum KEEP_SCELLS;
        enum DECONF_SCELLS;
        enum DECONF_UL_SUPPRESS_DL_SCELLS;
        enum DECONF_UL_SCELLS;
      }
    }
    leaf dlPowerRatio {
      type eytypes:int32_range_10-100;
      default "100";
      units "percent";
      description "range 10..100; Default value: 100.";
    }
    leaf dlPowerChangeRate {
      type eytypes:int32_range_1-10-34;
      default "1";
      units "%/second";
      description "range 1..10; Default value: 1.";
    }
    leaf dlPowerState {
      type enumeration {
        enum INVALID;
        enum STABLE;
        enum CHANGING;
      }
      config false;
    }
    leaf measGapShareSchemeCeABr {
      type enumeration {
        enum SCHEME_ZERO;
        enum SCHEME_ONE;
        enum SCHEME_TWO;
        enum SCHEME_THREE;
      }
    }
    leaf covTriggerdBlindHoAllowedBr {
      type boolean;
      default "true";
      description "Default value: true.";
    }
    leaf zzzTemporary83 {
      type int32;
      default "-2000000000";
      description "Default value: -2000000000.";
    }
    list endcAllowedPlmnList {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf latencyLongThreshold {
      type int32 {
        range "125..1200";
      }
      default "135";
      units "ms";
      description "range 125..1200; Default value: 135.";
    }
    leaf dynLoadCtrlMinNewConn {
      type int32 {
        range "1..110";
      }
      default "1";
      description "range 1..110; Default value: 1.";
    }
    leaf highBasebandPriority {
      type boolean;
      default "false";
      description "Default value: false.";
    }
    leaf lbabMinBarringFactorPrio3 {
      type eytypes:int32_range_0-100;
      default "0";
      units "percent";
      description "range 0..100; Default value: 0.";
    }
    leaf lbabMinBarringFactorPrio4 {
      type eytypes:int32_range_0-100;
      default "0";
      units "percent";
      description "range 0..100; Default value: 0.";
    }
    leaf plmn1AbConfProfileRef {
      type string;
    }
    leaf plmn2AbConfProfileRef {
      type string;
    }
    leaf plmn3AbConfProfileRef {
      type string;
    }
    leaf acBarringPlmnPabEnabled {
      type boolean;
      default "false";
      description "Default value: false.";
    }
    leaf plmnPabBarringPriorityLevel {
      type enumeration {
        enum PRIORITY0;
        enum PRIORITY1;
        enum PRIORITY2;
      }
      config false;
    }
    leaf primaryUpperLayerInd {
      type enumeration {
        enum OFF;
        enum ON;
      }
    }
    leaf-list additionalUpperLayerIndList {
      type enumeration {
        enum OFF;
        enum ON;
      }
    }
    leaf upperLayerIndR15Usage {
      type boolean;
      default "false";
      description "Default value: false.";
    }
    leaf ptmCellProfileRef {
      type string;
    }
    leaf mfbiFreqBandIndPrio {
      type boolean;
      default "false";
      description "Default value: false.";
    }
    leaf noOfCrsPorts {
      type ietfinet:port-number;
      config false;
    }
    leaf filterUeDlThpVolThr {
      type int32 {
        range "0..4000";
      }
      status deprecated;
      default "1000";
      units "kilobyte";
      description "range 0..4000; Default value: 1000; Takes effect: Next ROP; Status info: Since 21.Q4. Planned to be removed..";
      reference "Takes effect: Next ROP.";
    }
    leaf filterUeDlThpTimeThr {
      type int32 {
        range "0..200";
      }
      status deprecated;
      default "50";
      units "ms";
      description "range 0..200; Default value: 50; Takes effect: Next ROP; Status info: Since 21.Q4. Planned to be removed..";
      reference "Takes effect: Next ROP.";
    }
    leaf rwrCriticalZoneAllowed {
      type boolean;
      default "true";
      description "Default value: true.";
    }
    leaf rwrSearchZoneAllowed {
      type boolean;
      default "true";
      description "Default value: true.";
    }
    list loadBasedCaMsrThr {
      key "id";
      leaf id {
        type uint32;
        description "Synthetic key for struct entry.";
      }
      container attributes {
      leaf dlPrbUtilThreshHigh {
        type eytypes:int32_range_0-100-35;
        default "30";
        units "% of PRB in a cell";
        description "range 0..100; Default value: 30.";
      }
      leaf dlPrbUtilThreshLow {
        type eytypes:int32_range_0-100-35;
        default "20";
        units "% of PRB in a cell";
        description "range 0..100; Default value: 20.";
      }
      leaf ulPrbUtilThreshHigh {
        type eytypes:int32_range_0-100-35;
        default "30";
        units "% of PRB in a cell";
        description "range 0..100; Default value: 30.";
      }
      leaf ulPrbUtilThreshLow {
        type eytypes:int32_range_0-100-35;
        default "25";
        units "% of PRB in a cell";
        description "range 0..100; Default value: 25.";
      }
      leaf dlSeUtilThreshHigh {
        type eytypes:int32_range_0-100-36;
        default "60";
        units "% of the maximum SE/TTI";
        description "range 0..100; Default value: 60.";
      }
      leaf dlSeUtilThreshLow {
        type eytypes:int32_range_0-100-36;
        default "40";
        units "% of the maximum SE/TTI";
        description "range 0..100; Default value: 40.";
      }
      leaf ulSeUtilThreshHigh {
        type eytypes:int32_range_0-100-36;
        default "30";
        units "% of the maximum SE/TTI";
        description "range 0..100; Default value: 30.";
      }
      leaf ulSeUtilThreshLow {
        type eytypes:int32_range_0-100-36;
        default "20";
        units "% of the maximum SE/TTI";
        description "range 0..100; Default value: 20.";
      }
      leaf cceUtilThreshHigh {
        type eytypes:int32_range_0-100-37;
        default "40";
        units "% of CCE in a cell";
        description "range 0..100; Default value: 40.";
      }
      leaf cceUtilThreshLow {
        type eytypes:int32_range_0-100-37;
        default "20";
        units "% of CCE in a cell";
        description "range 0..100; Default value: 20.";
      }
      }
    }
    leaf loadBasedCaEnabled {
      type boolean;
      default "false";
      description "Default value: false.";
    }
    leaf nrOfPreallocatedSrRes {
      type int32 {
        range "-1..20";
      }
      config false;
      description "range -1..20.";
    }
    leaf zzzTemporary84 {
      type int32;
      default "-2000000000";
      description "Default value: -2000000000.";
    }
    leaf dlPowerRampUpInitRatio {
      type int32 {
        range "40..100";
      }
      default "100";
      units "percent";
      description "range 40..100; Default value: 100.";
    }
    leaf tTimeAlignmentTimerBr {
      type int32 {
        range "0 | 500 | 750 | 1280 | 1920 | 2560 | 5120 | 10240";
      }
      default "0";
      units "ms";
      description "Default value: 0.";
    }
    leaf caLockDueToHighLoad {
      type boolean;
      config false;
    }
    leaf eUlFssSwitchThresh {
      type eytypes:int32_range_0-100;
      default "100";
      units "percent";
      description "range 0..100; Default value: 100.";
    }
    leaf dsrTransMax {
      type int32 {
        range "4 | 8 | 16 | 32 | 64";
      }
      default "64";
      description "Default value: 64.";
    }
    list systemInformationBlock24 {
      key "id";
      leaf id {
        type uint32;
        description "Synthetic key for struct entry.";
      }
      container attributes {
      leaf tReselectionNR {
        type eytypes:int32_range_0-7-9;
        default "2";
        units "s";
        description "range 0..7; Default value: 2.";
      }
      leaf tReselectionNRSfMedium {
        type eytypes:int32_range_25-100-26;
        default "100";
        units "percent";
        description "range 25..100; Default value: 100.";
      }
      leaf tReselectionNRSfHigh {
        type eytypes:int32_range_25-100-26;
        default "100";
        units "percent";
        description "range 25..100; Default value: 100.";
      }
      }
    }
    leaf iflbAbEnabled {
      type boolean;
      default "false";
      description "Default value: false.";
    }
    leaf ul256qamEnabled {
      type boolean;
      default "false";
      description "Default value: false.";
    }
    leaf puschPwrOffset256qam {
      type eytypes:int32_range_0-20-38;
      default "0";
      units "dB";
      description "range 0..20; Default value: 0.";
    }
    leaf nRResCoordPattern {
      type enumeration {
        enum DEFAULT;
        enum PATTERN_1;
        enum PATTERN_2;
        enum PATTERN_3;
      }
    }
    leaf ulHeavyUeDetectEnabled {
      type boolean;
      default "false";
      description "Default value: false.";
    }
    leaf skipUlPadPreschedEnabled {
      type ietfinet:ip-address;
      description "Default value: false.";
    }
    leaf skipUlPadDynEnabled {
      type ietfinet:ip-address;
      description "Default value: false.";
    }
    leaf moVoiceDynUeAdmCtrlPrio {
      type boolean;
      default "false";
      description "Default value: false.";
    }
    leaf blerTargetConfigEnabled {
      type boolean;
      default "false";
      description "Default value: false.";
    }
    leaf dlCchAndRefSigBlockActive {
      type boolean;
      default "false";
      description "Default value: false.";
    }
    leaf dlCchAndRefSigBoost {
      type boolean;
      default "false";
      description "Default value: false.";
    }
    leaf ulCellCapCoeff {
      type eytypes:int32_range_0-8;
      default "2";
      description "range 0..8; Default value: 2.";
    }
    leaf zzzTemporary85 {
      type int32;
      default "-2000000000";
      description "Default value: -2000000000.";
    }
    leaf eranHighThpEnabled {
      type boolean;
      status deprecated;
      default "false";
      description "Default value: false; Takes effect: Next cell unlock; Status info: Since 20.Q2. Has no functional behavior. Planned to be removed..";
      reference "Takes effect: Next cell unlock.";
    }
    leaf zzzTemporary86 {
      type int32;
      default "-2000000000";
      description "Default value: -2000000000.";
    }
    leaf zzzTemporary87 {
      type int32;
      default "-2000000000";
      description "Default value: -2000000000.";
    }
    leaf csfbForVolteEnabled {
      type boolean;
      status deprecated;
      default "false";
      description "Default value: false; Status info: Since 20.Q1. Has no functional behavior. Planned to be removed..";
    }
    leaf reducedConnSetupTimeEnabled {
      type boolean;
      default "false";
      description "Default value: false.";
    }
    leaf covTrigMobErabSetupConfig {
      type enumeration {
        enum DISABLED;
        enum CSFB_TRIGGERED;
      }
    }
    leaf lbdarCoverageThreshold {
      type eytypes:int32_range_1-100-4;
      default "15";
      description "range 1..100; Default value: 15.";
    }
    leaf zzzTemporary88 {
      type string;
    }
    leaf zzzTemporary89 {
      type string;
    }
    leaf instantDl256QamMode {
      type enumeration {
        enum OFF;
        enum STATIC_HOM_MODE;
        enum DYNAMIC_HOM_MODE;
      }
    }
    leaf dlMaxRetxRrcReleaseThr {
      type int32 {
        range "-1..4 | 6 | 8 | 16 | 32";
      }
      default "-1";
      description "Default value: -1.";
    }
    leaf tPollRetxRrcReleaseDl {
      type int32 {
        range "-1 | 5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500";
      }
      default "-1";
      units "ms";
      description "Default value: -1.";
    }
    leaf rrcQueueT300Ratio {
      type eytypes:int32_range_0-95;
      default "80";
      description "range 0..95; Default value: 80.";
    }
    leaf upperLayerAutoConfEnabled {
      type boolean;
      default "false";
      description "Default value: false.";
    }
    leaf-list upperLayerAutoConfIndList {
      type boolean;
    }
    leaf includeDynPttMsrReservations {
      type boolean;
      default "false";
      description "Default value: false.";
    }
    leaf cceDynUeAdmCtrlPaOverloadThr {
      type eytypes:int32_range_0-1000-2;
      default "1000";
      description "range 0..1000; Default value: 1000.";
    }
    leaf dlDynUeAdmCtrlPaOverloadThr {
      type eytypes:int32_range_0-1000-2;
      default "1000";
      description "range 0..1000; Default value: 1000.";
    }
    leaf ulDynUeAdmCtrlPaOverloadThr {
      type eytypes:int32_range_0-1000-2;
      default "1000";
      description "range 0..1000; Default value: 1000.";
    }
    leaf maxHarqMsg3Tx {
      type eytypes:int32_range_1-8;
      default "4";
      description "range 1..8; Default value: 4.";
    }
    leaf ttiBundlingDataSwitchThres {
      type eytypes:int32_range_-200-200;
      default "-100";
      units "dB";
      description "range -200..200; Default value: -100.";
    }
    leaf noOfOuterZoneSrPrbPairs {
      type int32 {
        range "2 | 4";
      }
      default "2";
      description "Default value: 2.";
    }
    leaf minInterfSchedEnabled {
      type boolean;
      default "false";
      description "Default value: false.";
    }
    leaf minInterfUlRegionSize {
      type int32 {
        range "0..15";
      }
      default "0";
      units "PRB";
      description "range 0..15; Default value: 0.";
    }
    leaf zzzTemporary90 {
      type int32;
      default "-2000000000";
      description "Default value: -2000000000.";
    }
    leaf zzzTemporary91 {
      type int32;
      default "-2000000000";
      description "Default value: -2000000000.";
    }
    leaf zzzTemporary92 {
      type int32;
      default "-2000000000";
      description "Default value: -2000000000.";
    }
    list cellDefinedPrimaryPlmnId {
      key "id";
      leaf id {
        type uint32;
        description "Synthetic key for struct entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf ulHarqTxNoThresToRegion {
      type eytypes:int32_range_0-7;
      default "0";
      description "range 0..7; Default value: 0.";
    }
    leaf subbandSrsActive {
      type boolean;
      default "false";
      description "Default value: false.";
    }
    leaf enhVolteOptimizedCa {
      type boolean;
      default "false";
      description "Default value: false.";
    }
    leaf ueCapRefreshProhibitMoVoice {
      type boolean;
      default "false";
      description "Default value: false.";
    }
    leaf drxActiveBr {
      type enumeration {
        enum DISABLED;
        enum CE_LEVEL_0;
        enum CE_LEVEL_1;
        enum CE_LEVEL_0_AND_1;
      }
    }
    leaf maxRrcConnectedUsersBr {
      type eytypes:int32_range_1-1000-7;
      default "128";
      description "range 1..1000; Default value: 128.";
    }
    leaf zzzTemporary93 {
      type int32;
      default "-2000000000";
      description "Default value: -2000000000.";
    }
    leaf measGapPattEndc {
      type eytypes:int32_range_0-1;
      default "1";
      description "range 0..1; Default value: 1.";
    }
    leaf measGapPattEndcRestriction {
      type enumeration {
        enum NO_RESTRICTION;
        enum FDD;
        enum ESS_SA;
      }
    }
    leaf commonCqiPeriodicity {
      type ietfinet:ip-address;
      units "ms";
      description "Default value: 80.";
    }
    leaf aiAdvCellSupMode {
      type enumeration {
        enum OFF;
        enum OBSERVATION;
        enum NORMAL;
      }
    }
    leaf aiAdvCellSupAction {
      type enumeration {
        enum NO_ACTION;
        enum CELL_RESTART;
      }
    }
    leaf measGapPattern {
      type eytypes:int32_range_0-1;
      default "0";
      description "range 0..1; Default value: 0.";
    }
    leaf sib1AltSchInfo {
      type boolean;
      default "false";
      description "Default value: false.";
    }
    leaf rrcQueueAdaptivePulling {
      type boolean;
      default "false";
      description "Default value: false.";
    }
    leaf prachSfn {
      type int32 {
        range "-1 | 1 | 4 | 7";
      }
      default "-1";
      description "Default value: -1.";
    }
    leaf prachConfigurationIndex {
      type eytypes:int32_range_0-63;
      config false;
      description "range 0..63.";
    }
    leaf adjustCrsPowerEnhEnabled {
      type boolean;
      default "false";
      description "Default value: false.";
    }
    leaf noOfPreamblesCeLvl0Br {
      type eytypes:int32_range_1-63;
      default "4";
      description "range 1..63; Default value: 4.";
    }
    leaf noOfPreamblesCeLvl1Br {
      type eytypes:int32_range_1-63;
      default "4";
      description "range 1..63; Default value: 4.";
    }
    leaf noOfCbraPreambles {
      type int32 {
        range "4..64";
      }
      default "52";
      description "range 4..64; Default value: 52.";
    }
    leaf prachFreqSharing {
      type boolean;
      default "true";
      description "Default value: true.";
    }
    leaf catmEnhMpdcchCapEnabled {
      type boolean;
      default "true";
      description "Default value: true.";
    }
    leaf pa {
      type enumeration {
        enum DB_MINUS_6;
        enum DB_MINUS_4_DOT_77;
        enum DB_MINUS_3;
        enum DB_MINUS_1_DOT_77;
        enum DB_0;
        enum DB_1;
        enum DB_2;
        enum DB_3;
      }
      config false;
    }
    leaf pb {
      type eytypes:int32_range_0-3;
      config false;
      description "range 0..3.";
    }
    leaf siSib1RepetitionBr {
      type enumeration {
        enum NORMAL;
        enum MEDIUM;
        enum LARGE;
      }
    }
    leaf zzzTemporary94 {
      type int32;
    }
    leaf pimDetectionEnabled {
      type boolean;
      status deprecated;
      default "false";
      description "Default value: false; Status info: Since 24.Q1. Replaced by ENodeBFunction::pimDetectionEnabled. Planned to be removed..";
    }
    leaf spifhoDedicatedReportConfig {
      type ietfinet:port-number;
      description "Default value: false.";
    }
    leaf pdcchFlexibleBlerEnabled {
      type boolean;
      default "false";
      description "Default value: false.";
    }
    leaf optimizedPdcchCongestThres {
      type eytypes:int32_range_0-100;
      default "30";
      units "percent";
      description "range 0..100; Default value: 30.";
    }
    leaf optimizedPdcchDlPrbThres {
      type eytypes:int32_range_0-100;
      default "100";
      units "percent";
      description "range 0..100; Default value: 100.";
    }
    leaf optimizedPdcchUlPrbThres {
      type eytypes:int32_range_0-100;
      default "100";
      units "percent";
      description "range 0..100; Default value: 100.";
    }
    leaf optimizedPdcchMaxTargetBler {
      type eytypes:int32_range_1-200;
      default "200";
      units "percent";
      description "range 1..200; Default value: 200.";
    }
    leaf dlCatmEssShareSrb0 {
      type eytypes:int32_range_1-1000-39;
      default "60";
      units "PRB";
      description "range 1..1000; Default value: 60.";
    }
    leaf dlCatmEssShare {
      type eytypes:int32_range_1-1000-39;
      default "1000";
      units "PRB";
      description "range 1..1000; Default value: 1000.";
    }
    leaf ulCatmEssShare {
      type eytypes:int32_range_1-1000-39;
      default "1000";
      units "PRB";
      description "range 1..1000; Default value: 1000.";
    }
    leaf eCallOverImsSupport {
      type ietfinet:port-number;
      description "Default value: false.";
    }
    leaf pagingPriorityDiffThr {
      type enumeration {
        enum OFF;
        enum PRIO_LEVEL_1;
        enum PRIO_LEVEL_2;
        enum PRIO_LEVEL_3;
        enum PRIO_LEVEL_4;
        enum PRIO_LEVEL_5;
        enum PRIO_LEVEL_6;
        enum PRIO_LEVEL_7;
        enum PRIO_LEVEL_8;
      }
    }
    leaf pagingPriorityOverloadThr {
      type enumeration {
        enum OFF;
        enum PRIO_LEVEL_1;
        enum PRIO_LEVEL_2;
        enum PRIO_LEVEL_3;
        enum PRIO_LEVEL_4;
        enum PRIO_LEVEL_5;
        enum PRIO_LEVEL_6;
        enum PRIO_LEVEL_7;
        enum PRIO_LEVEL_8;
      }
    }
    leaf distributedEssInvalidSfDlBr {
      type int32 {
        range "0..20";
      }
      default "0";
      units "subframe";
      description "range 0..20; Default value: 0.";
    }
    leaf endcSetupDlPktAgeThr {
      type int32 {
        range "0 | 10..1000";
      }
      default "0";
      units "ms";
      description "Default value: 0.";
    }
    leaf endcSetupDlPktVolThr {
      type eytypes:int32_range_0-30000;
      default "0";
      units "kB";
      description "range 0..30000; Default value: 0.";
    }
    leaf sIntraSearchDeltaP {
      type int32 {
        range "0 | 6 | 9 | 12 | 15";
      }
      default "0";
      units "dB";
      description "Default value: 0.";
    }
    leaf dominQciFilter {
      type int32 {
        range "-1..0 | 3..64 | 67..255";
      }
      default "-1";
      description "Default value: -1.";
    }
    list dataInactTimerBr {
      key "id";
      leaf id {
        type uint32;
        description "Synthetic key for struct entry.";
      }
      container attributes {
      leaf dataInactTimerBrCe0 {
        type int32;
        default "0";
        units "s";
        description "Default value: 0.";
      }
      leaf dataInactTimerBrCe1 {
        type int32;
        default "0";
        units "s";
        description "Default value: 0.";
      }
      }
    }
    leaf endcB1MeasGapEnabled {
      type boolean;
      status deprecated;
      default "true";
      description "Default value: true; Takes effect: New connection; Status info: Since 23.Q1. Replaced by EUtranCellFDD::endcB1MeasGapConfig. Planned to be removed..";
      reference "Takes effect: New connection.";
    }
    leaf raBackoffCe0Br {
      type enumeration {
        enum NO_BACKOFF;
        enum STATIC_BACKOFF_10MS;
        enum STATIC_BACKOFF_20MS;
        enum STATIC_BACKOFF_30MS;
        enum STATIC_BACKOFF_40MS;
        enum STATIC_BACKOFF_60MS;
        enum STATIC_BACKOFF_80MS;
        enum STATIC_BACKOFF_120MS;
        enum STATIC_BACKOFF_160MS;
        enum STATIC_BACKOFF_240MS;
        enum STATIC_BACKOFF_320MS;
        enum STATIC_BACKOFF_480MS;
        enum STATIC_BACKOFF_960MS;
        enum DYNAMIC_BACKOFF;
      }
    }
    leaf raBackoffCe1Br {
      type enumeration {
        enum NO_BACKOFF;
        enum STATIC_BACKOFF_10MS;
        enum STATIC_BACKOFF_20MS;
        enum STATIC_BACKOFF_30MS;
        enum STATIC_BACKOFF_40MS;
        enum STATIC_BACKOFF_60MS;
        enum STATIC_BACKOFF_80MS;
        enum STATIC_BACKOFF_120MS;
        enum STATIC_BACKOFF_160MS;
        enum STATIC_BACKOFF_240MS;
        enum STATIC_BACKOFF_320MS;
        enum STATIC_BACKOFF_480MS;
        enum STATIC_BACKOFF_960MS;
        enum DYNAMIC_BACKOFF;
      }
    }
    leaf zzzTemporary95 {
      type int32;
      default "-2000000000";
      description "Default value: -2000000000.";
    }
    leaf ulVolteCovMobDetect {
      type enumeration {
        enum DISABLED;
        enum MEASBASEDHO;
        enum BLINDHO;
      }
    }
    leaf ulVolteCovMobThr {
      type eytypes:int32_range_1-31;
      default "5";
      description "range 1..31; Default value: 5.";
    }
    leaf p0ClpcExGoodEnabled {
      type boolean;
      default "false";
      description "Default value: false.";
    }
    leaf p0ClpcExBadEnabled {
      type boolean;
      default "false";
      description "Default value: false.";
    }
    leaf p0ClpcExBadSinrThr {
      type eytypes:int32_range_-40-40;
      default "-10";
      units "dB";
      description "range -40..40; Default value: -10.";
    }
    leaf p0ClpcExGoodSinrThr {
      type eytypes:int32_range_-40-40;
      default "21";
      units "dB";
      description "range -40..40; Default value: 21.";
    }
    leaf p0ClpcExGoodSinrOffset64Qam {
      type eytypes:int32_range_0-8-28;
      default "0";
      units "dB";
      description "range 0..8; Default value: 0.";
    }
    leaf p0ClpcExGoodSinrOffset256Qam {
      type eytypes:int32_range_0-20-38;
      default "0";
      units "dB";
      description "range 0..20; Default value: 0.";
    }
    leaf recBeamfrmGainCompPc {
      type boolean;
      default "true";
      description "Default value: true.";
    }
    leaf lbActionForEndcUe {
      type enumeration {
        enum NOT_ALLOWED;
        enum ENDC_CAPABLE_NOT_CONFIGURED;
        enum ENDC_CAPABLE_ALL;
      }
    }
    leaf pimDetected {
      type boolean;
      config false;
      status deprecated;
      description "MOM flags: noNotification, isNillable=true; Status info: Since 24.Q1. Planned to be removed..";
    }
    leaf voltePreschedulingEnabled {
      type boolean;
      default "false";
      description "Default value: false.";
    }
    leaf ipecGseEnabled {
      type ietfinet:ip-address;
      description "Default value: true.";
    }
    leaf diffPdcchMaxTargetBlerEnabled {
      type boolean;
      default "false";
      description "Default value: false.";
    }
    leaf pdcchMaxTargetBlerLow {
      type eytypes:int32_range_1-800;
      default "200";
      units "percent";
      description "range 1..800; Default value: 200.";
    }
    leaf pdcchMaxTargetBlerHigh {
      type eytypes:int32_range_1-800;
      default "200";
      units "percent";
      description "range 1..800; Default value: 200.";
    }
    leaf pdcchCongestMeasurePeriod {
      type eytypes:int32_range_1-30;
      default "1";
      units "s";
      description "range 1..30; Default value: 1.";
    }
    leaf diffPdcchMaxTargetBlerThres {
      type int32 {
        range "-100..250";
      }
      default "-10";
      units "dB";
      description "range -100..250; Default value: -10.";
    }
    leaf pZeroOffsetUlCa {
      type int32 {
        range "0..12 | 255";
      }
      default "255";
      units "dB";
      description "Default value: 255.";
    }
    leaf subscriptionRatioHighThresh {
      type ietfinet:ip-address;
      description "range 0..16000; Default value: 16000.";
    }
    leaf optimizedPdcchCceUtilThres {
      type eytypes:int32_range_0-100;
      default "0";
      units "percent";
      description "range 0..100; Default value: 0.";
    }
    leaf peUeToInterCellPreThrUnreg {
      type eytypes:int32_range_0-100-3;
      default "10";
      description "range 0..100; Default value: 10.";
    }
    leaf peUeToInterCellPreHyst {
      type int32 {
        range "5..100";
      }
      default "10";
      description "range 5..100; Default value: 10.";
    }
    leaf raResponseWindowSizeCe0Br {
      type enumeration {
        enum SF20;
        enum SF50;
        enum SF80;
        enum SF120;
        enum SF180;
        enum SF240;
        enum SF320;
        enum SF400;
      }
    }
    leaf raResponseWindowSizeCe1Br {
      type enumeration {
        enum SF20;
        enum SF50;
        enum SF80;
        enum SF120;
        enum SF180;
        enum SF240;
        enum SF320;
        enum SF400;
      }
    }
    leaf macContResTimerCe0Br {
      type ietfyang:mac-address;
    }
    leaf macContResTimerCe1Br {
      type ietfyang:mac-address;
    }
    leaf preambleTransMaxCeBr {
      type enumeration {
        enum N3;
        enum N4;
        enum N5;
        enum N6;
        enum N7;
        enum N8;
        enum N10;
        enum N20;
        enum N50;
        enum N100;
        enum N200;
      }
    }
    leaf maxNumPreambleAttemptCe0Br {
      type enumeration {
        enum N3;
        enum N4;
        enum N5;
        enum N6;
        enum N7;
        enum N8;
        enum N10;
      }
    }
    leaf endcB1MeasGapConfig {
      type enumeration {
        enum ENABLED;
        enum DISABLED;
        enum DISABLED_FR1;
        enum DISABLED_FR2;
      }
    }
    leaf raRange {
      type eytypes:int32_range_0-100000;
      default "0";
      units "m";
      description "range 0..100000; Default value: 0.";
    }
    leaf raObsMaxRange {
      type int32 {
        range "1..200000";
      }
      config false;
      units "m";
      description "range 1..200000.";
    }
    leaf paConnCellUeReservations {
      type eytypes:int32_range_0-90;
      default "1";
      units "percent";
      description "range 0..90; Default value: 1.";
    }
    leaf zzzTemporary101 {
      type int32;
      default "-2000000000";
      description "Default value: -2000000000.";
    }
    leaf loopingEndcProtectionEnabled {
      type boolean;
      default "false";
      description "Default value: false.";
    }
    leaf loopingEndcBackoffDuration {
      type eytypes:int32_range_0-86400;
      default "100";
      units "s";
      description "range 0..86400; Default value: 100.";
    }
    leaf loopingEndcShortScgSessTime {
      type eytypes:int32_range_0-30000-33;
      default "1500";
      units "ms";
      description "range 0..30000; Default value: 1500.";
    }
    leaf loopingEndcConsecFailThr {
      type eytypes:int32_range_1-100-4;
      default "5";
      description "range 1..100; Default value: 5.";
    }
    leaf pdcchCongCtrlParamEnabled {
      type boolean;
      default "false";
      description "Default value: false.";
    }
    leaf pdcchOutLoopInitAdjCong {
      type eytypes:int32_range_-200-200;
      default "-70";
      units "dB";
      description "range -200..200; Default value: -70.";
    }
    leaf pdcchOutLoopInitAdjPCellCong {
      type eytypes:int32_range_-200-200;
      default "-70";
      units "dB";
      description "range -200..200; Default value: -70.";
    }
    leaf pdcchPowerBoostMaxCong {
      type eytypes:int32_range_0-6;
      default "0";
      units "dB";
      description "range 0..6; Default value: 0.";
    }
    leaf pdcchTargetBlerAdjStep {
      type int32 {
        range "1..10";
      }
      default "5";
      units "percent";
      description "range 1..10; Default value: 5.";
    }
    leaf ulCompUserSelSinrThr {
      type eytypes:int32_range_-150-400;
      default "400";
      units "dB";
      description "range -150..400; Default value: 400.";
    }
    leaf ulCompUserSelSinrHys {
      type eytypes:int32_range_10-50;
      default "10";
      units "dB";
      description "range 10..50; Default value: 10.";
    }
    leaf noOfMpdcchCss2Br {
      type eytypes:int32_range_1-2;
      default "1";
      description "range 1..2; Default value: 1.";
    }
    leaf pimcuId {
      type int32;
      config false;
    }
    leaf tandemPimcuId {
      type int32;
      config false;
    }
    leaf zzzTemporary102 {
      type int32;
      status deprecated;
      default "-2000000000";
      description "Default value: -2000000000; Status info: Since 25.Q2. Replaced by interFreqHoHigherPrioSpid. Planned to be removed..";
    }
    leaf aiAdvCellSupAdjustMimoSleep {
      type boolean;
      default "true";
      description "Default value: true.";
    }
    leaf endcDistrProfileRef {
      type string;
    }
    leaf uttmCtrlForEndcUe {
      type enumeration {
        enum ENABLED_FOR_ALL_ENDC_UE;
        enum DISABLED_FOR_ENDC_ALLOWED_UE;
        enum DISABLED_FOR_ENDC_CONFIG_UE;
      }
    }
    leaf interFreqHoHigherPrioEnabled {
      type boolean;
      default "false";
      description "Default value: false.";
    }
    leaf minIntensityLimitForLbab {
      type eytypes:int32_range_0-32767;
      default "50";
      description "range 0..32767; Default value: 50.";
    }
    leaf dlVolteCovMobDetect {
      type enumeration {
        enum DISABLED;
        enum MEASBASEDHO;
        enum BLINDHO;
      }
    }
    leaf dlVolteCovMobWindowLen {
      type eytypes:int32_range_1-31;
      default "10";
      description "range 1..31; Default value: 10.";
    }
    leaf dlVolteCovMobThrHigh {
      type eytypes:int32_range_1-10;
      default "6";
      description "range 1..10; Default value: 6.";
    }
    leaf dlVolteCovMobThrLow {
      type eytypes:int32_range_1-10;
      default "4";
      description "range 1..10; Default value: 4.";
    }
    leaf srProhibitTimerCe0Br {
      type eytypes:int32_range_0-7;
      default "3";
      description "range 0..7; Default value: 3.";
    }
    leaf srProhibitTimerCe1Br {
      type eytypes:int32_range_0-7;
      default "3";
      description "range 0..7; Default value: 3.";
    }
    leaf pimAvoidanceControllerEnabled {
      type boolean;
      default "false";
      description "Default value: false.";
    }
    leaf pimAvoidanceModeStatus {
      type enumeration {
        enum AGGRESSOR;
        enum VICTIM;
        enum AGGRESSOR_VICTIM;
      }
      config false;
    }
    leaf pimVictimCellId {
      type eytypes:int32_range_0-255;
      config false;
      status deprecated;
      description "range 0..255; MOM flags: isNillable=true; Status info: Since 25.Q2. Planned to be removed..";
    }
    leaf pimVictimENodeBId {
      type int32 {
        range "0..1048576";
      }
      config false;
      status deprecated;
      description "range 0..1048576; MOM flags: isNillable=true; Status info: Since 25.Q2. Planned to be removed..";
    }
    leaf pimAggressorCellId {
      type eytypes:int32_range_0-16383;
      description "range 0..16383.";
    }
    leaf pimAggressorENodeBId {
      type eytypes:int32_range_0-1048575;
      description "range 0..1048575.";
    }
    leaf pimAvoidManualConfigEnabled {
      type boolean;
      default "false";
      description "Default value: false.";
    }
    leaf pimManualConfigCoefficient {
      type eytypes:int32_range_1-5-21;
      default "2";
      description "range 1..5; Default value: 2.";
    }
    leaf pimMinPrbReservedProportion {
      type ietfinet:port-number;
      default "10";
      description "range 10..100; Default value: 10.";
    }
    leaf pimPowerExcessReference {
      type int32 {
        range "10..200";
      }
      default "30";
      units "dB";
      description "range 10..200; Default value: 30.";
    }
    leaf pimAvoidPeriodicPauseEnabled {
      type boolean;
      default "false";
      description "Default value: false.";
    }
    leaf pciConflictUtvmEcgiMeas {
      type boolean;
      default "true";
      description "Default value: true.";
    }
    leaf endcSetupUlBsVolThr {
      type int32 {
        range "0..150000";
      }
      default "0";
      units "bytes";
      description "range 0..150000; Default value: 0.";
    }
    leaf restartBufMonAtMobility {
      type boolean;
      default "false";
      description "Default value: false.";
    }
    leaf nrMeasRepBlockedDuringHo {
      type boolean;
      default "false";
      description "Default value: false.";
    }
    leaf puschMaxNumRepCeModeABr {
      type int32 {
        range "8 | 16 | 32";
      }
      default "16";
      units "subframe";
      description "Default value: 16.";
    }
    leaf mpdcchCss2MaxNumRepCe1Br {
      type int32 {
        range "4 | 8 | 16";
      }
      default "8";
      units "subframe";
      description "Default value: 8.";
    }
    leaf rsrpThresholdPrachCe1Br {
      type int32 {
        range "-140..-43";
      }
      default "-125";
      units "dB";
      description "range -140..-43; Default value: -125.";
    }
    leaf decoupledPdcchLaEnabled {
      type boolean;
      default "false";
      description "Default value: false.";
    }
    leaf pdcchUlDtxWorseThres {
      type eytypes:int32_range_0-100;
      default "5";
      units "percent";
      description "range 0..100; Default value: 5.";
    }
    leaf pimDetectionRole {
      type enumeration {
        enum AGGRESSOR;
        enum VICTIM;
        enum VICTIM_AND_AGGRESSOR;
      }
      config false;
    }
    leaf pimDetectionStatus {
      type enumeration {
        enum NOT_APPLICABLE;
        enum NO_PIM_DETECTED;
        enum PIM_DETECTED;
      }
      config false;
    }
    leaf mpdcchNumRepetitionCeLev0 {
      type int32 {
        range "1..2 | 4 | 8";
      }
      default "8";
      description "Default value: 8.";
    }
    leaf msg2PdschRepCe1Br {
      type int32 {
        range "4 | 8 | 16";
      }
      default "16";
      units "subframe";
      description "Default value: 16.";
    }
    leaf msg4PdschRepCe1Br {
      type int32 {
        range "4 | 8 | 16";
      }
      default "16";
      units "subframe";
      description "Default value: 16.";
    }
    leaf dlInternalChannelFreqBias {
      type enumeration {
        enum FBT_LOWER;
        enum FBT_UPPER;
      }
    }
    leaf ulInternalChannelFreqBias {
      type enumeration {
        enum FBT_LOWER;
        enum FBT_UPPER;
      }
    }
    leaf interFreqHoHigherPrioSnRel {
      type boolean;
      default "false";
      description "Default value: false.";
    }
    leaf interFreqHoHigherPrioRre {
      type boolean;
      default "true";
      description "Default value: true.";
    }
    leaf-list nrMobilityTriggerQciRef {
      type string;
      ordered-by user;
    }
    leaf lbUlHeavyUeDetectEnabled {
      type boolean;
      default "false";
      description "Default value: false.";
    }
    leaf pwrBoostRaMsg2Pdcch {
      type int32 {
        range "0 | 15 | 20 | 25 | 30";
      }
      default "0";
      units "dB";
      description "Default value: 0.";
    }
    leaf pwrBoostRaMsg2Pdsch {
      type int32 {
        range "0 | 15 | 20 | 25 | 30";
      }
      default "0";
      units "dB";
      description "Default value: 0.";
    }
    leaf pwrBoostRaMsg2TaThr {
      type int32 {
        range "0..2560 | 65535";
      }
      default "65535";
      description "Default value: 65535.";
    }
    leaf interFreqHoHigherPrioEndc {
      type boolean;
      default "true";
      description "Default value: true.";
    }
    list siPeriodicityCe {
      key "id";
      leaf id {
        type uint32;
        description "Synthetic key for struct entry.";
      }
      container attributes {
      leaf siPeriodicitySI1 {
        type ietfinet:ip-address;
        units "radio frame";
        description "Default value: 64.";
      }
      leaf siPeriodicitySI10 {
        type ietfinet:ip-address;
        units "radio frame";
        description "Default value: 64.";
      }
      leaf siPeriodicitySI2 {
        type ietfinet:ip-address;
        units "radio frame";
        description "Default value: 64.";
      }
      leaf siPeriodicitySI3 {
        type ietfinet:ip-address;
        units "radio frame";
        description "Default value: 64.";
      }
      leaf siPeriodicitySI4 {
        type ietfinet:ip-address;
        units "radio frame";
        description "Default value: 64.";
      }
      leaf siPeriodicitySI5 {
        type ietfinet:ip-address;
        units "radio frame";
        description "Default value: 64.";
      }
      leaf siPeriodicitySI6 {
        type ietfinet:ip-address;
        units "radio frame";
        description "Default value: 64.";
      }
      leaf siPeriodicitySI7 {
        type ietfinet:ip-address;
        units "radio frame";
        description "Default value: 64.";
      }
      leaf siPeriodicitySI8 {
        type ietfinet:ip-address;
        units "radio frame";
        description "Default value: 64.";
      }
      leaf siPeriodicitySI9 {
        type ietfinet:ip-address;
        units "radio frame";
        description "Default value: 64.";
      }
      }
    }
    leaf ulCaPrioThreshold {
      type eytypes:int32_range_0-65535-10;
      default "200";
      description "range 0..65535; Default value: 200.";
    }
    leaf lessWindow1StartTime {
      type string {
        length "5";
      }
      default "00:00";
      description "length 5..5; Default value: 00:00.";
    }
    leaf lessWindow1EndTime {
      type string {
        length "5";
      }
      default "00:00";
      description "length 5..5; Default value: 00:00.";
    }
    leaf lessWindow2StartTime {
      type string {
        length "5";
      }
      default "00:00";
      description "length 5..5; Default value: 00:00.";
    }
    leaf lessWindow2EndTime {
      type string {
        length "5";
      }
      default "00:00";
      description "length 5..5; Default value: 00:00.";
    }
    leaf lessWindow1StartTimeApplied {
      type string {
        length "5";
      }
      config false;
      description "length 5..5.";
    }
    leaf lessWindow1EndTimeApplied {
      type string {
        length "5";
      }
      config false;
      description "length 5..5.";
    }
    leaf lessWindow2StartTimeApplied {
      type string {
        length "5";
      }
      config false;
      description "length 5..5.";
    }
    leaf lessWindow2EndTimeApplied {
      type string {
        length "5";
      }
      config false;
      description "length 5..5.";
    }
    leaf lessPrbUsageThresholdWindow2 {
      type eytypes:int32_range_0-100;
      default "90";
      units "percent";
      description "range 0..100; Default value: 90.";
    }
    leaf catmRarLoadControlEnabled {
      type boolean;
      default "false";
      description "Default value: false.";
    }
    leaf interFreqHoHigherPrioMeas {
      type boolean;
      default "false";
      description "Default value: false.";
    }
    leaf spidUeEnhLoadMgmtThr {
      type eytypes:int32_range_0-16000;
      default "0";
      description "range 0..16000; Default value: 0.";
    }
    leaf bitRateUpRecommTimer {
      type eytypes:int32_range_2-30;
      default "5";
      units "s";
      description "range 2..30; Default value: 5.";
    }
    leaf bitRateDownRecommTimer {
      type eytypes:int32_range_2-30;
      default "3";
      units "s";
      description "range 2..30; Default value: 3.";
    }
    leaf enhVolteRateRecommEnabled {
      type boolean;
      default "false";
      description "Default value: false.";
    }
    leaf pimManualMutingStartPoint {
      type enumeration {
        enum DOWNMOST;
        enum UPMOST;
      }
    }
    leaf decouplePdcchDtxThres {
      type eytypes:int32_range_0-100;
      default "5";
      units "percent";
      description "range 0..100; Default value: 5.";
    }
    leaf pdcchDlOlaDtxOffset {
      type eytypes:int32_range_0-100;
      default "5";
      units "percent";
      description "range 0..100; Default value: 5.";
    }
    leaf pimRunningAggressorCellId {
      type eytypes:int32_range_0-16383;
      config false;
      description "range 0..16383.";
    }
    leaf pimRunningAggressorENBId {
      type eytypes:int32_range_0-1048575;
      config false;
      description "range 0..1048575.";
    }
    leaf pimRunningVictimCellId {
      type eytypes:int32_range_0-255;
      config false;
      description "range 0..255.";
    }
    leaf pimRunningVictimENBId {
      type eytypes:int32_range_0-1048575;
      config false;
      description "range 0..1048575.";
    }
    leaf pimRunningAggressorGNBId {
      type eytypes:int64_range_0-4294967295;
      config false;
      description "range 0..4294967295.";
    }
    leaf pimAggressorGNodeBId {
      type eytypes:int64_range_0-4294967295;
      description "range 0..4294967295.";
    }
    leaf ulCaPowerScalingMode {
      type eytypes:int32_range_0-2;
      default "0";
      description "range 0..2; Default value: 0.";
    }
    leaf ulCaFallbackPolicy {
      type eytypes:int32_range_0-2;
      default "0";
      description "range 0..2; Default value: 0.";
    }
    leaf pZeroNominalPucchBr {
      type eytypes:int32_range_-127--96;
      default "-117";
      units "dBm";
      description "range -127..-96; Default value: -117.";
    }
    leaf pZeroNominalPuschBr {
      type eytypes:int32_range_-126-24;
      default "-103";
      units "dBm";
      description "range -126..24; Default value: -103.";
    }
    leaf servSpecficUlSchedForFcb {
      type boolean;
      default "false";
      description "Default value: false.";
    }
    leaf nomPdschRsEpreOffset {
      type eytypes:int32_range_-1-6;
      default "0";
      description "range -1..6; Default value: 0.";
    }
    leaf oneCwSelectionForVolteEnabled {
      type boolean;
      default "false";
      description "Default value: false.";
    }
    leaf dlConfigurableFrequencyEnabledBr {
      type boolean;
      default "false";
      description "Default value: false.";
    }
    leaf interFreqHoHigherPrioSpid {
      type boolean;
      default "true";
      description "Default value: true.";
    }
    leaf zzzTemporary103 {
      type int32;
      default "-2000000000";
      description "Default value: -2000000000.";
    }
    leaf ulHighInterferenceThr {
      type int32 {
        range "-120..-60";
      }
      default "-120";
      units "dBm";
      description "range -120..-60; Default value: -120.";
    }
    leaf pimDetectionReportedTime {
      type ietfinet:port-number;
      config false;
      description "length 0..19.";
    }
    list pimDetectionResultList {
      config false;
      container attributes {
      leaf aggressor1NodeType {
        type enumeration {
          enum LOCAL_NODE;
          enum EXTERNAL_ENODEB;
          enum EXTERNAL_GNODEB;
        }
      }
      leaf aggressor1NodeId {
        type eytypes:int64_range_0-4294967295;
        description "range 0..4294967295.";
      }
      leaf aggressor1CellId {
        type eytypes:int32_range_0-16383;
        description "range 0..16383.";
      }
      leaf aggressor2NodeType {
        type enumeration {
          enum LOCAL_NODE;
          enum EXTERNAL_ENODEB;
          enum EXTERNAL_GNODEB;
        }
      }
      leaf aggressor2NodeId {
        type eytypes:int64_range_0-4294967295;
        description "range 0..4294967295.";
      }
      leaf aggressor2CellId {
        type eytypes:int32_range_0-16383;
        description "range 0..16383.";
      }
      leaf imOrderLevel {
        type int32 {
          range "2..5";
        }
        description "range 2..5.";
      }
      leaf pimOverlapRatio {
        type eytypes:int32_range_1-100-4;
        description "range 1..100.";
      }
      leaf pimType {
        type enumeration {
          enum CLEAR;
          enum LIKELY;
        }
      }
      }
    }
    leaf cellMaxNoOfPagingRecords {
      type eytypes:int32_range_0-16;
      default "0";
      description "range 0..16; Default value: 0.";
    }
    leaf pdcchCceLevelUp1Thres {
      type int32 {
        range "1..5 | 255";
      }
      default "255";
      description "Default value: 255.";
    }
    leaf pdcchCceLevelUp2Thres {
      type int32 {
        range "6..10 | 255";
      }
      default "255";
      description "Default value: 255.";
    }
    leaf pdcchCceLevelUp3Thres {
      type int32 {
        range "11..15 | 255";
      }
      default "255";
      description "Default value: 255.";
    }
    leaf pdcchCceLevelDownHyst {
      type eytypes:int32_range_0-3;
      default "0";
      description "range 0..3; Default value: 0.";
    }
    list outerLoopAdjustmentBr {
      key "id";
      leaf id {
        type uint32;
        description "Synthetic key for struct entry.";
      }
      container attributes {
      leaf puschGainInit {
        type eytypes:int32_range_-200-200;
        default "-40";
        units "dB";
        description "range -200..200; Default value: -40.";
      }
      leaf puschStepSize {
        type eytypes:int32_range_0-30;
        default "3";
        units "dB";
        description "range 0..30; Default value: 3.";
      }
      leaf pdschGainInit {
        type eytypes:int32_range_-200-200;
        default "0";
        units "dB";
        description "range -200..200; Default value: 0.";
      }
      leaf pdschStepSizeCqi {
        type eytypes:int32_range_0-100-6;
        default "4";
        units "dB";
        description "range 0..100; Default value: 4.";
      }
      leaf pdschStepSizeNoCqi {
        type eytypes:int32_range_0-100-6;
        default "8";
        units "dB";
        description "range 0..100; Default value: 8.";
      }
      }
    }
    leaf preambleDetectionThrOffset {
      type eytypes:int32_range_0-10;
      default "0";
      description "range 0..10; Default value: 0.";
    }
    leaf ulMpdcchOlaEnabled {
      type boolean;
      default "false";
      description "Default value: false.";
    }
    leaf msg4RetxPdschMaxRepCe0Br {
      type int32 {
        range "1..4";
      }
      default "1";
      description "range 1..4; Default value: 1.";
    }
    leaf ueAllocGranularityPerNbBr {
      type int32 {
        range "1..128";
      }
      default "10";
      description "range 1..128; Default value: 10.";
    }
    leaf mpdcchRmaxInvalidSfCe0 {
      type eytypes:int32_range_1-2;
      default "1";
      description "range 1..2; Default value: 1.";
    }
    leaf allowMpdcchInOverlapSsCe0 {
      type boolean;
      default "false";
      description "Default value: false.";
    }
    leaf-list pmErabEstabAttRejAdmMsrAddedRpid {
      type uint32;
    }
    leaf-list pmCaConfDlFddSumDistr {
      type uint32;
    }
    leaf pmRadioThpVolTxDlSCellIcm {
      type uint32;
      config false;
    }
    leaf pmUeCtxtRelMmeAct {
      type uint32;
      config false;
    }
    leaf pmA3InterFBestCellEvalReportRsrp {
      type ietfinet:port-number;
      config false;
    }
    leaf pmMacSkipUlDtxPreschedVolte {
      type ietfinet:ip-address;
      config false;
      status deprecated;
      description "MOM flags: noNotification.";
    }
    leaf pmPdcpVolDlDrbTransPlmn3 {
      type uint32;
      config false;
    }
    leaf pmRrcConnLevSum {
      type uint32;
      config false;
    }
    leaf-list pmErabRelAbnormalMmeActArp {
      type uint32;
    }
    leaf pmRohcEstabFailUeCap {
      type uint32;
      config false;
    }
    leaf-list pmErabRelAbnormalEnbPeQci {
      type uint32;
    }
    leaf pmActiveUeDlCe1Max {
      type ietfyang:mac-address;
      config false;
    }
    leaf-list pmPrbUtilUlMaxEstDistr {
      type uint32;
    }
    leaf pmCellHoExeSuccLteIntraFCsg {
      type uint32;
      config false;
    }
    leaf pmFlexCellHoPrepAttLteIntraF {
      type uint32;
      config false;
    }
    leaf pmElcPdcchBlankedTti {
      type uint32;
      config false;
    }
    leaf pmUeCtxtRelAbnormalEnbCdtAuto {
      type uint32;
      config false;
    }
    leaf pmUeCtxtFetchAttNoNeighRel {
      type uint32;
      config false;
    }
    leaf pmRadioThpVolDl2ccPCell {
      type uint32;
      config false;
    }
    leaf pmRadioUeRepCqiSubband12Sum {
      type uint32;
      config false;
    }
    leaf pmMacUeThpTimeUl {
      type ietfyang:mac-address;
      config false;
    }
    leaf pmRadioRecInterferencePwrPrb62 {
      type uint32;
      config false;
    }
    leaf pmUeCtxtRelNaccCsfbGsm {
      type uint32;
      config false;
    }
    leaf-list pmPrbUtilDlDistr {
      type uint32;
    }
    leaf pmRrcConnEstabFailDynUeAdmCtrl {
      type uint32;
      config false;
    }
    leaf-list pmPrbUtilDlCellResource4Distr {
      type uint32;
      description "MOM flags: noNotification.";
    }
    leaf pmAnrCandNrelX2Add {
      type uint32;
      config false;
    }
    leaf pmCaCapableDlSamp {
      type uint32;
      config false;
    }
    leaf pmPrbAvailUlPuschHighRegion {
      type uint32;
      config false;
    }
    leaf pmActiveUeDlCe2Max {
      type ietfyang:mac-address;
      config false;
    }
    leaf pmZtemporary9 {
      type uint32;
      config false;
    }
    leaf pmDlAssigsTransNonMcPtt {
      type uint32;
      config false;
    }
    leaf pmUeCtxtRelCsfbHoPrepFail1xRtt {
      type uint32;
      config false;
    }
    leaf pmPdcpPktTransDl {
      type uint32;
      config false;
    }
    leaf pmMacPdschEmptySubframeForced {
      type ietfyang:mac-address;
      config false;
    }
    leaf pmPucchSrResShortUtilCell {
      type int32;
      config false;
    }
    leaf pmPrbUsedUlMax {
      type int32;
      config false;
    }
    leaf-list pmPucchSrBr {
      type uint32;
    }
    leaf pmHoPrepRejInMpOverload {
      type uint32;
      config false;
    }
    leaf pmPdcpLatPktTransDl {
      type uint32;
      config false;
    }
    leaf-list pmBadCovMeasTimeActDistr {
      type uint32;
    }
    leaf pmDlAssigsWithDetectedHarqAck {
      type uint32;
      config false;
    }
    leaf-list pmRaFailCbraMsg2DiscBr {
      type uint32;
    }
    leaf-list pmActiveUeUlSumLcg {
      type ietfyang:mac-address;
    }
    leaf pmZtemporary239 {
      type uint32;
      config false;
    }
    leaf-list pmPdschRadioUeOutLoopAdjCe0Distr {
      type uint32;
    }
    leaf-list pmRrcFastReturnBufInactTimeDistr {
      type uint32;
    }
    leaf pmRrcScgFailureArfcnNil {
      type uint32;
      config false;
    }
    leaf pmRrcConnReestFailLicMtReest {
      type uint32;
      config false;
    }
    leaf pmHoPrepRejInUlThres {
      type uint32;
      config false;
      status deprecated;
      description "MOM flags: noNotification.";
    }
    leaf-list pmRrcConnReestAttCe {
      type uint32;
    }
    leaf-list pmAasHorizontalDistr {
      type uint32;
    }
    leaf-list pmCaActivatedDl6ccSumDistr {
      type uint32;
    }
    leaf pmRadioRecInterferencePwrPrb63 {
      type uint32;
      config false;
    }
    leaf pmUlGrantsWithDetectedPusch {
      type uint32;
      config false;
    }
    leaf-list pmErabRelAbnormalEnbActUeLostQci {
      type uint32;
    }
    leaf pmRadioRecInterferencePwrPrb72 {
      type uint32;
      config false;
    }
    leaf pmRadioRecInterferencePwrPrb34 {
      type uint32;
      config false;
    }
    leaf pmCellHoExeAttLteInterFCsg {
      type uint32;
      config false;
    }
    leaf pmFlexMacHarqUl4 {
      type ietfyang:mac-address;
      config false;
    }
    leaf pmFlexLcgThpTimeUl {
      type uint32;
      config false;
    }
    leaf pmErabEstabFailInitLic {
      type uint32;
      config false;
    }
    leaf pmCellHoPrepAttLteInterFDtvm {
      type uint32;
      config false;
    }
    leaf pmFlexErabModFailOngoingProc {
      type uint32;
      config false;
    }
    leaf-list pmRadioUeRepCqiDistr4 {
      type uint32;
    }
    leaf pmFlexLcgThpVolUl {
      type uint32;
      config false;
    }
    leaf pmFlexCellHoPrepSuccLteInterF {
      type uint32;
      config false;
    }
    leaf-list pmRadioHomUeRepCqi2Distr {
      type uint32;
    }
    leaf pmFlexMacHarqDlNack16qam {
      type ietfyang:mac-address;
      config false;
    }
    leaf pmRadioRecInterferencePwrPrb23 {
      type uint32;
      config false;
    }
    leaf pmPdcpPktPdbUlOkNonMcPtt {
      type uint32;
      config false;
    }
    leaf-list pmMaxDeltaSinrDlComp {
      type uint32;
    }
    leaf-list pmCaConfDlSCellTddLaaSumDistr {
      type uint32;
    }
    leaf pmRrcConnNs05RepeaterZoneSamp {
      type uint32;
      config false;
    }
    leaf-list pmMacUeThpUlDistr {
      type ietfyang:mac-address;
    }
    leaf pmUeCtxtFetchSuccReconfRrcConnReest {
      type uint32;
      config false;
    }
    leaf pmFlexCellHoExeSuccGeran {
      type uint32;
      config false;
    }
    leaf pmActiveDrbUlSum {
      type ietfyang:mac-address;
      config false;
    }
    leaf pmCellHoExeAttLteInterFUtvm {
      type uint32;
      config false;
    }
    leaf pmFlexZtemporary13 {
      type uint32;
      config false;
    }
    leaf-list pmPagReceivedCe {
      type uint32;
      description "MOM flags: noNotification.";
    }
    leaf pmMacPdcchBlockingPdschTti {
      type ietfyang:mac-address;
      config false;
    }
    leaf pmUeExclThpDlSmallVol {
      type uint32;
      config false;
      status deprecated;
      description "MOM flags: noNotification.";
    }
    leaf pmRrcConnResumeFailDuIntens {
      type uint32;
      config false;
    }
    leaf pmErabRelAbnormalEnbActTnFail {
      type uint32;
      config false;
    }
    leaf pmUeCtxtRelSCNrB2Rsrq {
      type uint32;
      config false;
    }
    leaf pmHoPrepRejInLicRlcUm {
      type uint32;
      config false;
    }
    leaf pmZtemporary62 {
      type uint32;
      config false;
    }
    leaf pmRadioThpVolUl {
      type uint32;
      config false;
    }
    leaf pmUeCtxtRelAbnormalEnbAct {
      type uint32;
      config false;
    }
    leaf pmUeCtxtRelSCNr {
      type uint32;
      config false;
    }
    leaf pmErabRelAbnormalEnbActUeLostOosPft {
      type uint32;
      config false;
    }
    leaf pmRadioRecInterferencePwrPrb54 {
      type uint32;
      config false;
    }
    leaf pmZtemporary227 {
      type int32;
      config false;
    }
    leaf pmUeCtxtRelSCEUtraBestCellRsrq {
      type uint32;
      config false;
    }
    leaf pmErabEstabAttAddedCsfb {
      type uint32;
      config false;
    }
    leaf pmFlexUeCtxtRelMme {
      type uint32;
      config false;
    }
    leaf-list pmPdcpVolUlCmpHdrQci {
      type uint32;
    }
    leaf-list pmUeCtxtRelSCEUtraBestCellRsrpCe {
      type uint32;
    }
    leaf-list pmRlcDelayTimeDlQci {
      type uint32;
      description "MOM flags: noNotification.";
    }
    leaf pmFlexErabEstabSuccInit {
      type uint32;
      config false;
    }
    leaf pmFlexCellHoPrepAttNonMobIrat {
      type uint32;
      config false;
    }
    leaf-list pmErabEstabFailAddedErabIdInUseArp {
      type uint32;
    }
    leaf-list pmRrcConnSubsGroupSumDistr {
      type uint32;
    }
    leaf pmRrcConnReconfNoDrxMoVoice {
      type uint32;
      config false;
    }
    leaf pmUeCtxtFetchSuccIntraEnbHoPrep {
      type uint32;
      config false;
    }
    leaf pmPdcpVolDlDrbTransPlmn2 {
      type uint32;
      config false;
    }
    leaf pmUeCtxtFetchAttReconfErabRel {
      type uint32;
      config false;
    }
    leaf pmMacHarqUlSucc64Qam {
      type ietfyang:mac-address;
      config false;
    }
    leaf-list pmPdcchSym3PwrUtil {
      type uint32;
    }
    leaf pmPagEdrxDiscarded {
      type uint32;
      config false;
    }
    leaf pmZtemporary245 {
      type uint32;
      config false;
    }
    leaf pmUeCtxtRelAbnormalEnbUeLostOosPft {
      type uint32;
      config false;
    }
    leaf pmA1InterFHoHigherPrioConfig {
      type uint32;
      config false;
    }
    leaf pmPucchSr {
      type uint32;
      config false;
    }
    leaf-list pmHoPrepRejIntraCellDistr {
      type uint32;
    }
    leaf pmUeCtxtRetrReestAttEndcUe {
      type uint32;
      config false;
    }
    leaf pmZtemporary86 {
      type uint32;
      config false;
    }
    leaf-list pmMacTimeDlNoDrxSyncSampQci {
      type ietfyang:mac-address;
      description "MOM flags: noNotification.";
    }
    leaf-list pmCellIntensRrcConnResumeReqDistr {
      type uint32;
    }
    leaf pmFlexMacLatTimeDl {
      type ietfyang:mac-address;
      config false;
      status deprecated;
      description "MOM flags: noNotification.";
    }
    leaf pmUeCtxtFetchAttX2HoPrep {
      type uint32;
      config false;
    }
    leaf-list pmS1SigConnEstabAttDtaCe {
      type uint32;
    }
    leaf pmRrcConnLevSumUlOosCe1Br {
      type uint32;
      config false;
    }
    leaf pmUeCtxtRelCsfbLimitedDualRadioUeCdma {
      type uint32;
      config false;
    }
    leaf-list pmRadioHomUeRepCqi3Distr {
      type uint32;
    }
    leaf pmPrbUsedUlPuschCenterRegionSrb {
      type uint32;
      config false;
    }
    leaf pmRrcConnBrNoPdn {
      type uint32;
      config false;
    }
    leaf pmActiveUeDownlinkMax {
      type ietfyang:mac-address;
      config false;
    }
    leaf-list pmS1SigConnEstabAttCe {
      type uint32;
    }
    leaf pmUeCtxtRelAbnormalEnbActOos {
      type uint32;
      config false;
    }
    leaf-list pmRrcConnEstabAttReattDtaCe {
      type uint32;
    }
    leaf pmFlexSchedActivityUeUl {
      type uint32;
      config false;
    }
    leaf-list pmUeCtxtSuspendEnbRaiCe {
      type uint32;
    }
    leaf pmRadioUeRepCqi2Subband6Sum {
      type uint32;
      config false;
    }
    leaf-list pmRrcConnResumeFailCellIntensDLCCe {
      type uint32;
    }
    leaf pmErabRelAbnormalEnbCritCov {
      type uint32;
      config false;
    }
    leaf pmUeCtxtRetrReestSucc {
      type uint32;
      config false;
    }
    leaf pmCellDowntimeMan {
      type uint32;
      config false;
    }
    leaf pmUeCtxtFetchAttReconfUeCtxtEstabReconfFail {
      type uint32;
      config false;
    }
    leaf pmAnrHoSuccLevelLow {
      type uint32;
      config false;
    }
    leaf-list pmRrcConnEstabSuccModCe {
      type uint32;
    }
    leaf pmPdcpVolUlDrbPlmn1 {
      type uint32;
      config false;
    }
    leaf pmRadioRecInterferencePwrPrb28 {
      type uint32;
      config false;
    }
    leaf pmSchedActivityUeUlShortSps {
      type uint32;
      config false;
    }
    leaf pmRadioUeRepCqi2Subband11Sum {
      type uint32;
      config false;
    }
    leaf-list pmErabRelUlInactGapQci {
      type uint32;
    }
    leaf pmZtemporary125 {
      type uint32;
      config false;
    }
    leaf-list pmPdcchSym0PwrUtil {
      type uint32;
    }
    leaf-list pmRadioHomUeRepCqi4Distr {
      type uint32;
    }
    leaf pmRadioThpVolTxDl2ccSCell {
      type uint32;
      config false;
    }
    leaf pmServiceTimeDrb {
      type uint32;
      config false;
    }
    leaf-list pmRaMsg3DtxCbraTxDistr {
      type uint32;
    }
    leaf pmAnrNeighbrelRem {
      type uint32;
      config false;
    }
    leaf pmErabRelAbnormalEnbActOos {
      type uint32;
      config false;
    }
    leaf pmCellCatmEssShareUlMax {
      type int32;
      config false;
    }
    leaf-list pmZtemporary132Compr {
      type uint32;
    }
    leaf pmCellHoExeAttLteInterFEndcHo {
      type uint32;
      config false;
    }
    leaf pmUeCtxtRelMme {
      type uint32;
      config false;
    }
    leaf pmRadioUeRepCqi2Subband10Sum {
      type uint32;
      config false;
    }
    leaf pmRrcConnEstabFailBearerAdmissionRej {
      type uint32;
      config false;
    }
    leaf-list pmCaConfiguredUlSum {
      type uint32;
    }
    leaf-list pmPdcpLatTimeDlCatMDrxSyncQci {
      type uint32;
    }
    leaf pmRrcConnReestAttHo {
      type uint32;
      config false;
    }
    leaf pmPdcpVolDlDrbTransPlmn5 {
      type uint32;
      config false;
    }
    leaf pmPrbUsedDlAilgHighPrio {
      type uint32;
      config false;
    }
    leaf pmActiveUeDlCe3Max {
      type ietfyang:mac-address;
      config false;
    }
    leaf pmUeCtxtRelAbnormalEnbActPe {
      type uint32;
      config false;
    }
    leaf pmUeCtxtRelMmeHo {
      type uint32;
      config false;
    }
    leaf pmUeCtxtConnResumeAtt {
      type uint32;
      config false;
      status deprecated;
      description "MOM flags: noNotification.";
    }
    leaf-list pmRaMsg3NackCbraTxBrCe1Distr {
      type uint32;
    }
    leaf-list pmRaMsg3DtxCbraTxBrCe1Distr {
      type uint32;
    }
    leaf-list pmPdcchCceUsedUlQci {
      type uint32;
    }
    leaf pmCellHoExeSuccLteIntraF {
      type uint32;
      config false;
    }
    leaf pmUeExclThpUlRelativeLowVol {
      type uint32;
      config false;
    }
    leaf pmRadioRecInterferencePwrPrb18 {
      type uint32;
      config false;
    }
    leaf pmPrbUsedDlPcch {
      type uint32;
      config false;
    }
    leaf pmZtemporary14 {
      type uint32;
      config false;
    }
    leaf-list pmErabRelNormalEnbArp {
      type uint32;
    }
    leaf pmUeCtxtRelAbnormalEnbActUeLost {
      type uint32;
      config false;
    }
    leaf pmConfirmedUeRelReqPft {
      type uint32;
      config false;
    }
    leaf pmPagReceived {
      type uint32;
      config false;
    }
    leaf pmFlexCellHoPrepAttLteInterF {
      type uint32;
      config false;
    }
    leaf pmInSyncTimePft {
      type uint32;
      config false;
    }
    leaf pmFlexCellHoExeSuccUtranSrvcc {
      type uint32;
      config false;
    }
    leaf pmFlexErabRelNormalEnbGbr {
      type uint32;
      config false;
    }
    leaf pmErabRelAbnormalEnb {
      type uint32;
      config false;
    }
    leaf pmRrcConnEstabAttMod {
      type uint32;
      config false;
    }
    leaf pmRrcConnReestFailDynUeAdmCtrlPa {
      type uint32;
      config false;
    }
    leaf pmFlexMacHarqDlAck16qam {
      type ietfyang:mac-address;
      config false;
    }
    leaf-list pmPdcpPktLostUlRohcFail2Qci {
      type uint32;
    }
    leaf pmSchedTtiCellUlResFair {
      type uint32;
      config false;
      status deprecated;
      description "MOM flags: noNotification.";
    }
    leaf pmNumUlPotentialPktLossInd {
      type uint32;
      config false;
    }
    leaf pmRrcConnResumeFailDynUeAdmCtrl {
      type uint32;
      config false;
    }
    leaf pmFlexUeThpTimeDl {
      type uint32;
      config false;
    }
    leaf-list pmRlcDelayPktTransDlQci {
      type uint32;
    }
    leaf pmUeCtxtRelAbnormalEnbCritCov {
      type uint32;
      config false;
    }
    leaf pmPftEstablishedSession {
      type uint32;
      config false;
    }
    leaf pmRrcConnSuspend {
      type uint32;
      config false;
    }
    leaf pmUeCtxtRelAbnormalEnbLic {
      type uint32;
      config false;
    }
    leaf pmDlAssigsTransPCell {
      type uint32;
      config false;
    }
    leaf-list pmActiveUeDlSectorCarrierDistr {
      type ietfyang:mac-address;
    }
    leaf pmZtemporary63 {
      type uint32;
      config false;
    }
    leaf-list pmRrcConnEstabAttReattMtaCe {
      type uint32;
    }
    leaf pmEndcSetupScgUeAtt {
      type uint32;
      config false;
    }
    leaf pmHoPrepRejInUlThresCaRedirect {
      type uint32;
      config false;
      status deprecated;
      description "MOM flags: noNotification.";
    }
    leaf pmZtemporary124 {
      type uint32;
      config false;
    }
    leaf-list pmCellCcePttReservation {
      type uint32;
    }
    leaf pmMacUeThpVolUl {
      type ietfyang:mac-address;
      config false;
    }
    leaf pmRadioRecInterferencePwrPrb68 {
      type uint32;
      config false;
    }
    leaf pmErabRelAbnormalEnbSir {
      type uint32;
      config false;
    }
    leaf pmPuschSchedActivity {
      type uint32;
      config false;
    }
    leaf pmDsdReqPft {
      type uint32;
      config false;
    }
    leaf-list pmAccessClassBarringVideoPlmn1Distr {
      type ietfyang:mac-address;
    }
    leaf-list pmMacUeBitRateSelectUlDistr {
      type ietfyang:mac-address;
    }
    leaf pmCriticalBorderEvalReportAct {
      type ietfinet:port-number;
      config false;
    }
    leaf pmUeCtxtRelAbnormalEnbSirBb {
      type uint32;
      config false;
    }
    leaf pmRadioUeRepCqiSubband10Sum {
      type uint32;
      config false;
    }
    leaf-list pmAccessClassBarringVoiceDistr {
      type ietfyang:mac-address;
    }
    leaf pmMacSkipUlDtxTxSps {
      type ietfinet:ip-address;
      config false;
    }
    leaf pmFlexPrbUsedDlDtch {
      type uint32;
      config false;
    }
    leaf pmRohcUlDataDeconfigSucc {
      type uint32;
      config false;
    }
    leaf pmEndcSetupUeSucc {
      type uint32;
      config false;
    }
    leaf-list pmMacUeBitRateRecommDlDistr {
      type ietfyang:mac-address;
    }
    leaf-list pmPdcpLatTimeDlNoDrxNoSyncQci {
      type uint32;
    }
    leaf-list pmRaAttTaZone1Distr {
      type uint32;
    }
    leaf pmPdcpVolDlSrb {
      type uint32;
      config false;
    }
    leaf pmNasTransferFailPnrDlSrb2 {
      type uint32;
      config false;
    }
    leaf pmUeCtxtSuspendSucc {
      type uint32;
      config false;
    }
    leaf-list pmActiveUeUlSectorCarrierDistr {
      type ietfyang:mac-address;
    }
    leaf pmErabEstabSuccBrNoPdn {
      type uint32;
      config false;
    }
    leaf pmRadioUeRepCqiSubband9Sum {
      type uint32;
      config false;
    }
    leaf pmFlexSchedActivityCellUl {
      type uint32;
      config false;
    }
    leaf-list pmErabEstabAttInitArp {
      type uint32;
    }
    leaf pmHoPreventedNotInPlmnWL {
      type uint32;
      config false;
    }
    leaf-list pmRrcConnResumeFailMpMemCe {
      type uint32;
    }
    leaf pmZtemporary57 {
      type uint32;
      config false;
    }
    leaf pmUeCtxtFetchAttS1HoPrepSrvccUtran {
      type uint32;
      config false;
    }
    leaf pmErabRelAbnormalEnbUeLostOos {
      type uint32;
      config false;
    }
    leaf pmRaAccHarqFailAfterContRes {
      type uint32;
      config false;
    }
    leaf pmUeCtxtRelSCUtranB2Rsrq {
      type uint32;
      config false;
    }
    leaf-list pmPdcchDlDtxWorseDistr {
      type uint32;
    }
    leaf-list pmPrbUtilDlCellResource24Distr {
      type uint32;
      description "MOM flags: noNotification.";
    }
    leaf pmMeasConfigB1Endc {
      type uint32;
      config false;
    }
    leaf pmUeCtxtRelAbnormalMmeCritCov {
      type uint32;
      config false;
    }
    leaf pmCellHoExeSuccLteInterF {
      type uint32;
      config false;
    }
    leaf-list pmRaRrcRspDistr {
      type uint32;
    }
    leaf pmFlexUeCtxtRelSCEutra {
      type uint32;
      config false;
    }
    leaf pmFlexPdcpPktDiscDlStaleSdu {
      type uint32;
      config false;
    }
    leaf pmRadioRecInterferencePwrPrb94 {
      type uint32;
      config false;
    }
    leaf pmFlexEndcSetupScgUeAtt {
      type uint32;
      config false;
    }
    leaf-list pmRrcConnCeCellLevSum {
      type uint32;
    }
    leaf-list pmAcBarringMosSpecAcPlmn2Distr {
      type ietfyang:mac-address;
    }
    leaf pmDlAssigsWithUnknownRecNonMcPtt {
      type uint32;
      config false;
    }
    leaf-list pmUeThpDlMbbFilteredQciDistr {
      type uint32;
    }
    leaf-list pmZtemporary80 {
      type uint32;
    }
    leaf pmPtmHoBlocked {
      type uint32;
      config false;
    }
    leaf pmUeCtxtRelAbnormalEnbSir {
      type uint32;
      config false;
    }
    leaf pmRadioRecInterferencePwrPrb11 {
      type uint32;
      config false;
    }
    leaf pmDlAssigsWithDetectedHarqAckPCell {
      type uint32;
      config false;
    }
    leaf pmRadioRecInterferencePwrPrb70 {
      type uint32;
      config false;
    }
    leaf-list pmBitRateDownUlVoipTimeDistr {
      type ietfinet:ip-address;
    }
    leaf-list pmPdcpInactSecUlVolteDistr {
      type uint32;
    }
    leaf pmPdcpVolUlDrbPlmn2 {
      type uint32;
      config false;
    }
    leaf pmUeCtxtRelSCNrB1Rsrp {
      type uint32;
      config false;
    }
    leaf pmFlexPdcpPktReceivedDl {
      type uint32;
      config false;
    }
    leaf pmRaSuccSrInSync {
      type uint32;
      config false;
    }
    leaf pmHoPrepSuccInMfbiAdditional {
      type uint32;
      config false;
    }
    leaf pmRrcConnMaxEndcUnavail {
      type int32;
      config false;
    }
    leaf pmFlexRlcDelayTimeDl {
      type uint32;
      config false;
      status deprecated;
      description "MOM flags: noNotification.";
    }
    leaf pmSchedActivityUlTTI {
      type uint32;
      config false;
    }
    leaf pmRetransPostponedNs05FullBandSch {
      type uint32;
      config false;
    }
    leaf pmFlexUeCtxtEstabSucc {
      type uint32;
      config false;
    }
    leaf pmZtemporary126 {
      type uint32;
      config false;
    }
    leaf pmMacHarqUlSuccQpsk {
      type ietfyang:mac-address;
      config false;
    }
    leaf pmUeCtxtRelCsfbGsm {
      type uint32;
      config false;
    }
    leaf pmRrcConnQueueSuccMtaVoice {
      type uint32;
      config false;
    }
    leaf pmRadioUeRepCqiSubband7Sum {
      type uint32;
      config false;
    }
    leaf pmDrxTotalTime {
      type uint32;
      config false;
    }
    leaf pmUeCtxtRelCsfbUlHoPrepTxTO1xRtt {
      type uint32;
      config false;
    }
    leaf pmRrcConnReestSuccHo {
      type uint32;
      config false;
    }
    leaf pmUlGrantsTransPCell {
      type uint32;
      config false;
    }
    leaf pmRrcConnEstabFailDynUeAdmCtrlMoVoicePtt {
      type uint32;
      config false;
    }
    leaf pmFlexCellHoPrepSuccGeran {
      type uint32;
      config false;
    }
    leaf pmZtemporary19 {
      type uint32;
      config false;
    }
    leaf pmRadioRecInterferencePwrPrb65 {
      type uint32;
      config false;
    }
    leaf pmZtemporary92 {
      type uint32;
      config false;
    }
    leaf-list pmPuschMcsSubsGroup2Distr {
      type uint32;
    }
    leaf pmFlexMacHarqUl5 {
      type ietfyang:mac-address;
      config false;
    }
    leaf pmIdleModeRelDistrMediumHighLoad {
      type uint32;
      config false;
    }
    leaf pmCellHoExeSuccLteIntraFHybridCsg {
      type uint32;
      config false;
    }
    leaf pmRadioUeRepCqi2Subband9Sum {
      type uint32;
      config false;
    }
    leaf-list pmRadioDynBlerTargetDlDistr {
      type uint32;
    }
    leaf pmRrcConnBrCellLevSamp {
      type uint32;
      config false;
    }
    leaf pmRrcConnMaxEndc1 {
      type int32;
      config false;
    }
    leaf pmRadioRecInterferencePwrPrb82 {
      type uint32;
      config false;
    }
    leaf pmFlexMacHarqDlAck256qam {
      type ietfyang:mac-address;
      config false;
    }
    leaf pmS1SigConnEstabAttMta {
      type uint32;
      config false;
    }
    leaf pmPdcpVolUlDrbPlmn6 {
      type uint32;
      config false;
    }
    leaf pmWifiAccessEval {
      type uint32;
      config false;
    }
    leaf-list pmAccessClassBarringModPlmn3Distr {
      type ietfyang:mac-address;
    }
    leaf pmRrcConnQueueOverflow {
      type uint32;
      config false;
    }
    leaf pmPrbUsedUlPuschCenterRegionDtch {
      type uint32;
      config false;
    }
    leaf pmUeCtxtFetchAttS1HoExe {
      type uint32;
      config false;
    }
    leaf-list pmPuschMcsVoipDistr {
      type ietfinet:ip-address;
    }
    leaf pmFlexErabRelAbnormalEnbActGbr {
      type uint32;
      config false;
    }
    leaf-list pmUeCtxtResumeAttCe {
      type uint32;
    }
    leaf pmUlGrantsDetPuschNonMcPttNDO {
      type uint32;
      config false;
    }
    leaf pmPrbUsedDlMpdcchPdschBr {
      type uint32;
      config false;
    }
    leaf pmPdcchCceUsedUlPresched {
      type uint32;
      config false;
    }
    leaf pmDrxCommandPft {
      type uint32;
      config false;
    }
    leaf-list pmRrcConnResumeFailCellIntensStatCe {
      type uint32;
    }
    leaf pmFlexPdcpPktTransDl {
      type uint32;
      config false;
    }
    leaf pmWifiAccessEvalFailLic {
      type uint32;
      config false;
    }
    leaf-list pmCellDlPrbPttReservation {
      type uint32;
    }
    leaf pmUeCapabilityAsrMismatch {
      type uint32;
      config false;
    }
    leaf pmRadioRecInterferencePwrPrb84 {
      type uint32;
      config false;
    }
    leaf pmZtemporary137 {
      type uint32;
      config false;
    }
    leaf-list pmErabQciLevSum {
      type uint32;
    }
    leaf pmMacSkipUlDtxPresched {
      type ietfinet:ip-address;
      config false;
    }
    leaf-list pmCaActivatedDlIcmSum {
      type uint32;
      description "MOM flags: noNotification.";
    }
    leaf pmUeCapabilityGUtran {
      type uint32;
      config false;
    }
    leaf-list pmEranCompUlDeltaSinrPuschDistr {
      type uint32;
      description "MOM flags: noNotification.";
    }
    leaf pmUlTrafficA5MeasRepUe {
      type uint32;
      config false;
    }
    leaf pmLbSubRatioSum {
      type uint32;
      config false;
    }
    leaf pmZtemporary146 {
      type uint32;
      config false;
    }
    leaf pmDlAssigsWithUnknownReceptionPCell {
      type uint32;
      config false;
    }
    leaf pmRadioRecInterferencePwrPrb33 {
      type uint32;
      config false;
    }
    leaf pmEndcSetupUeAtt {
      type uint32;
      config false;
    }
    leaf pmPdcpVolDlDrbCa {
      type uint32;
      config false;
    }
    leaf pmPdcpPktDiscDlHo {
      type uint32;
      config false;
    }
    leaf pmUeCapabilityUlDelay {
      type uint32;
      config false;
    }
    leaf pmErabModQci5EmInactTimer {
      type uint32;
      config false;
    }
    leaf pmMeasConfigB1GUtran {
      type uint32;
      config false;
      status deprecated;
      description "MOM flags: noNotification.";
    }
    leaf pmDlAssigsWithUnknownRecMcPtt {
      type uint32;
      config false;
    }
    leaf-list pmTaInitBrDistr {
      type uint32;
    }
    leaf pmFlexZtemporary23 {
      type uint32;
      config false;
    }
    leaf-list pmLaaActivatedIcmSumDistr {
      type uint32;
    }
    leaf pmEndcSetupBufMonReport {
      type ietfinet:port-number;
      config false;
    }
    leaf pmFlexCellHoPrepAttNonMobLte {
      type uint32;
      config false;
    }
    leaf pmCellSubscriptionRatioHigh {
      type ietfinet:ip-address;
      config false;
    }
    leaf pmErabEstabAttAddedCsfbPl {
      type uint32;
      config false;
    }
    leaf-list pmAcBarringVideoSpecAcPlmn1Distr {
      type ietfyang:mac-address;
    }
    leaf pmPwsRestartIndicationSent {
      type uint32;
      config false;
    }
    leaf pmPdschBlankedSubframe {
      type uint32;
      config false;
    }
    leaf pmSchedActivityCellUl {
      type uint32;
      config false;
    }
    leaf pmUlGrantsWithDetectedPuschPCell {
      type uint32;
      config false;
    }
    leaf-list pmCaAssignedPf3ResDistr {
      type uint32;
    }
    leaf pmMcPttQualityRbUlNok {
      type uint32;
      config false;
    }
    leaf pmRadioRecInterferencePwrPrb50 {
      type uint32;
      config false;
    }
    leaf pmPdcpRtpSnReorderDetected {
      type uint32;
      config false;
    }
    leaf pmZtemporary11 {
      type uint32;
      config false;
    }
    leaf pmPucchFailSr {
      type uint32;
      config false;
    }
    leaf pmFlexCellHoExeAttUtran {
      type uint32;
      config false;
    }
    leaf pmUeCtxtModAttCsfb {
      type uint32;
      config false;
    }
    leaf pmFlexMacHarqUl3 {
      type ietfyang:mac-address;
      config false;
    }
    leaf pmActiveUeUlCe2Max {
      type ietfyang:mac-address;
      config false;
    }
    leaf pmRrcConnEstabSuccMos {
      type uint32;
      config false;
    }
    leaf pmRrcConnReconfAttNoMobDacc {
      type uint32;
      config false;
    }
    leaf pmCellHoExeSuccLteInterFDtvm {
      type uint32;
      config false;
    }
    leaf pmUeCtxtFetchAttS1HoExeSrvccUtran {
      type uint32;
      config false;
    }
    leaf pmPrioFreqBandConfigured {
      type uint32;
      config false;
    }
    leaf pmS1SigConnEstabSuccMoVoice {
      type uint32;
      config false;
    }
    leaf-list pmErabEstabAttAddedGbrArp {
      type uint32;
    }
    leaf pmFlexRlcArqDlNack {
      type uint32;
      config false;
    }
    leaf pmUeCtxtRelAbnormalEnbActCdtAutoPnr {
      type uint32;
      config false;
    }
    leaf-list pmPdcpPktLostUlSrbTooLarge {
      type uint32;
    }
    leaf-list pmCaScheduledDlIcmSumDistr {
      type uint32;
    }
    leaf pmErabBrMax {
      type int32;
      config false;
    }
    leaf pmMcPttQualityRbUlLowSampl {
      type uint32;
      config false;
    }
    leaf-list pmErabRelAbnormalMmeGbrArp {
      type uint32;
    }
    leaf-list pmPrbUtilDlCellResource14Distr {
      type uint32;
      description "MOM flags: noNotification.";
    }
    leaf pmRadioRecInterferencePwrPrb81 {
      type uint32;
      config false;
    }
    leaf pmZtemporary28 {
      type uint32;
      config false;
    }
    leaf-list pmErabRelAbnormalEnbTnFailQci {
      type uint32;
    }
    leaf pmFlexMacTimeDlSamp {
      type ietfyang:mac-address;
      config false;
      status deprecated;
      description "MOM flags: noNotification.";
    }
    leaf pmCellHoPrepAttLteInterFMbms {
      type uint32;
      config false;
    }
    leaf-list pmPuschMcsSubsGroup6Distr {
      type uint32;
    }
    leaf-list pmRrcConnReestFailDynUeAdmCtrlCe {
      type uint32;
    }
    leaf pmRaSuccSrOosCe0Br {
      type uint32;
      config false;
    }
    leaf pmErabRelAbnormalEnbSirBb {
      type uint32;
      config false;
    }
    leaf-list pmMacUeBitRateSelectDlMcPttDistr {
      type ietfyang:mac-address;
    }
    leaf pmDlAssigsWithDetectedHarqAckVolte {
      type uint32;
      config false;
    }
    leaf pmCaConfiguredNoMeasAtt {
      type uint32;
      config false;
    }
    leaf pmPdcchResyncSuccCe1Br {
      type uint32;
      config false;
    }
    leaf-list pmPdschRadioUeOutLoopAdjCe1Distr {
      type uint32;
    }
    leaf-list pmS1SigConnEstabSuccDtaCe {
      type uint32;
    }
    leaf pmUlGrantsShortSps {
      type uint32;
      config false;
    }
    leaf pmUeCapabilityLoggedMdt {
      type uint32;
      config false;
    }
    leaf pmRadioRecInterferencePwrPrb85 {
      type uint32;
      config false;
    }
    leaf-list pmPdcpInactSecUlNonMcPttDistr {
      type uint32;
    }
    leaf-list pmPrbUtilUlNonRetransDistr {
      type uint32;
    }
    leaf-list pmMacDrbThpVolDlQci {
      type ietfyang:mac-address;
      description "MOM flags: noNotification.";
    }
    leaf-list pmRobustCallSetupGuardTimeDistr {
      type uint32;
    }
    leaf pmRrcConnEstabFailCellIntensStat {
      type uint32;
      config false;
    }
    leaf pmPrbAvailUlPucchAckNack {
      type uint32;
      config false;
    }
    leaf pmUeCtxtRelCsfbCdma1xRtt {
      type uint32;
      config false;
    }
    leaf pmPdcpVolDlDrbTransPlmn6 {
      type uint32;
      config false;
    }
    leaf pmFlexMacHarqUlFail16qam {
      type ietfyang:mac-address;
      config false;
    }
    leaf-list pmTm9CapableDistr {
      type uint32;
    }
    leaf pmUeCtxtRetrReestFailEndcUe {
      type uint32;
      config false;
      status deprecated;
      description "MOM flags: noNotification.";
    }
    leaf pmErabEstabSuccInitBrNoPdn {
      type uint32;
      config false;
    }
    leaf pmUeCtxtRelAbnormalEnbHo {
      type uint32;
      config false;
    }
    leaf pmErabRelAbnormalEnbUeLostOosPft {
      type uint32;
      config false;
    }
    leaf pmPrbUsedDlSamp {
      type uint32;
      config false;
    }
    leaf pmFlexErabEstabAttAddedHoOngoingGbr {
      type uint32;
      config false;
    }
    leaf pmCellHoExeAttLteIntraFTuneOut {
      type uint32;
      config false;
    }
    leaf pmRadioThpVolTxDl3ccSCell {
      type uint32;
      config false;
    }
    leaf pmMpdcchMaxPrbAvail {
      type uint32;
      config false;
      status deprecated;
      description "MOM flags: noNotification.";
    }
    leaf pmZtemporary117 {
      type uint32;
      config false;
    }
    leaf pmCellHoPrepAttLteInterF {
      type uint32;
      config false;
    }
    leaf pmGoodCovSearchEvalReportRsrp {
      type ietfinet:port-number;
      config false;
    }
    leaf pmRrcConnQueueSuccMoVoice {
      type uint32;
      config false;
    }
    leaf pmFlexCellHoExeAttUtranSrvcc {
      type uint32;
      config false;
    }
    leaf-list pmUeCtxtRelNormalEnbBuffCe {
      type uint32;
    }
    leaf pmUeCtxtFetchAttUeCapEnq {
      type uint32;
      config false;
    }
    leaf-list pmPdcpLatTimeDlCatMDrxNoSyncQci {
      type uint32;
    }
    leaf-list pmRadioHomUeRepCqiDistr {
      type uint32;
    }
    leaf pmFlexErabRelAbnormalEnbPeGbr {
      type uint32;
      config false;
    }
    leaf pmPdcchTxConservative {
      type uint32;
      config false;
    }
    leaf pmRadioThpVolDl3ccPCell {
      type uint32;
      config false;
    }
    leaf pmHoPrepRejInDynUeAdmCtrl {
      type uint32;
      config false;
    }
    leaf-list pmBitRateUpUlVoipTimeDistr {
      type ietfinet:ip-address;
    }
    leaf pmFlexMacHarqUlDtx64qam {
      type ietfyang:mac-address;
      config false;
    }
    leaf pmUlGrantsTransPCellNoAck {
      type uint32;
      config false;
    }
    leaf pmUeCtxtRelAbnormalEnbActTnFail {
      type uint32;
      config false;
    }
    leaf-list pmPdcpVolUlHdrQci {
      type uint32;
    }
    leaf-list pmSrGrantLatDistr {
      type uint32;
    }
    leaf pmRrcConnEstabLowCovUeAtt {
      type uint32;
      config false;
    }
    leaf pmCellHoExeSuccLteInterFUl {
      type uint32;
      config false;
    }
    leaf pmFlexMacLatTimeDlNoDrxSync {
      type ietfyang:mac-address;
      config false;
      status deprecated;
      description "MOM flags: noNotification.";
    }
    leaf pmFlexErabEstabAttAddedCsfb {
      type uint32;
      config false;
    }
    leaf pmCellHoPrepCancelGbr {
      type uint32;
      config false;
    }
    leaf pmFlexCellHoExeAttLteIntraF {
      type uint32;
      config false;
    }
    leaf pmUeCtxtRelSC1xRttUlSinr {
      type uint32;
      config false;
      status deprecated;
      description "MOM flags: noNotification.";
    }
    leaf-list pmErabRelMmeActQci {
      type uint32;
    }
    leaf pmErabRelMmeActUnspecified {
      type uint32;
      config false;
    }
    leaf-list pmPdcpVolDlDrbLastTTIQci {
      type uint32;
    }
    leaf pmDtdReqPft {
      type uint32;
      config false;
    }
    leaf pmFlexZtemporary11 {
      type uint32;
      config false;
    }
    leaf-list pmAcBarringCsfbSpecialAcDistr {
      type ietfyang:mac-address;
    }
    leaf-list pmUlSinrDistr {
      type uint32;
    }
    leaf pmUeCtxtRelAbnormalEnbActUeLostOos {
      type uint32;
      config false;
    }
    leaf pmUeCtxtEstabAtt {
      type uint32;
      config false;
    }
    leaf pmRadioThpVolUlSCell {
      type uint32;
      config false;
    }
    leaf pmUeExclThpVolte {
      type uint32;
      config false;
    }
    leaf pmZtemporary118 {
      type uint32;
      config false;
    }
    leaf pmUlGrantsTransNDO {
      type uint32;
      config false;
    }
    leaf-list pmAccessClassBarringCsfbPlmn3Distr {
      type ietfyang:mac-address;
    }
    leaf pmPdcpLatPktTransDlDrxSync {
      type uint32;
      config false;
    }
    leaf pmBadCovOutSearchEvalReport {
      type ietfinet:port-number;
      config false;
    }
    leaf pmCellHoPrepAttLteInterFUlTraffic {
      type uint32;
      config false;
    }
    leaf pmUeCtxtFetchAttS1HoExeSrvccGeran {
      type uint32;
      config false;
    }
    leaf pmFlexErabEstabFailRes {
      type uint32;
      config false;
    }
    leaf pmRrcConnSuspendBr {
      type uint32;
      config false;
    }
    leaf-list pmRadioRecInterferencePwr {
      type uint32;
    }
    leaf pmZtemporary136 {
      type uint32;
      config false;
    }
    leaf-list pmCaConfDlEranSumDistr {
      type uint32;
    }
    leaf pmErabRelMmeHo {
      type uint32;
      config false;
    }
    leaf-list pmUeCtxtConnResumeSuccCe {
      type uint32;
      description "MOM flags: noNotification.";
    }
    leaf pmFlexMacHarqDlNackComp {
      type ietfyang:mac-address;
      config false;
    }
    leaf pmFlexRrcConnSum {
      type uint32;
      config false;
    }
    leaf pmEndcHoA5MeasRepUe {
      type uint32;
      config false;
    }
    leaf pmCellHoPrepSuccLteInterFUlTraffic {
      type uint32;
      config false;
    }
    leaf pmFlexUeThpTimeDlCa {
      type uint32;
      config false;
    }
    leaf pmRadioRecInterferencePwrPrb97 {
      type uint32;
      config false;
    }
    leaf pmRaFailCfraMsg1DiscOoc {
      type uint32;
      config false;
    }
    leaf pmErabRelAbnormalEnbOos {
      type uint32;
      config false;
    }
    leaf pmPwsEtwsPrimSucc {
      type uint32;
      config false;
    }
    leaf-list pmErabRelAbnormalMmeArp {
      type uint32;
    }
    leaf pmFlexZtemporary7 {
      type uint32;
      config false;
    }
    leaf pmHoPrepRejInCellIntensSwC {
      type uint32;
      config false;
    }
    leaf pmDrxTotalTimePft {
      type uint32;
      config false;
    }
    leaf pmCgiMeasSuccDrxQci1 {
      type uint32;
      config false;
    }
    leaf-list pmPdcpPktReceivedDlQci {
      type uint32;
    }
    leaf pmFlexUeThpTimeUlCa {
      type uint32;
      config false;
    }
    leaf-list pmRlcArqRetxDl {
      type uint32;
    }
    leaf-list pmAccessClassBarringVideoPlmn2Distr {
      type ietfyang:mac-address;
    }
    leaf-list pmActiveUeUlMaxCe {
      type ietfyang:mac-address;
      description "MOM flags: noNotification.";
    }
    leaf pmUeCtxtFetchSuccEndcSetup {
      type uint32;
      config false;
    }
    leaf pmZtemporary13 {
      type uint32;
      config false;
    }
    leaf pmB1BestCellEvalReportRsrp {
      type ietfinet:port-number;
      config false;
    }
    leaf pmSchedActivityUeDl {
      type uint32;
      config false;
    }
    leaf pmRrcConnEstabAttHpa {
      type uint32;
      config false;
    }
    leaf-list pmZtemporary190 {
      type uint32;
    }
    leaf pmRrcConnQueueAllocSucc {
      type uint32;
      config false;
    }
    leaf pmFlexPdcpPktFwdDl {
      type uint32;
      config false;
    }
    leaf pmErabRelMmeActEutra {
      type uint32;
      config false;
    }
    leaf pmPwsCmasReq {
      type uint32;
      config false;
    }
    leaf pmRobustCallSetupDelayedUtGeran {
      type uint32;
      config false;
    }
    leaf-list pmAcBarringVoiceSpecAcPlmn1Distr {
      type ietfyang:mac-address;
    }
    leaf pmFlexZtemporary5 {
      type uint32;
      config false;
    }
    leaf-list pmDynUeAdmCtrlQueueTimeDistr {
      type uint32;
      description "MOM flags: noNotification.";
    }
    leaf pmRrcConnReestFailMISigQCong {
      type uint32;
      config false;
    }
    leaf-list pmErabEstabFailAddedErabIdInUseQci {
      type uint32;
    }
    leaf pmCellDownLockMan {
      type uint32;
      config false;
    }
    leaf pmHoPrepRejInOffloadAdmission {
      type uint32;
      config false;
    }
    leaf pmRadioThpVolTxDl4ccSCell {
      type uint32;
      config false;
    }
    leaf pmRrcConnReconfSuccNoMob {
      type uint32;
      config false;
    }
    leaf pmActiveDrbDlSum {
      type ietfyang:mac-address;
      config false;
    }
    leaf pmUeCtxtFetchAtt {
      type uint32;
      config false;
    }
    leaf pmRlcArqDlAck {
      type uint32;
      config false;
    }
    leaf-list pmErabRelAbnormalEnbActCdtAutoQci {
      type uint32;
    }
    leaf pmRadioRecInterferencePwrPrb3 {
      type uint32;
      config false;
    }
    leaf pmZtemporary123 {
      type uint32;
      config false;
    }
    leaf-list pmMacLatTimeDlDrxSyncQci {
      type ietfyang:mac-address;
      description "MOM flags: noNotification.";
    }
    leaf-list pmActiveUeDlSumQci {
      type ietfyang:mac-address;
    }
    leaf pmRrcConnReconfSuccNoMobEarfcnCa {
      type uint32;
      config false;
    }
    leaf pmErabRelAbnormalEnbActPe {
      type uint32;
      config false;
    }
    leaf-list pmDrbThpTimeDlQci {
      type uint32;
    }
    leaf pmNasTransDlBrNoPdn {
      type uint32;
      config false;
    }
    leaf pmRrcConnReestFailDynUeAdmCtrlPaPtt {
      type uint32;
      config false;
    }
    leaf pmUeCtxtRelCsfbGsmEm {
      type uint32;
      config false;
    }
    leaf pmHoPrepRejInDynUeAdmCtrlPtt {
      type uint32;
      config false;
    }
    leaf-list pmErabRelAbnormalEnbCdtAutoQci {
      type uint32;
    }
    leaf pmFlexErabEstabFailAddedOngoingProc {
      type uint32;
      config false;
    }
    leaf pmUeCtxtRelAbnormalEnbDataStall {
      type uint32;
      config false;
    }
    leaf-list pmMacTimeDlNoDrxNoSyncSampQci {
      type ietfyang:mac-address;
      description "MOM flags: noNotification.";
    }
    leaf pmUeCtxtFetchAttS1HoPrepSrvccGeran {
      type uint32;
      config false;
    }
    leaf pmSchedActivityUeUlComp {
      type uint32;
      config false;
    }
    leaf-list pmCaSCellUpswitchDistr {
      type uint32;
    }
    leaf pmHoPrepRejInDlOnlyCell {
      type uint32;
      config false;
    }
    leaf-list pmPdcchTargetBlerHighRatioDistr {
      type uint32;
    }
    leaf pmUeCtxtRelAbnormalEnbPeInterCell {
      type uint32;
      config false;
    }
    leaf pmUeCtxtRelAbnormalEnbUeLost {
      type uint32;
      config false;
    }
    leaf-list pmPrbUtilDl {
      type uint32;
    }
    leaf pmFlexErabRelAbnormalMmeGbr {
      type uint32;
      config false;
    }
    leaf-list pmErabRelAbnormalMmeActGbrArp {
      type uint32;
    }
    leaf pmErabRelMmeActUserInactivity {
      type uint32;
      config false;
    }
    leaf-list pmPrbUsedMimoLayersDlDistr {
      type uint32;
    }
    leaf pmB2BestCellEvalReportRsrp {
      type ietfinet:port-number;
      config false;
    }
    leaf pmFlexMacHarqUlFailQpsk {
      type ietfyang:mac-address;
      config false;
    }
    leaf pmZtemporary2 {
      type uint32;
      config false;
    }
    leaf pmZtemporary119 {
      type uint32;
      config false;
    }
    leaf pmZtemporary170 {
      type uint32;
      config false;
    }
    leaf-list pmMbbHighVolUeSampCqi {
      type uint32;
    }
    leaf pmRadioUeRepCqi2Subband1Sum {
      type uint32;
      config false;
    }
    leaf pmRrcConnEstabFailMmeOvlMos {
      type uint32;
      config false;
    }
    leaf pmRrcConnEstabAttReattMos {
      type uint32;
      config false;
    }
    leaf pmPagDiscardedBr {
      type uint32;
      config false;
    }
    leaf-list pmPdcchCceAggregationUlDistr {
      type uint32;
    }
    leaf pmPrbUsedDlCatmMax {
      type int32;
      config false;
    }
    leaf pmCellHoPrepSuccLteInterFUl {
      type uint32;
      config false;
    }
    leaf pmCaDeconfigured {
      type uint32;
      config false;
    }
    leaf pmRrcConnNs05Samp {
      type uint32;
      config false;
    }
    leaf pmHoPrepRejInMpMem {
      type uint32;
      config false;
    }
    leaf pmFlexEndcSetupUeSucc {
      type uint32;
      config false;
    }
    leaf pmRadioRecInterferencePwrPrb71 {
      type uint32;
      config false;
    }
    leaf pmCellHoExeAttLteInterF {
      type uint32;
      config false;
    }
    leaf pmUeCtxtFetchAttS1HoPrep {
      type uint32;
      config false;
    }
    leaf pmPdcpPktLostUl {
      type uint32;
      config false;
    }
    leaf pmPdcpVolUlDrbPlmn4 {
      type uint32;
      config false;
    }
    leaf pmDlAssigsDetectedHarqVolteNDO {
      type uint32;
      config false;
    }
    leaf pmHoPreventedNotInPlmnWLUtran {
      type uint32;
      config false;
    }
    leaf-list pmPrbAvailUtilDlDistr {
      type uint32;
    }
    leaf pmZtemporary247 {
      type uint32;
      config false;
    }
    leaf pmRrcConnQueueAttMtaHp {
      type uint32;
      config false;
    }
    leaf pmUeCtxtRelAbnormalEnbActCritCov {
      type uint32;
      config false;
    }
    leaf pmRrcConnReestFailBb {
      type uint32;
      config false;
    }
    leaf pmEndcUaiRecOverheating {
      type uint32;
      config false;
    }
    leaf pmRrcConnMaxEndc0 {
      type int32;
      config false;
    }
    leaf-list pmPrbUtilDlCellResource3Distr {
      type uint32;
      description "MOM flags: noNotification.";
    }
    leaf pmFlexMacHarqDlAllDtx {
      type ietfyang:mac-address;
      config false;
    }
    leaf pmCriticalBorderEvalReportUl {
      type ietfinet:port-number;
      config false;
    }
    leaf pmRaContResOnly {
      type uint32;
      config false;
    }
    leaf pmUlGrantsTransNonMcPttNDO {
      type uint32;
      config false;
    }
    leaf pmCgiMeasSuccAgQci1 {
      type uint32;
      config false;
    }
    leaf-list pmPdcchCfiUtil {
      type uint32;
    }
    leaf pmRaSuccSrOosCe1Br {
      type uint32;
      config false;
    }
    leaf pmUeCtxtFetchAttIntraEnbHoPrep {
      type uint32;
      config false;
    }
    leaf pmRrcConnEstabAttReattMoVoice {
      type uint32;
      config false;
    }
    leaf-list pmPrbUtilDlCellResource2Distr {
      type uint32;
      description "MOM flags: noNotification.";
    }
    leaf pmRaFailCbraMsg1DiscOoc {
      type uint32;
      config false;
    }
    leaf pmRrcConnQueueAtt {
      type uint32;
      config false;
    }
    leaf pmPrbUsedDlDtchSCellExt {
      type uint32;
      config false;
    }
    leaf pmPdcpPktPdbUlOkMcPtt {
      type uint32;
      config false;
    }
    leaf pmRrcConnResumeFailLic {
      type uint32;
      config false;
    }
    leaf pmRrcConnEstabAttMoVoice {
      type uint32;
      config false;
    }
    leaf-list pmModImeisvParamSet {
      type uint32;
    }
    leaf pmDlAssigsTransMcPtt {
      type uint32;
      config false;
    }
    leaf pmBestCellEvalReport {
      type ietfinet:port-number;
      config false;
    }
    leaf-list pmRaMsg3DtxCbraTxBrCe0Distr {
      type uint32;
    }
    leaf-list pmZtemporary131Compr {
      type uint32;
    }
    leaf pmUeCtxtFetchSuccS1HoExeSrvccGeran {
      type uint32;
      config false;
    }
    leaf-list pmPrbUtilUlDistr {
      type uint32;
    }
    leaf pmEndcCapableUeInitSetup {
      type uint32;
      config false;
      status deprecated;
      description "MOM flags: noNotification.";
    }
    leaf pmSchedActivityUeUl {
      type uint32;
      config false;
    }
    leaf-list pmPdcchCongestDistr {
      type uint32;
    }
    leaf-list pmRaFailMsg1DiscDistr {
      type uint32;
    }
    leaf pmFlexMacSkipUlDtxTxSps {
      type ietfinet:ip-address;
      config false;
    }
    leaf pmZtemporary61 {
      type uint32;
      config false;
    }
    leaf pmEndcNotAllowedExpiredMoVoice {
      type uint32;
      config false;
    }
    leaf pmRrcConnResumeFailCellIntensDLC {
      type uint32;
      config false;
    }
    leaf-list pmZtemporary81 {
      type uint32;
    }
    leaf pmPwsEtwsPrimReq {
      type uint32;
      config false;
    }
    leaf pmPdcpRtpSnGapDetected {
      type uint32;
      config false;
    }
    leaf pmErabEstabQci5EmInactTimer {
      type uint32;
      config false;
    }
    leaf pmS1RerouteNasRequestReceived {
      type uint32;
      config false;
    }
    leaf-list pmDrxReqPftDistr {
      type uint32;
    }
    leaf pmA3InterFBestCellEvalReportUl {
      type ietfinet:port-number;
      config false;
    }
    leaf pmMcPttQualityRbUlOk {
      type uint32;
      config false;
    }
    leaf pmActiveUeDlCe0Max {
      type ietfyang:mac-address;
      config false;
    }
    leaf-list pmCaCapableDlFddTddSum {
      type uint32;
    }
    leaf pmCovSearchZoneSum {
      type uint32;
      config false;
    }
    leaf-list pmRadioUeRepCqiDistr {
      type uint32;
    }
    leaf pmFlexCellHoPrepSuccNonMobLte {
      type uint32;
      config false;
    }
    leaf pmRadioRecInterferencePwrPrb26 {
      type uint32;
      config false;
    }
    leaf pmErabRelMmeActHo {
      type uint32;
      config false;
    }
    leaf pmMacSkipUlDtxDynamic {
      type ietfinet:ip-address;
      config false;
    }
    leaf-list pmRadioUeRepTm4Rank4PmiDistr {
      type uint32;
    }
    leaf pmFlexMacHarqUl2 {
      type ietfyang:mac-address;
      config false;
    }
    leaf-list pmCaActivatedDl3ccSumDistr {
      type uint32;
    }
    leaf pmCellHoPrepAttLteInterFEndcHo {
      type uint32;
      config false;
    }
    leaf pmPrbUsedDlDcchBr {
      type uint32;
      config false;
    }
    leaf-list pmAasSchedPrbDlVerticalDistr {
      type uint32;
    }
    leaf pmEndcSetupUeAttBufDl {
      type uint32;
      config false;
    }
    leaf pmErabRelAbnormalEnbTnFail {
      type uint32;
      config false;
    }
    leaf-list pmPtmSubRatioSumDistr {
      type uint32;
    }
    leaf pmRadioRecInterferencePwrPrb58 {
      type uint32;
      config false;
    }
    leaf pmPwsEtwsSecSucc {
      type uint32;
      config false;
    }
    leaf pmFlexPdcpVolDlDrbLastTTIUe {
      type uint32;
      config false;
    }
    leaf pmPrbUsedDlSrbFirstTrans {
      type uint32;
      config false;
    }
    leaf pmRadioRecInterferencePwrPrb1 {
      type uint32;
      config false;
    }
    leaf pmCrsIcCapableSum {
      type uint32;
      config false;
    }
    leaf pmRadioRecInterferencePwrPrb91 {
      type uint32;
      config false;
    }
    leaf pmMeasGapFailLicInterFOtdoa {
      type uint32;
      config false;
    }
    leaf-list pmRrcConnEstabFailMpMemCe {
      type uint32;
      description "MOM flags: noNotification.";
    }
    leaf pmRadioUeRepCqi2Subband4Sum {
      type uint32;
      config false;
    }
    leaf pmPrbUsedUlBr {
      type uint32;
      config false;
    }
    leaf-list pmLaaConfiguredDlSum {
      type uint32;
    }
    leaf pmErabEstabSuccAddedHpa {
      type uint32;
      config false;
    }
    leaf-list pmPdcchSym1PwrUtil {
      type uint32;
    }
    leaf-list pmErabReestAttRejAdmMsrArp {
      type uint32;
    }
    leaf pmPrbUsedDlDtchSCellEran {
      type uint32;
      config false;
    }
    leaf-list pmRadioUeRepTm4Rank3PmiDistr {
      type uint32;
    }
    leaf pmUeCtxtFetchSuccEndcRel {
      type uint32;
      config false;
    }
    leaf pmErabRelAbnormalEnbOosPft {
      type uint32;
      config false;
    }
    leaf pmFlexVoipQualityRbUlOk {
      type ietfinet:ip-address;
      config false;
    }
    leaf pmZtemporary90 {
      type uint32;
      config false;
    }
    leaf pmRrcConnResumeFailDynUeAdmCtrlPtt {
      type uint32;
      config false;
    }
    leaf pmUeCtxtFetchAttCgiMeas {
      type uint32;
      config false;
    }
    leaf pmRrcConnResumeFailMpMem {
      type uint32;
      config false;
    }
    leaf pmMacHarqUlFailIua16qam {
      type ietfyang:mac-address;
      config false;
    }
    leaf pmFlexMacHarqDlNack256qam {
      type ietfyang:mac-address;
      config false;
    }
    leaf pmErabRelAbnormalEnbActHo {
      type uint32;
      config false;
    }
    leaf pmErabEstabAttAddedHoOngoing {
      type uint32;
      config false;
    }
    leaf pmCaDeconfiguredLostCoverageNoA1 {
      type uint32;
      config false;
    }
    leaf pmA5BestCellEvalReportUl {
      type ietfinet:port-number;
      config false;
    }
    leaf-list pmDrxSwitchPftDistr {
      type uint32;
    }
    leaf pmPrbUsedDlDtch {
      type uint32;
      config false;
    }
    leaf-list pmAccessClassBarringModPlmn1Distr {
      type ietfyang:mac-address;
    }
    leaf pmUeThpTimeUlInitial {
      type uint32;
      config false;
    }
    leaf pmRadioRecInterferencePwrPrb45 {
      type uint32;
      config false;
    }
    leaf-list pmErabEstabSuccInitQci {
      type uint32;
    }
    leaf-list pmCaActivatedDlEranSumDistr {
      type uint32;
    }
    leaf pmZtemporary3 {
      type uint32;
      config false;
    }
    leaf pmPwrBoostAttLowCovUe {
      type uint32;
      config false;
    }
    leaf pmCellHoExeAttLteInterFHybridCsg {
      type uint32;
      config false;
    }
    leaf-list pmPuschHomMcsDistr {
      type uint32;
    }
    leaf pmA2InterFHoHigherPrioEvalReport {
      type ietfinet:port-number;
      config false;
    }
    leaf pmUeMeasAttCsfb1xRttEm {
      type uint32;
      config false;
    }
    leaf pmErabRelNormalEnbAct {
      type uint32;
      config false;
    }
    leaf-list pmEabBrCatCDistr {
      type uint32;
    }
    leaf pmRrcConnEstabFailDynUeAdmCtrlPaPtt {
      type uint32;
      config false;
    }
    leaf pmCellHoPrepAttLteInterFUtvm {
      type uint32;
      config false;
    }
    leaf pmFlexZtemporary16 {
      type uint32;
      config false;
    }
    leaf pmRrcConnResumeFallbackAtt {
      type uint32;
      config false;
    }
    leaf pmRrcConnLevSumUlOutOfSync {
      type uint32;
      config false;
    }
    leaf pmUeCtxtRelAbnormalEnbPe {
      type uint32;
      config false;
    }
    leaf-list pmErabRelAbnormalEnbActPeQci {
      type uint32;
    }
    leaf-list pmCaConfDlSCellFddLaaSumDistr {
      type uint32;
    }
    leaf pmZtemporary21 {
      type uint32;
      config false;
    }
    leaf pmRaAttCfra {
      type uint32;
      config false;
    }
    leaf pmUeCtxtRelAbnormalEnbPsFail {
      type uint32;
      config false;
    }
    leaf pmPrbUsedDlDtchSCellIcm {
      type uint32;
      config false;
    }
    leaf-list pmRrcSegmentUlDistr {
      type uint32;
    }
    leaf-list pmRrcConnEstabAttMtaPagPrioDistr {
      type uint32;
    }
    leaf-list pmCaScheduledDl4ccSumDistr {
      type uint32;
    }
    leaf pmUeThpTimeUlCa {
      type uint32;
      config false;
    }
    leaf pmRadioRecInterferencePwrPrb42 {
      type uint32;
      config false;
    }
    leaf-list pmRaSuccTaDistr {
      type uint32;
    }
    leaf pmRadioThpVolTxDlSCellEranOffl {
      type uint32;
      config false;
    }
    leaf-list pmPimPowerExcessDistr {
      type uint32;
    }
    leaf pmRrcConnReestFailDynUeAdmCtrl {
      type uint32;
      config false;
    }
    leaf pmSinrWithPimAvoidOnSum {
      type uint32;
      config false;
    }
    leaf pmFlexMacHarqUlAllDtx {
      type ietfyang:mac-address;
      config false;
    }
    leaf pmUeCtxtEstabAttCsfb {
      type uint32;
      config false;
    }
    leaf pmRaSuccCfra {
      type uint32;
      config false;
    }
    leaf-list pmErabRelAbnormalEnbActHoQci {
      type uint32;
    }
    leaf pmUeCtxtRelSCNrB1Rsrq {
      type uint32;
      config false;
    }
    leaf pmRrcConnEstabFailMmeOvlMod {
      type uint32;
      config false;
    }
    leaf pmS1SigConnEstabSuccDta {
      type uint32;
      config false;
      status deprecated;
      description "MOM flags: noNotification.";
    }
    leaf-list pmUlSinrPdcchDistr {
      type uint32;
    }
    leaf pmCellHoExeAttLteInterFMbms {
      type uint32;
      config false;
    }
    leaf pmRadioRecInterferencePwrPrb99 {
      type uint32;
      config false;
    }
    leaf pmEndcSetupFailNrRa {
      type uint32;
      config false;
    }
    leaf pmOutOfSyncTimePft {
      type uint32;
      config false;
    }
    leaf pmMacHarqDlDtx16qam {
      type ietfyang:mac-address;
      config false;
    }
    leaf pmHoPrepRejInSl {
      type uint32;
      config false;
    }
    leaf pmCellHoPrepAttLteIntraF {
      type uint32;
      config false;
    }
    leaf-list pmRrcConnEstabFailMtaDynUeAdmCtrlPagPrioDistr {
      type uint32;
    }
    leaf-list pmCaScheduledDl7ccSumDistr {
      type uint32;
    }
    leaf pmCgiMeasSuccDrx {
      type uint32;
      config false;
    }
    leaf pmDlAssigsTransVolte {
      type uint32;
      config false;
    }
    leaf pmRadioUeRepCqiSubband1Sum {
      type uint32;
      config false;
    }
    leaf-list pmLcgThpTimeUlNs05Distr {
      type uint32;
    }
    leaf pmRadioRecInterferencePwrPrb41 {
      type uint32;
      config false;
    }
    leaf pmFlexUeCtxtEstabAtt {
      type uint32;
      config false;
    }
    leaf pmB1MeasRepEndcConfigRestart {
      type uint32;
      config false;
    }
    leaf pmPrbUsedUlCatmSamp {
      type uint32;
      config false;
    }
    leaf pmRaAllocCfra {
      type uint32;
      config false;
    }
    leaf pmUeCtxtFetchAttReconf {
      type uint32;
      config false;
    }
    leaf pmUeCtxtFetchAttIntraEnbHoIn {
      type uint32;
      config false;
    }
    leaf-list pmMbbHighVolUeThpDlSumCqi {
      type uint32;
    }
    leaf pmBadCovOutSearchEvalReportRsrp {
      type ietfinet:port-number;
      config false;
    }
    leaf pmPrbUsedDlFirstTransCatm {
      type uint32;
      config false;
    }
    leaf pmIdcUlCaSum {
      type uint32;
      config false;
    }
    leaf pmGoodCovSearchEvalReportUl {
      type ietfinet:port-number;
      config false;
    }
    leaf pmRaUnassignedCfraSum {
      type uint32;
      config false;
    }
    leaf pmTtiNs05FullBandSch {
      type uint32;
      config false;
    }
    leaf pmPucchSrCqiResAllocAtt {
      type uint32;
      config false;
    }
    leaf pmPrbUsedDlBr {
      type uint32;
      config false;
    }
    leaf pmUeCtxtRelAbnormalEnbUeLostOos {
      type uint32;
      config false;
    }
    leaf pmRrcConnEstabSuccDta {
      type uint32;
      config false;
      status deprecated;
      description "MOM flags: noNotification.";
    }
    leaf-list pmCellIntensRrcConnReconfDistr {
      type uint32;
    }
    leaf pmUeCtxtRelSCCdmaA2Rsrp {
      type uint32;
      config false;
    }
    leaf-list pmAcBarringMosSpecAcPlmn3Distr {
      type ietfyang:mac-address;
    }
    leaf pmErabRelAbnormalEnbActHpr {
      type uint32;
      config false;
    }
    leaf-list pmZtemporary133Compr {
      type uint32;
    }
    leaf pmRrcConnQueueSuccMtaHp {
      type uint32;
      config false;
    }
    leaf-list pmCaConfDlTddSumDistr {
      type uint32;
    }
    leaf-list pmZtemporary16Qci {
      type uint32;
    }
    leaf pmErabRelAbnormalEnbHo {
      type uint32;
      config false;
    }
    leaf pmRobustCallSetupDelayedIntraLte {
      type uint32;
      config false;
    }
    leaf-list pmRrcConnReestFailInAdmMsrRpid {
      type uint32;
    }
    leaf pmMiMimoSleepOut {
      type uint32;
      config false;
    }
    leaf pmEndcSetupBufMonReportUl {
      type ietfinet:port-number;
      config false;
    }
    leaf pmMacVolUlUnresUePreemptGrant {
      type ietfyang:mac-address;
      config false;
    }
    leaf-list pmMacLatTimeDlNoDrxNoSyncQci {
      type ietfyang:mac-address;
      description "MOM flags: noNotification.";
    }
    leaf pmPucchCqiResMediumUtilCell {
      type int32;
      config false;
    }
    leaf pmS1InitialUeMsgReroute {
      type uint32;
      config false;
    }
    leaf pmRobustCallSetupTimerExp {
      type uint32;
      config false;
    }
    leaf-list pmPdcpPktDiscDlRbLimitQci {
      type uint32;
    }
    leaf pmErabRelAbnormalEnbExtIat {
      type uint32;
      config false;
    }
    leaf pmPdcchResyncFailCe1Br {
      type uint32;
      config false;
    }
    leaf pmFlexMcPttQualityRbUlNok {
      type uint32;
      config false;
    }
    leaf pmRrcConnReconfSuccNoMobDlComp {
      type uint32;
      config false;
    }
    leaf pmUlGrantsDetectedPuschNDO {
      type uint32;
      config false;
    }
    leaf pmMacTimeUlResUe {
      type ietfyang:mac-address;
      config false;
    }
    leaf pmZtemporary113 {
      type uint32;
      config false;
    }
    leaf pmLbSubRatioSamp {
      type uint32;
      config false;
    }
    leaf pmMacUeThpTimeDl {
      type ietfyang:mac-address;
      config false;
      status deprecated;
      description "MOM flags: noNotification.";
    }
    leaf pmHoPrepRejInCellIntensDLC {
      type uint32;
      config false;
    }
    leaf pmHoPrepRejInPtm {
      type uint32;
      config false;
    }
    leaf-list pmErabRelAbnormalEnbActHprQci {
      type uint32;
    }
    leaf pmEranCompUlNack {
      type uint32;
      config false;
    }
    leaf pmCellHoPrepSuccLteInterFMbms {
      type uint32;
      config false;
    }
    leaf-list pmRlcSduEstLostUlVoipTtiBundling {
      type ietfinet:ip-address;
    }
    leaf pmUeCtxtRelSCNrB1ServTrigRsrq {
      type uint32;
      config false;
    }
    leaf pmPrbUsedUlPuschLowRegionSrb {
      type uint32;
      config false;
    }
    leaf pmCellHoPrepAttNrServTrig {
      type uint32;
      config false;
    }
    leaf pmFlexCellHoExeSuccNonMobIrat {
      type uint32;
      config false;
    }
    leaf pmRadioRecInterferencePwrPrb8 {
      type uint32;
      config false;
    }
    leaf pmZtemporary144 {
      type uint32;
      config false;
    }
    leaf pmFlexPdcpPktLostUl {
      type uint32;
      config false;
    }
    leaf pmUeCtxtRelSCUtranB2Rsrp {
      type uint32;
      config false;
    }
    leaf pmHoPrepRejInDynUeAdmCtrlPaPtt {
      type uint32;
      config false;
    }
    leaf pmHoPrepRejOutUlThres {
      type uint32;
      config false;
    }
    leaf pmMacHarqFail {
      type ietfyang:mac-address;
      config false;
    }
    leaf pmFlexMacHarqDlAck64qam {
      type ietfyang:mac-address;
      config false;
    }
    leaf pmMacHarqDlNackQpsk {
      type ietfyang:mac-address;
      config false;
    }
    leaf pmPdcchResyncSucc {
      type uint32;
      config false;
    }
    leaf-list pmMpdcchRadioUeOutLoopAdjCe1Distr {
      type uint32;
    }
    leaf pmUeCtxtFetchSucc {
      type uint32;
      config false;
    }
    leaf pmRrcConnMaxPlmn4 {
      type int32;
      config false;
    }
    leaf pmRadioRecInterferencePwrPrb92 {
      type uint32;
      config false;
    }
    leaf-list pmRlcSduRecUlNonMcPttTtiBundl {
      type uint32;
    }
    leaf pmUlGrantsWithDetPuschMcPtt {
      type uint32;
      config false;
    }
    leaf-list pmPdschRepBrDistr {
      type uint32;
    }
    leaf-list pmErabRelMmeGbrArp {
      type uint32;
    }
    leaf pmEndcSetupScgUeSucc {
      type uint32;
      config false;
    }
    leaf pmCellHoExeSuccLteInterFCsg {
      type uint32;
      config false;
    }
    leaf pmSchedTtiCellUlFreqSel {
      type uint32;
      config false;
      status deprecated;
      description "MOM flags: noNotification.";
    }
    leaf-list pmRaMsg3NackCbraTxDistr {
      type uint32;
    }
    leaf pmUeExclThpUlShortTimeLowVol {
      type uint32;
      config false;
    }
    leaf pmRachNumContentionReport {
      type ietfinet:port-number;
      config false;
    }
    leaf pmBadCovSearchEvalReport {
      type ietfinet:port-number;
      config false;
    }
    leaf pmFlexDrbThpTimeDl {
      type uint32;
      config false;
    }
    leaf-list pmIdcUlCaVictimOnDistr {
      type uint32;
    }
    leaf pmPdcpPktDiscDlPelr {
      type uint32;
      config false;
    }
    leaf pmPtmCellReservedSubRatio {
      type uint32;
      config false;
    }
    leaf-list pmPdcchCceUtilDistr {
      type uint32;
    }
    leaf pmRlcArqUlNack {
      type uint32;
      config false;
    }
    leaf pmRlcArqUlAck {
      type uint32;
      config false;
    }
    leaf pmUeCtxtRelCsfbCdma1xRttEm {
      type uint32;
      config false;
    }
    leaf-list pmMacHarqUlDtxDistr {
      type ietfyang:mac-address;
    }
    leaf pmFlexMacHarqUlDtxQpsk {
      type ietfyang:mac-address;
      config false;
    }
    leaf pmPdcpLatTimeDl {
      type uint32;
      config false;
    }
    leaf pmCellHoPrepAttLowCovUe {
      type uint32;
      config false;
    }
    leaf pmErabRelAbnormalMmeActCritCov {
      type uint32;
      config false;
    }
    leaf pmRadioRecInterferencePwrPrb90 {
      type uint32;
      config false;
    }
    leaf-list pmMimoSleepTimeDistr {
      type uint32;
    }
    leaf pmRrcConnEstabFailDuSwC {
      type uint32;
      config false;
    }
    leaf pmFlexCellHoPrepAttNr {
      type uint32;
      config false;
    }
    leaf pmRrcConnBrMax {
      type int32;
      config false;
    }
    leaf pmRrcConnEstabFailCellLatency {
      type uint32;
      config false;
    }
    leaf pmRadioRecInterferencePwrPrb27 {
      type uint32;
      config false;
    }
    leaf-list pmPdcpPktDiscDlHoQci {
      type uint32;
    }
    leaf pmUeCtxtFetchSuccX2HoPrep {
      type uint32;
      config false;
    }
    leaf pmUlGrantsTransMcPttNoAck {
      type uint32;
      config false;
    }
    leaf-list pmErabEstabSuccInitGbrArp {
      type uint32;
    }
    leaf pmZtemporary167 {
      type uint32;
      config false;
    }
    leaf pmErabRelAbnormalEnbAct {
      type uint32;
      config false;
    }
    leaf pmHoPrepRejInLicLowCovUe {
      type uint32;
      config false;
    }
    leaf-list pmPdcpLatTimeDlDrxSyncQci {
      type uint32;
    }
    leaf pmTtiBundlingDisable {
      type uint32;
      config false;
    }
    leaf pmAcBarringEmSpecAcPlmn1 {
      type ietfyang:mac-address;
      config false;
    }
    leaf-list pmRrcLatencyCapEnqDistr {
      type uint32;
    }
    leaf pmZtemporary23 {
      type uint32;
      config false;
    }
    leaf-list pmLcgThpVolUlNs05Distr {
      type uint32;
    }
    leaf pmNasTransferSuccDlSrb2 {
      type uint32;
      config false;
    }
    leaf pmZtemporary91 {
      type uint32;
      config false;
    }
    leaf pmEndcPrioNonServFreq {
      type uint32;
      config false;
    }
    leaf pmRrcConnMax {
      type int32;
      config false;
    }
    leaf-list pmPrbUtilDlNonRetransDistr {
      type uint32;
    }
    leaf-list pmPtmAtoMeasuredUeDistr {
      type uint32;
    }
    leaf-list pmPdcchCceUsedDlQci {
      type uint32;
    }
    leaf pmCellHoPrepSuccLteIntraF {
      type uint32;
      config false;
    }
    leaf pmZtemporary114 {
      type uint32;
      config false;
    }
    leaf pmS1SigConnEstabAttHpa {
      type uint32;
      config false;
    }
    leaf pmCgiMeasSuccAg {
      type uint32;
      config false;
    }
    leaf-list pmRlcSduRecUlMcPttTtiBundl {
      type uint32;
    }
    leaf pmS1SigConnEstabAttMoVoice {
      type uint32;
      config false;
    }
    leaf pmRrcConnSamp {
      type uint32;
      config false;
    }
    leaf pmDlAssigsWithDetectedHarqAckSCell {
      type uint32;
      config false;
    }
    leaf-list pmZtemporary134Compr {
      type uint32;
    }
    leaf pmAnrHoSuccLevelMedium {
      type uint32;
      config false;
    }
    leaf pmRadioRecInterferencePwrPrb29 {
      type uint32;
      config false;
    }
    leaf pmActiveUeUlPresched {
      type ietfyang:mac-address;
      config false;
    }
    leaf-list pmEabBrCatADistr {
      type uint32;
    }
    leaf pmZtemporary65 {
      type uint32;
      config false;
    }
    leaf pmMacVolUl {
      type ietfyang:mac-address;
      config false;
    }
    leaf pmZtemporary67 {
      type uint32;
      config false;
    }
    leaf-list pmRrcConnEstabAttDtaCe {
      type uint32;
    }
    leaf pmZtemporary87 {
      type uint32;
      config false;
    }
    leaf-list pmRaAttCbraBr {
      type uint32;
    }
    leaf-list pmErabModSuccQci {
      type uint32;
    }
    leaf pmUeCtxtRelSCEutraUlSinr {
      type uint32;
      config false;
    }
    leaf pmRaMsg2AttCbra {
      type uint32;
      config false;
    }
    leaf-list pmEranUlCompDeltaSinrPuschDistr {
      type uint32;
    }
    leaf pmS1SigConnEstabAttDta {
      type uint32;
      config false;
      status deprecated;
      description "MOM flags: noNotification.";
    }
    leaf pmRadioRecInterferencePwrPrb59 {
      type uint32;
      config false;
    }
    leaf pmHoPrepRejInBb {
      type uint32;
      config false;
    }
    leaf pmUeExclThpDlSmallVol2 {
      type uint32;
      config false;
    }
    leaf pmPdschBlankedSubframeLess {
      type uint32;
      config false;
    }
    leaf pmPrbUsedDlSum {
      type uint32;
      config false;
    }
    leaf-list pmAdjustAccessDynLoadCtrlDistr {
      type uint32;
    }
    leaf pmInactiveUeRelInHighLoad {
      type uint32;
      config false;
    }
    leaf pmUeCtxtFetchSuccX2HoExe {
      type uint32;
      config false;
    }
    leaf pmPdcchResyncAtt {
      type uint32;
      config false;
    }
    leaf pmMacCellThpTimeUl {
      type ietfyang:mac-address;
      config false;
    }
    leaf pmZtemporary193 {
      type uint32;
      config false;
    }
    leaf pmZtemporary236 {
      type uint32;
      config false;
    }
    leaf pmRrcConnResumeFailCellIntensSwC {
      type uint32;
      config false;
    }
    leaf pmUlGrantsDetectedPuschVolteNDO {
      type uint32;
      config false;
    }
    leaf pmMacHarqUlDtxQpsk {
      type ietfyang:mac-address;
      config false;
    }
    leaf-list pmAccessClassBarringModDistr {
      type ietfyang:mac-address;
    }
    leaf pmRrcConnReconfSuccNoMobDacc {
      type uint32;
      config false;
    }
    leaf pmCellHoExeSuccLteInterFUtvm {
      type uint32;
      config false;
    }
    leaf pmUlGrantsTransMcPtt {
      type uint32;
      config false;
    }
    leaf pmFlexRlcDelayTimeDl2 {
      type uint32;
      config false;
    }
    leaf pmRadioRecInterferencePwrPrb75 {
      type uint32;
      config false;
    }
    leaf pmEndcSetupScgUeAttBufDl {
      type uint32;
      config false;
    }
    leaf pmEndcPrioServFreq {
      type uint32;
      config false;
    }
    leaf pmRrcConnEstabFailMpOverload {
      type uint32;
      config false;
    }
    leaf pmRadioRecInterferencePwrPrb78 {
      type uint32;
      config false;
    }
    leaf pmUlGrantsTransNonMcPttNoAck {
      type uint32;
      config false;
    }
    leaf pmServiceTimeUe {
      type uint32;
      config false;
    }
    leaf pmFlexErabEstabAttAdded {
      type uint32;
      config false;
    }
    leaf pmPdcchResyncFailCe0Br {
      type uint32;
      config false;
    }
    leaf-list pmPdcpLatPktTransDlCatMNoDrxSyncQci {
      type uint32;
    }
    leaf pmUeCtxtFetchSuccS1HoExe {
      type uint32;
      config false;
    }
    leaf-list pmRrcConnEstabFailMmeOvlModCe {
      type uint32;
    }
    leaf-list pmPdcpPktDiscDlPelrQci {
      type uint32;
    }
    leaf-list pmRadioUeRepTm4Rank2PmiDistr {
      type uint32;
    }
    leaf pmErabRelAbnormalEnbActOosPft {
      type uint32;
      config false;
    }
    leaf pmRobustCallSetupDelayedEndc {
      type uint32;
      config false;
    }
    leaf pmFlexMacTimeDlNoDrxSyncSamp {
      type ietfyang:mac-address;
      config false;
      status deprecated;
      description "MOM flags: noNotification.";
    }
    leaf pmUeExclThpUlRelativeQciHighVol {
      type uint32;
      config false;
    }
    leaf pmFlexMacHarqDlDtx16qam {
      type ietfyang:mac-address;
      config false;
    }
    leaf-list pmCellUlPrbUtilization {
      type uint32;
    }
    leaf pmElcOffBadCov {
      type uint32;
      config false;
    }
    leaf pmUePeAttSrResPa {
      type uint32;
      config false;
    }
    leaf pmRadioUeRepCqiSubband11Sum {
      type uint32;
      config false;
    }
    leaf pmZtemporary242 {
      type uint32;
      config false;
    }
    leaf pmEndcSetupUeAttNrRestricted {
      type uint32;
      config false;
    }
    leaf pmRadioThpVolTxDlSCell {
      type uint32;
      config false;
    }
    leaf pmPdcchCceActivity {
      type uint32;
      config false;
    }
    leaf-list pmRlcSduEstLostUlMcPttTtiBundl {
      type uint32;
    }
    leaf-list pmRaAttTaZone0Distr {
      type uint32;
    }
    leaf-list pmPdcchTargetBlerHighRatioPcellDistr {
      type uint32;
    }
    leaf pmCellCaLockTimeHighLoad {
      type uint32;
      config false;
    }
    leaf-list pmCellDlSePttReservation {
      type uint32;
    }
    leaf pmPrbAvailUlPucchCqi {
      type uint32;
      config false;
    }
    leaf pmRadioRecInterferencePwrPrb64 {
      type uint32;
      config false;
    }
    leaf-list pmMpdcchRadioUeOutLoopAdjCe0Distr {
      type uint32;
    }
    leaf pmFlexUeCtxtRelNormalEnb {
      type uint32;
      config false;
    }
    leaf pmUeCtxtRelSCCdma {
      type uint32;
      config false;
    }
    leaf pmPdcpVolDlDrb {
      type uint32;
      config false;
    }
    leaf pmUlGrantsTransVolteNDO {
      type uint32;
      config false;
    }
    leaf pmClpcUlSinr {
      type uint32;
      config false;
    }
    leaf-list pmPrbUtilDlCellResource23Distr {
      type uint32;
      description "MOM flags: noNotification.";
    }
    leaf pmFlexZtemporary25 {
      type uint32;
      config false;
    }
    leaf pmMacHarqDlAck16qam {
      type ietfyang:mac-address;
      config false;
    }
    leaf pmRadioThpVolDl6ccPCell {
      type uint32;
      config false;
    }
    leaf pmUeThpVolUlInitial {
      type uint32;
      config false;
    }
    leaf pmFlexCellHoPrepAtt1xRttSrvcc {
      type uint32;
      config false;
    }
    leaf pmOocNewDataUlGrants {
      type uint32;
      config false;
    }
    leaf pmCellHoExeAttLteInterFUlTraffic {
      type uint32;
      config false;
    }
    leaf pmZtemporary27 {
      type uint32;
      config false;
    }
    leaf pmMeasConfigB1EndcDistribution {
      type uint32;
      config false;
    }
    leaf pmRadioRecInterferencePwrPrb79 {
      type uint32;
      config false;
    }
    leaf pmCellHoPrepSuccLteInterF {
      type uint32;
      config false;
    }
    leaf pmPdcchResyncAttCe1Br {
      type uint32;
      config false;
    }
    leaf pmEndcSetupFailUeCap {
      type uint32;
      config false;
    }
    leaf-list pmPdcpVolDlDrbFiltQci {
      type uint32;
      description "MOM flags: noNotification.";
    }
    leaf pmErabEstabSuccAdded {
      type uint32;
      config false;
    }
    leaf pmAdjustAccessDynLoadCtrl {
      type uint32;
      config false;
    }
    leaf-list pmPrbUtilDlCellResource18Distr {
      type uint32;
      description "MOM flags: noNotification.";
    }
    leaf-list pmDeltaSinrDlComp {
      type uint32;
    }
    leaf pmRohcEstabFailCid {
      type uint32;
      config false;
    }
    leaf pmRrcConnEstabAttMos {
      type uint32;
      config false;
    }
    leaf pmAnrCandNrelRem {
      type uint32;
      config false;
    }
    leaf-list pmRrcConnEstabFailCellIntensStatCe {
      type uint32;
    }
    leaf pmZtemporary22 {
      type uint32;
      config false;
    }
    leaf-list pmZtemporary135Compr {
      type uint32;
    }
    leaf pmPwsCmasSucc {
      type uint32;
      config false;
    }
    leaf pmFlexErabEstabAttInitGbr {
      type uint32;
      config false;
    }
    leaf pmUeCtxtRelSCNrB1ServTrigRsrp {
      type uint32;
      config false;
    }
    leaf-list pmPdcchSym2PwrUtil {
      type uint32;
    }
    leaf-list pmErabEstabAttAddedHoOngoingArp {
      type uint32;
    }
    leaf pmRrcConnResumeAtt {
      type uint32;
      config false;
    }
    leaf pmRadioRecInterferencePwrPrb76 {
      type uint32;
      config false;
    }
    leaf pmHoPrepRejInLicConnUsers {
      type uint32;
      config false;
    }
    leaf pmUlGrantsTransVolteNoAck {
      type uint32;
      config false;
    }
    leaf-list pmCellDlSeUtilization {
      type uint32;
    }
    leaf pmFlexMacHarqUlFailIuaQpsk {
      type ietfyang:mac-address;
      config false;
    }
    leaf-list pmCaConfiguredDlFddTddSum {
      type uint32;
    }
    leaf pmFlexMacHarqDlNackQpsk {
      type ietfyang:mac-address;
      config false;
    }
    leaf pmRrcConnEstabSucc {
      type uint32;
      config false;
    }
    leaf pmUeCtxtRelNaccCsfbGsmEm {
      type uint32;
      config false;
    }
    leaf pmRrcConnEstabSuccHpa {
      type uint32;
      config false;
    }
    leaf pmTtiBundlingFailTO {
      type uint32;
      config false;
    }
    leaf pmUeThpTimeUl {
      type uint32;
      config false;
    }
    leaf-list pmErabRelMmeQci {
      type uint32;
    }
    leaf pmCellHoExeSuccLteInterFUeMeas {
      type uint32;
      config false;
    }
    leaf-list pmAccessClassBarringCsfbPlmn2Distr {
      type ietfyang:mac-address;
    }
    leaf-list pmCellDlPrbUtilization {
      type uint32;
    }
    leaf-list pmBadCovMeasTimeDistr {
      type uint32;
    }
    leaf pmRadioUeRepCqiSubband2Sum {
      type uint32;
      config false;
    }
    leaf-list pmZtemporary224Compr {
      type uint32;
    }
    leaf pmUeCtxtRelAbnormalEnbOos {
      type uint32;
      config false;
    }
    leaf-list pmCaScheduledDlEranSumDistr {
      type uint32;
    }
    leaf pmUeCtxtRelSCEUtraBestCellRsrp {
      type uint32;
      config false;
    }
    leaf pmMacHarqDlNack64qam {
      type ietfyang:mac-address;
      config false;
    }
    leaf pmMacVolUlUnresUeBsrGrant {
      type ietfyang:mac-address;
      config false;
    }
    leaf pmMeasRepGoodCovElc {
      type uint32;
      config false;
    }
    leaf pmPdcpBitrateUlDrbMax {
      type int32;
      config false;
    }
    leaf-list pmPuschRepBrDistr {
      type uint32;
    }
    leaf pmFlexEndcSetupUeAtt {
      type uint32;
      config false;
    }
    leaf-list pmPdcchTargetBlerLowRatioDistr {
      type uint32;
    }
    leaf-list pmRrcConnResumeTimeDistr {
      type uint32;
    }
    leaf pmErabActQci5EmInactTimer {
      type uint32;
      config false;
    }
    leaf pmCellHoExeSuccLteInterFEndcHo {
      type uint32;
      config false;
    }
    leaf pmRlcDelayTimeDl {
      type uint32;
      config false;
      status deprecated;
      description "MOM flags: noNotification.";
    }
    leaf pmUeCtxtRelAbnormalMme {
      type uint32;
      config false;
    }
    leaf pmS1SigConnEstabAtt {
      type uint32;
      config false;
    }
    leaf pmPdcchTxAggressive {
      type uint32;
      config false;
    }
    leaf-list pmLaaCapableDlSum {
      type uint32;
    }
    leaf pmSinrWithPimAvoidOffSamp {
      type uint32;
      config false;
    }
    leaf-list pmMacUeThpUlMbbLowVolDistr {
      type ietfyang:mac-address;
    }
    leaf pmErabEstabAttAddedHpa {
      type uint32;
      config false;
    }
    leaf pmUeCtxtRelCsfbUlHoPrepTxTO1xRttEm {
      type uint32;
      config false;
    }
    leaf pmFlexPdcpVolDlDrbLastTTIUeCa {
      type uint32;
      config false;
    }
    leaf pmFlexRlcArqUlNack {
      type uint32;
      config false;
    }
    leaf pmFlexPdcpVolDlDrbLastTTI {
      type uint32;
      config false;
    }
    leaf pmZtemporary121 {
      type uint32;
      config false;
    }
    leaf pmCaConfiguredAiBasedAtt {
      type uint32;
      config false;
    }
    leaf pmPrbUsedUlCcchBr {
      type uint32;
      config false;
    }
    leaf pmHoPrepSuccInMfbiPrimary {
      type ietfinet:ip-address;
      config false;
    }
    leaf pmMimoSleepOppTime {
      type uint32;
      config false;
    }
    leaf pmUeCtxtRelSCTdScdma {
      type uint32;
      config false;
    }
    leaf-list pmUlPathlossDistr {
      type uint32;
    }
    leaf-list pmPdcpPktTransDlQci {
      type uint32;
    }
    leaf pmUlGrantsTransNoAck {
      type uint32;
      config false;
    }
    leaf pmMacHarqUlFailIuaQpsk {
      type ietfyang:mac-address;
      config false;
    }
    leaf-list pmPdcpLatTimeDlCatMNoDrxNoSyncQci {
      type uint32;
    }
    leaf pmRadioUeRepCqiSubband8Sum {
      type uint32;
      config false;
    }
    leaf-list pmZtemporary230Compr {
      type uint32;
    }
    leaf pmRrcConnReestFailMpMem {
      type uint32;
      config false;
    }
    leaf pmCellCatmEssShareDlSrb0Max {
      type int32;
      config false;
    }
    leaf pmMacVolUlUnresUePucchSrGrant {
      type ietfyang:mac-address;
      config false;
    }
    leaf pmActiveUeUlCe0Max {
      type ietfyang:mac-address;
      config false;
    }
    leaf-list pmRadioUeRepRankDistr {
      type uint32;
    }
    leaf-list pmPdcpVolDlDrbQci {
      type uint32;
    }
    leaf pmCellDowntimeAuto {
      type uint32;
      config false;
    }
    leaf-list pmCaActivatedDl5ccSumDistr {
      type uint32;
    }
    leaf pmFlexErabRelAbnormalEnbPe {
      type uint32;
      config false;
    }
    leaf pmPdcpBitrateDlDrbMin {
      type int32;
      config false;
    }
    leaf pmRadioThpVolTxDlSCellIcmOffl {
      type uint32;
      config false;
    }
    leaf pmErabRelAbnormalEnbActCritCov {
      type uint32;
      config false;
    }
    leaf pmUeCtxtRelSCCdmaA2Rsrq {
      type uint32;
      config false;
    }
    leaf-list pmRrcConnEstabAttMtaCe {
      type uint32;
    }
    leaf-list pmRrcConnEstabAttCe {
      type uint32;
    }
    leaf pmRaFailCfraMsg2Disc {
      type uint32;
      config false;
    }
    leaf pmRadioRecInterferencePwrPrb12 {
      type uint32;
      config false;
    }
    leaf pmUeCtxtRelCsfbTdScdma {
      type uint32;
      config false;
    }
    leaf pmFlexCellHoExeAttNr {
      type uint32;
      config false;
    }
    leaf-list pmHoPrepRejInAdmMsrRpid {
      type uint32;
    }
    leaf pmRobustCallSetupTimerQci1 {
      type uint32;
      config false;
    }
    leaf pmPimAvoidMutedPrbsSamp {
      type uint32;
      config false;
    }
    leaf pmZtemporary195 {
      type uint32;
      config false;
    }
    leaf pmUeCtxtFetchAttIntraEnbHoExe {
      type uint32;
      config false;
    }
    leaf-list pmPdcchTargetBlerDistr {
      type uint32;
    }
    leaf pmFlexNonMcPttQualityRbUlOk {
      type uint32;
      config false;
    }
    leaf-list pmUeCategoryDistr {
      type uint32;
    }
    leaf-list pmUeCtxtRelSCEUtraCe {
      type uint32;
    }
    leaf pmRadioRecInterferencePwrPrb39 {
      type uint32;
      config false;
    }
    leaf pmRrcConnResumeFallbackSucc {
      type uint32;
      config false;
    }
    leaf-list pmErabEstabAttRejAdmMsrInitPttArp {
      type uint32;
    }
    leaf pmPdcpVolDlDrbTransPlmn0 {
      type uint32;
      config false;
    }
    leaf pmFlexUeThpVolUl {
      type uint32;
      config false;
    }
    leaf pmCellHoExeSuccLteInterFUlTraffic {
      type uint32;
      config false;
    }
    leaf pmUeExclThpUlRelativeQciLowVol {
      type uint32;
      config false;
    }
    leaf pmUeCtxtRelSCUtranA2Rsrq {
      type uint32;
      config false;
    }
    leaf pmIdcUlCaCapableMax {
      type int32;
      config false;
    }
    leaf pmFlexErabRelNormalEnbUserInactivity {
      type uint32;
      config false;
      status deprecated;
      description "MOM flags: noNotification.";
    }
    leaf pmCaConfiguredNoMeasSucc {
      type uint32;
      config false;
    }
    leaf-list pmUeCtxtFetchSuccErabActQci {
      type uint32;
    }
    leaf-list pmAccessClassBarringVoicePlmn2Distr {
      type ietfyang:mac-address;
    }
    leaf-list pmCaCapableUlSum {
      type uint32;
    }
    leaf pmPdcpVolDlDrbLastTTI {
      type uint32;
      config false;
    }
    leaf pmRaRejHarqFailAfterContRes {
      type uint32;
      config false;
    }
    leaf pmPrbUsedUlSrb {
      type uint32;
      config false;
    }
    leaf pmZtemporary145 {
      type uint32;
      config false;
    }
    leaf pmPrbUsedDlFirstTrans {
      type uint32;
      config false;
    }
    leaf pmSchedNewTxUlRsvdRegion {
      type uint32;
      config false;
    }
    leaf pmPdcpUeThpTimeDl {
      type uint32;
      config false;
      status deprecated;
      description "MOM flags: noNotification.";
    }
    leaf pmRadioRecInterferencePwrPrb100 {
      type uint32;
      config false;
    }
    leaf-list pmSessionTimeDrbQci {
      type uint32;
    }
    leaf pmFlexCellHoPrepSuccUtran {
      type uint32;
      config false;
    }
    leaf-list pmErabQciMax {
      type uint32;
    }
    leaf-list pmUeThp2UlDistr {
      type uint32;
    }
    leaf-list pmLaaScheduledDlDistr {
      type uint32;
    }
    leaf-list pmRrcConnResumeTimeDistrBr {
      type uint32;
    }
    leaf pmRadioRecInterferencePwrPrb19 {
      type uint32;
      config false;
    }
    leaf-list pmErabRelAbnormalEnbActGbrArp {
      type uint32;
    }
    leaf-list pmRrcConnEstabFailCellLatencyCe {
      type uint32;
    }
    leaf pmPdcpPktDiscDlPelrUu {
      type uint32;
      config false;
    }
    leaf pmErabEstabFailAddedOngoingProc {
      type uint32;
      config false;
    }
    leaf pmRaContResAndRrcRsp {
      type uint32;
      config false;
    }
    leaf-list pmPdcpPktDiscDlAqmQci {
      type uint32;
    }
    leaf pmRadioUeRepCqiSubband3Sum {
      type uint32;
      config false;
    }
    leaf pmRrcConnEstabSuccMoVoice {
      type uint32;
      config false;
    }
    leaf pmUeCtxtRelAbnormalEnb {
      type uint32;
      config false;
    }
    leaf pmFlexMacHarqUl1 {
      type ietfyang:mac-address;
      config false;
    }
    leaf pmEndcRelMnMcgRelocAtt {
      type uint32;
      config false;
    }
    leaf pmUeCtxtRetrReestFailShortMacVer {
      type ietfyang:mac-address;
      config false;
      status deprecated;
      description "MOM flags: noNotification.";
    }
    leaf pmHoPrepRejInLicMultiErab {
      type uint32;
      config false;
    }
    leaf pmRadioThpVolDlScellEran {
      type uint32;
      config false;
    }
    leaf pmActiveUeUlPreschedData {
      type ietfyang:mac-address;
      config false;
    }
    leaf pmPwsCmasRepReq {
      type uint32;
      config false;
    }
    leaf pmFlexMcPttQualityRbUlOk {
      type uint32;
      config false;
    }
    leaf pmUeCtxtRelSCEUtraA2Rsrq {
      type uint32;
      config false;
    }
    leaf pmUeThpVolUl {
      type uint32;
      config false;
    }
    leaf-list pmErabRelAbnormalEnbCdtQci {
      type uint32;
    }
    leaf-list pmPdcpPktDiscDlPelrUuQci {
      type uint32;
    }
    leaf pmPdcpVolUlSrb {
      type uint32;
      config false;
    }
    leaf pmRrcConnReestAtt {
      type uint32;
      config false;
    }
    leaf-list pmMacUeThpDlDistr {
      type ietfyang:mac-address;
      description "MOM flags: noNotification.";
    }
    leaf pmSinrWithPimAvoidOffSum {
      type uint32;
      config false;
    }
    leaf pmPdcchCceUsedUl {
      type uint32;
      config false;
    }
    leaf pmPwrBoostSuccLowCovUe {
      type uint32;
      config false;
    }
    leaf pmRrcConnSubsGroupSamp {
      type uint32;
      config false;
    }
    leaf pmZtemporary234 {
      type uint32;
      config false;
    }
    leaf-list pmRrcConnReestAttQci {
      type uint32;
    }
    leaf pmAcBarringEmSpecialAc {
      type ietfyang:mac-address;
      config false;
    }
    leaf pmRrcConnCe0CellLevMax {
      type int32;
      config false;
    }
    leaf pmFlexMacSkipUlDtxPresched {
      type ietfinet:ip-address;
      config false;
    }
    leaf pmRrcConnRelRlcFail {
      type uint32;
      config false;
    }
    leaf pmFlexMacHarqDlDtx256qam {
      type ietfyang:mac-address;
      config false;
    }
    leaf pmRrcConnEstabFailDuIntens {
      type uint32;
      config false;
    }
    leaf pmPucchCqiResShortUtilCell {
      type int32;
      config false;
    }
    leaf pmUeCtxtEstabSucc {
      type uint32;
      config false;
    }
    leaf pmDlAssigsWithUnknownReceptionSCell {
      type uint32;
      config false;
    }
    leaf-list pmMacUeBitRateRecommDlNonMcPttDistr {
      type ietfyang:mac-address;
    }
    leaf-list pmRadioUeRepTm4Rank1PmiDistr {
      type uint32;
    }
    leaf pmRrcConnEstabFailDynUeAdmCtrlPa {
      type uint32;
      config false;
    }
    leaf pmUeCtxtFetchSuccS1HoPrep {
      type uint32;
      config false;
    }
    leaf pmMacHarqUlFail64Qam {
      type ietfyang:mac-address;
      config false;
    }
    leaf pmSchedAdpReTxUlRsvdRegion {
      type uint32;
      config false;
    }
    leaf pmCellDownLockAuto {
      type uint32;
      config false;
    }
    leaf pmZtemporary32 {
      type uint32;
      config false;
    }
    leaf-list pmRadioTxRankDistr {
      type uint32;
    }
    leaf-list pmRrcConnReestSuccQci {
      type uint32;
    }
    leaf-list pmZtemporary231Compr {
      type uint32;
    }
    leaf-list pmRrcConnReestFailCellLatencyCe {
      type uint32;
    }
    leaf pmEndcRelMnMcgRelocSucc {
      type uint32;
      config false;
    }
    leaf pmNumDlPotentialPktLossInd {
      type uint32;
      config false;
    }
    leaf pmFlexZtemporary10 {
      type uint32;
      config false;
    }
    leaf pmFlexMacHarqDl1 {
      type ietfyang:mac-address;
      config false;
    }
    leaf pmRadioRecInterferencePwrPrb5 {
      type uint32;
      config false;
    }
    leaf-list pmErabRelAbnormalEnbActArp {
      type uint32;
    }
    leaf pmRadioRecInterferencePwrPrb20 {
      type uint32;
      config false;
    }
    leaf pmAcBarringEmSpecAcPlmn3 {
      type ietfyang:mac-address;
      config false;
    }
    leaf pmRadioRecInterferencePwrPrb40 {
      type uint32;
      config false;
    }
    leaf pmZtemporary196 {
      type uint32;
      config false;
    }
    leaf-list pmErabEstabAttAddedHoOngoingQci {
      type uint32;
    }
    leaf pmAdjustAccessMpLoadCtrl {
      type uint32;
      config false;
    }
    leaf pmErabEndcScgMax {
      type int32;
      config false;
    }
    leaf pmMacHarqDlNack16qam {
      type ietfyang:mac-address;
      config false;
    }
    leaf pmMacTimeDlCatmEssShareEnforced {
      type ietfyang:mac-address;
      config false;
    }
    leaf pmMacHarqDlDtxQpsk {
      type ietfyang:mac-address;
      config false;
    }
    leaf pmFlexZtemporary8 {
      type uint32;
      config false;
    }
    leaf-list pmUeThpDlMbbFiltered2Distr {
      type uint32;
    }
    leaf pmRrcConnEstabFailCellIntensSwC {
      type uint32;
      config false;
    }
    leaf pmRaFailCbraMsg2Disc {
      type uint32;
      config false;
    }
    leaf pmCellHoPrepAttLteIntraFHybridCsg {
      type uint32;
      config false;
    }
    leaf pmMacHarqDlAck256qam {
      type ietfyang:mac-address;
      config false;
    }
    leaf pmRadioRecInterferencePwrPrb86 {
      type uint32;
      config false;
    }
    leaf pmZtemporary84 {
      type uint32;
      config false;
    }
    leaf pmPdcpPktDiscDlAqm {
      type uint32;
      config false;
    }
    leaf-list pmErabRelAllMmeQci {
      type uint32;
    }
    leaf pmHoPrepRejInDuSwC {
      type uint32;
      config false;
    }
    leaf pmZtemporary160 {
      type uint32;
      config false;
    }
    leaf-list pmAcBarringVideoSpecialAcDistr {
      type ietfyang:mac-address;
    }
    leaf pmZtemporary149 {
      type uint32;
      config false;
    }
    leaf-list pmRrcConnResumeFailDuSwCCe {
      type uint32;
    }
    leaf pmZtemporary200 {
      type uint32;
      config false;
    }
    leaf pmEndcUaiRecOverheatingMiti {
      type uint32;
      config false;
    }
    leaf pmRadioRecInterferencePwrPrb30 {
      type uint32;
      config false;
    }
    leaf pmZtemporary172 {
      type uint32;
      config false;
    }
    leaf pmOocUesLevSum {
      type uint32;
      config false;
    }
    leaf pmPrbUsedDlBcch {
      type uint32;
      config false;
    }
    leaf pmRlcDelayTimeDl2 {
      type uint32;
      config false;
    }
    leaf pmFlexHoPrepRejInUlThres {
      type uint32;
      config false;
      status deprecated;
      description "MOM flags: noNotification.";
    }
    leaf-list pmRaAttCbraBrCe0Distr {
      type uint32;
    }
    leaf-list pmAccessClassBarringModPlmn2Distr {
      type ietfyang:mac-address;
    }
    leaf pmPrbAvailUlPuschLowRegion {
      type uint32;
      config false;
    }
    leaf pmUeCtxtRelNaccCsfbWcdmaEm {
      type uint32;
      config false;
    }
    leaf pmFlexErabRelAbnormalEnbGbr {
      type uint32;
      config false;
    }
    leaf-list pmSinrPuschDistr {
      type uint32;
    }
    leaf-list pmPrbUtilDlCellResource17Distr {
      type uint32;
      description "MOM flags: noNotification.";
    }
    leaf-list pmAccessClassBarringMosPlmn1Distr {
      type ietfyang:mac-address;
    }
    leaf pmUeCtxtFetchAttEndcSetup {
      type uint32;
      config false;
    }
    leaf pmRadioRecInterferencePwrPrb67 {
      type uint32;
      config false;
    }
    leaf pmErabRelAbnormalEnbUeLost {
      type uint32;
      config false;
    }
    leaf pmSchedTtiCellUlResAllocSwitched {
      type uint32;
      config false;
    }
    leaf pmRaAccHarqFailWithinContRes {
      type uint32;
      config false;
    }
    leaf pmRadioRecInterferencePwrPrb52 {
      type uint32;
      config false;
    }
    leaf pmLbEvalExpiredUe {
      type uint32;
      config false;
    }
    leaf-list pmPdcpLatTimeDlNoDrxSyncQci {
      type uint32;
    }
    leaf pmFlexErabRelAbnormalEnbAct {
      type uint32;
      config false;
    }
    leaf pmRadioRecInterferencePwrPrb17 {
      type uint32;
      config false;
    }
    leaf pmRadioThpVolDl7ccPCell {
      type uint32;
      config false;
    }
    leaf pmErabModFailLic {
      type uint32;
      config false;
    }
    leaf-list pmRadioUeOutLoopAdjDistr {
      type uint32;
    }
    leaf pmZtemporary229 {
      type uint32;
      config false;
    }
    leaf pmDlAssigsWithDetHarqAckMcPtt {
      type uint32;
      config false;
    }
    leaf pmUlGrantsTransNonMcPtt {
      type uint32;
      config false;
    }
    leaf pmFlexCellHoExeAttGeran {
      type uint32;
      config false;
    }
    leaf-list pmErabEstabSuccAddedQci {
      type uint32;
    }
    leaf pmRadioRecInterferencePwrPrb47 {
      type uint32;
      config false;
    }
    leaf pmRadioRecInterferencePwrPrb51 {
      type uint32;
      config false;
    }
    leaf pmPrbUsedUlDtch {
      type uint32;
      config false;
    }
    leaf pmPrbStartPosChgUlNewTxResFair {
      type uint32;
      config false;
    }
    leaf-list pmAccessClassBarringVoicePlmn3Distr {
      type ietfyang:mac-address;
    }
    leaf-list pmPrbUtilDlCellResource12Distr {
      type uint32;
      description "MOM flags: noNotification.";
    }
    leaf pmRadioThpVolTxDlSCellExtLaa {
      type uint32;
      config false;
    }
    leaf-list pmActiveDrbDlSumQci {
      type ietfyang:mac-address;
    }
    leaf pmMacHarqDlAckComp {
      type ietfyang:mac-address;
      config false;
    }
    leaf-list pmUeCtxtResumeSuccCe {
      type uint32;
    }
    leaf-list pmAccessClassBarringCsfbDistr {
      type ietfyang:mac-address;
    }
    leaf pmUeCtxtRelSCGsmA2Rsrq {
      type uint32;
      config false;
    }
    leaf pmRrcSegmentAttUl {
      type uint32;
      config false;
    }
    leaf-list pmPdcchCceAggregationDlDistr {
      type uint32;
    }
    leaf pmFlexMacHarqUlDtx16qam {
      type ietfyang:mac-address;
      config false;
    }
    leaf pmRrcConnEstabFailBb {
      type uint32;
      config false;
    }
    leaf-list pmErabRelAbnormalEnbUeLostQci {
      type uint32;
    }
    leaf-list pmPuschMcsSubsGroup4Distr {
      type uint32;
    }
    leaf pmLbCellHighLoaded {
      type uint32;
      config false;
    }
    leaf pmPdcpPktDiscDlBbmLimit {
      type uint32;
      config false;
    }
    leaf pmFlexUeCtxtRelMmeAct {
      type uint32;
      config false;
    }
    leaf pmLaaConfiguredDlSamp {
      type uint32;
      config false;
    }
    leaf pmFlexMacTimeDlNoDrxNoSyncSamp {
      type ietfyang:mac-address;
      config false;
      status deprecated;
      description "MOM flags: noNotification.";
    }
    leaf-list pmErabEstabAttAddedQci {
      type uint32;
    }
    leaf pmZtemporary69 {
      type uint32;
      config false;
    }
    leaf pmRadioThpVolDl {
      type uint32;
      config false;
    }
    leaf pmRadioRecInterferencePwrPrb4 {
      type uint32;
      config false;
    }
    leaf pmUeCtxtRelAbnormalEnbOosPft {
      type uint32;
      config false;
    }
    leaf pmUeCtxtRelNormalEnbTuneOut {
      type uint32;
      config false;
    }
    leaf pmFlexMacHarqDlAckQpsk {
      type ietfyang:mac-address;
      config false;
    }
    leaf-list pmHoExeOutSuccQci {
      type uint32;
    }
    leaf pmUlGrantsShortSpsDetPusch {
      type uint32;
      config false;
    }
    leaf-list pmPuschMcsSubsGroup0Distr {
      type uint32;
    }
    leaf pmPdcpBitrateDlDrbMax {
      type int32;
      config false;
    }
    leaf pmRadioRecInterferencePwrPrb66 {
      type uint32;
      config false;
    }
    leaf pmMacHarqUlFailQpsk {
      type ietfyang:mac-address;
      config false;
    }
    leaf pmNasTransUlBrNoPdn {
      type uint32;
      config false;
    }
    leaf pmUeCtxtResumeSucc {
      type uint32;
      config false;
    }
    leaf pmRadioRecInterferencePwrPrb35 {
      type uint32;
      config false;
    }
    leaf-list pmErabRelNormalEnbActQci {
      type uint32;
    }
    leaf-list pmRrcConnQueueTimeDistr {
      type uint32;
    }
    leaf-list pmAcBarringVoiceSpecAcPlmn2Distr {
      type ietfyang:mac-address;
    }
    leaf pmRrcConnBr {
      type uint32;
      config false;
    }
    leaf pmUeCtxtRelNaccSCGsm {
      type uint32;
      config false;
    }
    leaf-list pmPdcpLatPktTransDlDrxSyncQci {
      type uint32;
    }
    leaf pmFlexMacHarqDl4 {
      type ietfyang:mac-address;
      config false;
    }
    leaf pmRrcConnEstabAttReattHpa {
      type uint32;
      config false;
    }
    leaf-list pmAcBarringModSpecAcPlmn3Distr {
      type ietfyang:mac-address;
    }
    leaf-list pmUeCtxtConnResumeAttCe {
      type uint32;
      description "MOM flags: noNotification.";
    }
    leaf-list pmPdcpInactSecDlMcPttDistr {
      type uint32;
    }
    leaf pmPrbUsedDlCatmSamp {
      type uint32;
      config false;
    }
    leaf pmRadioRecInterferencePwrPrb56 {
      type uint32;
      config false;
    }
    leaf pmRaFailCbraMsg1DiscSched {
      type uint32;
      config false;
    }
    leaf-list pmCellCceUtilization {
      type uint32;
    }
    leaf-list pmIdcUlCaVictimOffDistr {
      type uint32;
    }
    leaf pmFlexSchedActivityUeDl {
      type uint32;
      config false;
    }
    leaf-list pmPuschMcsSubsGroup3Distr {
      type uint32;
    }
    leaf pmRobustCallSetupDelayedNr {
      type uint32;
      config false;
    }
    leaf pmSessionTimeDrb {
      type uint32;
      config false;
    }
    leaf-list pmRrcConnSuspendFailMpMemCe {
      type uint32;
    }
    leaf-list pmSinrPucchDistr {
      type uint32;
    }
    leaf-list pmRrcConnEstabFailDynUeAdmCtrlPttCe {
      type uint32;
    }
    leaf pmRadioRecInterferencePwrPrb44 {
      type uint32;
      config false;
    }
    leaf pmRrcConnQueueAttMtaVoice {
      type uint32;
      config false;
    }
    leaf pmZtemporary246 {
      type uint32;
      config false;
    }
    leaf-list pmCaScheduledDl5ccSumDistr {
      type uint32;
    }
    leaf-list pmRlcSduRecUlVoipTtiBundling {
      type ietfinet:ip-address;
    }
    leaf-list pmErabRelAbnormalEnbArp {
      type uint32;
    }
    leaf pmFlexUeCtxtRelAbnormalEnbPe {
      type uint32;
      config false;
    }
    leaf pmTtiBundlingEnable {
      type uint32;
      config false;
    }
    leaf pmPtmInhibitImp {
      type uint32;
      config false;
    }
    leaf pmPrbAvailUlPucchSr {
      type uint32;
      config false;
    }
    leaf-list pmPdcpVolDlCmpHdrQci {
      type uint32;
    }
    leaf-list pmZtemporary226Compr {
      type uint32;
    }
    leaf pmPucchCqiResLongUtilCell {
      type int32;
      config false;
    }
    leaf pmZtemporary139 {
      type uint32;
      config false;
    }
    leaf-list pmMeasGapDurationDistr {
      type uint32;
    }
    leaf pmFlexMacLatTimeDlNoDrxNoSync {
      type ietfyang:mac-address;
      config false;
      status deprecated;
      description "MOM flags: noNotification.";
    }
    leaf pmFlexPdcpPktDiscDlPelrUu {
      type uint32;
      config false;
    }
    leaf pmPrbAvailUl {
      type uint32;
      config false;
    }
    leaf-list pmAcBarringVideoSpecAcPlmn2Distr {
      type ietfyang:mac-address;
    }
    leaf pmUeAdmCtrlPreventivePe {
      type uint32;
      config false;
    }
    leaf pmRadioThpVolTxDl5ccSCell {
      type uint32;
      config false;
    }
    leaf pmEndcSetupScgUeOverloadRej {
      type uint32;
      config false;
    }
    leaf-list pmExtendedAccessBarringBrDistr {
      type uint32;
      description "MOM flags: noNotification.";
    }
    leaf-list pmRrcConnResumeSuccCe {
      type uint32;
    }
    leaf pmFlexErabEstabFailResGbr {
      type uint32;
      config false;
    }
    leaf pmZtemporary140 {
      type uint32;
      config false;
    }
    leaf pmRrcConnCe2CellLevMax {
      type int32;
      config false;
    }
    leaf-list pmZtemporary59 {
      type uint32;
    }
    leaf pmUeExclThpUlSmallVol {
      type uint32;
      config false;
    }
    leaf-list pmErabEstabSuccAddedGbrArp {
      type uint32;
    }
    leaf pmUeCtxtFetchAttReconfErabMod {
      type uint32;
      config false;
    }
    leaf pmRrcConnEstabAttReatt {
      type uint32;
      config false;
    }
    leaf pmRadioRecInterferencePwrPrb93 {
      type uint32;
      config false;
    }
    leaf pmErabEstabAttInitPa {
      type uint32;
      config false;
    }
    leaf pmUeCtxtRelSCNrA2Rsrp {
      type uint32;
      config false;
    }
    leaf pmUeCtxtFetchAttX2HoExe {
      type uint32;
      config false;
    }
    leaf pmIdleModeRelDistrMediumLoad {
      type uint32;
      config false;
    }
    leaf-list pmRrcConnEstabFailCellIntensDLCCe {
      type uint32;
    }
    leaf pmRrcConnMaxPlmn5 {
      type int32;
      config false;
    }
    leaf pmNasTransferAttDlSrb2 {
      type uint32;
      config false;
    }
    leaf pmZtemporary110 {
      type uint32;
      config false;
    }
    leaf-list pmRrcLatencyConnReconfigDistr {
      type uint32;
    }
    leaf pmCgiMeasFailAnrPciConflict {
      type uint32;
      config false;
    }
    leaf-list pmMpdcchEcceAggregationDistr {
      type uint32;
    }
    leaf pmUeCtxtRelAbnormalEnbActCdt {
      type uint32;
      config false;
    }
    leaf-list pmLaaConfiguredDlInterEnbSumDistr {
      type uint32;
    }
    leaf-list pmPdcpInactSecDlNonMcPttDistr {
      type uint32;
    }
    leaf pmBadCovMiMultiFreqTo {
      type uint32;
      config false;
    }
    leaf-list pmPuschMcsDistr {
      type uint32;
    }
    leaf pmPrbUsedDlAilgTot {
      type uint32;
      config false;
    }
    leaf pmRadioThpResDl {
      type uint32;
      config false;
    }
    leaf pmRrcConnEstabFailLowCovUeAdmCtrl {
      type uint32;
      config false;
    }
    leaf pmRrcConnEstabAttEm {
      type uint32;
      config false;
    }
    leaf pmMpdcchPrbUsed {
      type uint32;
      config false;
      status deprecated;
      description "MOM flags: noNotification.";
    }
    leaf pmFlexMacHarqUlFail {
      type ietfyang:mac-address;
      config false;
    }
    leaf pmPucchSrMax {
      type int32;
      config false;
    }
    leaf-list pmRrcLatencyConnResumeDistr {
      type uint32;
    }
    leaf-list pmPuschRadioUeOutLoopAdjCe1Distr {
      type uint32;
    }
    leaf-list pmCaConfDlIcmSumDistr {
      type uint32;
    }
    leaf-list pmMacUeThpUlMbbHighVolDistr {
      type ietfyang:mac-address;
    }
    leaf pmPrbUsedUlAilgTot {
      type uint32;
      config false;
    }
    leaf pmZtemporary89 {
      type uint32;
      config false;
    }
    leaf-list pmZtemporary158Compr {
      type uint32;
    }
    leaf pmFlexMacHarqUlFail64qam {
      type ietfyang:mac-address;
      config false;
    }
    leaf-list pmErabRelAbnormalEnbQci {
      type uint32;
    }
    leaf-list pmErabRelAbnormalEnbPsPartFailQci {
      type uint32;
    }
    leaf-list pmPrbAvailUtilUlDistr {
      type uint32;
    }
    leaf pmConfigRejDlComp {
      type uint32;
      config false;
    }
    leaf-list pmMacUeBitRateRecommUlDistr {
      type ietfyang:mac-address;
    }
    leaf pmB1NrServTrigEvalReportRsrp {
      type ietfinet:port-number;
      config false;
    }
    leaf pmBadCovEvalReport {
      type ietfinet:port-number;
      config false;
    }
    leaf-list pmErabEstabAttAddedArp {
      type uint32;
    }
    leaf pmUlGrantsWithDetPuschNonMcPtt {
      type uint32;
      config false;
    }
    leaf-list pmPagRecordBrDistr {
      type uint32;
    }
    leaf pmInvalidPftNum {
      type uint32;
      config false;
    }
    leaf pmCaDeconfiguredMeasTo {
      type uint32;
      config false;
      status deprecated;
      description "MOM flags: noNotification.";
    }
    leaf pmCellHoExeAttLteIntraF {
      type uint32;
      config false;
    }
    leaf pmPdcpLatTimeDlDrxSync {
      type uint32;
      config false;
    }
    leaf pmUeCtxtRelSCGsmB2Rsrq {
      type uint32;
      config false;
    }
    leaf pmOocStateEntries {
      type uint32;
      config false;
    }
    leaf-list pmLcgThpTimeUlLcg {
      type uint32;
    }
    leaf pmFlexRrcConnReestSucc {
      type uint32;
      config false;
    }
    leaf pmFlexMacHarqDl2 {
      type ietfyang:mac-address;
      config false;
    }
    leaf pmFlexCellHoPrepAttUtranSrvcc {
      type uint32;
      config false;
    }
    leaf pmA5InterFHigherPrioEvalReport {
      type ietfinet:port-number;
      config false;
    }
    leaf-list pmInhibitImeisvFeature {
      type uint32;
    }
    leaf pmUeCategoryDowngraded {
      type uint32;
      config false;
    }
    leaf pmZtemporary85 {
      type uint32;
      config false;
    }
    leaf pmZtemporary71 {
      type uint32;
      config false;
    }
    leaf pmHoPrepRejInDynUeAdmCtrlPa {
      type uint32;
      config false;
    }
    leaf pmDlAssigsTransNDO {
      type uint32;
      config false;
    }
    leaf-list pmPimAvoidMutedPrbsDistr {
      type uint32;
    }
    leaf pmVoipQualityUeUlNok {
      type ietfinet:ip-address;
      config false;
    }
    leaf-list pmAcBarringMosSpecAcPlmn1Distr {
      type ietfyang:mac-address;
    }
    leaf-list pmMacHarqDlDtxDistr {
      type ietfyang:mac-address;
    }
    leaf pmFlexErabRelAbnormalEnbActPe {
      type uint32;
      config false;
    }
    leaf pmErabRelAbnormalEnbActUeLostOos {
      type uint32;
      config false;
    }
    leaf pmFlexMacTimeDlDrxSyncSamp {
      type ietfyang:mac-address;
      config false;
      status deprecated;
      description "MOM flags: noNotification.";
    }
    leaf pmDlAssigsWithUnknownReception {
      type uint32;
      config false;
    }
    leaf pmCellHoPrepSuccLteIntraFHybridCsg {
      type uint32;
      config false;
    }
    leaf pmPrbUsedDlBcchBr {
      type uint32;
      config false;
    }
    leaf pmUeCtxtRelAbnormalEnbActCdtAuto {
      type uint32;
      config false;
    }
    leaf pmRrcConnNs05Max {
      type int32;
      config false;
    }
    leaf pmFlexErabRelAbnormalMme {
      type uint32;
      config false;
    }
    leaf pmPrbAvailDl {
      type uint32;
      config false;
    }
    leaf-list pmRadioHomUeRepRankDistr {
      type uint32;
    }
    leaf pmUeExclThpUlShortTimeQciHighVol {
      type uint32;
      config false;
    }
    leaf-list pmRaMsg3NackCbraTxBrCe0Distr {
      type uint32;
    }
    leaf pmBbUeMeasAllocSucc {
      type uint32;
      config false;
    }
    leaf pmSchedActivityCellDl {
      type uint32;
      config false;
    }
    leaf pmErabMax {
      type int32;
      config false;
    }
    leaf pmPdcpVolUlDrb {
      type uint32;
      config false;
    }
    leaf pmRrcConnQueueAttMoVoice {
      type uint32;
      config false;
    }
    leaf pmCovGoodZoneSamp {
      type uint32;
      config false;
    }
    leaf pmFlexCellHoPrepSuccNr {
      type uint32;
      config false;
    }
    leaf pmRrcConnReconfSuccNoMobEarfcnEndc {
      type uint32;
      config false;
    }
    leaf pmLaaConfigurableDlSamp {
      type uint32;
      config false;
      status deprecated;
      description "MOM flags: noNotification.";
    }
    leaf pmFlexZtemporary18 {
      type uint32;
      config false;
    }
    leaf-list pmRaSuccTaZone1Distr {
      type uint32;
    }
    leaf pmUeCtxtFetchAttNasTransferDl {
      type uint32;
      config false;
    }
    leaf pmRadioRecInterferencePwrPrb73 {
      type uint32;
      config false;
    }
    leaf-list pmCaActivatedDl4ccSumDistr {
      type uint32;
    }
    leaf-list pmErabEstabSuccAddedArp {
      type uint32;
    }
    leaf-list pmAcBarringCsfbSpecAcPlmn3Distr {
      type ietfyang:mac-address;
    }
    leaf pmPrachPrbOffsetUpdate {
      type uint32;
      config false;
    }
    leaf-list pmPdcpVolDlDrbTransQci {
      type uint32;
    }
    leaf-list pmAcBarringModSpecAcPlmn1Distr {
      type ietfyang:mac-address;
    }
    leaf pmErabRelAbnormalMmeS1Reset {
      type uint32;
      config false;
    }
    leaf-list pmLaaConfiguredDlIcmSumDistr {
      type uint32;
    }
    leaf pmRadioThpVolTxDlSCellOffl {
      type uint32;
      config false;
    }
    leaf-list pmRaBackoffBrCe1Distr {
      type uint32;
    }
    leaf-list pmCellIntensRrcConnReleaseDistr {
      type uint32;
    }
    leaf pmErabRelAbnormalMmeAct {
      type uint32;
      config false;
    }
    leaf-list pmCellIntensRrcConnReqDistr {
      type uint32;
    }
    leaf pmUeCtxtSuspendAttBr {
      type uint32;
      config false;
    }
    leaf pmUeCtxtRelSCGsmUlSinr {
      type uint32;
      config false;
    }
    leaf pmRrcConnResumeFailLicActiveUsers {
      type uint32;
      config false;
      status deprecated;
      description "MOM flags: noNotification.";
    }
    leaf pmRrcConnReestFailCellLatency {
      type uint32;
      config false;
    }
    leaf pmUeExclThpDlShortDrb2 {
      type uint32;
      config false;
    }
    leaf-list pmRrcConnEstabAttModCe {
      type uint32;
    }
    leaf pmErabEstabAttInit {
      type uint32;
      config false;
    }
    leaf pmPdcpPktFwdDl {
      type uint32;
      config false;
    }
    leaf pmIdleModeRelDistrLowLoad {
      type uint32;
      config false;
    }
    leaf pmFlexMacHarqDlDtx64qam {
      type ietfyang:mac-address;
      config false;
    }
    leaf pmRrcConnResumeFailCellLatency {
      type uint32;
      config false;
    }
    leaf pmZtemporary173 {
      type uint32;
      config false;
    }
    leaf pmFlexPdcpVolDlDrbTrans {
      type uint32;
      config false;
    }
    leaf pmUeCtxtRetrReestSuccEndcUe {
      type uint32;
      config false;
    }
    leaf pmHoPrepAttIntraCell {
      type uint32;
      config false;
    }
    leaf pmErabRelAbnormalEnbActCdtAuto {
      type uint32;
      config false;
    }
    leaf pmZtemporary243 {
      type uint32;
      config false;
    }
    leaf-list pmRaBackoffBrCe0Distr {
      type uint32;
    }
    leaf pmEndcUaiRecOverheatingDisc {
      type uint32;
      config false;
    }
    leaf pmUeCtxtRelAbnormalEnbActOosPft {
      type uint32;
      config false;
    }
    leaf pmPrbUsedUlDcchBr {
      type uint32;
      config false;
    }
    leaf pmEndcRelScgUeOverheating {
      type uint32;
      config false;
    }
    leaf-list pmRaFailCbraMsg1DiscBrDistr {
      type uint32;
    }
    leaf pmFlexErabEstabSuccAddedGbr {
      type uint32;
      config false;
    }
    leaf pmFlexMacHarqDlNack64qam {
      type ietfyang:mac-address;
      config false;
    }
    leaf pmRadioRecInterferencePwrPrb9 {
      type uint32;
      config false;
    }
    leaf-list pmRrcLatencyConnSetupDistr {
      type uint32;
    }
    leaf pmFlexErabRelAbnormalEnb {
      type uint32;
      config false;
    }
    leaf pmRrcConnResumeFailCellIntensStat {
      type uint32;
      config false;
    }
    leaf pmWifiAccessAllowed {
      type uint32;
      config false;
    }
    leaf pmCellHoPrepSuccLowCovUe {
      type uint32;
      config false;
    }
    leaf-list pmErabRelNormalEnbQci {
      type uint32;
    }
    leaf-list pmDlSinrPdcchDistr {
      type uint32;
    }
    leaf pmPwsCmasRepSucc {
      type uint32;
      config false;
    }
    leaf pmZtemporary198 {
      type uint32;
      config false;
    }
    leaf pmPrbUsedDlCcchBr {
      type uint32;
      config false;
    }
    leaf pmRrcConnEstabLowCovUeSucc {
      type uint32;
      config false;
    }
    leaf pmMacHarqUlSucc16qam {
      type ietfyang:mac-address;
      config false;
    }
    leaf-list pmRrcConnReestFailDynUeAdmCtrlPttCe {
      type uint32;
    }
    leaf pmRrcConnEstabAtt {
      type uint32;
      config false;
    }
    leaf pmS1SigConnEstabFailMmeOvlMos {
      type uint32;
      config false;
    }
    leaf-list pmCaConfDlSCellTddSumDistr {
      type uint32;
    }
    leaf pmUeCtxtRelSCUtranA2Rsrp {
      type uint32;
      config false;
    }
    leaf pmRrcConnEstabAttMta {
      type uint32;
      config false;
    }
    leaf pmA2InterFHoHigherPrioConfig {
      type uint32;
      config false;
    }
    leaf pmFlexServiceTimeUe {
      type uint32;
      config false;
    }
    leaf-list pmRrcConnQueueSizeDistr {
      type uint32;
    }
    leaf-list pmAcBarringModSpecAcPlmn2Distr {
      type ietfyang:mac-address;
    }
    leaf pmZtemporary31 {
      type uint32;
      config false;
    }
    leaf-list pmUeThpUlDistr {
      type uint32;
    }
    leaf-list pmErabModAttQci {
      type uint32;
    }
    leaf-list pmCaScheduledDlIcmSum {
      type uint32;
      description "MOM flags: noNotification.";
    }
    leaf-list pmRrcFastReturnRaiTimeDistr {
      type uint32;
    }
    leaf-list pmPdcpInactSecDlVolteDistr {
      type uint32;
    }
    leaf pmUeExclThpUlShortTimeQciLowVol {
      type uint32;
      config false;
    }
    leaf-list pmCaConfDlSCellFddSumDistr {
      type uint32;
    }
    leaf pmFlexPdcpPktDiscDlAqm {
      type uint32;
      config false;
    }
    leaf-list pmRrcConnEstabAttReattCe {
      type uint32;
    }
    leaf pmFlexServiceTimeDrb {
      type uint32;
      config false;
    }
    leaf pmActiveUeUlMax {
      type ietfyang:mac-address;
      config false;
    }
    leaf pmMacHarqUlDtx64Qam {
      type ietfyang:mac-address;
      config false;
    }
    leaf-list pmErabRelNormalEnbGbrArp {
      type uint32;
    }
    leaf pmDrxSleepTimePft {
      type uint32;
      config false;
    }
    leaf pmUeCtxtRetainArpHigh {
      type uint32;
      config false;
    }
    leaf-list pmPdcpInactSecUlMcPttDistr {
      type uint32;
    }
    leaf pmDlAssigsDetHarqNonMcPttNDO {
      type uint32;
      config false;
    }
    leaf pmErabLevSamp {
      type uint32;
      config false;
    }
    leaf pmMacPdschEmptySubframe {
      type ietfyang:mac-address;
      config false;
    }
    leaf pmCellHoExeSuccLteInterFHybridCsg {
      type uint32;
      config false;
    }
    leaf pmS1SigConnEstabSuccEm {
      type uint32;
      config false;
    }
    leaf pmFlexMacHarqDl6 {
      type ietfyang:mac-address;
      config false;
    }
    leaf-list pmPrbUsedDlDtchVirtualCellsDistr {
      type uint32;
    }
    leaf-list pmCaConfigDlOffloadingSumDistr {
      type uint32;
      description "MOM flags: noNotification.";
    }
    leaf-list pmErabEstabAttRejAdmMsrAddedPttArp {
      type uint32;
    }
    leaf-list pmCellIntensHoReqDistr {
      type uint32;
    }
    leaf pmRrcConnResumeFailMpOverload {
      type uint32;
      config false;
    }
    leaf-list pmPagAttemptCountBrDistr {
      type uint32;
    }
    leaf pmB1NrBestCellEvalReport {
      type ietfinet:port-number;
      config false;
      status deprecated;
      description "MOM flags: noNotification.";
    }
    leaf pmFlexCellHoExeSuccLteInterF {
      type uint32;
      config false;
    }
    leaf pmZtemporary205 {
      type uint32;
      config false;
    }
    leaf pmFlexPrbUsedUlDtch {
      type uint32;
      config false;
    }
    leaf pmFlexZtemporary21 {
      type uint32;
      config false;
    }
    leaf-list pmLaaScheduledDlEranDistr {
      type uint32;
    }
    leaf-list pmErabRelAbnormalEnbHoQci {
      type uint32;
    }
    leaf-list pmZtemporary159Compr {
      type uint32;
    }
    leaf pmErabRelAbnormalMme {
      type uint32;
      config false;
    }
    leaf pmPucchSrCqiResCongCqi {
      type uint32;
      config false;
    }
    leaf pmMacHarqUlFail16qam {
      type ietfyang:mac-address;
      config false;
    }
    leaf pmRaFailCfraMsg1DiscSched {
      type uint32;
      config false;
    }
    leaf pmUeCtxtFetchSuccReconf {
      type uint32;
      config false;
    }
    leaf-list pmRaMsg2AttCbraBr {
      type uint32;
    }
    leaf-list pmLaaActivatedInterEnbSumDistr {
      type uint32;
    }
    leaf pmRadioRecInterferencePwrPrb80 {
      type uint32;
      config false;
    }
    leaf pmZtemporary201 {
      type uint32;
      config false;
    }
    leaf-list pmErabRelAbnormalEnbActQci {
      type uint32;
    }
    leaf pmFlexMacHarqUlSucc16qam {
      type ietfyang:mac-address;
      config false;
    }
    leaf pmFlexErabRelAbnormalEnbActOos {
      type uint32;
      config false;
      status deprecated;
      description "MOM flags: noNotification.";
    }
    leaf pmHoPrepRejInBearerAdmissionRej {
      type uint32;
      config false;
    }
    leaf pmErabEstabFailAddedErabIdInUse {
      type uint32;
      config false;
    }
    leaf pmUeCtxtRelSCGsmB2Rsrp {
      type uint32;
      config false;
    }
    leaf pmCellHoPrepSuccLteInterFEndcHo {
      type uint32;
      config false;
    }
    leaf pmZtemporary241 {
      type uint32;
      config false;
    }
    leaf pmRrcConnResumeFailMISigQCong {
      type uint32;
      config false;
    }
    leaf pmUeExclThpUlRelativeHighVol {
      type uint32;
      config false;
    }
    leaf pmPimAvoidMutedPrbsSum {
      type uint32;
      config false;
    }
    leaf pmRrcConnReconfAttNoMobSkipUlIua {
      type ietfinet:ip-address;
      config false;
    }
    leaf pmRadioRecInterferencePwrPrb14 {
      type uint32;
      config false;
    }
    leaf pmMacHarqDlDtx256qam {
      type ietfyang:mac-address;
      config false;
    }
    leaf pmErabEstabFailAddedLic {
      type uint32;
      config false;
    }
    leaf pmMiMimoSleepTerm {
      type uint32;
      config false;
    }
    leaf-list pmPdcpLatTimeDlCatMNoDrxSyncQci {
      type uint32;
    }
    leaf pmUeCtxtRelNormalEnbAct {
      type uint32;
      config false;
    }
    leaf-list pmActiveUeUlSumCe {
      type ietfyang:mac-address;
    }
    leaf pmHoPreventedProblematicCell {
      type uint32;
      config false;
    }
    leaf pmMacHarqDlDtx64qam {
      type ietfyang:mac-address;
      config false;
    }
    leaf pmRrcConnQueueAttEm {
      type uint32;
      config false;
    }
    leaf pmZtemporary5 {
      type uint32;
      config false;
    }
    leaf pmMutedPrbsWithPimAvoidOnSum {
      type uint32;
      config false;
    }
    leaf pmZtemporary142 {
      type uint32;
      config false;
    }
    leaf pmPrbUsedDlMpdcchPuschBr {
      type uint32;
      config false;
    }
    leaf pmPagReceivedBr {
      type uint32;
      config false;
    }
    leaf-list pmPdcpPktLostUlMissingPdus2Qci {
      type uint32;
    }
    leaf-list pmCaWaitGoodCov {
      type uint32;
    }
    leaf pmDlAssigsDetectedHarqNDO {
      type uint32;
      config false;
    }
    leaf pmPrbRemainedUsableUl {
      type uint32;
      config false;
    }
    leaf-list pmZtemporary58 {
      type uint32;
    }
    leaf pmActiveDrbDlDelayedLess {
      type ietfyang:mac-address;
      config false;
    }
    leaf pmFlexMacHarqDl5 {
      type ietfyang:mac-address;
      config false;
    }
    leaf pmEndcHoB1MeasRepUe {
      type uint32;
      config false;
    }
    leaf-list pmRrcConnEstabFailMmeOvlMosCe {
      type uint32;
    }
    leaf pmZtemporary60 {
      type uint32;
      config false;
    }
    leaf pmDynUeAdmCtrlQueueTo {
      type uint32;
      config false;
      status deprecated;
      description "MOM flags: noNotification.";
    }
    leaf pmRrcConnEstabFailLic {
      type uint32;
      config false;
    }
    leaf pmCellHoExeAttNrServTrig {
      type uint32;
      config false;
    }
    leaf pmCellHoExeAttLteIntraFCsg {
      type uint32;
      config false;
    }
    leaf pmZtemporary70 {
      type uint32;
      config false;
    }
    leaf pmCellHoPrepAttLteInterFCsg {
      type uint32;
      config false;
    }
    leaf pmFlexCellHoPrepSuccUtranSrvcc {
      type uint32;
      config false;
    }
    leaf pmB2BestCellEvalReportUl {
      type ietfinet:port-number;
      config false;
    }
    leaf pmPtmCellReservedMsr {
      type uint32;
      config false;
    }
    leaf-list pmErabEstabFailUeAdmLicRejArp {
      type uint32;
    }
    leaf pmCellHoExeAttLteInterFUeMeasRsrp {
      type uint32;
      config false;
    }
    leaf pmUeCtxtRelSCEUtra {
      type uint32;
      config false;
    }
    leaf pmFlexCellHoPrepSuccLteIntraF {
      type uint32;
      config false;
    }
    leaf-list pmMacUeBitRateSelectDlVoipDistr {
      type ietfinet:ip-address;
    }
    leaf pmFlexMacHarqDlAckComp {
      type ietfyang:mac-address;
      config false;
    }
    leaf-list pmRadioUeRepCqiDistr3 {
      type uint32;
    }
    leaf-list pmZtemporary233Compr {
      type uint32;
    }
    leaf pmVoipQualityUeUlOk {
      type ietfinet:ip-address;
      config false;
    }
    leaf pmRadioUeRepCqi2Subband0Sum {
      type uint32;
      config false;
    }
    leaf pmFlexActiveUeUlPresched {
      type uint32;
      config false;
    }
    leaf pmRaSuccCbra {
      type uint32;
      config false;
    }
    leaf pmCovCriticalZoneSamp {
      type uint32;
      config false;
    }
    leaf-list pmMacUeBitRateRecommUlNonMcPttDistr {
      type ietfyang:mac-address;
    }
    leaf pmPtmStopIncomingIflb {
      type uint32;
      config false;
    }
    leaf-list pmRrcConnResumeFailDynUeAdmCtrlPttCe {
      type uint32;
    }
    leaf pmClpcUlP0 {
      type uint32;
      config false;
    }
    leaf pmUeCtxtFetchSuccX2HoIn {
      type uint32;
      config false;
    }
    leaf pmRadioRecInterferencePwrPrb95 {
      type uint32;
      config false;
    }
    leaf pmErabEstabAttBrNoPdn {
      type uint32;
      config false;
    }
    leaf pmPrbOccupiedUlShortSps {
      type uint32;
      config false;
    }
    leaf pmErabEstabAttInitHpa {
      type uint32;
      config false;
    }
    leaf pmMacHarqUlSucc256Qam {
      type ietfyang:mac-address;
      config false;
    }
    leaf pmPdcpPktPdbUlOkVoip {
      type ietfinet:ip-address;
      config false;
    }
    leaf-list pmLaaScheduledDlIcmDistr {
      type uint32;
    }
    leaf-list pmErabRelAbnormalEnbActTnFailQci {
      type uint32;
    }
    leaf-list pmMacLatTimeDlQci {
      type ietfyang:mac-address;
      description "MOM flags: noNotification.";
    }
    leaf pmA5BestCellEvalReportRsrp {
      type ietfinet:port-number;
      config false;
    }
    leaf pmRadioRecInterferencePwrPrb32 {
      type uint32;
      config false;
    }
    leaf-list pmEabBrCatBDistr {
      type uint32;
    }
    leaf pmFlexPdcpVolDlDrb {
      type uint32;
      config false;
    }
    leaf pmFlexUeThpVolUlCa {
      type uint32;
      config false;
    }
    leaf pmFlexMacHarqUl7 {
      type ietfyang:mac-address;
      config false;
    }
    leaf pmZtemporary20 {
      type uint32;
      config false;
    }
    leaf pmUeCtxtRelSCEUtraA2Rsrp {
      type uint32;
      config false;
    }
    leaf pmDynUeAdmCtrlQueueAtt {
      type uint32;
      config false;
      status deprecated;
      description "MOM flags: noNotification.";
    }
    leaf pmZtemporary1 {
      type uint32;
      config false;
    }
    leaf pmZtemporary202 {
      type uint32;
      config false;
    }
    leaf pmMacVolUlResUe {
      type ietfyang:mac-address;
      config false;
    }
    leaf-list pmRadioRecEffectiveIpNPwrDistr {
      type ietfinet:ip-address;
    }
    leaf pmFlexCellHoExeAttNonMobIrat {
      type uint32;
      config false;
    }
    leaf pmFlexRadioThpVolumeUl {
      type uint32;
      config false;
    }
    leaf-list pmMbbHighVolUeSpEffDlSumCqi {
      type uint32;
    }
    leaf pmRrcConnMaxPlmn3 {
      type int32;
      config false;
    }
    leaf pmZtemporary24 {
      type uint32;
      config false;
    }
    leaf-list pmUeThp2DlDistr {
      type uint32;
    }
    leaf pmRadioThpVolDl5ccPCell {
      type uint32;
      config false;
    }
    leaf pmUeCtxtRelSCCdmaB2Rsrq {
      type uint32;
      config false;
    }
    leaf-list pmCaConfiguredDlIeNbSum {
      type uint32;
    }
    leaf pmMeasRepBadCovElc {
      type uint32;
      config false;
    }
    leaf-list pmMpdcchRepBrDistr {
      type uint32;
    }
    leaf pmRadioThpVolDlSCell {
      type uint32;
      config false;
    }
    leaf pmMeasRepDiscDlComp {
      type uint32;
      config false;
    }
    leaf pmIdcCapableMax {
      type int32;
      config false;
    }
    leaf pmHoPrepRejInLicMob {
      type uint32;
      config false;
    }
    leaf-list pmPdcpVolUlDrbQci {
      type uint32;
    }
    leaf pmCaDeconfiguredSCellChange {
      type uint32;
      config false;
    }
    leaf pmRrcConnResumeFailDuSwC {
      type uint32;
      config false;
    }
    leaf pmHoPrepSuccIntraCell {
      type uint32;
      config false;
    }
    leaf-list pmServiceTimeDrbQci {
      type uint32;
    }
    leaf-list pmMacUeBitRateSelectDlNonMcPttDistr {
      type ietfyang:mac-address;
    }
    leaf pmLongDrxCommandPft {
      type uint32;
      config false;
    }
    leaf pmRadioRecInterferencePwrPrb74 {
      type uint32;
      config false;
    }
    leaf-list pmUeThpDlDistr {
      type uint32;
    }
    leaf pmRrcConnEstabAttReattMta {
      type uint32;
      config false;
    }
    leaf-list pmLcgThpVolUlNonNs05Distr {
      type uint32;
    }
    leaf-list pmMacUeBitRateRecommDlMcPttDistr {
      type ietfyang:mac-address;
    }
    leaf pmUeCtxtRetrReestFailOngUeProc {
      type uint32;
      config false;
    }
    leaf pmErabEstabSuccInitHpa {
      type uint32;
      config false;
    }
    leaf pmFlexZtemporary19 {
      type uint32;
      config false;
    }
    leaf-list pmCaAssignedCsSetsDistr {
      type uint32;
    }
    leaf pmPdcpVolDlDrbTransPlmn4 {
      type uint32;
      config false;
    }
    leaf pmUeThpTimeDl {
      type uint32;
      config false;
    }
    leaf pmS1SigConnEstabSuccMod {
      type uint32;
      config false;
    }
    leaf pmErabRelNormalEnbUserInactivity {
      type uint32;
      config false;
    }
    leaf pmRadioUeRepCqiSubband6Sum {
      type uint32;
      config false;
    }
    leaf pmUeCtxtRelNaccSCWcdma {
      type uint32;
      config false;
    }
    leaf pmPrbUsedDlMax {
      type int32;
      config false;
    }
    leaf pmSchedActivityCellUlBr {
      type uint32;
      config false;
    }
    leaf-list pmPrbUtilDlCellResource13Distr {
      type uint32;
      description "MOM flags: noNotification.";
    }
    leaf pmErabUlRlcBufferCongHandl {
      type uint32;
      config false;
    }
    leaf pmFlexZtemporary22 {
      type uint32;
      config false;
    }
    leaf pmUeCtxtRelCsfbMeasTO1xRtt {
      type uint32;
      config false;
    }
    leaf pmCellHoPrepSuccLteInterFCsg {
      type uint32;
      config false;
    }
    leaf pmRrcConnReestFailDynUeAdmCtrlPtt {
      type uint32;
      config false;
    }
    leaf pmFlexSessionTimeDrb {
      type uint32;
      config false;
    }
    leaf-list pmMacUeBitRateRecommDlVoipDistr {
      type ietfinet:ip-address;
    }
    leaf-list pmPdcchMsg2PwrBoostDistr {
      type uint32;
    }
    leaf pmFlexPdcpPktDiscDlHo {
      type uint32;
      config false;
    }
    leaf pmFlexCellHoExeSuccLteIntraF {
      type uint32;
      config false;
    }
    leaf-list pmErabEstabAttRejAdmMsrInitRpid {
      type uint32;
    }
    leaf pmUeCtxtRelAbnormalMmeAct {
      type uint32;
      config false;
    }
    leaf pmMacHarqUlDtx256Qam {
      type ietfyang:mac-address;
      config false;
    }
    leaf pmFlexErabRelNormalEnbAct {
      type uint32;
      config false;
      status deprecated;
      description "MOM flags: noNotification.";
    }
    leaf pmRadioUeRepCqi2SubbandSamp {
      type uint32;
      config false;
    }
    leaf pmZtemporary237 {
      type uint32;
      config false;
    }
    leaf pmRrcSegmentSuccUl {
      type uint32;
      config false;
    }
    leaf pmFlexErabEstabAttAddedGbr {
      type uint32;
      config false;
    }
    leaf pmRadioRecInterferencePwrPrb48 {
      type uint32;
      config false;
    }
    leaf pmFlexRadioThpVolumeDl {
      type uint32;
      config false;
    }
    leaf pmRrcConnEstabFailMISigQCong {
      type uint32;
      config false;
    }
    leaf pmOocStateExits {
      type uint32;
      config false;
    }
    leaf-list pmErabReestAttRejAdmMsrPttArp {
      type uint32;
    }
    leaf pmCellCatmEssShareDlMax {
      type int32;
      config false;
    }
    leaf-list pmRrcConnResumeFallbackAttCe {
      type uint32;
    }
    leaf pmBbUeMeasAllocAtt {
      type uint32;
      config false;
    }
    leaf pmFlexErabRelAbnormalMmeAct {
      type uint32;
      config false;
    }
    leaf pmFlexMacSkipUlDtxDynamic {
      type ietfinet:ip-address;
      config false;
    }
    leaf pmPucchSrCqiResCongSr {
      type uint32;
      config false;
    }
    leaf pmZtemporary161 {
      type uint32;
      config false;
    }
    leaf pmPwsEtwsSecReq {
      type uint32;
      config false;
    }
    leaf-list pmLaaConfigurableDlSum {
      type uint32;
      description "MOM flags: noNotification.";
    }
    leaf pmRadioUeRepCqiSubband5Sum {
      type uint32;
      config false;
    }
    leaf pmRaUnassignedCfraFalse {
      type uint32;
      config false;
    }
    leaf pmFlexErabRelAbnormalMmeActGbr {
      type uint32;
      config false;
    }
    leaf pmUeMeasAttCsfb1xRtt {
      type uint32;
      config false;
    }
    leaf pmFlexPdcpLatTimeDl {
      type uint32;
      config false;
    }
    leaf pmZtemporary127 {
      type uint32;
      config false;
    }
    leaf pmRadioRecInterferencePwrPrb43 {
      type uint32;
      config false;
    }
    leaf pmZtemporary197 {
      type uint32;
      config false;
    }
    leaf pmMacVolUlResUeLastTti {
      type ietfyang:mac-address;
      config false;
    }
    leaf pmFlexMacHarqUlFailIua16qam {
      type ietfyang:mac-address;
      config false;
    }
    leaf-list pmPdcchTargetBlerPcellDistr {
      type uint32;
    }
    leaf-list pmZtemporary82 {
      type uint32;
    }
    leaf pmZtemporary128 {
      type uint32;
      config false;
    }
    leaf pmRlcArqDlNack {
      type uint32;
      config false;
    }
    leaf-list pmAccessClassBarringCsfbPlmn1Distr {
      type ietfyang:mac-address;
    }
    leaf pmZtemporary203 {
      type uint32;
      config false;
    }
    leaf pmRrcConnSuspendFailMpMem {
      type uint32;
      config false;
    }
    leaf pmPdcchResyncSuccCe0Br {
      type uint32;
      config false;
    }
    leaf pmIdleModeRelDistrHighLoad {
      type uint32;
      config false;
    }
    leaf pmUeCtxtRelAbnormalEnbCdtAutoPnr {
      type uint32;
      config false;
    }
    leaf pmUeCtxtFetchSuccNasTransferDl {
      type uint32;
      config false;
    }
    leaf-list pmHoPrepRejInMpMemCe {
      type uint32;
      description "MOM flags: noNotification.";
    }
    leaf pmErabBrSum {
      type uint32;
      config false;
    }
    leaf pmPagEdrxReceivedBr {
      type uint32;
      config false;
    }
    leaf-list pmLcgThpVolUlLcg {
      type uint32;
    }
    leaf pmRadioRecInterferencePwrPrb46 {
      type uint32;
      config false;
    }
    leaf pmMacHarqUlDtx16qam {
      type ietfyang:mac-address;
      config false;
    }
    leaf pmRrcConnEstabSuccMod {
      type uint32;
      config false;
    }
    leaf pmMacHarqDlNack256qam {
      type ietfyang:mac-address;
      config false;
    }
    leaf pmAnrNrNoActionTooWeak {
      type uint32;
      config false;
    }
    leaf-list pmErabRelNormalEnbActArp {
      type uint32;
    }
    leaf pmPrbAvailUlPuschCenterRegion {
      type uint32;
      config false;
    }
    leaf-list pmMacUeBitRateSelectUlVoipDistr {
      type ietfinet:ip-address;
    }
    leaf pmZtemporary147 {
      type uint32;
      config false;
    }
    leaf pmRadioRecInterferencePwrPrb36 {
      type uint32;
      config false;
    }
    leaf-list pmPagDiscardedCe {
      type uint32;
      description "MOM flags: noNotification.";
    }
    leaf-list pmCaScheduledDl6ccSumDistr {
      type uint32;
    }
    leaf pmUeExclThpDlQciShortDrb {
      type uint32;
      config false;
    }
    leaf pmFastPucchAssignPft {
      type uint32;
      config false;
    }
    leaf pmZtemporary199 {
      type int32;
      config false;
    }
    leaf pmMacUeThpVolDl {
      type ietfyang:mac-address;
      config false;
      status deprecated;
      description "MOM flags: noNotification.";
    }
    leaf pmZtemporary25 {
      type uint32;
      config false;
    }
    leaf pmAnrCandNrelCgiAdd {
      type uint32;
      config false;
    }
    leaf pmDynUeAdmCtrlQueueOverflow {
      type uint32;
      config false;
      status deprecated;
      description "MOM flags: noNotification.";
    }
    leaf-list pmPrbUtilDlCellResource22Distr {
      type uint32;
      description "MOM flags: noNotification.";
    }
    leaf pmIpnWithPimAvoidOnSum {
      type ietfinet:ip-address;
      config false;
    }
    leaf pmHoPrepOutS1RejInvalidIntraFHybridCsg {
      type uint32;
      config false;
    }
    leaf pmCovSearchZoneSamp {
      type uint32;
      config false;
    }
    leaf pmUlGrantsTransVolte {
      type uint32;
      config false;
    }
    leaf pmRrcConnReestSuccOthVend {
      type uint32;
      config false;
    }
    leaf-list pmErabRelAbnormalEnbActCdtAutoPnrQci {
      type uint32;
    }
    leaf pmZtemporary204 {
      type uint32;
      config false;
    }
    leaf pmRadioRecInterferencePwrPrb55 {
      type uint32;
      config false;
    }
    leaf pmMacHarqDlAck64qam {
      type ietfyang:mac-address;
      config false;
    }
    leaf pmZtemporary120 {
      type uint32;
      config false;
    }
    leaf-list pmRrcConnEstabSuccDtaCe {
      type uint32;
    }
    leaf-list pmMacUeBitRateSelectUlMcPttDistr {
      type ietfyang:mac-address;
    }
    leaf-list pmPagMpdcchRepDistr {
      type uint32;
    }
    leaf-list pmErabRelAbnormalMmeActQci {
      type uint32;
    }
    leaf pmFlexMacHarqUlSucc64qam {
      type ietfyang:mac-address;
      config false;
    }
    leaf pmRrcConnNs05Sum {
      type uint32;
      config false;
    }
    leaf pmZtemporary7 {
      type uint32;
      config false;
    }
    leaf pmIdleModeRelDistrLowMediumLoad {
      type uint32;
      config false;
    }
    leaf pmErabRelQci1EmInactTimer {
      type uint32;
      config false;
    }
    leaf pmFlexMacTimeUlResUe {
      type ietfyang:mac-address;
      config false;
    }
    leaf pmZtemporary8 {
      type uint32;
      config false;
    }
    leaf pmRadioThpVolDlSCellIcm {
      type uint32;
      config false;
    }
    leaf pmCovGoodZoneSum {
      type uint32;
      config false;
    }
    leaf pmRrcConnMaxPlmn2 {
      type int32;
      config false;
    }
    leaf pmRrcConnEstabFailMpMem {
      type uint32;
      config false;
    }
    leaf pmCellHoExeAttLteInterFUeMeas {
      type uint32;
      config false;
    }
    leaf pmFlexErabRelNormalEnb {
      type uint32;
      config false;
    }
    leaf pmRadioUeRepCqi2Subband12Sum {
      type uint32;
      config false;
    }
    leaf pmZtemporary15 {
      type uint32;
      config false;
    }
    leaf pmMacPdcchBlockingPuschTti {
      type ietfyang:mac-address;
      config false;
    }
    leaf pmErabBrSamp {
      type uint32;
      config false;
    }
    leaf pmCriticalBorderEvalReportRsrp {
      type ietfinet:port-number;
      config false;
    }
    leaf pmErabRelMme {
      type uint32;
      config false;
    }
    leaf pmFlexErabEstabAttInit {
      type uint32;
      config false;
    }
    leaf pmUeThpTimeDlCa {
      type uint32;
      config false;
    }
    leaf-list pmPrbUtilDlCellResource7Distr {
      type uint32;
      description "MOM flags: noNotification.";
    }
    leaf pmActiveUeUlSum {
      type ietfyang:mac-address;
      config false;
    }
    leaf-list pmZtemporary191 {
      type uint32;
    }
    leaf-list pmRrcConnResumeFallbackSuccCe {
      type uint32;
    }
    leaf pmActiveUeDrbSamp {
      type ietfyang:mac-address;
      config false;
    }
    leaf pmMacHarqDlAckQpsk {
      type ietfyang:mac-address;
      config false;
    }
    leaf pmFlexSessionTimeUe {
      type uint32;
      config false;
    }
    leaf pmPrbUsedUlPuschHighRegionDtch {
      type uint32;
      config false;
    }
    leaf pmPrbUsedDlReTrans {
      type uint32;
      config false;
    }
    leaf pmRadioThpVolTxDl6ccSCell {
      type uint32;
      config false;
    }
    leaf pmFlexErabRelMmeAct {
      type uint32;
      config false;
    }
    leaf pmFlexUeCtxtRelAbnormalEnb {
      type uint32;
      config false;
    }
    leaf-list pmPuschMcsSubsGroup9Distr {
      type uint32;
    }
    leaf-list pmLcgThpTimeUlNonNs05Distr {
      type uint32;
    }
    leaf-list pmRadioRecInterferencePwrPucch {
      type uint32;
    }
    leaf pmFlexCellHoExeAttNonMobLte {
      type uint32;
      config false;
    }
    leaf pmMutedPrbsWithPimAvoidOnSamp {
      type uint32;
      config false;
    }
    leaf-list pmErabRelNormalEnbUserInactivityQci {
      type uint32;
    }
    leaf pmRadioRecInterferencePwrPrb16 {
      type uint32;
      config false;
    }
    leaf pmIpnWithPimAvoidOffSum {
      type ietfinet:ip-address;
      config false;
    }
    leaf pmUeCtxtResumeAtt {
      type uint32;
      config false;
    }
    leaf pmUeCapabilityGnss {
      type uint32;
      config false;
    }
    leaf pmFlexZtemporary15 {
      type uint32;
      config false;
    }
    leaf pmZtemporary10 {
      type uint32;
      config false;
    }
    leaf pmRrcConnMaxEndc2 {
      type int32;
      config false;
    }
    leaf pmCellHoExeAttLteIntraFAfterResync {
      type uint32;
      config false;
    }
    leaf pmFlexErabRelMmeGbr {
      type uint32;
      config false;
    }
    leaf pmPrbUsedDlCatmSum {
      type uint32;
      config false;
      status deprecated;
      description "MOM flags: noNotification.";
    }
    leaf pmRrcConnCe3CellLevMax {
      type int32;
      config false;
    }
    leaf-list pmPrbUtilUl {
      type uint32;
    }
    leaf pmRrcConnReconfAttNoMobDlComp {
      type uint32;
      config false;
    }
    leaf pmFlexZtemporary1 {
      type uint32;
      config false;
    }
    leaf pmZtemporary194 {
      type uint32;
      config false;
    }
    leaf pmDlAssigsWithUnknownReceptionVolte {
      type uint32;
      config false;
    }
    leaf pmRrcConnQueueAttHpa {
      type uint32;
      config false;
    }
    leaf pmRadioRecInterferencePwrPrb22 {
      type uint32;
      config false;
    }
    leaf pmUeCtxtFetchSuccS1HoPrepSrvccGeran {
      type uint32;
      config false;
    }
    leaf-list pmS1SigConnEstabSuccModCe {
      type uint32;
    }
    leaf pmRrcConnEstabFailDynUeAdmCtrlPtt {
      type uint32;
      config false;
    }
    leaf pmFlexMacHarqDlDtxQpsk {
      type ietfyang:mac-address;
      config false;
    }
    leaf pmFlexUeCtxtRelSCWcdma {
      type uint32;
      config false;
    }
    leaf-list pmCellIntensHoRrcConnReqDistr {
      type uint32;
      description "MOM flags: noNotification.";
    }
    leaf pmZtemporary6 {
      type uint32;
      config false;
    }
    leaf pmMacHarqDlNackComp {
      type ietfyang:mac-address;
      config false;
    }
    leaf-list pmCaConfDlSCellFddTddSumDistr {
      type uint32;
    }
    leaf pmFlexMacHarqDl7 {
      type ietfyang:mac-address;
      config false;
    }
    leaf pmUeCtxtSuspendAtt {
      type uint32;
      config false;
    }
    leaf pmPdcpPktReceivedDl {
      type uint32;
      config false;
    }
    leaf pmA5BestCellEvalReport {
      type ietfinet:port-number;
      config false;
    }
    leaf pmUeCtxtRelSCUtraUlSinr {
      type uint32;
      config false;
    }
    leaf pmUlGrantsWithDetectedPuschVolte {
      type uint32;
      config false;
    }
    leaf pmPdcpPktReceivedUl {
      type uint32;
      config false;
    }
    leaf pmRadioUeRepCqi2Subband7Sum {
      type uint32;
      config false;
    }
    leaf pmEndcSetupUeOverloadRej {
      type uint32;
      config false;
    }
    leaf pmErabRelAbnormalMmeExtIat {
      type uint32;
      config false;
    }
    leaf pmRadioThpResUl {
      type uint32;
      config false;
    }
    leaf-list pmCaConfDlSCellLaaSumDistr {
      type uint32;
    }
    leaf pmErabRelAbnormalEnbCdtAutoPnr {
      type uint32;
      config false;
    }
    leaf pmPrbUsedUlPuschHighRegionSrb {
      type uint32;
      config false;
    }
    leaf pmZtemporary116 {
      type uint32;
      config false;
    }
    leaf pmRadioRecInterferencePwrPrb53 {
      type uint32;
      config false;
    }
    leaf pmRrcConnTuneOutLevSum {
      type uint32;
      config false;
    }
    leaf pmErabRelAbnormalEnbPe {
      type uint32;
      config false;
    }
    leaf pmFlexPdcpVolDlDrbCa {
      type uint32;
      config false;
    }
    leaf pmErabRelAbnormalEnbActCdt {
      type uint32;
      config false;
    }
    leaf-list pmTaInitDistr {
      type uint32;
      description "MOM flags: noNotification.";
    }
    leaf-list pmRaFailCbraMsg1DiscSchedCe {
      type uint32;
    }
    leaf pmHoPrepRejInCellLatency {
      type uint32;
      config false;
    }
    leaf pmFlexUeThpTimeUl {
      type uint32;
      config false;
    }
    leaf-list pmS1SigConnEstabAttModCe {
      type uint32;
    }
    leaf pmCellHoExeAttLteInterFDtvm {
      type uint32;
      config false;
    }
    leaf pmFlexZtemporary9 {
      type uint32;
      config false;
    }
    leaf pmFlexMacHarqDl3 {
      type ietfyang:mac-address;
      config false;
    }
    leaf pmS1InitialUeMsgSendBack {
      type uint32;
      config false;
    }
    leaf-list pmPuschMcsSubsGroup1Distr {
      type uint32;
    }
    leaf pmFlexZtemporary6 {
      type uint32;
      config false;
    }
    leaf-list pmTaInit2Distr {
      type uint32;
    }
    leaf pmCaConfiguredMeasAtt {
      type uint32;
      config false;
    }
    leaf-list pmPdcpLatPktTransDlDrxNoSyncQci {
      type uint32;
    }
    leaf pmEndcSetupUeSuccNrRestricted {
      type uint32;
      config false;
    }
    leaf pmRohcUlDataDeconfiguredCid {
      type uint32;
      config false;
      status deprecated;
      description "MOM flags: noNotification.";
    }
    leaf-list pmPuschMcsSubsGroup7Distr {
      type uint32;
    }
    leaf-list pmPrbUtilDlCellResource11Distr {
      type uint32;
      description "MOM flags: noNotification.";
    }
    leaf pmActiveUeUlCe3Max {
      type ietfyang:mac-address;
      config false;
    }
    leaf-list pmPdcpLatPktTransDlCatMDrxSyncQci {
      type uint32;
    }
    leaf pmRrcConnEstabFailLowCovUeLic {
      type uint32;
      config false;
    }
    leaf-list pmUeCtxtSuspendEnbBuffCe {
      type uint32;
    }
    leaf pmErabEstabSuccInit {
      type uint32;
      config false;
    }
    leaf pmAcBarringEmSpecAcPlmn2 {
      type ietfyang:mac-address;
      config false;
    }
    leaf pmCellHoExeSuccLteInterFUeMeasRsrp {
      type uint32;
      config false;
    }
    leaf-list pmErabEstabAttRejAdmMsrAddedArp {
      type uint32;
    }
    leaf pmB1MeasRepEndcConfig {
      type uint32;
      config false;
    }
    leaf pmCellHoExeSuccLteIntraFAfterResync {
      type uint32;
      config false;
    }
    leaf pmErabRelNormalEnb {
      type uint32;
      config false;
    }
    leaf-list pmPdcchUlDtxWorseDistr {
      type uint32;
    }
    leaf pmNonMcPttQualityRbUlLowSampl {
      type uint32;
      config false;
    }
    leaf-list pmPdcpLatTimeDlQci {
      type uint32;
    }
    leaf pmFlexCellHoExeSuccUtran {
      type uint32;
      config false;
    }
    leaf-list pmErabVolteTimeDistr {
      type uint32;
    }
    leaf pmRrcConnReestSucc {
      type uint32;
      config false;
    }
    leaf-list pmCellUlSeUtilization {
      type uint32;
    }
    leaf pmRrcConnNs05RepeaterZoneSum {
      type uint32;
      config false;
    }
    leaf pmLaaCapableDlSamp {
      type uint32;
      config false;
    }
    leaf pmRrcConnQueueSucc {
      type uint32;
      config false;
    }
    leaf-list pmCaActivatedDlIcmSumDistr {
      type uint32;
    }
    leaf-list pmRrcConnEstabSuccMtaCe {
      type uint32;
    }
    leaf-list pmPrbUtilDlCellResource10Distr {
      type uint32;
      description "MOM flags: noNotification.";
    }
    leaf pmCellHoPrepAttLteInterFHybridCsg {
      type uint32;
      config false;
    }
    leaf pmMeasRepDlComp {
      type uint32;
      config false;
    }
    leaf pmBadCovSearchEvalReportUl {
      type ietfinet:port-number;
      config false;
    }
    leaf pmUeCtxtFetchAttReconfErabEstab {
      type uint32;
      config false;
    }
    leaf pmRrcConnEstabFailDynUeAdmCtrlMoVoice {
      type uint32;
      config false;
    }
    leaf pmMeasMissingNeighRel {
      type uint32;
      config false;
    }
    leaf pmRadioRecInterferencePwrPrb60 {
      type uint32;
      config false;
    }
    leaf pmUeCtxtRetrReestAtt {
      type uint32;
      config false;
    }
    leaf-list pmCaScheduledDlSum {
      type uint32;
    }
    leaf pmRadioRecInterferencePwrPrb69 {
      type uint32;
      config false;
    }
    leaf pmPrbUsedUlSamp {
      type uint32;
      config false;
    }
    leaf pmUeCtxtFetchSuccCgiMeas {
      type uint32;
      config false;
    }
    leaf pmErabEstabAttAddedCsfbSinr {
      type uint32;
      config false;
    }
    leaf pmRrcConnMaxPlmn1 {
      type int32;
      config false;
    }
    leaf pmMacHarqUlFail256Qam {
      type ietfyang:mac-address;
      config false;
    }
    leaf pmRrcConnEstabSuccGummeiNative {
      type uint32;
      config false;
    }
    leaf pmFlexErabEstabSuccInitGbr {
      type uint32;
      config false;
    }
    leaf pmFlexZtemporary3 {
      type uint32;
      config false;
    }
    leaf-list pmPrbUtilDlCellResource19Distr {
      type uint32;
      description "MOM flags: noNotification.";
    }
    leaf pmHoPrepSuccInMfbiPrimaryPrio {
      type ietfinet:ip-address;
      config false;
    }
    leaf pmMultiUserMimoSchedPrbDl {
      type uint32;
      config false;
    }
    leaf pmPagEdrxReceived {
      type uint32;
      config false;
    }
    leaf pmZtemporary235 {
      type uint32;
      config false;
    }
    leaf pmRadioRecInterferencePwrPrb7 {
      type uint32;
      config false;
    }
    leaf pmFlexCellHoPrepAttGeran {
      type uint32;
      config false;
    }
    leaf-list pmPrbUsedUlDtchQci {
      type uint32;
    }
    leaf pmPucchSrResMediumUtilCell {
      type int32;
      config false;
    }
    leaf pmCellHoExeSuccNrServTrig {
      type uint32;
      config false;
    }
    leaf-list pmHoExeOutAttQci {
      type uint32;
    }
    leaf-list pmErabLevRopStartQci {
      type uint32;
    }
    leaf pmFlexZtemporary4 {
      type uint32;
      config false;
    }
    leaf pmRrcConnEstabSuccMta {
      type uint32;
      config false;
    }
    leaf pmErabRelAbnormalEnbPsFail {
      type uint32;
      config false;
    }
    leaf pmUeCtxtRelAbnormalEnbCdt {
      type uint32;
      config false;
    }
    leaf pmErabEstabFailGbrDlEnb {
      type uint32;
      config false;
    }
    leaf-list pmErabEstabAttAddedCsfbQci {
      type uint32;
    }
    leaf pmUeExclThpDlShortDrb {
      type uint32;
      config false;
      status deprecated;
      description "MOM flags: noNotification.";
    }
    leaf pmPdcpBitrateUlDrbMin {
      type int32;
      config false;
    }
    leaf pmCellSleepTime {
      type uint32;
      config false;
    }
    leaf-list pmAccessClassBarringMosPlmn2Distr {
      type ietfyang:mac-address;
    }
    leaf pmRrcConnResumeSucc {
      type uint32;
      config false;
    }
    leaf pmHoPrepSuccInMfbiAdditionalPrio {
      type uint32;
      config false;
    }
    leaf pmErabRelAbnormalEnbActUeLost {
      type uint32;
      config false;
    }
    leaf pmPdcchResyncFail {
      type uint32;
      config false;
      status deprecated;
      description "MOM flags: noNotification.";
    }
    leaf pmWifiAccessDecisionByWic {
      type uint32;
      config false;
    }
    leaf-list pmAcBarringModSpecialAcDistr {
      type ietfyang:mac-address;
    }
    leaf-list pmZtemporary225Compr {
      type uint32;
    }
    leaf-list pmAccessClassBarringVideoDistr {
      type ietfyang:mac-address;
    }
    leaf pmIdcSamp {
      type uint32;
      config false;
    }
    leaf pmUeCtxtFetchSuccS1HoExeSrvccUtran {
      type uint32;
      config false;
    }
    leaf pmZtemporary150 {
      type uint32;
      config false;
    }
    leaf pmUeCtxtRelSCNrA2Rsrq {
      type uint32;
      config false;
    }
    leaf pmPucchSrResLongUtilCell {
      type int32;
      config false;
    }
    leaf pmDlAssigsTransNonMcPttNDO {
      type uint32;
      config false;
    }
    leaf-list pmCaActivatedDl7ccSumDistr {
      type uint32;
    }
    leaf pmRadioTbsPwrRestricted {
      type uint32;
      config false;
    }
    leaf-list pmCaScheduledUlSum {
      type uint32;
    }
    leaf pmUeCtxtFetchAttX2HoIn {
      type uint32;
      config false;
    }
    leaf-list pmRrcConnEstabFailCellIntensSwCCe {
      type uint32;
    }
    leaf pmB1NrServTrigEvalReport {
      type ietfinet:port-number;
      config false;
    }
    leaf pmA3InterFBestCellEvalReport {
      type ietfinet:port-number;
      config false;
    }
    leaf pmCovCriticalZoneSum {
      type uint32;
      config false;
    }
    leaf-list pmPuschRadioUeOutLoopAdjCe0Distr {
      type uint32;
    }
    leaf-list pmLaaActivatedSum {
      type uint32;
    }
    leaf pmRrcConnReconfAttNoMobEarfcnEndc {
      type uint32;
      config false;
    }
    leaf pmRaSuccSrOutOfSyncPft {
      type uint32;
      config false;
    }
    leaf pmRadioRecInterferencePwrPrb49 {
      type uint32;
      config false;
    }
    leaf pmUeExclThpDlVolteMbb {
      type uint32;
      config false;
      status deprecated;
      description "MOM flags: noNotification.";
    }
    leaf-list pmRrcConnEstabSuccMtaPagPrioDistr {
      type uint32;
    }
    leaf pmCaDeconfiguredVolte {
      type uint32;
      config false;
    }
    leaf pmPrbUsedDlDtchSCell {
      type uint32;
      config false;
    }
    leaf-list pmRrcFastReturnInactTimeDistr {
      type uint32;
    }
    leaf pmRrcConnEstabAttReattEm {
      type uint32;
      config false;
    }
    leaf pmRadioUeRepCqi2Subband5Sum {
      type uint32;
      config false;
    }
    leaf pmNonMcPttQualityRbUlOk {
      type uint32;
      config false;
    }
    leaf pmUeCtxtRelNaccCsfbWcdma {
      type uint32;
      config false;
    }
    leaf pmFlexMacHarqUlSucc256qam {
      type ietfyang:mac-address;
      config false;
    }
    leaf pmHoPrepRejInDuIntens {
      type uint32;
      config false;
    }
    leaf pmA1InterFHoHigherPrioEvalReport {
      type ietfinet:port-number;
      config false;
    }
    leaf pmS1SigConnEstabSuccHpa {
      type uint32;
      config false;
    }
    leaf pmUlGrantsDetPuschMcPttNDO {
      type uint32;
      config false;
    }
    leaf pmFlexPdcpPktDiscDlRbLimit {
      type uint32;
      config false;
    }
    leaf pmZtemporary115 {
      type uint32;
      config false;
    }
    leaf pmZtemporary238 {
      type uint32;
      config false;
    }
    leaf pmSchedTtiCellDl {
      type uint32;
      config false;
    }
    leaf pmFlexMacHarqUlFail256qam {
      type ietfyang:mac-address;
      config false;
    }
    leaf pmFlexZtemporary14 {
      type uint32;
      config false;
    }
    leaf-list pmCellIntensRrcConnSuspendDistr {
      type uint32;
    }
    leaf pmRrcConnEstabAttDta {
      type uint32;
      config false;
      status deprecated;
      description "MOM flags: noNotification.";
    }
    leaf-list pmCompUlDeltaSinrPuschDistr {
      type uint32;
    }
    leaf pmCellHoPrepAttLteIntraFCsg {
      type uint32;
      config false;
    }
    leaf pmZtemporary64 {
      type uint32;
      config false;
    }
    leaf pmRadioUeRepCqiSubbandSamp {
      type uint32;
      config false;
    }
    leaf pmEndcHoQualifiedUe {
      type uint32;
      config false;
    }
    leaf pmIdcUlCaCapableSum {
      type uint32;
      config false;
    }
    leaf pmFlexCellHoExeAttLteInterF {
      type uint32;
      config false;
    }
    leaf-list pmMacTimeDlSampQci {
      type ietfyang:mac-address;
      description "MOM flags: noNotification.";
    }
    leaf pmRadioRecInterferencePwrPrb25 {
      type uint32;
      config false;
    }
    leaf pmActiveUeDlMax {
      type ietfyang:mac-address;
      config false;
    }
    leaf pmRrcConnResumeFailBearerAdmRej {
      type uint32;
      config false;
    }
    leaf pmCpriExtDelayChange {
      type uint32;
      config false;
    }
    leaf-list pmSinrPdcchDistr {
      type uint32;
    }
    leaf pmHoPreventedNotInPlmnWLGeran {
      type uint32;
      config false;
    }
    leaf-list pmAcBarringVoiceSpecialAcDistr {
      type ietfyang:mac-address;
    }
    leaf pmCrsIcCapableSamp {
      type uint32;
      config false;
    }
    leaf pmPrbUsedUlPuschLowRegionDtch {
      type uint32;
      config false;
    }
    leaf pmSchedTtiCellUl {
      type uint32;
      config false;
    }
    leaf pmErabModFailOngoingProc {
      type uint32;
      config false;
    }
    leaf pmPdcpVolUlDrbPlmn0 {
      type uint32;
      config false;
    }
    leaf-list pmRaBackoffDistr {
      type uint32;
    }
    leaf-list pmMacUeThpUlMbbHighVolQciDistr {
      type ietfyang:mac-address;
    }
    leaf pmRlcPollRetxUl {
      type uint32;
      config false;
    }
    leaf-list pmCaActDlIeNbSum {
      type uint32;
    }
    leaf pmRadioUeRepCqiSubband0Sum {
      type uint32;
      config false;
    }
    leaf pmCellHoPrepSuccLteIntraFCsg {
      type uint32;
      config false;
    }
    leaf-list pmAccessClassBarringMosPlmn3Distr {
      type ietfyang:mac-address;
    }
    leaf pmHoExeAttIntraCell {
      type uint32;
      config false;
    }
    leaf-list pmRrcConnEstabSuccCe {
      type uint32;
    }
    leaf pmRrcConnReconfAttNoMob {
      type uint32;
      config false;
    }
    leaf pmHoPrepOutS1RejInvalidInterFCsg {
      type uint32;
      config false;
    }
    leaf pmRrcConnQueueSuccHpa {
      type uint32;
      config false;
    }
    leaf pmRadioThpVolDlSCellExt {
      type uint32;
      config false;
    }
    leaf pmUeCtxtRetrReestFailUeCtxtRel {
      type uint32;
      config false;
    }
    leaf pmFlexErabEstabAttAddedHoOngoing {
      type uint32;
      config false;
    }
    leaf pmRrcConnMaxPlmn6 {
      type int32;
      config false;
    }
    leaf-list pmPrbUtilDlCellResource6Distr {
      type uint32;
      description "MOM flags: noNotification.";
    }
    leaf-list pmPrbUtilDlCellResource1Distr {
      type uint32;
      description "MOM flags: noNotification.";
    }
    leaf-list pmPuschMcsSubsGroup8Distr {
      type uint32;
    }
    leaf pmRadioRecInterferencePwrPrb31 {
      type uint32;
      config false;
    }
    leaf pmRadioRecInterferencePwrPrb98 {
      type uint32;
      config false;
    }
    leaf-list pmMacUeThpUlMbbLowVolQciDistr {
      type ietfyang:mac-address;
    }
    leaf pmUeCtxtRelSCCdmaB2Rsrp {
      type uint32;
      config false;
    }
    leaf pmZtemporary30 {
      type uint32;
      config false;
    }
    leaf-list pmRrcConnReconfDataInactTimerCe {
      type uint32;
    }
    leaf pmCaDeconfiguredLostCoverage {
      type uint32;
      config false;
    }
    leaf pmUeCtxtRetrReestFailRreEval {
      type uint32;
      config false;
    }
    leaf pmUeExclThpDlVolte {
      type uint32;
      config false;
      status deprecated;
      description "MOM flags: noNotification.";
    }
    leaf pmRadioRecInterferencePwrPrb6 {
      type uint32;
      config false;
    }
    leaf-list pmHoPrepRejInAdmMsrPttArp {
      type uint32;
    }
    leaf pmOocStateExitsUeRel {
      type uint32;
      config false;
    }
    leaf pmBadCovMiMultiFreqSel {
      type uint32;
      config false;
    }
    leaf pmUeCtxtRelCsfbHoPrepFail1xRttEm {
      type uint32;
      config false;
    }
    leaf-list pmPimAvoidMissingReportDistr {
      type ietfinet:port-number;
    }
    leaf-list pmCaConfiguredDlSum {
      type uint32;
    }
    leaf pmFlexRadioThpVolDl {
      type uint32;
      config false;
      status deprecated;
      description "MOM flags: noNotification.";
    }
    leaf pmFlexPdcpPktDiscDlPelr {
      type uint32;
      config false;
    }
    leaf-list pmCaScheduledDl2ccSumDistr {
      type uint32;
    }
    leaf-list pmPdcpPktReceivedUlQci {
      type uint32;
    }
    leaf-list pmPrbUtilDlCellResource20Distr {
      type uint32;
      description "MOM flags: noNotification.";
    }
    leaf pmRohcEstabFailLic {
      type uint32;
      config false;
    }
    leaf pmCaConfiguredDlSamp {
      type uint32;
      config false;
    }
    leaf pmRrcConnQueueSuccEm {
      type uint32;
      config false;
    }
    leaf pmRrcConnLevSumUlOosCe0Br {
      type uint32;
      config false;
    }
    leaf pmFlexErabRelMme {
      type uint32;
      config false;
    }
    leaf-list pmCellIntensHoRrcConnReqResumeReqDistr {
      type uint32;
    }
    leaf-list pmRrcConnEstabFailDynUeAdmCtrlCe {
      type uint32;
    }
    leaf pmFlexSchedActivityCellDl {
      type uint32;
      config false;
    }
    leaf pmPdcpVolUlDrbPlmn3 {
      type uint32;
      config false;
    }
    leaf pmUeCtxtRelAbnormalEnbPeSrResPa {
      type uint32;
      config false;
    }
    leaf pmCellHoExeSuccLteIntraFTuneOut {
      type uint32;
      config false;
    }
    leaf-list pmAasSchedPrbDlHorizontalDistr {
      type uint32;
    }
    leaf pmCaConfiguredAiBasedSucc {
      type uint32;
      config false;
    }
    leaf pmFlexHoPrepRejOutUlThres {
      type uint32;
      config false;
    }
    leaf pmErabEstabSuccInitPa {
      type uint32;
      config false;
    }
    leaf pmDlAssigsTransSCell {
      type uint32;
      config false;
    }
    leaf pmVoipQualityUeUlLowSampl {
      type ietfinet:ip-address;
      config false;
    }
    leaf pmUeCtxtRelSCCdmaUlSinr {
      type uint32;
      config false;
    }
    leaf pmUeCtxtRelSrvccA2Critical1xRtt {
      type uint32;
      config false;
    }
    leaf pmFlexMacHarqUlSuccQpsk {
      type ietfyang:mac-address;
      config false;
    }
    leaf-list pmAasVerticalDistr {
      type uint32;
    }
    leaf pmCellHoExeSuccLteInterFMbms {
      type uint32;
      config false;
    }
    leaf-list pmRrcConnEstabAttReattModCe {
      type uint32;
    }
    leaf pmFlexCellHoPrepSuccNonMobIrat {
      type uint32;
      config false;
    }
    leaf-list pmRadioUeRepRankAggrDistr {
      type uint32;
      description "MOM flags: noNotification.";
    }
    leaf pmFlexZtemporary2 {
      type uint32;
      config false;
    }
    leaf pmMacSkipUlDtxDynamicVolte {
      type ietfinet:ip-address;
      config false;
      status deprecated;
      description "MOM flags: noNotification.";
    }
    leaf pmPrbUsedUlCatmSum {
      type uint32;
      config false;
    }
    leaf pmEndcSetupScgUeAttBufUl {
      type uint32;
      config false;
    }
    leaf pmIdcUlCaMax {
      type int32;
      config false;
    }
    leaf pmZtemporary111 {
      type uint32;
      config false;
    }
    leaf pmFlexPdcpVolUlDrb {
      type uint32;
      config false;
    }
    leaf-list pmZtemporary17Qci {
      type uint32;
    }
    leaf-list pmActiveUeDlSumCe {
      type ietfyang:mac-address;
    }
    leaf pmFlexCellHoPrepSucc1xRttSrvcc {
      type uint32;
      config false;
    }
    leaf pmMacTimeDlCatmEssShareSrb0Enforced {
      type ietfyang:mac-address;
      config false;
    }
    leaf pmErabRelAbnormalMmeCritCov {
      type uint32;
      config false;
    }
    leaf pmRrcConnEstabAttReattMod {
      type uint32;
      config false;
    }
    leaf-list pmRaSuccCbraBr {
      type uint32;
    }
    leaf-list pmRaAttTaZone2Distr {
      type uint32;
    }
    leaf pmRadioThpVolTxDlSCellLaa {
      type uint32;
      config false;
    }
    leaf pmCellDownUnlockMan {
      type uint32;
      config false;
    }
    leaf-list pmCaActivatedDlFddTddSum {
      type uint32;
    }
    leaf pmUeCtxtRelSCGsmA2Rsrp {
      type uint32;
      config false;
    }
    leaf pmDlAssigsTrans {
      type uint32;
      config false;
    }
    leaf pmRadioUeRepCqiSubband4Sum {
      type uint32;
      config false;
    }
    leaf pmMacCellThpTimeDl {
      type ietfyang:mac-address;
      config false;
      status deprecated;
      description "MOM flags: noNotification.";
    }
    leaf pmZtemporary141 {
      type uint32;
      config false;
    }
    leaf-list pmMacUeBitRateSelectDlDistr {
      type ietfyang:mac-address;
    }
    leaf pmPdcpVolUlDrbPlmn5 {
      type uint32;
      config false;
    }
    leaf pmZtemporary189 {
      type uint32;
      config false;
    }
    leaf pmErabRelAbnormalEnbActCdtAutoPnr {
      type uint32;
      config false;
    }
    leaf pmB1BestCellEvalReport {
      type ietfinet:port-number;
      config false;
    }
    leaf pmS1SigConnEstabAttEm {
      type uint32;
      config false;
    }
    leaf pmPrbUsedDlReTransCatm {
      type uint32;
      config false;
    }
    leaf pmRrcConnMaxPlmn0 {
      type int32;
      config false;
    }
    leaf-list pmCaConfDlSCellFddTddLaaSumDistr {
      type uint32;
    }
    leaf-list pmPdcpLatPktTransDlCatMNoDrxNoSyncQci {
      type uint32;
    }
    leaf pmCellHoPrepSuccLteInterFDtvm {
      type uint32;
      config false;
    }
    leaf pmZtemporary122 {
      type uint32;
      config false;
    }
    leaf pmRrcConnCatmMax {
      type int32;
      config false;
      status deprecated;
      description "MOM flags: noNotification.";
    }
    leaf-list pmErabRelDlInactGapQci {
      type uint32;
    }
    leaf pmTtiBundlingUeSum {
      type uint32;
      config false;
    }
    leaf pmCellHoPrepSuccLteInterFUtvm {
      type uint32;
      config false;
    }
    leaf pmZtemporary143 {
      type uint32;
      config false;
    }
    leaf pmUeCtxtRelCsfbTdScdmaEm {
      type uint32;
      config false;
    }
    leaf pmRaAttCbra {
      type uint32;
      config false;
    }
    leaf pmRrcConnEstabFailLicActiveUsers {
      type uint32;
      config false;
      status deprecated;
      description "MOM flags: noNotification.";
    }
    leaf pmDlAssigsTransVolteNDO {
      type uint32;
      config false;
    }
    leaf pmMacTimeUlCatmEssShareEnforced {
      type ietfyang:mac-address;
      config false;
    }
    leaf-list pmS1SigConnEstabAttMtaCe {
      type uint32;
    }
    leaf pmUeCtxtRelAbnormalMmeS1Reset {
      type uint32;
      config false;
    }
    leaf pmCellSleepFailUeCap {
      type uint32;
      config false;
    }
    leaf pmSessionTimeUe {
      type uint32;
      config false;
    }
    leaf pmRrcConnEstabSuccEm {
      type uint32;
      config false;
    }
    leaf pmPrbRemainedUl {
      type uint32;
      config false;
      status deprecated;
      description "MOM flags: noNotification.";
    }
    leaf pmFlexUeCtxtRelSCNr {
      type uint32;
      config false;
    }
    leaf-list pmRachPreambleDist {
      type uint32;
    }
    leaf-list pmPrbUsedDlDtchFirstTransQci {
      type uint32;
    }
    leaf pmEndcSetupBufMonConfig {
      type uint32;
      config false;
    }
    leaf pmS1SigConnEstabAttMos {
      type uint32;
      config false;
    }
    leaf pmPdcpPktLostUlLimitations {
      type uint32;
      config false;
    }
    leaf pmPdcpVolDlSrbTrans {
      type uint32;
      config false;
    }
    leaf pmUeCtxtRelCsfbMeasTO1xRttEm {
      type uint32;
      config false;
    }
    leaf pmActiveUeDlSum {
      type ietfyang:mac-address;
      config false;
    }
    leaf pmRrcConnReconfSuccNoMobUpswitch {
      type uint32;
      config false;
    }
    leaf pmFlexErabEstabFailAddedErabIdInUse {
      type uint32;
      config false;
    }
    leaf pmPdcchResyncAttCe0Br {
      type uint32;
      config false;
    }
    leaf-list pmRrcConnResumeFailCellLatencyCe {
      type uint32;
    }
    leaf pmS1SigConnEstabSuccMos {
      type uint32;
      config false;
    }
    leaf pmUeCtxtRelSrvccMeasTO1xRtt {
      type uint32;
      config false;
    }
    leaf pmErabRelAbnormalEnbCdt {
      type uint32;
      config false;
    }
    leaf pmPrbUsedUlDtchNs05FullBandSch {
      type uint32;
      config false;
    }
    leaf pmUeCtxtRelSCGsm {
      type uint32;
      config false;
    }
    leaf pmRrcConnResumeFailLowCovUeAdmCtrl {
      type uint32;
      config false;
      status deprecated;
      description "MOM flags: noNotification.";
    }
    leaf pmFlexCellHoPrepAttUtran {
      type uint32;
      config false;
    }
    leaf-list pmErabEstabSuccInitArp {
      type uint32;
    }
    leaf-list pmRlcPduBufferUtilUlCellDistr {
      type uint32;
    }
    leaf-list pmPtmIfoMeasuredUeDistr {
      type uint32;
    }
    leaf-list pmRrcConnReestFailMpMemCe {
      type uint32;
      description "MOM flags: noNotification.";
    }
    leaf-list pmPdschMsg2PwrBoostDistr {
      type uint32;
    }
    leaf pmFlexRrcConnReestAtt {
      type uint32;
      config false;
    }
    leaf pmSchedActivityCellDlBr {
      type uint32;
      config false;
    }
    leaf pmFlexZtemporary20 {
      type uint32;
      config false;
    }
    leaf pmZtemporary12 {
      type uint32;
      config false;
    }
    leaf pmErabRopEndBr {
      type uint32;
      config false;
    }
    leaf-list pmRaSuccTaZone2Distr {
      type uint32;
    }
    leaf pmS1SigConnEstabSuccMta {
      type uint32;
      config false;
    }
    leaf-list pmRrcConnEstabFailMpOverloadCe {
      type uint32;
    }
    leaf pmRrcConnQueueTo {
      type uint32;
      config false;
    }
    leaf pmFlexZtemporary24 {
      type uint32;
      config false;
    }
    leaf-list pmUeThpDlMbbFilteredDistr {
      type uint32;
      description "MOM flags: noNotification.";
    }
    leaf pmSchedTtiCellUlResAllocKept {
      type uint32;
      config false;
    }
    leaf-list pmRrcConnEstabFailDuSwCCe {
      type uint32;
    }
    leaf pmFlexMacVolUlResUe {
      type ietfyang:mac-address;
      config false;
    }
    leaf pmRadioRecInterferencePwrPrb87 {
      type uint32;
      config false;
    }
    leaf pmPagDiscarded {
      type uint32;
      config false;
    }
    leaf pmRaSuccSrOutOfSync {
      type uint32;
      config false;
    }
    leaf pmRadioRecInterferencePwrPrb37 {
      type uint32;
      config false;
    }
    leaf pmDrxSleepTime {
      type uint32;
      config false;
    }
    leaf-list pmPdcchCceAggregationDistr {
      type uint32;
    }
    leaf pmFlexUeCtxtRelSCGsm {
      type uint32;
      config false;
    }
    leaf pmRadioRecInterferencePwrPrb24 {
      type uint32;
      config false;
    }
    leaf pmVoipQualityRbUlLowSampl {
      type ietfinet:ip-address;
      config false;
    }
    leaf pmZtemporary33 {
      type uint32;
      config false;
    }
    leaf-list pmMacLcgThpVolUlLcg {
      type ietfyang:mac-address;
    }
    leaf pmZtemporary129 {
      type uint32;
      config false;
    }
    leaf pmPdcpVolDlDrbLastTTICa {
      type uint32;
      config false;
    }
    leaf-list pmRadioUeRepCqiCe1Distr {
      type uint32;
    }
    leaf-list pmCaScheduledDl3ccSumDistr {
      type uint32;
    }
    leaf pmMimoSleepTime {
      type uint32;
      config false;
    }
    leaf pmMiMimoSleepOpp {
      type uint32;
      config false;
    }
    leaf pmMacDelayTimeDl {
      type ietfyang:mac-address;
      config false;
    }
    leaf pmCellHoExeAttLteIntraFHybridCsg {
      type uint32;
      config false;
    }
    leaf pmPdcpVolDlDrbTransPlmn1 {
      type uint32;
      config false;
    }
    leaf-list pmRrcConnEstabFailDuIntensCe {
      type uint32;
    }
    leaf pmUeCtxtRelAbnormalEnbActUeLostOosPft {
      type uint32;
      config false;
    }
    leaf pmFlexErabRelMmeActEutra {
      type uint32;
      config false;
    }
    leaf pmErabRelMmeAct {
      type uint32;
      config false;
    }
    leaf pmRrcConnEstabFailLicMoVoice {
      type uint32;
      config false;
    }
    leaf pmRadioRecInterferencePwrPrb83 {
      type uint32;
      config false;
    }
    leaf pmZtemporary171 {
      type uint32;
      config false;
    }
    leaf-list pmMacLatTimeDlNoDrxSyncQci {
      type ietfyang:mac-address;
      description "MOM flags: noNotification.";
    }
    leaf pmRadioThpVolTxDlSCellEran {
      type uint32;
      config false;
    }
    leaf-list pmCaScheduledDlIeNbSum {
      type uint32;
    }
    leaf-list pmPdcpLatPktTransDlQci {
      type uint32;
    }
    leaf pmZtemporary4 {
      type uint32;
      config false;
    }
    leaf pmEndcCapableUe {
      type uint32;
      config false;
    }
    leaf pmSinrWithPimAvoidOnSamp {
      type uint32;
      config false;
    }
    leaf pmRlcPollRetxDl {
      type uint32;
      config false;
    }
    leaf pmAnrNeighbrelAdd {
      type uint32;
      config false;
    }
    leaf pmEndcNotAllowedMoVoice {
      type uint32;
      config false;
    }
    leaf pmUeCtxtRelSCWcdma {
      type uint32;
      config false;
    }
    leaf pmFlexMacLatTimeDlDrxSync {
      type ietfyang:mac-address;
      config false;
      status deprecated;
      description "MOM flags: noNotification.";
    }
    leaf-list pmRadioUeRepCqiCe0Distr {
      type uint32;
    }
    leaf pmRadioRecInterferencePwrPrb77 {
      type uint32;
      config false;
    }
    leaf-list pmErabEstabAttRejAdmMsrInitArp {
      type uint32;
    }
    leaf-list pmPdcpVolDlHdrQci {
      type uint32;
    }
    leaf pmUeCtxtRelNormalEnb {
      type uint32;
      config false;
    }
    leaf pmMacVolUlUnresUe {
      type ietfyang:mac-address;
      config false;
    }
    leaf pmUlTrafficQualifiedUe {
      type uint32;
      config false;
    }
    leaf pmFlexCellHoExeSuccNonMobLte {
      type uint32;
      config false;
    }
    leaf pmFlexCellHoExeSuccNr {
      type uint32;
      config false;
    }
    leaf pmUeCtxtRelCsfbWcdma {
      type uint32;
      config false;
    }
    leaf-list pmMacLinkAdaptDlOutLoopAdjDeltaDistr {
      type ietfyang:mac-address;
    }
    leaf-list pmAcBarringCsfbSpecAcPlmn1Distr {
      type ietfyang:mac-address;
    }
    leaf pmRadioThpVolTxDlSCellIcmLaa {
      type uint32;
      config false;
    }
    leaf pmUeCtxtRelMmeActHo {
      type uint32;
      config false;
    }
    leaf pmB2BestCellEvalReport {
      type ietfinet:port-number;
      config false;
    }
    leaf pmUeCtxtFetchAttReconfRrcConnReest {
      type uint32;
      config false;
    }
    leaf pmRrcConnTuneOutLevSamp {
      type uint32;
      config false;
    }
    leaf pmFlexZtemporary12 {
      type uint32;
      config false;
    }
    leaf pmZtemporary112 {
      type uint32;
      config false;
    }
    leaf pmUeCtxtRelAbnormalEnbTuneOut {
      type uint32;
      config false;
    }
    leaf pmFlexEndcSetupScgUeSucc {
      type uint32;
      config false;
    }
    leaf pmRadioRecInterferencePwrPrb13 {
      type uint32;
      config false;
    }
    leaf pmVoipQualityRbUlNok {
      type ietfinet:ip-address;
      config false;
    }
    leaf pmRadioRecInterferencePwrPrb10 {
      type uint32;
      config false;
    }
    leaf pmFlexZtemporary17 {
      type uint32;
      config false;
    }
    leaf pmUeCtxtFetchAttReconfUeCtxtEstab {
      type uint32;
      config false;
    }
    leaf pmZtemporary138 {
      type uint32;
      config false;
    }
    leaf pmRadioRecInterferencePwrPrb15 {
      type uint32;
      config false;
    }
    leaf pmErabRelMmeCellUnavail {
      type uint32;
      config false;
    }
    leaf-list pmAcBarringMosSpecialAcDistr {
      type ietfyang:mac-address;
    }
    leaf pmFlexMacHarqUlDtx256qam {
      type ietfyang:mac-address;
      config false;
    }
    leaf pmActiveUeUlCe1Max {
      type ietfyang:mac-address;
      config false;
    }
    leaf-list pmPrbUtilDlCellResource15Distr {
      type uint32;
      description "MOM flags: noNotification.";
    }
    leaf pmNonMcPttQualityRbUlNok {
      type uint32;
      config false;
    }
    leaf pmErabEndcScgLevSamp {
      type uint32;
      config false;
    }
    leaf-list pmRrcLatencySecModeCmdDistr {
      type uint32;
    }
    leaf pmRadioRecInterferencePwrPrb21 {
      type uint32;
      config false;
    }
    leaf-list pmPdcpPktDiscDlStaleSduQci {
      type uint32;
    }
    leaf-list pmZtemporary18Qci {
      type uint32;
    }
    leaf pmRadioThpVolDl4ccPCell {
      type uint32;
      config false;
    }
    leaf-list pmErabRelAbnormalEnbGbrArp {
      type uint32;
    }
    leaf-list pmErabEstabAttInitGbrArp {
      type uint32;
    }
    leaf pmRrcConnQueueAllocAtt {
      type uint32;
      config false;
    }
    leaf-list pmMacLcgThpTimeUlLcg {
      type ietfyang:mac-address;
    }
    leaf pmErabResumeArpLow {
      type uint32;
      config false;
    }
    leaf-list pmCaCapableDlSum {
      type uint32;
    }
    leaf pmUeCtxtSuspendSuccBr {
      type uint32;
      config false;
    }
    leaf pmTtiBundlingUeMax {
      type int32;
      config false;
    }
    leaf-list pmMacUeBitRateRecommUlVoipDistr {
      type ietfinet:ip-address;
    }
    leaf pmVoipQualityRbUlOk {
      type ietfinet:ip-address;
      config false;
    }
    leaf pmTtiBundlingUeSamp {
      type uint32;
      config false;
    }
    leaf pmErabRelAbnormalEnbHpr {
      type uint32;
      config false;
    }
    leaf-list pmAccessClassBarringMosDistr {
      type ietfyang:mac-address;
    }
    leaf pmBadCovSearchEvalReportRsrp {
      type ietfinet:port-number;
      config false;
    }
    leaf pmPrbUsedUlPresched {
      type uint32;
      config false;
    }
    leaf pmFlexMacHarqUl6 {
      type ietfyang:mac-address;
      config false;
    }
    leaf pmZtemporary228 {
      type uint32;
      config false;
    }
    leaf pmRaRejHarqFailWithinContRes {
      type uint32;
      config false;
    }
    leaf pmUeExclThpUlShortTimeHighVol {
      type uint32;
      config false;
    }
    leaf pmFlexPdcpLatPktTransDl {
      type uint32;
      config false;
    }
    leaf pmS1SigConnEstabSucc {
      type uint32;
      config false;
    }
    leaf pmUeThpVolUlCa {
      type uint32;
      config false;
    }
    leaf pmErabRelAbnormalEnbPsPartFail {
      type uint32;
      config false;
    }
    leaf-list pmRaSuccTaZone0Distr {
      type uint32;
    }
    leaf-list pmRadioUeRepCqiDistr2 {
      type uint32;
    }
    leaf pmZtemporary29 {
      type uint32;
      config false;
    }
    leaf pmFlexRlcArqUlAck {
      type uint32;
      config false;
    }
    leaf pmZtemporary130 {
      type uint32;
      config false;
    }
    leaf pmHoPrepOutS1RejInvalidInterFHybridCsg {
      type uint32;
      config false;
    }
    leaf-list pmPuschMcsSubsGroup5Distr {
      type uint32;
    }
    leaf pmCgiMeasSuccAnrPciConflict {
      type uint32;
      config false;
    }
    leaf-list pmErabRelAbnormalEnbCdtAutoPnrQci {
      type uint32;
    }
    leaf pmMeasRep {
      type uint32;
      config false;
    }
    leaf-list pmUeCtxtRelNormalEnbRaiCe {
      type uint32;
    }
    leaf pmUnackedUeRelease {
      type uint32;
      config false;
    }
    leaf pmRadioTbsPwrUnrestricted {
      type uint32;
      config false;
    }
    leaf-list pmRlcSduEstLostUlNonMcPttTtiBundl {
      type uint32;
    }
    leaf-list pmAccessClassBarringVideoPlmn3Distr {
      type ietfyang:mac-address;
    }
    leaf-list pmRaAttCbraBrCe1Distr {
      type uint32;
    }
    leaf pmPrbAvailDlMbms {
      type uint32;
      config false;
    }
    leaf-list pmRrcConnResumeFailMpOverloadCe {
      type uint32;
    }
    leaf pmRrcConnLevSamp {
      type uint32;
      config false;
    }
    leaf-list pmS1SigConnEstabFailMmeOvlMosCe {
      type uint32;
    }
    leaf pmRadioRecInterferencePwrPrb61 {
      type uint32;
      config false;
    }
    leaf-list pmErabRelAbnormalEnbActPeRpid {
      type uint32;
    }
    leaf-list pmRlcDelayTimeDl2Qci {
      type uint32;
    }
    leaf pmHoPrepRejInCellIntensStat {
      type uint32;
      config false;
    }
    leaf pmErabEstabAttAdded {
      type uint32;
      config false;
    }
    leaf pmRadioUeRepCqi2Subband2Sum {
      type uint32;
      config false;
    }
    leaf pmPrbUsedDlPcchBr {
      type uint32;
      config false;
    }
    leaf-list pmPrbUsedMimoLayersUlDistr {
      type uint32;
    }
    leaf pmRrcConnReconfAttNoMobSkipUlDyn {
      type ietfinet:ip-address;
      config false;
    }
    leaf pmCellHoPrepAttLteInterFUl {
      type uint32;
      config false;
    }
    leaf pmUeCtxtFetchSuccIntraEnbHoIn {
      type uint32;
      config false;
    }
    leaf pmRrcConnReconfAttNoMobUpswitch {
      type uint32;
      config false;
    }
    leaf-list pmAcBarringVideoSpecAcPlmn3Distr {
      type ietfyang:mac-address;
    }
    leaf pmFlexRlcArqDlAck {
      type uint32;
      config false;
    }
    leaf-list pmPrbUtilDlCellResource16Distr {
      type uint32;
      description "MOM flags: noNotification.";
    }
    leaf-list pmZtemporary192 {
      type uint32;
    }
    leaf pmDlAssigsTransMcPttNDO {
      type uint32;
      config false;
    }
    leaf pmFlexUeCtxtRelAbnormalEnbActPe {
      type uint32;
      config false;
    }
    leaf-list pmCaActivatedDl2ccSumDistr {
      type uint32;
    }
    leaf-list pmRrcConnEstabAttReattMtaPagPrioDistr {
      type uint32;
    }
    leaf pmZtemporary26 {
      type uint32;
      config false;
    }
    leaf pmZtemporary68 {
      type uint32;
      config false;
    }
    leaf pmDynUeAdmCtrlQueueSucc {
      type uint32;
      config false;
      status deprecated;
      description "MOM flags: noNotification.";
    }
    leaf pmEndcSetupUeAttBufUl {
      type uint32;
      config false;
    }
    leaf pmFlexRlcDelayPktTransDl {
      type uint32;
      config false;
    }
    leaf pmUeCtxtFetchSuccIntraEnbHoExe {
      type uint32;
      config false;
    }
    leaf pmNasTransferAttAbortDlSrb2 {
      type uint32;
      config false;
    }
    leaf pmRrcConnCe1CellLevMax {
      type int32;
      config false;
    }
    leaf-list pmRrcConnQueueAdptPullDelayDistr {
      type uint32;
    }
    leaf pmUeCtxtRelAbnormalEnbActHo {
      type uint32;
      config false;
    }
    leaf-list pmCaActivatedDlSum {
      type uint32;
    }
    leaf-list pmUeCategoryDlUlCombDistr {
      type uint32;
    }
    leaf pmFlexRadioThpVolUl {
      type uint32;
      config false;
      status deprecated;
      description "MOM flags: noNotification.";
    }
    leaf pmCaConfiguredMeasSucc {
      type uint32;
      config false;
    }
    leaf-list pmErabRelAbnormalEnbHprQci {
      type uint32;
    }
    leaf pmDlAssigsDetHarqMcPttNDO {
      type uint32;
      config false;
    }
    leaf pmErabEndcScgLevSum {
      type uint32;
      config false;
    }
    leaf-list pmErabRelAbnormalMmeQci {
      type uint32;
    }
    leaf pmInvalidPftMsg {
      type uint32;
      config false;
    }
    leaf-list pmMacDrbThpTimeDlQci {
      type ietfyang:mac-address;
      description "MOM flags: noNotification.";
    }
    leaf-list pmHoPrepRejInAdmMsrArp {
      type uint32;
    }
    leaf pmErabEstabAttAddedPa {
      type uint32;
      config false;
    }
    leaf pmHoPrepOutS1RejInvalidIntraFCsg {
      type uint32;
      config false;
    }
    leaf pmHoExeSuccIntraCell {
      type uint32;
      config false;
    }
    leaf pmRateShapeTimeUl {
      type uint32;
      config false;
    }
    leaf pmZtemporary66 {
      type uint32;
      config false;
    }
    leaf pmFlexVoipQualityRbUlNok {
      type ietfinet:ip-address;
      config false;
    }
    leaf pmRrcConnRelBrNoPdn {
      type uint32;
      config false;
    }
    leaf-list pmMacUeBitRateRecommUlMcPttDistr {
      type ietfyang:mac-address;
    }
    leaf-list pmZtemporary83 {
      type uint32;
    }
    leaf-list pmRaSuccSrBr {
      type uint32;
    }
    leaf pmRadioRecInterferencePwrPrb57 {
      type uint32;
      config false;
    }
    leaf-list pmZtemporary232Compr {
      type uint32;
    }
    leaf pmUlGrantsTransMcPttNDO {
      type uint32;
      config false;
    }
    leaf-list pmAccessClassBarringVoicePlmn1Distr {
      type ietfyang:mac-address;
    }
    leaf-list pmAcBarringVoiceSpecAcPlmn3Distr {
      type ietfyang:mac-address;
    }
    leaf pmEndcSetupFailNrRaProblem {
      type uint32;
      config false;
    }
    leaf-list pmErabEstabAttInitQci {
      type uint32;
    }
    leaf pmErabEstabSuccAddedPa {
      type uint32;
      config false;
    }
    leaf pmUePeAttInterCell {
      type uint32;
      config false;
    }
    leaf pmZtemporary240 {
      type uint32;
      config false;
    }
    leaf pmUeCtxtFetchAttEndcRel {
      type uint32;
      config false;
    }
    leaf-list pmCaSchedDlOffloadingDistr {
      type uint32;
    }
    leaf-list pmPrbUtilDlCellResource8Distr {
      type uint32;
      description "MOM flags: noNotification.";
    }
    leaf pmRadioUeRepCqi2Subband8Sum {
      type uint32;
      config false;
    }
    leaf-list pmS1SigConnEstabSuccCe {
      type uint32;
    }
    leaf-list pmErabEstabAttAddedCsfbArp {
      type uint32;
    }
    leaf pmZtemporary148 {
      type uint32;
      config false;
    }
    leaf-list pmPrbUtilDlCellResource5Distr {
      type uint32;
      description "MOM flags: noNotification.";
    }
    leaf pmUeCtxtFetchSuccReconfErabEstab {
      type uint32;
      config false;
    }
    leaf pmRohcUlDataFailedMaxCid {
      type uint32;
      config false;
    }
    leaf-list pmTxPsdLoadUlDistr {
      type uint32;
    }
    leaf pmPdcchMaxCceAvail {
      type uint32;
      config false;
    }
    leaf-list pmPrbUtilDlCellResource9Distr {
      type uint32;
      description "MOM flags: noNotification.";
    }
    leaf pmRadioThpVolTxDl7ccSCell {
      type uint32;
      config false;
    }
    leaf-list pmRrcConnResumeFailCellIntensSwCCe {
      type uint32;
    }
    leaf-list pmRrcConnCeCellLevMax {
      type uint32;
      description "MOM flags: noNotification.";
    }
    leaf-list pmPdcchCceUtil {
      type uint32;
    }
    leaf pmRrcConnResumeFailLowCovUeLic {
      type uint32;
      config false;
      status deprecated;
      description "MOM flags: noNotification.";
    }
    leaf pmPagEdrxDiscardedBr {
      type uint32;
      config false;
    }
    leaf-list pmRrcConnResumeFailDuIntensCe {
      type uint32;
    }
    leaf pmRadioRecInterferencePwrPrb89 {
      type uint32;
      config false;
    }
    leaf pmCellHoPrepSuccNrServTrig {
      type uint32;
      config false;
    }
    leaf pmUeCtxtRelAbnormalMmeActCritCov {
      type uint32;
      config false;
    }
    leaf pmDlAssigsWithDetHarqAckNonMcPtt {
      type uint32;
      config false;
    }
    leaf pmRadioUeRepCqi2Subband3Sum {
      type uint32;
      config false;
    }
    leaf pmElcPdschBlankedTti {
      type uint32;
      config false;
    }
    leaf pmMacVolUlResUeLate {
      type ietfyang:mac-address;
      config false;
    }
    leaf pmRrcConnEstabAttReattDta {
      type uint32;
      config false;
      status deprecated;
      description "MOM flags: noNotification.";
    }
    leaf pmUeCtxtFetchSuccNoNeighRel {
      type uint32;
      config false;
    }
    leaf pmFlexPdcpPktReceivedUl {
      type uint32;
      config false;
    }
    leaf pmUeCtxtRelCsfbWcdmaEm {
      type uint32;
      config false;
    }
    leaf pmBadCovMiMultiFreqSucc {
      type uint32;
      config false;
    }
    leaf pmUeCtxtFetchSuccS1HoPrepSrvccUtran {
      type uint32;
      config false;
    }
    leaf pmZtemporary88 {
      type uint32;
      config false;
    }
    leaf pmUlGrantsTrans {
      type uint32;
      config false;
    }
    leaf pmRohcUlDataDeconfigAtt {
      type uint32;
      config false;
    }
    leaf-list pmPdcpPktLostUlQci {
      type uint32;
    }
    leaf-list pmMacTimeDlDrxSyncSampQci {
      type ietfyang:mac-address;
      description "MOM flags: noNotification.";
    }
    leaf pmGoodCovSearchEvalReport {
      type ietfinet:port-number;
      config false;
    }
    leaf-list pmRrcConnResumeFailDynUeAdmCtrlCe {
      type uint32;
    }
    leaf pmHoPrepRejOutUlThresCaRedirect {
      type uint32;
      config false;
    }
    leaf-list pmPrbUtilDlCellResource21Distr {
      type uint32;
      description "MOM flags: noNotification.";
    }
    leaf-list pmRaAttTaDistr {
      type uint32;
    }
    leaf pmUeCtxtConnResumeSucc {
      type uint32;
      config false;
      status deprecated;
      description "MOM flags: noNotification.";
    }
    leaf-list pmPdcpLatPktTransDlNoDrxNoSyncQci {
      type uint32;
    }
    leaf pmFlexCellHoExeCancelUtranSrvcc {
      type uint32;
      config false;
    }
    leaf pmCriticalBorderEvalReport {
      type ietfinet:port-number;
      config false;
    }
    leaf pmRlcDelayPktTransDl {
      type uint32;
      config false;
    }
    leaf pmS1SigConnEstabAttMod {
      type uint32;
      config false;
    }
    leaf pmUeCtxtRelSCNrB2Rsrp {
      type uint32;
      config false;
    }
    leaf-list pmPdcpLatPktTransDlNoDrxSyncQci {
      type uint32;
    }
    leaf pmCellHoPrepSuccLteInterFHybridCsg {
      type uint32;
      config false;
    }
    leaf pmRrcConnEstabFailCellIntensDLC {
      type uint32;
      config false;
    }
    leaf pmZtemporary93 {
      type uint32;
      config false;
    }
    leaf-list pmRrcConnResumeAttCe {
      type uint32;
    }
    leaf-list pmErabRelMmeArp {
      type uint32;
    }
    leaf pmErabRelAbnormalEnbCdtAuto {
      type uint32;
      config false;
    }
    leaf pmRadioRecInterferencePwrPrb96 {
      type uint32;
      config false;
    }
    leaf pmFlexErabEstabSuccAdded {
      type uint32;
      config false;
    }
    leaf-list pmErabRelAbnormalEnbActCdtQci {
      type uint32;
    }
    leaf-list pmS1SigConnEstabSuccMtaCe {
      type uint32;
    }
    leaf pmRadioRecInterferencePwrPrb38 {
      type uint32;
      config false;
    }
    leaf pmZtemporary244 {
      type uint32;
      config false;
    }
    leaf pmWifiAccessRej {
      type uint32;
      config false;
    }
    leaf-list pmErabRelAllEnbQci {
      type uint32;
    }
    leaf-list pmActiveUeDlMaxCe {
      type ietfyang:mac-address;
      description "MOM flags: noNotification.";
    }
    leaf-list pmPdcpLatTimeDlDrxNoSyncQci {
      type uint32;
    }
    leaf pmObsLocalEventDiscPmLoad {
      type uint32;
      config false;
    }
    leaf-list pmMacUeBitRateSelectUlNonMcPttDistr {
      type ietfyang:mac-address;
    }
    leaf pmRadioRecInterferencePwrPrb2 {
      type uint32;
      config false;
    }
    leaf-list pmPdcchTargetBlerLowRatioPcellDistr {
      type uint32;
    }
    leaf pmUeCtxtRetrReestFailUnknUeCtxt {
      type uint32;
      config false;
      status deprecated;
      description "MOM flags: noNotification.";
    }
    leaf pmRadioRecInterferencePwrPrb88 {
      type uint32;
      config false;
    }
    leaf pmMiMimoSleepIn {
      type uint32;
      config false;
    }
    leaf-list pmAcBarringCsfbSpecAcPlmn2Distr {
      type ietfyang:mac-address;
    }
    leaf-list pmErabRelAbnormalEnbPeRpid {
      type uint32;
    }
    leaf pmEranCompUlAvoidedNack {
      type uint32;
      config false;
    }
    leaf pmCellHoExeAttLteInterFUl {
      type uint32;
      config false;
    }
    leaf pmPrbUsedUlSum {
      type uint32;
      config false;
    }
    leaf pmRadioThpVolTxDlSCellExt {
      type uint32;
      config false;
    }
    leaf pmErabEstabFailGbrUlEnb {
      type uint32;
      config false;
    }
    leaf-list pmMiMimoModelAccuracyDistr {
      type uint32;
    }
    leaf pmPrbUsedUlCatmMax {
      type int32;
      config false;
    }
    leaf pmRrcConnReconfAttNoMobEarfcnCa {
      type uint32;
      config false;
    }
    leaf-list pmCompUlDeltaSinrPuschInterEnbDistr {
      type uint32;
    }
    leaf pmFlexNonMcPttQualityRbUlNok {
      type uint32;
      config false;
    }
    leaf pmIdcCapableSum {
      type uint32;
      config false;
    }
    leaf-list pmPdcpLatPktTransDlCatMDrxNoSyncQci {
      type uint32;
    }
    leaf-list pmRaContResRejDistr {
      type uint32;
    }
    leaf-list pmRaContResAccDistr {
      type uint32;
    }
    leaf-list pmDynUeAdmCtrlQueueSizeDistr {
      type uint32;
      description "MOM flags: noNotification.";
    }
    leaf pmHoPrepRejInMISigQCong {
      type uint32;
      config false;
    }
    leaf pmErabLevSum {
      type uint32;
      config false;
    }
    leaf pmUeCtxtFetchSuccUeCapEnq {
      type uint32;
      config false;
    }
  }
  grouping EUtranCellRelation-attributes {
    leaf eUtranCellRelationId {
      type string;
      mandatory true;
    }
    leaf cellIndividualOffsetEUtran {
      type int32 {
        range "-24 | -22 | -20 | -18 | -16 | -14 | -12 | -10 | -8 | -6..6 | 8 | 10 | 12 | 14 | 16 | 18 | 20 | 22 | 24";
      }
      default "0";
      units "dB";
      description "Default value: 0.";
    }
    leaf neighborCellRef {
      type string;
      mandatory true;
    }
    leaf isHoAllowed {
      type boolean;
      default "true";
      description "Default value: true.";
    }
    leaf qOffsetCellEUtran {
      type int32 {
        range "-24 | -22 | -20 | -18 | -16 | -14 | -12 | -10 | -8 | -6..6 | 8 | 10 | 12 | 14 | 16 | 18 | 20 | 22 | 24";
      }
      default "0";
      units "dB";
      description "Default value: 0.";
    }
    leaf isRemoveAllowed {
      type boolean;
      default "false";
      description "Default value: false.";
    }
    leaf includeInSystemInformation {
      type boolean;
      default "true";
      description "Default value: true.";
    }
    leaf coverageIndicator {
      type enumeration {
        enum NONE;
        enum COVERS;
        enum OVERLAP;
        enum CONTAINED_IN;
      }
    }
    leaf createdBy {
      type enumeration {
        enum ANR;
        enum X2;
        enum OPERATOR;
      }
      config false;
    }
    leaf timeOfCreation {
      type string {
        length "0..19";
      }
      config false;
      description "length 0..19.";
    }
    leaf lastModification {
      type enumeration {
        enum ANR_MODIFICATION;
        enum X2_MODIFICATION;
        enum OPERATOR_MODIFICATION;
        enum ANR_DELETE;
        enum X2_DELETE;
        enum OPERATOR_DELETE;
        enum NOT_MODIFIED;
        enum MRO_MODIFICATION;
        enum PCI_MODIFICATION;
        enum MLB_MODIFICATION;
        enum RACH_OPT_MODIFICATION;
        enum LM_MODIFICATION;
      }
      config false;
    }
    leaf timeOfLastModification {
      type string {
        length "0..19";
      }
      config false;
      description "length 0..19.";
    }
    leaf loadBalancing {
      type enumeration {
        enum NOT_ALLOWED;
        enum ALLOWED;
        enum OFFLOAD;
        enum IFO_AND_IFLB;
      }
    }
    leaf sCellCandidate {
      type enumeration {
        enum NOT_ALLOWED;
        enum ALLOWED;
        enum AUTO;
        enum ONLY_ALLOWED_FOR_DL;
      }
    }
    leaf lbBnrAllowed {
      type boolean;
      default "true";
      description "Default value: true.";
    }
    leaf incomingLoadBalancing {
      type boolean;
      config false;
    }
    leaf lbCovIndicated {
      type boolean;
      default "false";
      description "Default value: false.";
    }
    leaf sleepModeCovCellCandidate {
      type enumeration {
        enum NOT_ALLOWED;
        enum ALLOWED;
        enum AUTO;
      }
    }
    leaf sleepModeCapacityCell {
      type boolean;
      config false;
    }
    leaf sleepModeCoverageCell {
      type boolean;
      config false;
    }
    leaf covCellDlPrbWakeUpThreshold {
      type eytypes:int32_range_0-100;
      config false;
      units "percent";
      description "range 0..100.";
    }
    leaf covCellRrcConnWakeUpThreshold {
      type eytypes:int32_range_0-3000-40;
      config false;
      description "range 0..3000.";
    }
    leaf covCellWakeupMonitorDurTimer {
      type eytypes:int32_range_1-120;
      config false;
      units "minutes";
      description "range 1..120.";
    }
    leaf crsAssistanceInfoPriority {
      type eytypes:int32_range_0-100-3;
      default "0";
      description "range 0..100; Default value: 0.";
    }
    list mobilityStatus {
      config false;
      container attributes {
      leaf available {
        type string;
      }
      leaf reason {
        type string;
      }
      }
    }
    leaf hoSuccLevel {
      type enumeration {
        enum OFF;
        enum HIGH;
        enum MEDIUM;
        enum LOW;
      }
      config false;
    }
    leaf esCellCaConfigurationAvail {
      type enumeration {
        enum DISABLED;
        enum ENABLED;
        enum NOT_APPLICABLE;
        enum ENABLED_ERAN;
        enum EANBLED_IENB;
        enum DISABLED_CELLSTATE;
        enum DISABLED_LICENSE;
        enum DISABLED_BB_COMPATABILITY;
        enum DISABLED_LINK;
        enum DISABLED_MISMATCHED_MODE;
        enum ENABLED_IENB;
        enum DISABLED_BB_COMPATIBILITY;
        enum LINK_REMOVED_BY_REMOTE_ENB;
        enum ESCELL_LIMIT_EXCEEDED;
        enum CPRI_LATENCY_EXCEEDED;
        enum VLAN_MISMATCH;
        enum TERMPOINT_TO_ENB_DISABLED;
        enum PCELL_DISABLED;
        enum ESCELL_DISABLED;
        enum MAX_PARTNERS_ON_REMOTE_ENB;
        enum MAX_PARTNERS_ON_LOCAL_ENB;
      }
      config false;
      status deprecated;
      description "Takes effect: New connection; MOM flags: noNotification; Status info: Since 21.Q2. Replaced by sCellCaConfigurationAvail. Planned to be removed..";
      reference "Takes effect: New connection.";
    }
    leaf amoAllowed {
      type boolean;
      default "true";
      description "Default value: true.";
    }
    leaf amoState {
      type enumeration {
        enum DISABLED;
        enum ENABLED;
      }
      config false;
    }
    leaf sCellPriority {
      type eytypes:int32_range_-1-7;
      default "7";
      description "range -1..7; Default value: 7.";
    }
    leaf isShuttingdownSCellAllowed {
      type boolean;
    }
    leaf ieNBUlCompCoopCellAllowed {
      type boolean;
      default "true";
      description "Default value: true.";
    }
    leaf externalUlCompGroupAvail {
      type enumeration {
        enum DISABLED;
        enum ENABLED;
      }
      config false;
    }
    leaf eranExternalUlCompGroupAvail {
      type enumeration {
        enum DISABLED;
        enum ENABLED;
      }
      config false;
    }
    leaf eranUlCompCoopCellAllowed {
      type boolean;
      default "true";
      description "Default value: true.";
    }
    leaf isHoAllowedBr {
      type boolean;
      default "true";
      description "Default value: true.";
    }
    leaf cellIndividualOffsetEUtranQci1 {
      type int32 {
        range "-24 | -22 | -20 | -18 | -16 | -14 | -12 | -10 | -8 | -6..6 | 8 | 10 | 12 | 14 | 16 | 18 | 20 | 22 | 24";
      }
      default "0";
      units "dB";
      description "Default value: 0.";
    }
    leaf coverageIndicatorBr {
      type enumeration {
        enum NONE;
        enum COVERS;
        enum OVERLAP;
        enum CONTAINED_IN;
      }
    }
    leaf zzzTemporary1 {
      type int32;
      default "-2000000000";
      description "Default value: -2000000000.";
    }
    leaf zzzTemporary2 {
      type int32;
      default "-2000000000";
      description "Default value: -2000000000.";
    }
    leaf zzzTemporary3 {
      type string;
    }
    leaf reportDlActivity {
      type ietfinet:port-number;
    }
    leaf interferenceScoreDl {
      type eytypes:int32_range_0-32767;
      config false;
      description "range 0..32767.";
    }
    leaf asmStatus {
      type enumeration {
        enum NOT_ALLOWED;
        enum CANDIDATE;
        enum ALLOWED;
        enum ONLY_ALLOWED_FOR_DL;
      }
      config false;
    }
    leaf asmSCellDlOnlyAllowed {
      type enumeration {
        enum DL_ONLY;
        enum DL_UL;
      }
    }
    leaf sCellCaConfigurationAvail {
      type enumeration {
        enum DISABLED;
        enum ENABLED_LOCAL;
        enum ENABLED_ERAN;
        enum ENABLED_IENB;
        enum DISABLED_LICENSE;
        enum DISABLED_BB_COMPATIBILITY;
        enum DISABLED_LINK;
        enum DISABLED_MISMATCHED_MODE;
        enum LINK_REMOVED_BY_REMOTE_ENB;
        enum ESCELL_LIMIT_EXCEEDED;
        enum CANDIDATE_LIMIT_EXCEEDED;
        enum CPRI_LATENCY_EXCEEDED;
        enum VLAN_MISMATCH;
        enum TERMPOINT_TO_ENB_DISABLED;
        enum PCELL_DISABLED;
        enum ESCELL_DISABLED;
        enum LOCAL_SCELL_DISABLED;
        enum MAX_PARTNERS_ON_REMOTE_ENB;
        enum MAX_PARTNERS_ON_LOCAL_ENB;
        enum ERAN_MAX_RTT_DELAY_MISMATCH;
        enum ENABLED_ICM;
        enum CM_SCELL_DISABLED;
        enum ICM_SCELL_DISABLED;
      }
      config false;
    }
    leaf pciConflictPreferredCellMan {
      type boolean;
      default "false";
      description "Default value: false.";
    }
    leaf pciConflictPreferredCellAuto {
      type boolean;
      config false;
    }
    leaf barringLowHoAllowed {
      type boolean;
      default "true";
      description "Default value: true.";
    }
    leaf blockedPlmnCell {
      type boolean;
      config false;
    }
    leaf pmHoWrongCellQci1 {
      type uint32;
      config false;
    }
    leaf pmHoPrepSuccLteInterFDtvm {
      type uint32;
      config false;
    }
    leaf pmHoWrongCellReestQci1 {
      type uint32;
      config false;
    }
    leaf pmZtemporary36 {
      type uint32;
      config false;
    }
    leaf pmCaRedirectMeasRepUe {
      type uint32;
      config false;
    }
    leaf pmHoPrepAttLteInterFCaRedirect {
      type uint32;
      config false;
    }
    leaf pmHoPrepAttLteSpifho {
      type uint32;
      config false;
    }
    leaf pmHoExeSuccLteInterFRedirectCsg {
      type uint32;
      config false;
    }
    leaf pmPrbUtilSubscrFailRep {
      type uint32;
      config false;
    }
    leaf pmHoExeSuccLteInterFMbms {
      type uint32;
      config false;
    }
    leaf pmHoExeAttLteIntraFTuneOut {
      type uint32;
      config false;
    }
    leaf pmHoExeSuccLteIntraFTuneOut {
      type uint32;
      config false;
    }
    leaf pmHoWrongCellReestInterF {
      type uint32;
      config false;
    }
    leaf pmAtoQualifiedUe {
      type uint32;
      config false;
    }
    leaf pmHoExeAttLteSpifho {
      type uint32;
      config false;
    }
    leaf pmHoExecSuccLteInterFCaRedirect {
      type uint32;
      config false;
    }
    leaf pmHoOscQci1 {
      type uint32;
      config false;
    }
    leaf pmHoExeAttLteInterFHigherPrio {
      type uint32;
      config false;
    }
    leaf pmHoPrepAttLteInterF {
      type uint32;
      config false;
    }
    leaf pmHoPrepAttLteInterFLb {
      type uint32;
      config false;
    }
    leaf pmHoExeSuccLteIntraF {
      type uint32;
      config false;
    }
    leaf pmZtemporary74 {
      type uint32;
      config false;
    }
    leaf pmLbTpEvalUe {
      type uint32;
      config false;
    }
    leaf pmZtemporary73 {
      type uint32;
      config false;
    }
    leaf pmHoExeAttLteInterFUtvm {
      type uint32;
      config false;
    }
    leaf pmHoPrepAttLteInterFUlTraffic {
      type uint32;
      config false;
    }
    leaf pmHoPrepAttLteInterFEndcHo {
      type uint32;
      config false;
    }
    leaf pmHoPrepSuccLteInterFUlTraffic {
      type uint32;
      config false;
    }
    leaf pmZtemporary72 {
      type uint32;
      config false;
    }
    leaf pmSpifhoReportedUe {
      type ietfinet:port-number;
      config false;
    }
    leaf pmHoPrepAttLteInterFRedirectCsg {
      type uint32;
      config false;
    }
    leaf pmHoPrepAttLteInterFHigherPrio {
      type uint32;
      config false;
    }
    leaf pmHoOscInterF {
      type uint32;
      config false;
    }
    leaf pmHoExeAttLteInterFLb {
      type uint32;
      config false;
    }
    leaf pmHoPrepSuccLteInterFHigherPrio {
      type uint32;
      config false;
    }
    leaf pmHoExeAttLteInterFMbms {
      type uint32;
      config false;
    }
    leaf pmHoExeSuccLteInterFEndcHo {
      type uint32;
      config false;
    }
    leaf pmLbTpUlAcceptedUe {
      type uint32;
      config false;
    }
    leaf pmHoPrepSuccLteInterFMbms {
      type uint32;
      config false;
    }
    leaf pmHoExeAttLteIntraF {
      type uint32;
      config false;
    }
    leaf pmHoPrepSuccLteInterFRedirectCsg {
      type uint32;
      config false;
    }
    leaf pmHoWrongCellInterF {
      type uint32;
      config false;
    }
    leaf pmHoTooEarlyHoInterF {
      type uint32;
      config false;
    }
    leaf pmHoExeAttLteInterFRedirectCsg {
      type uint32;
      config false;
    }
    leaf pmHoTooEarlyHoQci1 {
      type uint32;
      config false;
    }
    leaf pmAtoMeasRepUe {
      type uint32;
      config false;
    }
    leaf pmHoWrongCellReestIntraF {
      type uint32;
      config false;
    }
    leaf pmHoExeOutSuccLteInterFQci1 {
      type uint32;
      config false;
    }
    leaf pmHoExeSuccLteSpifho {
      type uint32;
      config false;
    }
    leaf pmHoExeAttLteInterFEndcHo {
      type uint32;
      config false;
    }
    leaf pmHoPrepAttLteInterFUtvm {
      type uint32;
      config false;
    }
    leaf pmHoExeSuccNonMob {
      type uint32;
      config false;
    }
    leaf pmZtemporary77 {
      type uint32;
      config false;
    }
    leaf pmHoPrepSuccLteInterF {
      type uint32;
      config false;
    }
    leaf pmHoWrongCellIntraF {
      type uint32;
      config false;
    }
    leaf pmHoPrepSuccLteInterFUtvm {
      type uint32;
      config false;
    }
    leaf pmPrbUtilSubscrAtt {
      type uint32;
      config false;
    }
    leaf pmLbQualifiedUe {
      type uint32;
      config false;
    }
    leaf pmHoExeSuccLteInterF {
      type uint32;
      config false;
    }
    leaf pmHoTooLateHoQci1 {
      type uint32;
      config false;
    }
    leaf pmHoOscIntraF {
      type uint32;
      config false;
    }
    leaf pmHoPrepSuccLteInterFEndcHo {
      type uint32;
      config false;
    }
    leaf pmZtemporary76 {
      type uint32;
      config false;
    }
    leaf pmHoPrepSuccNonMob {
      type uint32;
      config false;
    }
    leaf pmCaRedirectQualifiedUe {
      type uint32;
      config false;
    }
    leaf pmHoPrepSuccLteSpifho {
      type uint32;
      config false;
    }
    leaf pmLbTpAcceptedUe {
      type uint32;
      config false;
    }
    leaf pmHoPrepSuccLteInterFCaRedirect {
      type uint32;
      config false;
    }
    leaf pmHoExeSuccLteInterFDtvm {
      type uint32;
      config false;
    }
    leaf pmZtemporary75 {
      type uint32;
      config false;
    }
    leaf pmHoExeAttLteInterFUlTraffic {
      type uint32;
      config false;
    }
    leaf pmHoExeSuccLteInterFHigherPrio {
      type uint32;
      config false;
    }
    leaf pmHoTooEarlyHoIntraF {
      type uint32;
      config false;
    }
    leaf pmHoExeAttLteInterFDtvm {
      type uint32;
      config false;
    }
    leaf pmHoExeOutAttLteInterFQci1 {
      type uint32;
      config false;
    }
    leaf pmHoPrepAttLteInterFUl {
      type uint32;
      config false;
    }
    leaf pmHoPrepAttNonMob {
      type uint32;
      config false;
    }
    leaf pmHoPrepSuccLteInterFLb {
      type uint32;
      config false;
    }
    leaf pmHoPrepAttLteInterFDtvm {
      type uint32;
      config false;
    }
    leaf pmHoExeSuccLteInterFUlTraffic {
      type uint32;
      config false;
    }
    leaf pmHoTooLateHoInterF {
      type uint32;
      config false;
    }
    leaf pmZtemporary78 {
      type uint32;
      config false;
    }
    leaf pmHoPrepSuccLteIntraF {
      type uint32;
      config false;
    }
    leaf pmLbMeasRepUe {
      type uint32;
      config false;
    }
    leaf pmHoExeAttLteInterF {
      type uint32;
      config false;
    }
    leaf pmHoExeSuccLteInterFUtvm {
      type uint32;
      config false;
    }
    leaf pmHoPrepSuccLteInterFUl {
      type uint32;
      config false;
    }
    leaf pmHoTooLateHoIntraF {
      type uint32;
      config false;
    }
    leaf pmHoExecAttLteInterFCaRedirect {
      type uint32;
      config false;
    }
    leaf pmPrbUtilSubscrSucc {
      type uint32;
      config false;
    }
    leaf pmHoExeSuccLteInterFLb {
      type uint32;
      config false;
    }
    leaf pmZtemporary79 {
      type uint32;
      config false;
    }
    leaf pmHoExeAttNonMob {
      type uint32;
      config false;
    }
    leaf pmHoPrepAttLteIntraF {
      type uint32;
      config false;
    }
    leaf pmHoPrepAttLteInterFMbms {
      type uint32;
      config false;
    }
  }
  grouping EUtranCellRelationUnlicensed-attributes {
    leaf eUtranCellRelationUnlicensedId {
      type string;
      mandatory true;
    }
    leaf earfcn {
      type int32 {
        range "0..17999 | 46590..262143";
      }
      default "0";
      description "Default value: 0.";
    }
    leaf sCellPriority {
      type eytypes:int32_range_-1-7;
      default "7";
      description "range -1..7; Default value: 7.";
    }
    leaf coverageIndicator {
      type enumeration {
        enum NONE;
        enum COVERS;
        enum OVERLAP;
        enum CONTAINED_IN;
      }
    }
    leaf neighborCellRef {
      type string;
      mandatory true;
    }
    leaf esCellCaConfigurationAvail {
      type enumeration {
        enum DISABLED;
        enum ENABLED;
        enum NOT_APPLICABLE;
        enum ENABLED_ERAN;
        enum EANBLED_IENB;
        enum DISABLED_CELLSTATE;
        enum DISABLED_LICENSE;
        enum DISABLED_BB_COMPATABILITY;
        enum DISABLED_LINK;
        enum DISABLED_MISMATCHED_MODE;
        enum ENABLED_IENB;
        enum DISABLED_BB_COMPATIBILITY;
        enum LINK_REMOVED_BY_REMOTE_ENB;
        enum ESCELL_LIMIT_EXCEEDED;
        enum CPRI_LATENCY_EXCEEDED;
        enum VLAN_MISMATCH;
        enum TERMPOINT_TO_ENB_DISABLED;
        enum PCELL_DISABLED;
        enum ESCELL_DISABLED;
        enum MAX_PARTNERS_ON_REMOTE_ENB;
        enum MAX_PARTNERS_ON_LOCAL_ENB;
      }
      config false;
      status deprecated;
      description "Takes effect: New connection; Status info: Since 21.Q2. Replaced by sCellCaConfigurationAvail. Planned to be removed..";
      reference "Takes effect: New connection.";
    }
    leaf sCellCaConfigurationAvail {
      type enumeration {
        enum DISABLED;
        enum ENABLED_LOCAL;
        enum ENABLED_ERAN;
        enum ENABLED_IENB;
        enum DISABLED_LICENSE;
        enum DISABLED_BB_COMPATIBILITY;
        enum DISABLED_LINK;
        enum DISABLED_MISMATCHED_MODE;
        enum LINK_REMOVED_BY_REMOTE_ENB;
        enum ESCELL_LIMIT_EXCEEDED;
        enum CANDIDATE_LIMIT_EXCEEDED;
        enum CPRI_LATENCY_EXCEEDED;
        enum VLAN_MISMATCH;
        enum TERMPOINT_TO_ENB_DISABLED;
        enum PCELL_DISABLED;
        enum ESCELL_DISABLED;
        enum LOCAL_SCELL_DISABLED;
        enum MAX_PARTNERS_ON_REMOTE_ENB;
        enum MAX_PARTNERS_ON_LOCAL_ENB;
        enum ERAN_MAX_RTT_DELAY_MISMATCH;
        enum ENABLED_ICM;
        enum CM_SCELL_DISABLED;
        enum ICM_SCELL_DISABLED;
      }
      config false;
    }
  }
  grouping EUtranCellTDD-attributes {
    leaf subframeAssignment {
      type eytypes:int32_range_1-2;
      mandatory true;
      description "range 1..2.";
    }
    leaf specialSubframePattern {
      type int32 {
        range "5..7";
      }
      default "7";
      description "range 5..7; Default value: 7.";
    }
    leaf channelBandwidth {
      type int32 {
        range "5000 | 10000 | 15000 | 20000";
      }
      default "20000";
      units "kHz";
      description "Default value: 20000.";
    }
    leaf earfcn {
      type int32 {
        range "36000..262143";
      }
      mandatory true;
      description "range 36000..262143.";
    }
    leaf eUtranCellTDDId {
      type string;
      mandatory true;
    }
    list frameStartOffset {
      key "id";
      leaf id {
        type uint32;
        description "Synthetic key for struct entry.";
      }
      container attributes {
      leaf subFrameOffset {
        type eytypes:int32_range_0-4;
        default "0";
        description "range 0..4; Default value: 0.";
      }
      leaf timeOffset {
        type int32 {
          range "0..1000000";
        }
        default "0";
        units "ns";
        description "range 0..1000000; Default value: 0.";
      }
      }
    }
    leaf noOfPucchCqiUsers {
      type eytypes:int32_range_0-4000;
      default "16";
      description "range 0..4000; Default value: 16.";
    }
    leaf noOfPucchSrUsers {
      type eytypes:int32_range_0-4000;
      default "16";
      description "range 0..4000; Default value: 16.";
    }
    leaf cellRange {
      type int32 {
        range "1..100";
      }
      default "15";
      units "km";
      description "range 1..100; Default value: 15.";
    }
    leaf transmissionMode {
      type enumeration {
        enum TRANSMISSION_MODE_2;
        enum TRANSMISSION_MODE_3;
        enum TRANSMISSION_MODE_4;
        enum TRANSMISSION_MODE_7;
        enum TRANSMISSION_MODE_8;
        enum TRANSMISSION_MODE_9;
      }
    }
    leaf zzzTemporary3 {
      type string;
    }
    leaf zzzTemporary4 {
      type string;
    }
    leaf zzzTemporary5 {
      type string;
    }
    leaf zzzTemporary6 {
      type string;
    }
    leaf zzzTemporary7 {
      type string;
    }
    leaf zzzTemporary8 {
      type string;
    }
    leaf zzzTemporary9 {
      type int32;
      default "-2000000000";
      description "Default value: -2000000000.";
    }
    leaf zzzTemporary10 {
      type int32;
      default "-2000000000";
      description "Default value: -2000000000.";
    }
    leaf zzzTemporary11 {
      type int32;
      default "-2000000000";
      description "Default value: -2000000000.";
    }
    leaf zzzTemporary12 {
      type int32;
      default "-2000000000";
      description "Default value: -2000000000.";
    }
    leaf commonSrPeriodicity {
      type int32 {
        range "5 | 10 | 20";
      }
      default "20";
      units "ms";
      description "Default value: 20.";
    }
    leaf noOfChannelSelectionSets {
      type int32 {
        range "0 | 4..12";
      }
      default "6";
      units "CS sets";
      description "Default value: 6.";
    }
    leaf csiRsConfigType8TxTDD {
      type enumeration {
        enum NZP_CSIRS;
        enum NZP_ZP_CSIRS;
        enum NZP_CSIRS_TDD;
        enum NZP_ZP_CSIRS_TDD;
      }
    }
    leaf nonCaAnModeMuxEnable {
      type boolean;
      default "false";
      description "Default value: false.";
    }
    leaf nonCaAnModeF3Enable {
      type boolean;
      default "false";
      description "Default value: false.";
    }
    leaf nonCaF3SelectionThreshold {
      type int32 {
        range "1..6000";
      }
      status deprecated;
      default "100";
      description "range 1..6000; Default value: 100; Takes effect: New connection; Status info: Since 17.Q1. Planned to be removed..";
      reference "Takes effect: New connection.";
    }
    leaf noOfPucchFormat3PrbPairs {
      type eytypes:int32_range_0-3;
      default "1";
      description "range 0..3; Default value: 1.";
    }
    leaf isLaa {
      type boolean;
      default "false";
      description "Default value: false.";
    }
    leaf isDlOnly {
      type boolean;
      default "false";
      description "Default value: false.";
    }
    leaf nonCaF3ResCollisionThresh {
      type eytypes:int32_range_1-100;
      default "20";
      units "percent";
      description "range 1..100; Default value: 20.";
    }
    leaf nonCaHarqAnModeMuxThresh {
      type eytypes:int32_range_1-100-4;
      default "2";
      description "range 1..100; Default value: 2.";
    }
    leaf timePhaseMaxDeviationTddIndex {
      type enumeration {
        enum TIME_PHASE_MAX_DEVIATION_TDD_IDX0;
        enum TIME_PHASE_MAX_DEVIATION_TDD_IDX1;
        enum TIME_PHASE_MAX_DEVIATION_TDD_IDX2;
        enum TIME_PHASE_MAX_DEVIATION_TDD_IDX3;
        enum TIME_PHASE_MAX_DEVIATION_TDD_IDX4;
        enum TIME_PHASE_MAX_DEVIATION_TDD_IDX5;
        enum TIME_PHASE_MAX_DEVIATION_TDD_IDX6;
        enum TIME_PHASE_MAX_DEVIATION_TDD_IDX7;
      }
    }
    leaf ulMaxMuMimoLayers {
      type int32 {
        range "0 | 2 | 4 | 8";
      }
      default "0";
      description "Default value: 0.";
    }
    leaf dlMaxMuMimoLayers {
      type int32 {
        range "0 | 2 | 4 | 6 | 8 | 10 | 12 | 14 | 16";
      }
      default "0";
      description "Default value: 0.";
    }
    leaf tm7ModeSwitchingEnabled {
      type boolean;
      default "false";
      description "Default value: false.";
    }
    leaf tm8ModeSwitchingEnabled {
      type boolean;
      default "false";
      description "Default value: false.";
    }
    leaf extGUtranCellRef {
      type string;
    }
    leaf cbrsCell {
      type boolean;
      default "false";
      description "Default value: false.";
    }
    leaf cbrsTxExpireTime {
      type string {
        length "0..31";
      }
      config false;
      description "length 0..31.";
    }
    leaf prachFrequencyAllocation {
      type eytypes:int32_range_0-1;
      default "0";
      description "range 0..1; Default value: 0.";
    }
    leaf noOfPucchFormat1PrbPairsPerFrameConf {
      type eytypes:int32_range_0-22;
      default "3";
      description "range 0..22; Default value: 3.";
    }
    leaf noOfPucchFormat2PrbPairsPerFrameConf {
      type eytypes:int32_range_0-22;
      default "1";
      description "range 0..22; Default value: 1.";
    }
    leaf noOfPucchSrUsersCalc {
      type eytypes:int32_range_0-4000;
      config false;
      description "range 0..4000.";
    }
    leaf noOfPucchCqiUsersCalc {
      type eytypes:int32_range_0-4000;
      config false;
      description "range 0..4000.";
    }
    leaf zzzTemporary90 {
      type string;
    }
    leaf zzzTemporary91 {
      type string;
    }
    leaf zzzTemporary92 {
      type int32;
      default "-2000000000";
      description "Default value: -2000000000.";
    }
    leaf zzzTemporary93 {
      type int32;
      default "-2000000000";
      description "Default value: -2000000000.";
    }
    leaf zzzTemporary94 {
      type int32;
      default "-2000000000";
      description "Default value: -2000000000.";
    }
    leaf csiRsConfigType {
      type enumeration {
        enum NZP_CSIRS;
        enum NZP_ZP_CSIRS;
        enum NZP_CSIRS_TDD;
        enum NZP_ZP_CSIRS_TDD;
        enum NZP_CSIRS_RE_CFG_IDX_20_TDD;
      }
    }
    leaf tm9Allowed {
      type boolean;
      default "false";
      description "Default value: false.";
    }
    leaf tm9ModeSwitchingEnabled {
      type boolean;
      default "false";
      description "Default value: false.";
    }
    list ductIntPerfTuning {
      key "id";
      leaf id {
        type uint32;
        description "Synthetic key for struct entry.";
      }
      container attributes {
      leaf ductIntBgNoiseThr {
        type int32 {
          range "-130..-80";
        }
        default "-110";
        units "dBm";
        description "range -130..-80; Default value: -110.";
      }
      leaf ductIntCharSeqCorrPeakThr {
        type int32 {
          range "5..50";
        }
        default "20";
        description "range 5..50; Default value: 20.";
      }
      leaf ductIntCharSeqPwrDiff {
        type int32 {
          range "0..7";
        }
        default "5";
        units "dB";
        description "range 0..7; Default value: 5.";
      }
      leaf ductIntRedTriggerThr {
        type eytypes:int32_range_0-20;
        default "8";
        description "range 0..20; Default value: 8.";
      }
      leaf ductIntRedRecovThr {
        type eytypes:int32_range_0-20;
        default "2";
        description "range 0..20; Default value: 2.";
      }
      leaf ductIntCharSeqPwrThr {
        type int32 {
          range "-120..-80";
        }
        default "-120";
        units "dBm";
        description "range -120..-80; Default value: -120.";
      }
      leaf ductIntSlopePwrDiffThr {
        type eytypes:int32_range_1-8-14;
        default "3";
        units "dB";
        description "range 1..8; Default value: 3.";
      }
      leaf ductIntSlopeDetectPeriod {
        type int32 {
          range "1..30";
        }
        default "10";
        units "minutes";
        description "range 1..30; Default value: 10.";
      }
      leaf ductIntSlopeDetectRatioThr {
        type eytypes:int32_range_1-100;
        default "50";
        units "percent";
        description "range 1..100; Default value: 50.";
      }
      leaf ductIntCharSeqTransThr {
        type int32 {
          range "1..20";
        }
        default "3";
        description "range 1..20; Default value: 3.";
      }
      }
    }
    leaf ductIntOpMode {
      type enumeration {
        enum DISABLED;
        enum DETECTION;
        enum LOCATION;
        enum REDUCTION;
      }
    }
    leaf ductIntSspStatus {
      type int32 {
        range "5..7";
      }
      config false;
      description "range 5..7.";
    }
    leaf ductIntSlopeDetectionStatus {
      type boolean;
      config false;
    }
    leaf ductIntCharSeqDetectionStatus {
      type boolean;
      config false;
    }
    leaf ductIntReductionStatus {
      type boolean;
      config false;
    }
    leaf ailgRef {
      type string;
    }
    leaf ailgActive {
      type boolean;
      config false;
    }
    list changeNotification {
      key "id";
      leaf id {
        type uint32;
        description "Synthetic key for struct entry.";
      }
      container attributes {
      leaf changeNotificationSIB2 {
        type boolean;
        default "true";
        description "Default value: true.";
      }
      leaf changeNotificationSIB3 {
        type boolean;
        default "true";
        description "Default value: true.";
      }
      leaf changeNotificationSIB4 {
        type boolean;
        default "true";
        description "Default value: true.";
      }
      leaf changeNotificationSIB5 {
        type boolean;
        default "true";
        description "Default value: true.";
      }
      leaf changeNotificationSIB6 {
        type boolean;
        default "true";
        description "Default value: true.";
      }
      leaf changeNotificationSIB7 {
        type boolean;
        default "true";
        description "Default value: true.";
      }
      leaf changeNotificationSIB8 {
        type boolean;
        default "true";
        description "Default value: true.";
      }
      leaf changeNotificationSIB1 {
        type boolean;
        default "true";
        description "Default value: true.";
      }
      leaf changeNotificationSIB15 {
        type boolean;
        default "true";
        description "Default value: true.";
      }
      leaf changeNotificationSIB16 {
        type boolean;
        default "true";
        description "Default value: true.";
      }
      leaf changeNotificationSIB13 {
        type boolean;
        default "true";
        description "Default value: true.";
      }
      leaf changeNotificationSIB24 {
        type boolean;
        default "true";
        description "Default value: true.";
      }
      }
    }
    list mappingInfo {
      key "id";
      leaf id {
        type uint32;
        description "Synthetic key for struct entry.";
      }
      container attributes {
      leaf mappingInfoSIB4 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB5 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB6 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB7 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB8 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB3 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB10 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB11 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB12 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB15 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB16 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB13 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB24 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      }
    }
    leaf modificationPeriodCoeff {
      type int32 {
        range "2 | 4 | 8 | 16";
      }
      default "2";
      description "Default value: 2.";
    }
    list siPeriodicity {
      key "id";
      leaf id {
        type uint32;
        description "Synthetic key for struct entry.";
      }
      container attributes {
      leaf siPeriodicitySI9 {
        type ietfinet:ip-address;
        units "rf (radio frames)";
        description "Default value: 64.";
      }
      leaf siPeriodicitySI8 {
        type ietfinet:ip-address;
        units "rf (radio frames)";
        description "Default value: 64.";
      }
      leaf siPeriodicitySI10 {
        type ietfinet:ip-address;
        units "rf (radio frames)";
        description "Default value: 64.";
      }
      leaf siPeriodicitySI2 {
        type ietfinet:ip-address;
        units "rf (radioframes)";
        description "Default value: 64.";
      }
      leaf siPeriodicitySI3 {
        type ietfinet:ip-address;
        units "rf (radioframes)";
        description "Default value: 64.";
      }
      leaf siPeriodicitySI4 {
        type ietfinet:ip-address;
        units "rf (radioframes)";
        description "Default value: 64.";
      }
      leaf siPeriodicitySI5 {
        type ietfinet:ip-address;
        units "rf (radioframes)";
        description "Default value: 64.";
      }
      leaf siPeriodicitySI6 {
        type ietfinet:ip-address;
        units "rf (radioframes)";
        description "Default value: 64.";
      }
      leaf siPeriodicitySI7 {
        type ietfinet:ip-address;
        units "rf (radioframes)";
        description "Default value: 64.";
      }
      leaf siPeriodicitySI1 {
        type ietfinet:ip-address;
        units "rf (radioframes)";
        description "Default value: 8.";
      }
      }
    }
    leaf siWindowLength {
      type int32 {
        range "1..2 | 5 | 10 | 15 | 20 | 40";
      }
      default "10";
      units "ms";
      description "Default value: 10.";
    }
    leaf qRxLevMin {
      type eytypes:int32_range_-140--44;
      default "-140";
      units "dBm";
      description "range -140..-44; Default value: -140.";
    }
    leaf minBestCellHoAttempts {
      type eytypes:int32_range_1-10;
      default "1";
      description "range 1..10; Default value: 1.";
    }
    list systemInformationBlock6 {
      key "id";
      leaf id {
        type uint32;
        description "Synthetic key for struct entry.";
      }
      container attributes {
      leaf tReselectionUtra {
        type eytypes:int32_range_0-7-9;
        default "2";
        units "s";
        description "range 0..7; Default value: 2.";
      }
      leaf tReselectionUtraSfMedium {
        type eytypes:int32_range_25-100-26;
        default "100";
        units "percent";
        description "range 25..100; Default value: 100.";
      }
      leaf tReselectionUtraSfHigh {
        type eytypes:int32_range_25-100-26;
        default "100";
        units "percent";
        description "range 25..100; Default value: 100.";
      }
      }
    }
    list systemInformationBlock7 {
      key "id";
      leaf id {
        type uint32;
        description "Synthetic key for struct entry.";
      }
      container attributes {
      leaf tReselectionGeran {
        type eytypes:int32_range_0-7;
        default "2";
        description "range 0..7; Default value: 2.";
      }
      leaf tReselectionGeranSfMedium {
        type eytypes:int32_range_25-100;
        default "100";
        description "range 25..100; Default value: 100.";
      }
      leaf tReselectionGeranSfHigh {
        type eytypes:int32_range_25-100;
        default "100";
        description "range 25..100; Default value: 100.";
      }
      }
    }
    list systemInformationBlock8 {
      key "id";
      leaf id {
        type uint32;
        description "Synthetic key for struct entry.";
      }
      container attributes {
      leaf searchWindowSizeCdma {
        type eytypes:int32_range_0-15;
        default "8";
        description "range 0..15; Default value: 8.";
      }
      leaf tReselectionCdmaHrpd {
        type eytypes:int32_range_0-7-9;
        default "2";
        units "s";
        description "range 0..7; Default value: 2.";
      }
      leaf tReselectionCdmaHrpdSfMedium {
        type eytypes:int32_range_25-100-26;
        default "100";
        units "percent";
        description "range 25..100; Default value: 100.";
      }
      leaf tReselectionCdmaHrpdSfHigh {
        type eytypes:int32_range_25-100-26;
        default "100";
        units "percent";
        description "range 25..100; Default value: 100.";
      }
      leaf tReselectionCdma1xRtt {
        type int32 {
          range "0..7";
        }
        default "2";
        units "second";
        description "range 0..7; Default value: 2.";
      }
      leaf tReselectionCdma1xRttSfHigh {
        type eytypes:int32_range_25-100-26;
        default "100";
        units "percent";
        description "range 25..100; Default value: 100.";
      }
      leaf tReselectionCdma1xRttSfMedium {
        type eytypes:int32_range_25-100-26;
        default "100";
        units "percent";
        description "range 25..100; Default value: 100.";
      }
      }
    }
    leaf-list reservedBy {
      type string;
    }
    list systemInformationBlock3 {
      key "id";
      leaf id {
        type uint32;
        description "Synthetic key for struct entry.";
      }
      container attributes {
      leaf qHyst {
        type int32;
        default "4";
        units "dB";
        description "Default value: 4.";
      }
      leaf tEvaluation {
        type int32;
        default "240";
        units "s";
        description "Default value: 240.";
      }
      leaf tHystNormal {
        type int32;
        default "240";
        units "s";
        description "Default value: 240.";
      }
      leaf nCellChangeMedium {
        type eytypes:int32_range_1-16;
        default "16";
        description "range 1..16; Default value: 16.";
      }
      leaf nCellChangeHigh {
        type eytypes:int32_range_1-16;
        default "16";
        description "range 1..16; Default value: 16.";
      }
      leaf qHystSfMedium {
        type eytypes:int32_range_-6-0;
        default "0";
        units "dB";
        description "range -6..0; Default value: 0.";
      }
      leaf qHystSfHigh {
        type eytypes:int32_range_-6-0;
        default "0";
        units "dB";
        description "range -6..0; Default value: 0.";
      }
      leaf sIntraSearch {
        type int32;
        default "1000";
        units "dB";
        description "Default value: 1000.";
      }
      leaf sNonIntraSearch {
        type int32;
        default "0";
        units "dB";
        description "Default value: 0.";
      }
      leaf sIntraSearchQ {
        type eytypes:int32_range_0-31;
        default "0";
        units "dB";
        description "range 0..31; Default value: 0.";
      }
      leaf sIntraSearchP {
        type eytypes:int32_range_0-62;
        default "62";
        units "dB";
        description "range 0..62; Default value: 62.";
      }
      leaf sNonIntraSearchQ {
        type eytypes:int32_range_0-31;
        default "0";
        units "dB";
        description "range 0..31; Default value: 0.";
      }
      leaf sNonIntraSearchP {
        type eytypes:int32_range_0-62;
        default "0";
        units "dB";
        description "range 0..62; Default value: 0.";
      }
      leaf threshServingLowQ {
        type int32;
        default "1000";
        units "dB";
        description "Default value: 1000.";
      }
      leaf sIntraSearchv920Active {
        type boolean;
        default "false";
        description "Default value: false.";
      }
      leaf sNonIntraSearchv920Active {
        type boolean;
        default "false";
        description "Default value: false.";
      }
      }
    }
    leaf ulInterferenceManagementActive {
      type boolean;
      default "true";
      description "Default value: true.";
    }
    leaf ulInterferenceManagementDuration {
      type eytypes:int32_range_0-10000-25;
      default "5000";
      units "s";
      description "range 0..10000; Default value: 5000.";
    }
    leaf-list activeMtdMeasurements {
      type eytypes:int32_range_0-255;
    }
    leaf cellBarred {
      type enumeration {
        enum BARRED;
        enum NOT_BARRED;
      }
    }
    leaf dlInterferenceManagementActive {
      type boolean;
      default "false";
      description "Default value: false.";
    }
    leaf dlInterferenceManagementDuration {
      type eytypes:int32_range_0-10000-25;
      default "100";
      units "s";
      description "range 0..10000; Default value: 100.";
    }
    leaf pMaxServingCell {
      type int32 {
        range "-30..33 | 1000";
      }
      default "1000";
      description "Default value: 1000.";
    }
    leaf pZeroNominalPucch {
      type eytypes:int32_range_-127--96;
      default "-117";
      units "dBm";
      description "range -127..-96; Default value: -117.";
    }
    leaf pZeroNominalPusch {
      type eytypes:int32_range_-126-24;
      default "-103";
      units "dBm";
      description "range -126..24; Default value: -103.";
    }
    leaf qciTableRef {
      type string;
    }
    leaf rachNoOfAllocationsPerFrame {
      type int32 {
        range "5 | 10 | 20 | 30 | 50 | 100";
      }
      default "10";
      description "Default value: 10.";
    }
    leaf rachPreambleRepetition {
      type boolean;
      default "false";
      description "Default value: false.";
    }
    leaf rachRootSequence {
      type eytypes:int32_range_0-837;
      default "386";
      description "range 0..837; Default value: 386.";
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf operationalState {
      type enumeration {
        enum DISABLED;
        enum ENABLED;
      }
      config false;
    }
    leaf administrativeState {
      type enumeration {
        enum LOCKED;
        enum UNLOCKED;
        enum SHUTTINGDOWN;
      }
    }
    leaf cellId {
      type eytypes:int32_range_0-255;
      mandatory true;
      description "range 0..255.";
    }
    leaf physicalLayerCellIdGroup {
      type eytypes:int32_range_0-167;
      mandatory true;
      description "range 0..167.";
    }
    leaf physicalLayerSubCellId {
      type eytypes:int32_range_0-2;
      mandatory true;
      description "range 0..2.";
    }
    leaf userLabel {
      type string {
        length "1..128";
      }
      description "length 1..128.";
    }
    leaf tac {
      type eytypes:int32_range_0-65535-10;
      mandatory true;
      description "range 0..65535.";
    }
    leaf drxActive {
      type boolean;
      default "false";
      description "Default value: false.";
    }
    leaf networkSignallingValue {
      type enumeration {
        enum NS_01;
        enum NS_03;
        enum NS_04;
        enum NS_05;
        enum NS_06;
        enum NS_07;
        enum NS_08;
        enum NS_09;
        enum NS_10;
        enum NS_11;
        enum NS_12;
        enum NS_13;
        enum NS_14;
        enum NS_15;
        enum NS_16;
        enum NS_17;
        enum NS_18;
        enum NS_19;
        enum NS_20;
        enum NS_21;
        enum NS_22;
        enum NS_23;
        enum NS_24;
        enum NS_25;
        enum NS_26;
        enum NS_27;
        enum NS_28;
        enum NS_29;
        enum NS_30;
        enum NS_31;
        enum NS_32;
        enum NS_35;
      }
    }
    leaf initCdma2000SysTimeType {
      type enumeration {
        enum NONE;
        enum SYNCHRONOUS;
        enum ASYNCHRONOUS;
      }
    }
    leaf bcCdma2000SysTimeType {
      type enumeration {
        enum NONE;
        enum SYNCHRONOUS;
        enum ASYNCHRONOUS;
      }
      config false;
    }
    leaf pucchOverdimensioning {
      type int32 {
        range "0..49";
      }
      default "0";
      units "Resource Block";
      description "range 0..49; Default value: 0.";
    }
    leaf qRxLevMinOffset {
      type int32 {
        range "2..16 | 1000";
      }
      default "1000";
      units "dB";
      description "Default value: 1000.";
    }
    leaf estimatedE2ERTT {
      type int32 {
        range "0..2048";
      }
      default "100";
      units "ms";
      description "range 0..2048; Default value: 100.";
    }
    leaf otdoaSuplActive {
      type boolean;
      default "false";
      description "Default value: false.";
    }
    leaf prsConfigIndex {
      type int32 {
        range "-1..4095";
      }
      default "-1";
      description "range -1..4095; Default value: -1.";
    }
    leaf noConsecutiveSubframes {
      type enumeration {
        enum SF1;
        enum SF2;
        enum SF4;
        enum SF6;
      }
    }
    leaf latitude {
      type eytypes:int32_range_-90000000-90000000;
      default "0";
      units "degrees";
      description "range -90000000..90000000; Default value: 0.";
    }
    leaf longitude {
      type eytypes:int32_range_-180000000-180000000;
      default "0";
      units "degrees";
      description "range -180000000..180000000; Default value: 0.";
    }
    leaf altitude {
      type int32 {
        range "-32768..32767";
      }
      default "0";
      units "meter";
      description "range -32768..32767; Default value: 0.";
    }
    leaf uncertSemiMajor {
      type eytypes:int32_range_0-127;
      default "0";
      description "range 0..127; Default value: 0.";
    }
    leaf uncertSemiMinor {
      type eytypes:int32_range_0-127;
      default "0";
      description "range 0..127; Default value: 0.";
    }
    leaf orientMajorAxis {
      type int32 {
        range "0..179";
      }
      default "0";
      units "degrees";
      description "range 0..179; Default value: 0.";
    }
    leaf uncertAltitude {
      type eytypes:int32_range_0-127;
      default "0";
      description "range 0..127; Default value: 0.";
    }
    leaf confidence {
      type eytypes:int32_range_0-100-27;
      default "100";
      units "percent";
      description "range 0..100; Default value: 100.";
    }
    leaf gpsTimeSFN0DecimalSecond {
      type eytypes:int64_range_0-4294967295;
      config false;
      description "range 0..4294967295.";
    }
    leaf primaryPlmnReserved {
      type boolean;
      default "false";
      description "Default value: false.";
    }
    leaf-list additionalPlmnReservedList {
      type boolean;
    }
    list additionalPlmnList {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    list activePlmnList {
      config false;
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf gpsTimeSFN0Seconds {
      type int64 {
        range "0..4294967295";
      }
      config false;
      units "seconds";
      description "range 0..4294967295.";
    }
    leaf prsPeriod {
      type enumeration {
        enum PP160;
        enum PP320;
        enum PP640;
        enum PP1280;
      }
    }
    leaf covTriggerdBlindHoAllowed {
      type boolean;
      default "true";
      description "Default value: true.";
    }
    leaf dlConfigurableFrequencyStart {
      type eytypes:int32_range_0-100-27;
      default "0";
      units "percent";
      description "range 0..100; Default value: 0.";
    }
    leaf ulConfigurableFrequencyStart {
      type eytypes:int32_range_0-100-27;
      default "0";
      units "percent";
      description "range 0..100; Default value: 0.";
    }
    leaf dlFrequencyAllocationProportion {
      type ietfinet:port-number;
      default "100";
      units "percent";
      description "range 0..100; Default value: 100.";
    }
    leaf ulFrequencyAllocationProportion {
      type ietfinet:port-number;
      default "100";
      units "percent";
      description "range 0..100; Default value: 100.";
    }
    list eutranCellPolygon {
      key "id";
      leaf id {
        type uint32;
        description "Synthetic key for struct sequence entry.";
      }
      container attributes {
      leaf cornerLatitude {
        type eytypes:int32_range_-90000000-90000000;
        default "0";
        units "degrees";
        description "range -90000000..90000000; Default value: 0.";
      }
      leaf cornerLongitude {
        type eytypes:int32_range_-180000000-180000000;
        default "0";
        units "degrees";
        description "range -180000000..180000000; Default value: 0.";
      }
      }
    }
    leaf prsConfigIndexMapped {
      type eytypes:int32_range_0-4095;
      config false;
      description "range 0..4095.";
    }
    list eutranCellCoverage {
      key "id";
      leaf id {
        type uint32;
        description "Synthetic key for struct entry.";
      }
      container attributes {
      leaf posCellRadius {
        type eytypes:int32_range_0-200000;
        default "0";
        units "meter";
        description "range 0..200000; Default value: 0.";
      }
      leaf posCellOpeningAngle {
        type eytypes:int32_range_-1-3599;
        default "-1";
        units "degrees";
        description "range -1..3599; Default value: -1.";
      }
      leaf posCellBearing {
        type eytypes:int32_range_-1-3599;
        default "-1";
        units "degrees";
        description "range -1..3599; Default value: -1.";
      }
      }
    }
    leaf qQualMin {
      type int32 {
        range "-34..-3 | 0";
      }
      default "0";
      units "dB";
      description "Default value: 0.";
    }
    leaf qQualMinOffset {
      type eytypes:int32_range_0-8-28;
      default "0";
      units "dB";
      description "range 0..8; Default value: 0.";
    }
    leaf pdcchCfiMode {
      type enumeration {
        enum CFI_STATIC_BY_BW;
        enum CFI_STATIC_1;
        enum CFI_STATIC_2;
        enum CFI_STATIC_3;
        enum CFI_AUTO_MAXIMUM_2;
        enum CFI_AUTO_MAXIMUM_3;
      }
    }
    leaf ulSrsEnable {
      type boolean;
      default "false";
      description "Default value: false.";
    }
    leaf rateShapingActive {
      type boolean;
      default "false";
      description "Default value: false.";
    }
    leaf cellSubscriptionCapacity {
      type ietfinet:ip-address;
      description "range 0..1000000; Default value: 1000.";
    }
    leaf threshServingLow {
      type eytypes:int32_range_0-62;
      default "0";
      units "dB";
      description "range 0..62; Default value: 0.";
    }
    leaf-list pciConflict {
      type enumeration {
        enum NO;
        enum NO_CONFLICTING_CELL;
        enum YES;
        enum YES_CONFLICTING_CELL;
      }
    }
    leaf lastModification {
      type enumeration {
        enum OPERATOR;
        enum PCI_MODIFICATION;
        enum RACH_OPT_MODIFICATION;
        enum OSS_PCI_MODIFICATION;
      }
    }
    list pciConflictCell {
      key "id";
      leaf id {
        type uint32;
        description "Synthetic key for struct sequence entry.";
      }
      container attributes {
      leaf enbId {
        type eytypes:int32_range_0-1048575;
        default "0";
        description "range 0..1048575; Default value: 0.";
      }
      leaf cellId {
        type eytypes:int32_range_0-255;
        default "0";
        description "range 0..255; Default value: 0.";
      }
      leaf mcc {
        type eytypes:int32_range_0-999;
        default "1";
        description "range 0..999; Default value: 1.";
      }
      leaf mnc {
        type eytypes:int32_range_0-999;
        default "1";
        description "range 0..999; Default value: 1.";
      }
      leaf mncLength {
        type eytypes:int32_range_2-3;
        default "2";
        description "range 2..3; Default value: 2.";
      }
      }
    }
    leaf timeOfLastModification {
      type string {
        length "0..19";
      }
      description "length 0..19.";
    }
    leaf cfraEnable {
      type boolean;
      default "false";
      description "Default value: false.";
    }
    leaf acBarringInfoPresent {
      type boolean;
      default "false";
      description "Default value: false.";
    }
    list acBarringForMoSignalling {
      key "id";
      leaf id {
        type uint32;
        description "Synthetic key for struct entry.";
      }
      container attributes {
      leaf acBarringFactor {
        type int32;
        default "95";
        units "percent";
        description "Default value: 95.";
      }
      leaf acBarringTime {
        type int32;
        default "64";
        units "s";
        description "Default value: 64.";
      }
      leaf acBarringForSpecialAC {
        type string;
      }
      }
    }
    list acBarringForMoData {
      key "id";
      leaf id {
        type uint32;
        description "Synthetic key for struct entry.";
      }
      container attributes {
      leaf acBarringFactor {
        type int32;
        default "95";
        units "percent";
        description "Default value: 95.";
      }
      leaf acBarringTime {
        type int32;
        default "64";
        units "s";
        description "Default value: 64.";
      }
      leaf acBarringForSpecialAC {
        type string;
      }
      }
    }
    leaf ssacBarringForMMTELVoicePresent {
      type boolean;
      status deprecated;
      default "false";
      description "Default value: false; Status info: Since 17.Q3. Replaced by AcBarringPresence.acBarringForMmtelVoicePresence in EUtranCellFDD/EUtranCellTDD::acBarringPresence. Planned to be removed..";
    }
    leaf ssacBarringForMMTELVideoPresent {
      type boolean;
      status deprecated;
      default "false";
      description "Default value: false; Status info: Since 17.Q3. Replaced by AcBarringPresence.acBarringForMmtelVideoPresence in EUtranCellFDD/EUtranCellTDD::acBarringPresence. Planned to be removed..";
    }
    list ssacBarringForMMTELVoice {
      key "id";
      leaf id {
        type uint32;
        description "Synthetic key for struct entry.";
      }
      container attributes {
      leaf acBarringFactor {
        type int32;
        default "95";
        units "percent";
        description "Default value: 95.";
      }
      leaf acBarringTime {
        type int32;
        default "64";
        units "s";
        description "Default value: 64.";
      }
      leaf acBarringForSpecialAC {
        type string;
      }
      }
    }
    list ssacBarringForMMTELVideo {
      key "id";
      leaf id {
        type uint32;
        description "Synthetic key for struct entry.";
      }
      container attributes {
      leaf acBarringFactor {
        type int32;
        default "95";
        units "percent";
        description "Default value: 95.";
      }
      leaf acBarringTime {
        type int32;
        default "64";
        units "s";
        description "Default value: 64.";
      }
      leaf acBarringForSpecialAC {
        type string;
      }
      }
    }
    leaf acBarringForEmergency {
      type boolean;
      default "false";
      description "Default value: false.";
    }
    list pciDetectingCell {
      key "id";
      leaf id {
        type uint32;
        description "Synthetic key for struct sequence entry.";
      }
      container attributes {
      leaf enbId {
        type eytypes:int32_range_0-1048575;
        default "0";
        description "range 0..1048575; Default value: 0.";
      }
      leaf cellId {
        type eytypes:int32_range_0-255;
        default "0";
        description "range 0..255; Default value: 0.";
      }
      leaf mcc {
        type eytypes:int32_range_0-999;
        default "1";
        description "range 0..999; Default value: 1.";
      }
      leaf mnc {
        type eytypes:int32_range_0-999;
        default "1";
        description "range 0..999; Default value: 1.";
      }
      leaf mncLength {
        type eytypes:int32_range_2-3;
        default "2";
        description "range 2..3; Default value: 2.";
      }
      }
    }
    leaf-list emergencyAreaId {
      type eytypes:int32_range_-1-16777215;
    }
    leaf hostingDigitalUnit {
      type string;
      config false;
    }
    leaf highSpeedUEActive {
      type boolean;
      default "false";
      description "Default value: false.";
    }
    leaf advCellSupSensitivity {
      type eytypes:int32_range_0-100-3;
      default "0";
      description "range 0..100; Default value: 0.";
    }
    leaf advCellSupAction {
      type enumeration {
        enum NO_ACTION;
        enum CELL_RESTART;
        enum CELL_AND_NODE_RESTART;
      }
    }
    leaf hoOptStatTime {
      type int32 {
        range "1..32767";
      }
      default "24";
      units "hour";
      description "range 1..32767; Default value: 24.";
    }
    leaf hoOptStatNum {
      type eytypes:int32_range_1-32767;
      default "200";
      description "range 1..32767; Default value: 200.";
    }
    leaf mobCtrlAtPoorCovActive {
      type boolean;
      default "false";
      description "Default value: false.";
    }
    leaf sdmActive {
      type ietfyang:mac-address;
      description "Default value: false.";
    }
    leaf-list sectorCarrierRef {
      type string;
    }
    leaf lbUtranOffloadThreshold {
      type int32 {
        range "0..1600";
      }
      default "100";
      description "range 0..1600; Default value: 100.";
    }
    leaf externalCdma20001xRttCellRef {
      type string;
    }
    list acBarringForCsfb {
      key "id";
      leaf id {
        type uint32;
        description "Synthetic key for struct entry.";
      }
      container attributes {
      leaf acBarringFactor {
        type int32;
        default "95";
        units "percent";
        description "Default value: 95.";
      }
      leaf acBarringTime {
        type int32;
        default "64";
        units "s";
        description "Default value: 64.";
      }
      leaf acBarringForSpecialAC {
        type string;
      }
      }
    }
    leaf zzzTemporary14 {
      type int32;
      status deprecated;
      default "-2000000000";
      description "Default value: -2000000000; Status info: Since 20.Q1. Has no functional behavior. Planned to be removed..";
    }
    leaf zzzTemporary17 {
      type int32;
      default "-2000000000";
      description "Default value: -2000000000.";
    }
    leaf-list activeServiceAreaId {
      type eytypes:int32_range_0-65535-10;
    }
    leaf pdcchPowerBoostMax {
      type eytypes:int32_range_0-6;
      default "0";
      units "dB";
      description "range 0..6; Default value: 0.";
    }
    leaf alpha {
      type int32 {
        range "0 | 4..10";
      }
      default "10";
      units ".";
      description "Default value: 10.";
    }
    leaf lbEUtranTriggerOffloadThreshold {
      type eytypes:int32_range_0-1600;
      default "100";
      units ".";
      description "range 0..1600; Default value: 100.";
    }
    leaf lbEUtranAcceptOffloadThreshold {
      type eytypes:int32_range_0-1600;
      default "50";
      units ".";
      description "range 0..1600; Default value: 50.";
    }
    leaf lbEUtranCellOffloadCapacity {
      type eytypes:int32_range_0-1000000-18;
      default "1000";
      description "range 0..1000000; Default value: 1000.";
    }
    leaf-list additionalFreqBandList {
      type eytypes:int32_range_1-256;
    }
    leaf freqBand {
      type eytypes:int32_range_1-256;
      config false;
      description "range 1..256.";
    }
    leaf hoOptAdjThresholdAbs {
      type eytypes:int32_range_0-32767;
      default "5";
      description "range 0..32767; Default value: 5.";
    }
    leaf hoOptAdjThresholdPerc {
      type eytypes:int32_range_0-1000-11;
      default "50";
      units "percent";
      description "range 0..1000; Default value: 50.";
    }
    leaf crsGain {
      type int32 {
        range "-300 | -200 | -100 | 0 | 177 | 300 | 477 | 600";
      }
      default "0";
      units "dB";
      description "Default value: 0.";
    }
    leaf dynCellSubscrCap {
      type eytypes:int32_range_0-1000000;
      config false;
      units "kbps";
      description "range 0..1000000.";
    }
    leaf cellCapMinCellSubCap {
      type eytypes:int32_range_0-1000000;
      default "500";
      units "kbps";
      description "range 0..1000000; Default value: 500.";
    }
    leaf cellCapMaxCellSubCap {
      type eytypes:int32_range_0-1000000;
      default "1500";
      units "kbps";
      description "range 0..1000000; Default value: 1500.";
    }
    leaf-list additionalSpectrumEmissionValues {
      type enumeration {
        enum NS_01;
        enum NS_03;
        enum NS_04;
        enum NS_05;
        enum NS_06;
        enum NS_07;
        enum NS_08;
        enum NS_09;
        enum NS_10;
        enum NS_11;
        enum NS_12;
        enum NS_13;
        enum NS_14;
        enum NS_15;
        enum NS_16;
        enum NS_17;
        enum NS_18;
        enum NS_19;
        enum NS_20;
        enum NS_21;
        enum NS_22;
        enum NS_23;
        enum NS_24;
        enum NS_25;
        enum NS_26;
        enum NS_27;
        enum NS_28;
        enum NS_29;
        enum NS_30;
        enum NS_31;
        enum NS_32;
        enum NS_35;
      }
    }
    list spectrumEmissionReqMapping {
      key "id";
      leaf id {
        type uint32;
        description "Synthetic key for struct sequence entry.";
      }
      container attributes {
      leaf freqBand {
        type eytypes:int32_range_1-256;
        default "1";
        description "range 1..256; Default value: 1.";
      }
      leaf spectrumEmissionReq {
        type enumeration {
          enum NS_01;
          enum NS_03;
          enum NS_04;
          enum NS_05;
          enum NS_06;
          enum NS_07;
          enum NS_08;
          enum NS_09;
          enum NS_10;
          enum NS_11;
          enum NS_12;
          enum NS_13;
          enum NS_14;
          enum NS_15;
          enum NS_16;
          enum NS_17;
          enum NS_18;
          enum NS_19;
          enum NS_20;
          enum NS_21;
          enum NS_22;
          enum NS_23;
          enum NS_24;
          enum NS_25;
          enum NS_26;
          enum NS_27;
          enum NS_28;
          enum NS_29;
          enum NS_30;
          enum NS_31;
          enum NS_32;
          enum NS_35;
        }
      }
      }
    }
    leaf expectedMaxNoOfUsersInCell {
      type int32 {
        range "-1..32768";
      }
      default "-1";
      description "range -1..32768; Default value: -1.";
    }
    leaf measuredMaxNoOfUsersInCell {
      type eytypes:int32_range_0-32768;
      config false;
      description "range 0..32768.";
    }
    leaf pdcchLaGinrMargin {
      type int32 {
        range "-50..150";
      }
      default "100";
      units "dB";
      description "range -50..150; Default value: 100.";
    }
    leaf initialBufferSizeDefault {
      type eytypes:int32_range_1-10000;
      default "86";
      units "bytes";
      description "range 1..10000; Default value: 86.";
    }
    leaf cioUpperLimitAdjBySon {
      type eytypes:int32_range_0-24-29;
      default "4";
      units "dB";
      description "range 0..24; Default value: 4.";
    }
    leaf cioLowerLimitAdjBySon {
      type eytypes:int32_range_-24-0;
      default "-3";
      units "dB";
      description "range -24..0; Default value: -3.";
    }
    leaf servOrPrioTriggeredIFHo {
      type enumeration {
        enum QCI;
        enum ARP;
        enum NOT_ACTIVATED;
      }
    }
    leaf otdoaCheckEnabled {
      type boolean;
      default "false";
      description "Default value: false.";
    }
    leaf servOrPrioRedirectEnabled {
      type boolean;
      default "true";
      description "Default value: true.";
    }
    leaf-list arpPriorityLevelForSPIFHo {
      type boolean;
    }
    leaf lbabIncr {
      type eytypes:int32_range_5-100;
      default "5";
      units "percent";
      description "range 5..100; Default value: 5.";
    }
    list acBarringPresence {
      key "id";
      leaf id {
        type uint32;
        description "Synthetic key for struct entry.";
      }
      container attributes {
      leaf acBarringForMoDataPresence {
        type enumeration {
          enum OFF;
          enum MANUAL;
          enum AUTO;
        }
      }
      leaf acBarringForMoSignPresence {
        type enumeration {
          enum OFF;
          enum MANUAL;
          enum AUTO;
        }
      }
      leaf acBarringForCsfbPresence {
        type enumeration {
          enum OFF;
          enum MANUAL;
          enum AUTO;
        }
      }
      leaf acBarringForMmtelVoicePresence {
        type enumeration {
          enum OFF;
          enum MANUAL;
          enum AUTO;
        }
      }
      leaf acBarringForMmtelVideoPresence {
        type enumeration {
          enum OFF;
          enum MANUAL;
          enum AUTO;
        }
      }
      leaf acBarringPriorityCsfb {
        type enumeration {
          enum PRIORITY0;
          enum PRIORITY1;
          enum PRIORITY2;
          enum PRIORITY3;
          enum PRIORITY4;
        }
      }
      leaf acBarringPriorityMoData {
        type enumeration {
          enum PRIORITY0;
          enum PRIORITY1;
          enum PRIORITY2;
          enum PRIORITY3;
          enum PRIORITY4;
        }
      }
      leaf acBarringPriorityMoSignaling {
        type enumeration {
          enum PRIORITY0;
          enum PRIORITY1;
          enum PRIORITY2;
          enum PRIORITY3;
          enum PRIORITY4;
        }
      }
      leaf acBarringPriorityMmtelVoice {
        type enumeration {
          enum PRIORITY0;
          enum PRIORITY1;
          enum PRIORITY2;
          enum PRIORITY3;
          enum PRIORITY4;
        }
      }
      leaf acBarringPriorityMmtelVideo {
        type enumeration {
          enum PRIORITY0;
          enum PRIORITY1;
          enum PRIORITY2;
          enum PRIORITY3;
          enum PRIORITY4;
        }
      }
      leaf acBarringForEmergencySpecAcPres {
        type enumeration {
          enum MANUAL;
          enum AUTO;
        }
      }
      leaf acBarringPrioCsfbSpecAc {
        type string;
      }
      leaf acBarringPrioMmtelVideoSpecAc {
        type string;
      }
      leaf acBarringPrioMmtelVoiceSpecAc {
        type string;
      }
      leaf acBarringPrioMoDataSpecAc {
        type string;
      }
      leaf acBarringPrioMoSignalingSpecAc {
        type string;
      }
      leaf acBarringPrioEmergencySpecAc {
        type enumeration {
          enum PRIORITY0;
          enum PRIORITY1;
          enum PRIORITY2;
          enum PRIORITY3;
          enum PRIORITY4;
        }
      }
      }
    }
    leaf lbabThreshTimeHigh {
      type eytypes:int32_range_0-4095-30;
      default "30";
      units "s";
      description "range 0..4095; Default value: 30.";
    }
    leaf lbabThreshTimeLow {
      type eytypes:int32_range_0-4095-30;
      default "30";
      units "s";
      description "range 0..4095; Default value: 30.";
    }
    leaf lbabThreshRejectRateHigh {
      type eytypes:int32_range_0-1000-11;
      default "200";
      units "percent";
      description "range 0..1000; Default value: 200.";
    }
    leaf lbabThreshRejectRateLow {
      type eytypes:int32_range_0-1000-11;
      default "20";
      units "percent";
      description "range 0..1000; Default value: 20.";
    }
    leaf lbabDecr {
      type eytypes:int32_range_5-100;
      default "5";
      units "percent";
      description "range 5..100; Default value: 5.";
    }
    leaf lbabPeriod {
      type eytypes:int32_range_0-4095-30;
      default "120";
      units "s";
      description "range 0..4095; Default value: 120.";
    }
    leaf loadBasedBarringFactor {
      type eytypes:int32_range_0-100;
      config false;
      units "percent";
      description "range 0..100.";
    }
    leaf prsTransmisScheme {
      type enumeration {
        enum ANTENNA_SWITCHING;
        enum PRECODER_SWITCHING;
      }
    }
    leaf prsPowerBoosting {
      type eytypes:int32_range_0-3;
      default "0";
      description "range 0..3; Default value: 0.";
    }
    leaf prsMutingPatternLen {
      type int32 {
        range "1..2 | 4 | 8 | 16";
      }
      default "1";
      units "bits";
      description "Default value: 1.";
    }
    leaf prsMutingPattern {
      type string {
        length "1..16";
      }
      config false;
      description "length 1..16.";
    }
    leaf preambleInitialReceivedTargetPower {
      type eytypes:int32_range_-120--90;
      default "-110";
      units "dBm";
      description "range -120..-90; Default value: -110.";
    }
    leaf initialBufferSizeMsg5Default {
      type eytypes:int32_range_1-10000;
      default "86";
      units "bytes";
      description "range 1..10000; Default value: 86.";
    }
    leaf assumedUePowerMsg3 {
      type int32 {
        range "230 | 260 | 310 | 1000";
      }
      default "1000";
      units "dBm";
      description "Default value: 1000.";
    }
    leaf servOrPrioTriggeredErabAction {
      type enumeration {
        enum SETUP;
        enum REJECT;
      }
    }
    leaf pdschTypeBGain {
      type eytypes:int32_range_0-3;
      default "0";
      description "range 0..3; Default value: 0.";
    }
    leaf zzzTemporary21 {
      type int32;
      status deprecated;
      default "-2000000000";
      description "Default value: -2000000000; Status info: Since 20.Q1. Has no functional behavior. Planned to be removed..";
    }
    leaf zzzTemporary22 {
      type int32;
      default "-2000000000";
      description "Default value: -2000000000.";
    }
    leaf zzzTemporary23 {
      type int32;
      default "-2000000000";
      description "Default value: -2000000000.";
    }
    leaf zzzTemporary24 {
      type int32;
      default "-2000000000";
      description "Default value: -2000000000.";
    }
    leaf incrPrioServingFreqActive {
      type boolean;
      status deprecated;
      default "false";
      description "Default value: false; Status info: Since 17.Q3. Has no functional behavior. Planned to be removed..";
    }
    leaf puschMaxNrOfPrbsPerUe {
      type int32 {
        range "1..100";
      }
      default "100";
      units "Resource Block";
      description "range 1..100; Default value: 100.";
    }
    leaf dummyCdmaBandClass {
      type enumeration {
        enum BAND_CLASS_0;
        enum BAND_CLASS_1;
        enum BAND_CLASS_2;
        enum BAND_CLASS_3;
        enum BAND_CLASS_4;
        enum BAND_CLASS_5;
        enum BAND_CLASS_6;
        enum BAND_CLASS_7;
        enum BAND_CLASS_8;
        enum BAND_CLASS_9;
        enum BAND_CLASS_10;
        enum BAND_CLASS_11;
        enum BAND_CLASS_12;
        enum BAND_CLASS_13;
        enum BAND_CLASS_14;
        enum BAND_CLASS_15;
        enum BAND_CLASS_16;
        enum BAND_CLASS_17;
        enum BAND_CLASS_18;
        enum BAND_CLASS_19;
        enum BAND_CLASS_20;
        enum BAND_CLASS_21;
        enum UNDEFINED_VALUE;
      }
    }
    leaf loadCtrlPrioOfMta {
      type boolean;
      default "false";
      description "Default value: false.";
    }
    leaf ulHarqVolteBlerTarget {
      type int32 {
        range "0..10";
      }
      default "5";
      units "percent";
      description "range 0..10; Default value: 5.";
    }
    leaf tTimeAlignmentTimer {
      type int32 {
        range "0 | 500 | 750 | 1280 | 1920 | 2560 | 5120 | 10240";
      }
      default "0";
      units "ms";
      description "Default value: 0.";
    }
    leaf cellCapMinMaxWriProt {
      type ietfinet:ip-address;
      description "Default value: false.";
    }
    leaf noOfPucchFormat1PrbPairsPerFrame {
      type int32 {
        range "0..1000 | 65535";
      }
      config false;
      units "PRB";
    }
    leaf noOfPucchFormat2PrbPairsPerFrame {
      type int32 {
        range "0..1000 | 65535";
      }
      config false;
      units "PRB";
    }
    leaf noOfPucchFormat3PrbPairsPerFrame {
      type int32 {
        range "0..1000 | 65535";
      }
      config false;
      units "PRB";
    }
    leaf lbTpNonQualFraction {
      type int32 {
        range "0 | 20..80";
      }
      default "35";
      description "Default value: 35.";
    }
    leaf lbTpRankThreshMin {
      type int32 {
        range "-100 | -60..60";
      }
      default "-20";
      description "Default value: -20.";
    }
    leaf primaryPlmnAlarmSuppr {
      type boolean;
      default "false";
      description "Default value: false.";
    }
    leaf-list additionalPlmnAlarmSupprList {
      type boolean;
    }
    leaf zzzTemporary29 {
      type int32;
      default "-2000000000";
      description "Default value: -2000000000.";
    }
    leaf zzzTemporary30 {
      type int32;
      default "-2000000000";
      description "Default value: -2000000000.";
    }
    leaf zzzTemporary31 {
      type int32;
      default "-2000000000";
      description "Default value: -2000000000.";
    }
    leaf zzzTemporary32 {
      type int32;
      default "-2000000000";
      description "Default value: -2000000000.";
    }
    leaf zzzTemporary33 {
      type int32;
      default "-2000000000";
      description "Default value: -2000000000.";
    }
    leaf zzzTemporary34 {
      type int32;
      status deprecated;
      default "-2000000000";
      description "Default value: -2000000000; Status info: Since 17.Q1. Replaced by transmissionMode. Planned to be removed..";
    }
    leaf idleModePrioAtReleaseRef {
      type string;
    }
    leaf-list includeLcgInMacUeThp {
      type ietfyang:mac-address;
    }
    leaf acBarringSkipForMmtelVoice {
      type ietfinet:ip-address;
      description "Default value: false.";
    }
    leaf acBarringSkipForMmtelVideo {
      type ietfinet:ip-address;
      description "Default value: false.";
    }
    leaf acBarringSkipForSms {
      type ietfinet:ip-address;
      description "Default value: false.";
    }
    leaf puschPwrOffset64qam {
      type eytypes:int32_range_0-8-28;
      default "0";
      units "dB";
      description "range 0..8; Default value: 0.";
    }
    leaf ul64qamEnabled {
      type boolean;
      default "true";
      description "Default value: true.";
    }
    leaf ulDynUeAdmCtrlOverloadThr {
      type eytypes:int32_range_0-1000-2;
      default "600";
      description "range 0..1000; Default value: 600.";
    }
    leaf dlDynUeAdmCtrlOverloadThr {
      type eytypes:int32_range_0-1000-2;
      default "600";
      description "range 0..1000; Default value: 600.";
    }
    leaf cceDynUeAdmCtrlOverloadThr {
      type eytypes:int32_range_0-1000-2;
      default "600";
      description "range 0..1000; Default value: 600.";
    }
    leaf ulDynUeAdmCtrlRetDiffThr {
      type eytypes:int32_range_0-1000-2;
      default "500";
      description "range 0..1000; Default value: 500.";
    }
    leaf dlDynUeAdmCtrlRetDiffThr {
      type eytypes:int32_range_0-1000-2;
      default "500";
      description "range 0..1000; Default value: 500.";
    }
    leaf cceDynUeAdmCtrlRetDiffThr {
      type eytypes:int32_range_0-1000-2;
      default "500";
      description "range 0..1000; Default value: 500.";
    }
    leaf dynUeAdmCtrlFilterConst {
      type eytypes:int32_range_0-10000;
      default "3000";
      units "ms";
      description "range 0..10000; Default value: 3000.";
    }
    leaf dynUeAdmCtrlEnabled {
      type boolean;
      default "false";
      description "Default value: false.";
    }
    leaf servOrPrioIFHoSetupBearer {
      type boolean;
      default "true";
      description "Default value: true.";
    }
    leaf networkSignallingValueCa {
      type enumeration {
        enum CA_NS_01;
        enum CA_NS_02;
        enum CA_NS_03;
        enum CA_NS_04;
        enum CA_NS_05;
        enum CA_NS_06;
        enum CA_NS_07;
        enum CA_NS_08;
        enum CA_NS_31;
      }
    }
    leaf elcEnabled {
      type boolean;
      default "false";
      description "Default value: false.";
    }
    leaf cellDownlinkCaCapacity {
      type eytypes:int32_range_0-1000000-18;
      default "0";
      description "range 0..1000000; Default value: 0.";
    }
    leaf estCellCapUsableFraction {
      type int32 {
        range "0..100";
      }
      default "100";
      units "Percent";
      description "range 0..100; Default value: 100.";
    }
    leaf maxSoftLockBackoffTime {
      type int32 {
        range "10..90";
      }
      default "90";
      units "s";
      description "range 10..90; Default value: 90.";
    }
    leaf ailgAutoRestartEnabled {
      type boolean;
      default "false";
      description "Default value: false.";
    }
    leaf ulBlerTargetEnabled {
      type boolean;
      default "false";
      description "Default value: false.";
    }
    leaf rtpTimeout {
      type int32 {
        range "1..15";
      }
      default "10";
      units "seconds";
      description "range 1..15; Default value: 10.";
    }
    leaf dl256QamEnabled {
      type boolean;
      default "true";
      description "Default value: true.";
    }
    leaf dl256QamStatus {
      type enumeration {
        enum NOT_SUPPORTED;
        enum SUPPORTED;
      }
      config false;
    }
    leaf zzzTemporary41 {
      type int32;
      default "-2000000000";
      description "Default value: -2000000000.";
    }
    leaf zzzTemporary42 {
      type int32;
      default "-2000000000";
      description "Default value: -2000000000.";
    }
    leaf zzzTemporary43 {
      type int32;
      default "-2000000000";
      description "Default value: -2000000000.";
    }
    leaf zzzTemporary44 {
      type int32;
      status deprecated;
      default "-2000000000";
      description "Default value: -2000000000; Status info: Since 17.Q2. Replaced by dlBlerTargetEnabled. Planned to be removed..";
    }
    leaf zzzTemporary45 {
      type int32;
      status deprecated;
      default "-2000000000";
      description "Default value: -2000000000; Status info: Since 17.Q2. Replaced by dlHarqVoLTEBlerTarget. Planned to be removed..";
    }
    leaf zzzTemporary46 {
      type int32;
    }
    leaf zzzTemporary47 {
      type int32;
    }
    leaf maxNoClusteredPuschAlloc {
      type eytypes:int32_range_0-5;
      default "0";
      description "range 0..5; Default value: 0.";
    }
    leaf clusteredPuschMprFactor {
      type int32 {
        range "0..200";
      }
      default "100";
      units "percent";
      description "range 0..200; Default value: 100.";
    }
    leaf enableUeAssistedAdaptiveDrx {
      type boolean;
      default "true";
      description "Default value: true.";
    }
    leaf enableUeAssistedSigReduction {
      type boolean;
      default "true";
      description "Default value: true.";
    }
    leaf spifhoSetupBearerAtInitialCtxtSetup {
      type boolean;
      default "false";
      description "Default value: false.";
    }
    leaf allocThrPucchFormat1 {
      type eytypes:int32_range_0-2000-31;
      default "50";
      description "range 0..2000; Default value: 50.";
    }
    leaf allocTimerPucchFormat1 {
      type eytypes:int32_range_0-36000;
      default "50";
      units "ms";
      description "range 0..36000; Default value: 50.";
    }
    leaf deallocThrPucchFormat1 {
      type eytypes:int32_range_0-2000-31;
      default "100";
      description "range 0..2000; Default value: 100.";
    }
    leaf deallocTimerPucchFormat1 {
      type eytypes:int32_range_0-36000;
      default "6000";
      units "ms";
      description "range 0..36000; Default value: 6000.";
    }
    leaf primaryPsdOffset {
      type eytypes:int32_range_0-31;
      default "0";
      units "dB";
      description "range 0..31; Default value: 0.";
    }
    leaf outOfCoverageThreshold {
      type eytypes:int32_range_1-63;
      default "20";
      description "range 1..63; Default value: 20.";
    }
    leaf outOfCoverageDepth {
      type eytypes:int32_range_0-20;
      default "1";
      description "range 0..20; Default value: 1.";
    }
    leaf outOfCoverageSparseGrantingBsr {
      type int32 {
        range "1..1000";
      }
      default "4";
      units "byte";
      description "range 1..1000; Default value: 4.";
    }
    leaf outOfCoverageSrTimerPeriodicity {
      type int32 {
        range "40 | 80 | 160 | 320 | 640 | 960 | 1280";
      }
      default "320";
      units "ms";
      description "Default value: 320.";
    }
    leaf ulSchedCtrlForOocUesEnabled {
      type boolean;
      default "true";
      description "Default value: true.";
    }
    leaf resourcePartitionGroupRef {
      type string;
    }
    leaf zzzTemporary48 {
      type int32;
    }
    leaf zzzTemporary49 {
      type int32;
    }
    leaf zzzTemporary50 {
      type int32;
      default "-2000000000";
      description "Default value: -2000000000.";
    }
    leaf ulTrigActive {
      type boolean;
      default "true";
      description "Default value: true.";
    }
    leaf pdcchCovImproveSrb {
      type boolean;
      default "false";
      description "Default value: false.";
    }
    leaf pdcchCovImproveQci1 {
      type boolean;
      default "false";
      description "Default value: false.";
    }
    leaf pdcchCovImproveDtx {
      type boolean;
      default "false";
      description "Default value: false.";
    }
    leaf ulSCellPriority {
      type eytypes:int32_range_0-5;
      default "5";
      description "range 0..5; Default value: 5.";
    }
    leaf-list prioAdditionalFreqBandList {
      type eytypes:int32_range_1-256;
    }
    leaf srDetectHighThres {
      type eytypes:int32_range_0-300;
      default "70";
      units "dB";
      description "range 0..300; Default value: 70.";
    }
    leaf srProcessingLevel {
      type enumeration {
        enum NO_ADDITIONAL_SR_NEEDED;
        enum TWO_SR_FOR_LOW_THRESHOLD_SR_PROCESSING;
        enum TWO_SR_FOR_ALL_SR_PROCESSING;
      }
    }
    leaf adaptiveCfiHoProhibit {
      type enumeration {
        enum NO_HO_PROHIBIT_CFI;
        enum HO_PROHIBIT_CFI_1;
        enum HO_PROHIBIT_CFI_1_AND_2;
      }
    }
    leaf lastSchedLinkAdaptEnabled {
      type boolean;
      default "true";
      description "Default value: true.";
    }
    leaf pdschMaxNrOfPrbsPerUe {
      type eytypes:int32_range_1-100-4;
      default "100";
      description "range 1..100; Default value: 100.";
    }
    list mappingInfoBr {
      key "id";
      leaf id {
        type uint32;
        description "Synthetic key for struct sequence entry.";
      }
      description "Takes effect: Object unlocked; Status info: Since 17.Q4. Planned to be removed.; Specification: 3GPP 36331_CR2069r3_(Rel-13).";
      container attributes {
      leaf mappingInfoSIB10 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB11 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB12 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB13 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB15 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB16 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB3 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB4 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB5 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB6 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB7 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB8 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB14 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      }
    }
    leaf siValidityTimeBr {
      type enumeration {
        enum VALIDITY_TIME_3H;
        enum VALIDITY_TIME_24H;
      }
    }
    leaf qRxLevMinCe {
      type eytypes:int32_range_-140--44;
      default "-140";
      units "dBm";
      description "range -140..-44; Default value: -140.";
    }
    leaf qQualMinRsrqCe {
      type int32 {
        range "-34..-3 | 0";
      }
      default "0";
      units "dB";
      description "Default value: 0.";
    }
    leaf dynUlResourceAllocEnabled {
      type boolean;
      default "false";
      description "Default value: false.";
    }
    leaf enableSinrUplinkClpc {
      type boolean;
      default "false";
      description "Default value: false.";
    }
    leaf rxSinrTargetClpc {
      type eytypes:int32_range_-50-50;
      default "25";
      units "dB";
      description "range -50..50; Default value: 25.";
    }
    leaf interferenceThresholdSinrClpc {
      type int32 {
        range "-125..-60";
      }
      default "-105";
      units "dBm";
      description "range -125..-60; Default value: -105.";
    }
    leaf ulPsdLoadThresholdSinrClpc {
      type eytypes:int32_range_-126-24;
      default "2";
      units "dBm";
      description "range -126..24; Default value: 2.";
    }
    leaf zzzTemporary51 {
      type int32;
      status deprecated;
      default "-2000000000";
      description "Default value: -2000000000; Status info: Since 18.Q1. Replaced by ns05FullBandSchedEnabled. Planned to be removed..";
    }
    leaf zzzTemporary52 {
      type int32;
      status deprecated;
      default "-2000000000";
      description "Default value: -2000000000; Status info: Since 18.Q1. Replaced by ns05FullBandUsersInCellThres. Planned to be removed..";
    }
    leaf caPrioThreshold {
      type eytypes:int32_range_0-65535-10;
      default "300";
      description "range 0..65535; Default value: 300.";
    }
    leaf measBasedElcControl {
      type boolean;
      default "false";
      description "Default value: false.";
    }
    leaf pdcchOuterLoopInitialAdj {
      type eytypes:int32_range_-200-200;
      default "-70";
      units "dB";
      description "range -200..200; Default value: -70.";
    }
    leaf pdcchOuterLoopInitialAdjVolte {
      type eytypes:int32_range_-200-200;
      default "-70";
      units "dB";
      description "range -200..200; Default value: -70.";
    }
    leaf pdcchOuterLoopInitialAdjPCell {
      type eytypes:int32_range_-200-200;
      default "-70";
      units "dB";
      description "range -200..200; Default value: -70.";
    }
    leaf pdcchOuterLoopUpStep {
      type eytypes:int32_range_0-100-6;
      default "8";
      units "dB";
      description "range 0..100; Default value: 8.";
    }
    leaf pdcchOuterLoopUpStepVolte {
      type eytypes:int32_range_0-100-6;
      default "6";
      units "dB";
      description "range 0..100; Default value: 6.";
    }
    leaf pdcchOuterLoopUpStepPCell {
      type eytypes:int32_range_0-100-6;
      default "6";
      units "dB";
      description "range 0..100; Default value: 6.";
    }
    leaf pdcchTargetBler {
      type eytypes:int32_range_1-200;
      default "24";
      units "percent";
      description "range 1..200; Default value: 24.";
    }
    leaf pdcchTargetBlerVolte {
      type eytypes:int32_range_1-200;
      default "22";
      units "percent";
      description "range 1..200; Default value: 22.";
    }
    leaf pdcchTargetBlerPCell {
      type eytypes:int32_range_1-200;
      default "22";
      units "percent";
      description "range 1..200; Default value: 22.";
    }
    leaf eDrxAllowed {
      type boolean;
      default "false";
      description "Default value: false.";
    }
    leaf elcLongDrxCycle {
      type enumeration {
        enum SF40;
        enum SF320;
      }
    }
    leaf zzzTemporary53 {
      type int32;
      status deprecated;
      default "-2000000000";
      description "Default value: -2000000000; Status info: Since 18.Q1. Replaced by ns05LowBandSchedMode. Planned to be removed..";
    }
    leaf zzzTemporary54 {
      type int32;
      status deprecated;
      default "-2000000000";
      description "Default value: -2000000000; Status info: Since 18.Q1. Replaced by ns05PathlossOffsetThres. Planned to be removed..";
    }
    leaf zzzTemporary55 {
      type int32;
      status deprecated;
      default "-2000000000";
      description "Default value: -2000000000; Status info: Since 18.Q1. Replaced by liteMcsReduction. Planned to be removed..";
    }
    leaf zzzTemporary56 {
      type int32;
      status deprecated;
      default "-2000000000";
      description "Default value: -2000000000; Status info: Since 18.Q3. Has no functional behavior. Planned to be removed..";
    }
    leaf zzzTemporary57 {
      type int32;
      default "-2000000000";
      description "Default value: -2000000000.";
    }
    leaf zzzTemporary58 {
      type int32;
      status deprecated;
      default "-2000000000";
      description "Default value: -2000000000; Status info: Since 18.Q2. Has no functional behavior. Planned to be removed..";
    }
    leaf zzzTemporary59 {
      type int32;
    }
    leaf zzzTemporary60 {
      type int32;
      default "-2000000000";
      description "Default value: -2000000000.";
    }
    leaf zzzTemporary61 {
      type int32;
      status deprecated;
      default "-2000000000";
      description "Default value: -2000000000; Status info: Since 20.Q1. Replaced by eranHighThpEnabled. Planned to be removed..";
    }
    leaf zzzTemporary62 {
      type int32;
    }
    leaf tReorderingAutoConfiguration {
      type boolean;
      default "false";
      description "Default value: false.";
    }
    leaf harqOffsetDl {
      type eytypes:int32_range_-20-20;
      default "3";
      units "ms";
      description "range -20..20; Default value: 3.";
    }
    leaf harqOffsetUl {
      type eytypes:int32_range_-20-20;
      default "3";
      units "ms";
      description "range -20..20; Default value: 3.";
    }
    leaf enableDrxAwareRlcArq {
      type boolean;
      default "false";
      description "Default value: false.";
    }
    leaf enableServiceSpecificHARQ {
      type boolean;
      default "false";
      description "Default value: false.";
    }
    leaf lessPrbUsageThreshold {
      type eytypes:int32_range_0-100;
      default "90";
      units "percent";
      description "range 0..100; Default value: 90.";
    }
    leaf dlBlerTargetEnabled {
      type boolean;
      default "false";
      description "Default value: false.";
    }
    leaf interEnbUlCompUserSelSinrThr {
      type eytypes:int32_range_-150-250;
      default "100";
      units "dB";
      description "range -150..250; Default value: 100.";
    }
    leaf interEnbUlCompUserSelSinrHys {
      type eytypes:int32_range_10-50;
      default "10";
      units "dB";
      description "range 10..50; Default value: 10.";
    }
    leaf ulTxPsdDistrThr {
      type eytypes:int32_range_0-100-3;
      default "40";
      description "range 0..100; Default value: 40.";
    }
    list commonSFAllocList {
      config false;
      container attributes {
      leaf radioframeAllocationPeriod {
        type int32;
      }
      leaf radioframeAllocationOffset {
        type eytypes:int32_range_0-7;
        description "range 0..7.";
      }
      leaf subframeAllocation {
        type int32;
      }
      leaf subframeAllocationOneFrame {
        type string;
      }
      leaf subframeAllocationFourFrame {
        type string;
      }
      leaf sfAllocationFourFrame {
        type eytypes:int32_range_0-16777215;
        description "range 0..16777215.";
      }
      leaf sfAllocationOneFrame {
        type eytypes:int32_range_0-63;
        description "range 0..63.";
      }
      }
    }
    leaf ulImprovedUeSchedLastEnabled {
      type boolean;
      default "true";
      description "Default value: true.";
    }
    leaf noOfUlImprovedUe {
      type eytypes:int32_range_0-5;
      default "1";
      description "range 0..5; Default value: 1.";
    }
    leaf ulImprovedUeAdapRetransEnabled {
      type boolean;
      status deprecated;
      default "true";
      description "Default value: true; Status info: Since 17.Q3. Has no functional behavior. Planned to be removed..";
    }
    leaf bsrThreshold {
      type int32 {
        range "0..32767";
      }
      default "0";
      units "Bytes";
      description "range 0..32767; Default value: 0.";
    }
    leaf tUeBlockingTimer {
      type int32 {
        range "50..200";
      }
      default "200";
      units "s";
      description "range 50..200; Default value: 200.";
    }
    leaf sCellHpueEnabled {
      type boolean;
      status deprecated;
      default "true";
      description "Default value: true; Status info: Since 17.Q3. Has no functional behavior. Planned to be removed..";
    }
    leaf zzzTemporary63 {
      type int32;
    }
    leaf zzzTemporary64 {
      type int32;
      default "-2000000000";
      description "Default value: -2000000000.";
    }
    leaf zzzTemporary65 {
      type int32;
      default "-2000000000";
      description "Default value: -2000000000.";
    }
    leaf zzzTemporary66 {
      type int32;
      default "-2000000000";
      description "Default value: -2000000000.";
    }
    leaf lbabBarringPriorityLevel {
      type enumeration {
        enum PRIORITY0;
        enum PRIORITY1;
        enum PRIORITY2;
        enum PRIORITY3;
        enum PRIORITY4;
      }
      config false;
    }
    leaf lbabMinBarringFactor {
      type eytypes:int32_range_0-100;
      default "0";
      units "percent";
      description "range 0..100; Default value: 0.";
    }
    leaf lbabMinBarringFactorPrio1 {
      type eytypes:int32_range_0-100;
      default "0";
      units "percent";
      description "range 0..100; Default value: 0.";
    }
    leaf lbabMinBarringFactorPrio2 {
      type eytypes:int32_range_0-100;
      default "0";
      units "percent";
      description "range 0..100; Default value: 0.";
    }
    leaf physicalLayerCellId {
      type eytypes:int32_range_0-503;
      config false;
      description "range 0..503.";
    }
    leaf prioHpueCapability {
      type enumeration {
        enum NO_PRIORITIZATION;
        enum PRIORITIZE_IN_CA;
      }
    }
    leaf noOfEnhAdptReTxCand {
      type int32 {
        range "-1..5";
      }
      default "0";
      description "range -1..5; Default value: 0.";
    }
    list mappingInfoCe {
      key "id";
      leaf id {
        type uint32;
        description "Synthetic key for struct entry.";
      }
      container attributes {
      leaf mappingInfoSIB10 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB11 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB12 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB13 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB15 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB16 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB3 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB4 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB5 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB6 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB7 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB8 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoSIB14 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      }
    }
    leaf prescheduling {
      type boolean;
      default "true";
      description "Default value: true.";
    }
    leaf eranUlCompUserSelSinrThr {
      type eytypes:int32_range_-150-400;
      default "150";
      units "dB";
      description "range -150..400; Default value: 150.";
    }
    leaf eranUlCompUserSelSinrHys {
      type eytypes:int32_range_10-50;
      default "10";
      units "dB";
      description "range 10..50; Default value: 10.";
    }
    leaf-list cellResourceRef {
      type string;
      description "Takes effect: Next cell unlock; Status info: Since 18.Q2. Has no functional behavior. Planned to be removed..";
    }
    leaf liteMcsReduction {
      type enumeration {
        enum OFF;
        enum ON;
        enum ON_WHEN_NO_ELC;
      }
    }
    leaf zzzTemporary67 {
      type int32;
      status deprecated;
      default "-2000000000";
      description "Default value: -2000000000; Status info: Since 20.Q3. Planned to be removed..";
    }
    leaf measCellGroupCellRef {
      type string;
    }
    leaf iuaEnabled {
      type boolean;
      status deprecated;
      default "false";
      description "Default value: false; Status info: Since 18.Q3. Replaced by InstantUplinkAccess::iuaEnabled. Planned to be removed..";
    }
    leaf iuaInterval {
      type eytypes:int32_range_0-5-32;
      status deprecated;
      default "1";
      units "ms";
      description "range 0..5; Default value: 1; Status info: Since 18.Q3. Replaced by InstantUplinkAccess::iuaInterval. Planned to be removed.; Specification: 3GPP 36.331.";
    }
    leaf iuaMaxResourcePerCell {
      type eytypes:int32_range_0-100;
      status deprecated;
      default "20";
      units "percent";
      description "range 0..100; Default value: 20; Status info: Since 18.Q3. Replaced by InstantUplinkAccess::iuaCellResourceLimit. Planned to be removed..";
    }
    leaf iuaMaxPrbsPerUe {
      type eytypes:int32_range_0-100;
      status deprecated;
      default "20";
      units "percent";
      description "range 0..100; Default value: 20; Status info: Since 18.Q3. Replaced by InstantUplinkAccess::iuaUePrbLimit. Planned to be removed..";
    }
    leaf ns05FullBandSchedEnabled {
      type boolean;
      default "false";
      description "Default value: false.";
    }
    leaf ns05FullBandUsersInCellThres {
      type eytypes:int32_range_1-100-4;
      default "10";
      description "range 1..100; Default value: 10.";
    }
    leaf ns05LowBandSchedMode {
      type enumeration {
        enum ALWAYS_PROHIBIT;
        enum ALWAYS_AVAILABLE;
        enum ADAPTIVE_AVAILABLE_BY_REPEATER_DETECTION;
      }
    }
    leaf ns05PathlossOffsetThres {
      type int32 {
        range "0..1000";
      }
      default "50";
      units "dB";
      description "range 0..1000; Default value: 50.";
    }
    leaf zzzTemporary68 {
      type int32;
      status deprecated;
      default "-2000000000";
      description "Default value: -2000000000; Status info: Since 20.Q3. Planned to be removed..";
    }
    leaf zzzTemporary69 {
      type int32;
      status deprecated;
      default "-2000000000";
      description "Default value: -2000000000; Status info: Since 20.Q3. Planned to be removed..";
    }
    leaf zzzTemporary70 {
      type int32;
      status deprecated;
      default "-2000000000";
      description "Default value: -2000000000; Status info: Since 21.Q1. Replaced by UeMeasControl::endcCheckForRwrToNRDisabled. Planned to be removed..";
    }
    leaf zzzTemporary71 {
      type int32;
      default "-2000000000";
      description "Default value: -2000000000.";
    }
    leaf srvccDelayTimer {
      type eytypes:int32_range_0-30000-33;
      default "0";
      units "ms";
      description "range 0..30000; Default value: 0.";
    }
    leaf voiceMeasAccEnabled {
      type boolean;
      status deprecated;
      default "false";
      description "Default value: false; Takes effect: New connection; Status info: Since 18.Q2. Has no functional behavior. Planned to be removed..";
      reference "Takes effect: New connection.";
    }
    leaf hpueCaSwitchThres {
      type eytypes:int32_range_-150-450;
      default "-150";
      units "dB";
      description "range -150..450; Default value: -150.";
    }
    leaf hpueCaSwitchHyst {
      type eytypes:int32_range_0-150;
      default "20";
      units "dB";
      description "range 0..150; Default value: 20.";
    }
    leaf hpueCaSwitchTimeToTrigger {
      type int32 {
        range "0 | 40 | 64 | 80 | 100 | 128 | 160 | 256 | 320 | 480 | 512 | 640 | 1024 | 1280 | 2560 | 5120";
      }
      default "40";
      units "ms";
      description "Default value: 40.";
    }
    list additionalMultipleNSPmax {
      config false;
      container attributes {
      leaf multiplePmax {
        type ietfinet:ip-address;
      }
      leaf multipleNSvalue {
        type ietfinet:ip-address;
      }
      }
    }
    list multipleNSPmaxReqMapping {
      key "id";
      leaf id {
        type uint32;
        description "Synthetic key for struct sequence entry.";
      }
      container attributes {
      leaf additionalFreqBand {
        type eytypes:int32_range_1-256;
        default "1";
        description "range 1..256; Default value: 1.";
      }
      leaf additionalPMax {
        type int32;
        default "1000";
        description "Default value: 1000.";
      }
      leaf additionalNSvalue {
        type enumeration {
          enum NS_01;
          enum NS_03;
          enum NS_04;
          enum NS_05;
          enum NS_06;
          enum NS_07;
          enum NS_08;
          enum NS_09;
          enum NS_10;
          enum NS_11;
          enum NS_12;
          enum NS_13;
          enum NS_14;
          enum NS_15;
          enum NS_16;
          enum NS_17;
          enum NS_18;
          enum NS_19;
          enum NS_20;
          enum NS_21;
          enum NS_22;
          enum NS_23;
          enum NS_24;
          enum NS_25;
          enum NS_26;
          enum NS_27;
          enum NS_28;
          enum NS_29;
          enum NS_30;
          enum NS_31;
          enum NS_32;
          enum NS_35;
        }
      }
      }
    }
    leaf dlPowerRampUpInitialRatio {
      type eytypes:int32_range_10-100;
      status deprecated;
      default "100";
      units "percent";
      description "range 10..100; Default value: 100; Takes effect: Cell lock/unlock; Status info: Since 18.Q4. Planned to be removed..";
      reference "Takes effect: Cell lock/unlock.";
    }
    leaf dlPowerRampUpRate {
      type eytypes:int32_range_1-10-34;
      default "1";
      units "%/second";
      description "range 1..10; Default value: 1.";
    }
    leaf puschNcpChannelEstWindowSize {
      type enumeration {
        enum NORMAL_SIZE;
        enum LARGE_SIZE;
      }
    }
    leaf useBandPrioritiesInSib1 {
      type boolean;
      status deprecated;
      default "false";
      description "Default value: false; Takes effect: New connection; Status info: Since 18.Q4. Replaced by mfbiFreqBandIndPrio. Planned to be removed..";
      reference "Takes effect: New connection.";
    }
    leaf-list measCellGroupUeRef {
      type string;
    }
    leaf catmMbmsDlSubframes {
      type eytypes:int32_range_0-2;
      default "0";
      description "range 0..2; Default value: 0.";
    }
    leaf-list validDlBrSubframes {
      type eytypes:int32_range_0-1023-23;
    }
    leaf zzzTemporary72 {
      type int32;
      default "-2000000000";
      description "Default value: -2000000000.";
    }
    leaf zzzTemporary82 {
      type int32;
      default "-2000000000";
      description "Default value: -2000000000.";
    }
    leaf zzzTemporary73 {
      type int32;
      default "-2000000000";
      description "Default value: -2000000000.";
    }
    leaf zzzTemporary74 {
      type int32;
      default "-2000000000";
      description "Default value: -2000000000.";
    }
    leaf zzzTemporary75 {
      type string;
    }
    leaf zzzTemporary76 {
      type string;
    }
    leaf zzzTemporary77 {
      type string;
    }
    leaf zzzTemporary78 {
      type int32;
      status deprecated;
      default "-2000000000";
      description "Default value: -2000000000; Status info: Since 23.Q2. Replaced by paConnCellUeReservations. Planned to be removed..";
    }
    leaf zzzTemporary79 {
      type int32;
      default "-2000000000";
      description "Default value: -2000000000.";
    }
    leaf zzzTemporary80 {
      type int32;
      default "-2000000000";
      description "Default value: -2000000000.";
    }
    leaf zzzTemporary81 {
      type int32;
      default "-2000000000";
      description "Default value: -2000000000.";
    }
    leaf hoOptStatNumQci1 {
      type eytypes:int32_range_1-32767;
      default "200";
      description "range 1..32767; Default value: 200.";
    }
    leaf hoOptAdjThresholdPercQci1 {
      type eytypes:int32_range_0-1000-11;
      default "50";
      units "percent";
      description "range 0..1000; Default value: 50.";
    }
    leaf hoOptAdjThresholdAbsQci1 {
      type eytypes:int32_range_0-32767;
      default "5";
      description "range 0..32767; Default value: 5.";
    }
    leaf diffAdmCtrlFilteringProfRef {
      type string;
    }
    leaf sCellHandlingAtVolteCall {
      type enumeration {
        enum KEEP_SCELLS;
        enum DECONF_SCELLS;
        enum DECONF_UL_SUPPRESS_DL_SCELLS;
        enum DECONF_UL_SCELLS;
      }
    }
    leaf dlPowerRatio {
      type eytypes:int32_range_10-100;
      default "100";
      units "percent";
      description "range 10..100; Default value: 100.";
    }
    leaf dlPowerChangeRate {
      type eytypes:int32_range_1-10-34;
      default "1";
      units "%/second";
      description "range 1..10; Default value: 1.";
    }
    leaf dlPowerState {
      type enumeration {
        enum INVALID;
        enum STABLE;
        enum CHANGING;
      }
      config false;
    }
    leaf measGapShareSchemeCeABr {
      type enumeration {
        enum SCHEME_ZERO;
        enum SCHEME_ONE;
        enum SCHEME_TWO;
        enum SCHEME_THREE;
      }
    }
    leaf covTriggerdBlindHoAllowedBr {
      type boolean;
      default "true";
      description "Default value: true.";
    }
    leaf zzzTemporary83 {
      type int32;
      default "-2000000000";
      description "Default value: -2000000000.";
    }
    list endcAllowedPlmnList {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf latencyLongThreshold {
      type int32 {
        range "125..1200";
      }
      default "135";
      units "ms";
      description "range 125..1200; Default value: 135.";
    }
    leaf dynLoadCtrlMinNewConn {
      type int32 {
        range "1..110";
      }
      default "1";
      description "range 1..110; Default value: 1.";
    }
    leaf highBasebandPriority {
      type boolean;
      default "false";
      description "Default value: false.";
    }
    leaf lbabMinBarringFactorPrio3 {
      type eytypes:int32_range_0-100;
      default "0";
      units "percent";
      description "range 0..100; Default value: 0.";
    }
    leaf lbabMinBarringFactorPrio4 {
      type eytypes:int32_range_0-100;
      default "0";
      units "percent";
      description "range 0..100; Default value: 0.";
    }
    leaf plmn1AbConfProfileRef {
      type string;
    }
    leaf plmn2AbConfProfileRef {
      type string;
    }
    leaf plmn3AbConfProfileRef {
      type string;
    }
    leaf acBarringPlmnPabEnabled {
      type boolean;
      default "false";
      description "Default value: false.";
    }
    leaf plmnPabBarringPriorityLevel {
      type enumeration {
        enum PRIORITY0;
        enum PRIORITY1;
        enum PRIORITY2;
      }
      config false;
    }
    leaf primaryUpperLayerInd {
      type enumeration {
        enum OFF;
        enum ON;
      }
    }
    leaf-list additionalUpperLayerIndList {
      type enumeration {
        enum OFF;
        enum ON;
      }
    }
    leaf upperLayerIndR15Usage {
      type boolean;
      default "false";
      description "Default value: false.";
    }
    leaf ptmCellProfileRef {
      type string;
    }
    leaf mfbiFreqBandIndPrio {
      type boolean;
      default "false";
      description "Default value: false.";
    }
    leaf noOfCrsPorts {
      type ietfinet:port-number;
      config false;
    }
    leaf filterUeDlThpVolThr {
      type int32 {
        range "0..4000";
      }
      status deprecated;
      default "1000";
      units "kilobyte";
      description "range 0..4000; Default value: 1000; Takes effect: Next ROP; Status info: Since 21.Q4. Planned to be removed..";
      reference "Takes effect: Next ROP.";
    }
    leaf filterUeDlThpTimeThr {
      type int32 {
        range "0..200";
      }
      status deprecated;
      default "50";
      units "ms";
      description "range 0..200; Default value: 50; Takes effect: Next ROP; Status info: Since 21.Q4. Planned to be removed..";
      reference "Takes effect: Next ROP.";
    }
    leaf rwrCriticalZoneAllowed {
      type boolean;
      default "true";
      description "Default value: true.";
    }
    leaf rwrSearchZoneAllowed {
      type boolean;
      default "true";
      description "Default value: true.";
    }
    list loadBasedCaMsrThr {
      key "id";
      leaf id {
        type uint32;
        description "Synthetic key for struct entry.";
      }
      container attributes {
      leaf dlPrbUtilThreshHigh {
        type eytypes:int32_range_0-100-35;
        default "30";
        units "% of PRB in a cell";
        description "range 0..100; Default value: 30.";
      }
      leaf dlPrbUtilThreshLow {
        type eytypes:int32_range_0-100-35;
        default "20";
        units "% of PRB in a cell";
        description "range 0..100; Default value: 20.";
      }
      leaf ulPrbUtilThreshHigh {
        type eytypes:int32_range_0-100-35;
        default "30";
        units "% of PRB in a cell";
        description "range 0..100; Default value: 30.";
      }
      leaf ulPrbUtilThreshLow {
        type eytypes:int32_range_0-100-35;
        default "25";
        units "% of PRB in a cell";
        description "range 0..100; Default value: 25.";
      }
      leaf dlSeUtilThreshHigh {
        type eytypes:int32_range_0-100-36;
        default "60";
        units "% of the maximum SE/TTI";
        description "range 0..100; Default value: 60.";
      }
      leaf dlSeUtilThreshLow {
        type eytypes:int32_range_0-100-36;
        default "40";
        units "% of the maximum SE/TTI";
        description "range 0..100; Default value: 40.";
      }
      leaf ulSeUtilThreshHigh {
        type eytypes:int32_range_0-100-36;
        default "30";
        units "% of the maximum SE/TTI";
        description "range 0..100; Default value: 30.";
      }
      leaf ulSeUtilThreshLow {
        type eytypes:int32_range_0-100-36;
        default "20";
        units "% of the maximum SE/TTI";
        description "range 0..100; Default value: 20.";
      }
      leaf cceUtilThreshHigh {
        type eytypes:int32_range_0-100-37;
        default "40";
        units "% of CCE in a cell";
        description "range 0..100; Default value: 40.";
      }
      leaf cceUtilThreshLow {
        type eytypes:int32_range_0-100-37;
        default "20";
        units "% of CCE in a cell";
        description "range 0..100; Default value: 20.";
      }
      }
    }
    leaf loadBasedCaEnabled {
      type boolean;
      default "false";
      description "Default value: false.";
    }
    leaf nrOfPreallocatedSrRes {
      type int32 {
        range "-1..20";
      }
      config false;
      description "range -1..20.";
    }
    leaf zzzTemporary84 {
      type int32;
      default "-2000000000";
      description "Default value: -2000000000.";
    }
    leaf dlPowerRampUpInitRatio {
      type int32 {
        range "40..100";
      }
      default "100";
      units "percent";
      description "range 40..100; Default value: 100.";
    }
    leaf tTimeAlignmentTimerBr {
      type int32 {
        range "0 | 500 | 750 | 1280 | 1920 | 2560 | 5120 | 10240";
      }
      status deprecated;
      default "0";
      units "ms";
      description "Default value: 0; Takes effect: Next cell unlock; Status info: Since 21.Q3. Has no functional behavior. Planned to be removed..";
      reference "Takes effect: Next cell unlock.";
    }
    leaf caLockDueToHighLoad {
      type boolean;
      config false;
    }
    leaf eUlFssSwitchThresh {
      type eytypes:int32_range_0-100;
      default "100";
      units "percent";
      description "range 0..100; Default value: 100.";
    }
    leaf dsrTransMax {
      type int32 {
        range "4 | 8 | 16 | 32 | 64";
      }
      default "64";
      description "Default value: 64.";
    }
    list systemInformationBlock24 {
      key "id";
      leaf id {
        type uint32;
        description "Synthetic key for struct entry.";
      }
      container attributes {
      leaf tReselectionNR {
        type eytypes:int32_range_0-7-9;
        default "2";
        units "s";
        description "range 0..7; Default value: 2.";
      }
      leaf tReselectionNRSfMedium {
        type eytypes:int32_range_25-100-26;
        default "100";
        units "percent";
        description "range 25..100; Default value: 100.";
      }
      leaf tReselectionNRSfHigh {
        type eytypes:int32_range_25-100-26;
        default "100";
        units "percent";
        description "range 25..100; Default value: 100.";
      }
      }
    }
    leaf iflbAbEnabled {
      type boolean;
      default "false";
      description "Default value: false.";
    }
    leaf ul256qamEnabled {
      type boolean;
      default "false";
      description "Default value: false.";
    }
    leaf puschPwrOffset256qam {
      type eytypes:int32_range_0-20-38;
      default "0";
      units "dB";
      description "range 0..20; Default value: 0.";
    }
    leaf nRResCoordPattern {
      type enumeration {
        enum DEFAULT;
        enum PATTERN_1;
        enum PATTERN_2;
        enum PATTERN_3;
      }
    }
    leaf ulHeavyUeDetectEnabled {
      type boolean;
      default "false";
      description "Default value: false.";
    }
    leaf skipUlPadPreschedEnabled {
      type ietfinet:ip-address;
      description "Default value: false.";
    }
    leaf skipUlPadDynEnabled {
      type ietfinet:ip-address;
      description "Default value: false.";
    }
    leaf moVoiceDynUeAdmCtrlPrio {
      type boolean;
      default "false";
      description "Default value: false.";
    }
    leaf blerTargetConfigEnabled {
      type boolean;
      default "false";
      description "Default value: false.";
    }
    leaf dlCchAndRefSigBlockActive {
      type boolean;
      default "false";
      description "Default value: false.";
    }
    leaf dlCchAndRefSigBoost {
      type boolean;
      default "false";
      description "Default value: false.";
    }
    leaf ulCellCapCoeff {
      type eytypes:int32_range_0-8;
      default "2";
      description "range 0..8; Default value: 2.";
    }
    leaf zzzTemporary85 {
      type int32;
      default "-2000000000";
      description "Default value: -2000000000.";
    }
    leaf eranHighThpEnabled {
      type boolean;
      status deprecated;
      default "false";
      description "Default value: false; Takes effect: Next cell unlock; Status info: Since 20.Q2. Has no functional behavior. Planned to be removed..";
      reference "Takes effect: Next cell unlock.";
    }
    leaf zzzTemporary86 {
      type int32;
      default "-2000000000";
      description "Default value: -2000000000.";
    }
    leaf zzzTemporary87 {
      type int32;
      default "-2000000000";
      description "Default value: -2000000000.";
    }
    leaf csfbForVolteEnabled {
      type boolean;
      status deprecated;
      default "false";
      description "Default value: false; Status info: Since 20.Q1. Has no functional behavior. Planned to be removed..";
    }
    leaf reducedConnSetupTimeEnabled {
      type boolean;
      default "false";
      description "Default value: false.";
    }
    leaf covTrigMobErabSetupConfig {
      type enumeration {
        enum DISABLED;
        enum CSFB_TRIGGERED;
      }
    }
    leaf lbdarCoverageThreshold {
      type eytypes:int32_range_1-100-4;
      default "15";
      description "range 1..100; Default value: 15.";
    }
    leaf zzzTemporary88 {
      type string;
    }
    leaf zzzTemporary89 {
      type string;
    }
    leaf instantDl256QamMode {
      type enumeration {
        enum OFF;
        enum STATIC_HOM_MODE;
        enum DYNAMIC_HOM_MODE;
      }
    }
    leaf dlMaxRetxRrcReleaseThr {
      type int32 {
        range "-1..4 | 6 | 8 | 16 | 32";
      }
      default "-1";
      description "Default value: -1.";
    }
    leaf tPollRetxRrcReleaseDl {
      type int32 {
        range "-1 | 5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500";
      }
      default "-1";
      units "ms";
      description "Default value: -1.";
    }
    leaf rrcQueueT300Ratio {
      type eytypes:int32_range_0-95;
      default "80";
      description "range 0..95; Default value: 80.";
    }
    leaf upperLayerAutoConfEnabled {
      type boolean;
      default "false";
      description "Default value: false.";
    }
    leaf-list upperLayerAutoConfIndList {
      type boolean;
    }
    leaf includeDynPttMsrReservations {
      type boolean;
      default "false";
      description "Default value: false.";
    }
    leaf cceDynUeAdmCtrlPaOverloadThr {
      type eytypes:int32_range_0-1000-2;
      default "1000";
      description "range 0..1000; Default value: 1000.";
    }
    leaf dlDynUeAdmCtrlPaOverloadThr {
      type eytypes:int32_range_0-1000-2;
      default "1000";
      description "range 0..1000; Default value: 1000.";
    }
    leaf ulDynUeAdmCtrlPaOverloadThr {
      type eytypes:int32_range_0-1000-2;
      default "1000";
      description "range 0..1000; Default value: 1000.";
    }
    leaf maxHarqMsg3Tx {
      type eytypes:int32_range_1-8;
      default "4";
      description "range 1..8; Default value: 4.";
    }
    leaf minInterfSchedEnabled {
      type boolean;
      default "false";
      description "Default value: false.";
    }
    leaf minInterfUlRegionSize {
      type int32 {
        range "0..15";
      }
      default "0";
      units "PRB";
      description "range 0..15; Default value: 0.";
    }
    leaf zzzTemporary95 {
      type int32;
      default "-2000000000";
      description "Default value: -2000000000.";
    }
    leaf zzzTemporary96 {
      type int32;
      default "-2000000000";
      description "Default value: -2000000000.";
    }
    leaf zzzTemporary97 {
      type int32;
      default "-2000000000";
      description "Default value: -2000000000.";
    }
    list cellDefinedPrimaryPlmnId {
      key "id";
      leaf id {
        type uint32;
        description "Synthetic key for struct entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf ulHarqTxNoThresToRegion {
      type eytypes:int32_range_0-7;
      default "0";
      description "range 0..7; Default value: 0.";
    }
    leaf subbandSrsActive {
      type boolean;
      default "false";
      description "Default value: false.";
    }
    leaf enhVolteOptimizedCa {
      type boolean;
      default "false";
      description "Default value: false.";
    }
    leaf ueCapRefreshProhibitMoVoice {
      type boolean;
      default "false";
      description "Default value: false.";
    }
    leaf dlMuTransmissionMode {
      type enumeration {
        enum TRANSMISSION_MODE_8;
        enum TRANSMISSION_MODE_7;
      }
    }
    leaf cbrsCellPriority {
      type enumeration {
        enum NORMAL;
        enum HIGH;
      }
    }
    leaf cbrsCellPriorityRank {
      type eytypes:int32_range_1-10;
      default "1";
      description "range 1..10; Default value: 1.";
    }
    leaf cbrsCellBandwidthPreferred {
      type int32 {
        range "5000..20000";
      }
      default "20000";
      description "range 5000..20000; Default value: 20000.";
    }
    leaf srsBandwidthTddAas {
      type enumeration {
        enum FULL_BAND_FOR_ALL;
        enum HALF_AND_THIRD_BAND;
        enum QUARTER_BAND_AND_NA;
      }
    }
    leaf zzzTemporary98 {
      type int32;
      default "-2000000000";
      description "Default value: -2000000000.";
    }
    leaf measGapPattEndc {
      type eytypes:int32_range_0-1;
      default "1";
      description "range 0..1; Default value: 1.";
    }
    leaf measGapPattEndcRestriction {
      type enumeration {
        enum NO_RESTRICTION;
        enum FDD;
        enum ESS_SA;
      }
    }
    leaf commonCqiPeriodicity {
      type ietfinet:ip-address;
      units "ms";
      description "Default value: 80.";
    }
    leaf aiAdvCellSupMode {
      type enumeration {
        enum OFF;
        enum OBSERVATION;
        enum NORMAL;
      }
    }
    leaf aiAdvCellSupAction {
      type enumeration {
        enum NO_ACTION;
        enum CELL_RESTART;
      }
    }
    leaf measGapPattern {
      type eytypes:int32_range_0-1;
      default "0";
      description "range 0..1; Default value: 0.";
    }
    leaf sib1AltSchInfo {
      type boolean;
      default "false";
      description "Default value: false.";
    }
    leaf rrcQueueAdaptivePulling {
      type boolean;
      default "false";
      description "Default value: false.";
    }
    leaf cbrsCellCaOffset {
      type enumeration {
        enum AUTO;
        enum ONLY_ALLOWED_FOR_ADJACENT;
        enum NOT_ALLOWED;
      }
    }
    leaf prachSfn {
      type int32 {
        range "-1 | 2..3 | 7..8";
      }
      default "-1";
      description "Default value: -1.";
    }
    leaf prachConfigurationIndex {
      type eytypes:int32_range_0-63;
      config false;
      description "range 0..63.";
    }
    leaf adjustCrsPowerEnhEnabled {
      type boolean;
      default "false";
      description "Default value: false.";
    }
    leaf pa {
      type enumeration {
        enum DB_MINUS_6;
        enum DB_MINUS_4_DOT_77;
        enum DB_MINUS_3;
        enum DB_MINUS_1_DOT_77;
        enum DB_0;
        enum DB_1;
        enum DB_2;
        enum DB_3;
      }
      config false;
    }
    leaf pb {
      type eytypes:int32_range_0-3;
      config false;
      description "range 0..3.";
    }
    leaf zzzTemporary99 {
      type int32;
    }
    leaf pimDetectionEnabled {
      type boolean;
      status deprecated;
      default "false";
      description "Default value: false; Status info: Since 22.Q2. Planned to be removed..";
    }
    leaf spifhoDedicatedReportConfig {
      type ietfinet:port-number;
      description "Default value: false.";
    }
    leaf antennaSelectionEnabled {
      type boolean;
      default "false";
      description "Default value: false.";
    }
    leaf pdcchFlexibleBlerEnabled {
      type boolean;
      default "false";
      description "Default value: false.";
    }
    leaf optimizedPdcchCongestThres {
      type eytypes:int32_range_0-100;
      default "30";
      units "percent";
      description "range 0..100; Default value: 30.";
    }
    leaf optimizedPdcchDlPrbThres {
      type eytypes:int32_range_0-100;
      default "100";
      units "percent";
      description "range 0..100; Default value: 100.";
    }
    leaf optimizedPdcchUlPrbThres {
      type eytypes:int32_range_0-100;
      default "100";
      units "percent";
      description "range 0..100; Default value: 100.";
    }
    leaf optimizedPdcchMaxTargetBler {
      type eytypes:int32_range_1-200;
      default "200";
      units "percent";
      description "range 1..200; Default value: 200.";
    }
    leaf caOffloadDlSCellTddAas {
      type boolean;
      default "false";
      description "Default value: false.";
    }
    leaf eCallOverImsSupport {
      type ietfinet:port-number;
      description "Default value: false.";
    }
    leaf pagingPriorityDiffThr {
      type enumeration {
        enum OFF;
        enum PRIO_LEVEL_1;
        enum PRIO_LEVEL_2;
        enum PRIO_LEVEL_3;
        enum PRIO_LEVEL_4;
        enum PRIO_LEVEL_5;
        enum PRIO_LEVEL_6;
        enum PRIO_LEVEL_7;
        enum PRIO_LEVEL_8;
      }
    }
    leaf pagingPriorityOverloadThr {
      type enumeration {
        enum OFF;
        enum PRIO_LEVEL_1;
        enum PRIO_LEVEL_2;
        enum PRIO_LEVEL_3;
        enum PRIO_LEVEL_4;
        enum PRIO_LEVEL_5;
        enum PRIO_LEVEL_6;
        enum PRIO_LEVEL_7;
        enum PRIO_LEVEL_8;
      }
    }
    leaf endcSetupDlPktAgeThr {
      type int32 {
        range "0 | 10..1000";
      }
      default "0";
      units "ms";
      description "Default value: 0.";
    }
    leaf endcSetupDlPktVolThr {
      type eytypes:int32_range_0-30000;
      default "0";
      units "kB";
      description "range 0..30000; Default value: 0.";
    }
    leaf tm8SCellAllowed {
      type boolean;
      default "false";
      description "Default value: false.";
    }
    leaf sCell2RxTm9OverrideToTm8 {
      type boolean;
      default "true";
      description "Default value: true.";
    }
    leaf dominQciFilter {
      type int32 {
        range "-1..0 | 3..64 | 67..255";
      }
      default "-1";
      description "Default value: -1.";
    }
    leaf endcB1MeasGapEnabled {
      type boolean;
      status deprecated;
      default "true";
      description "Default value: true; Takes effect: New connection; Status info: Since 23.Q1. Replaced by EUtranCellTDD::endcB1MeasGapConfig. Planned to be removed..";
      reference "Takes effect: New connection.";
    }
    leaf zzzTemporary100 {
      type int32;
      default "-2000000000";
      description "Default value: -2000000000.";
    }
    leaf ductIntCharInfoValue {
      type eytypes:int32_range_-1-1048575;
      default "-1";
      description "range -1..1048575; Default value: -1.";
    }
    leaf ulVolteCovMobDetect {
      type enumeration {
        enum DISABLED;
        enum MEASBASEDHO;
        enum BLINDHO;
      }
    }
    leaf ulVolteCovMobThr {
      type eytypes:int32_range_1-31;
      default "5";
      description "range 1..31; Default value: 5.";
    }
    leaf p0ClpcExGoodEnabled {
      type boolean;
      default "false";
      description "Default value: false.";
    }
    leaf p0ClpcExBadEnabled {
      type boolean;
      default "false";
      description "Default value: false.";
    }
    leaf p0ClpcExBadSinrThr {
      type eytypes:int32_range_-40-40;
      default "-10";
      units "dB";
      description "range -40..40; Default value: -10.";
    }
    leaf p0ClpcExGoodSinrThr {
      type eytypes:int32_range_-40-40;
      default "21";
      units "dB";
      description "range -40..40; Default value: 21.";
    }
    leaf p0ClpcExGoodSinrOffset64Qam {
      type eytypes:int32_range_0-8-28;
      default "0";
      units "dB";
      description "range 0..8; Default value: 0.";
    }
    leaf p0ClpcExGoodSinrOffset256Qam {
      type eytypes:int32_range_0-20-38;
      default "0";
      units "dB";
      description "range 0..20; Default value: 0.";
    }
    leaf dlMaxDmrsMuMimoLayers {
      type eytypes:int32_range_0-8;
      default "8";
      description "range 0..8; Default value: 8.";
    }
    leaf dlDmrsMuMimoSinrThr {
      type int32 {
        range "-80..300";
      }
      default "50";
      units "dB";
      description "range -80..300; Default value: 50.";
    }
    leaf aiSrsAllocEnabled {
      type boolean;
    }
    leaf lbActionForEndcUe {
      type enumeration {
        enum NOT_ALLOWED;
        enum ENDC_CAPABLE_NOT_CONFIGURED;
        enum ENDC_CAPABLE_ALL;
      }
    }
    leaf voltePreschedulingEnabled {
      type boolean;
      default "false";
      description "Default value: false.";
    }
    leaf ductIntFlexibleDetectionOffset {
      type eytypes:int32_range_0-2;
      default "0";
      description "range 0..2; Default value: 0.";
    }
    leaf ipecGseEnabled {
      type ietfinet:ip-address;
      description "Default value: true.";
    }
    leaf diffPdcchMaxTargetBlerEnabled {
      type boolean;
      default "false";
      description "Default value: false.";
    }
    leaf pdcchMaxTargetBlerLow {
      type eytypes:int32_range_1-800;
      default "200";
      units "percent";
      description "range 1..800; Default value: 200.";
    }
    leaf pdcchMaxTargetBlerHigh {
      type eytypes:int32_range_1-800;
      default "200";
      units "percent";
      description "range 1..800; Default value: 200.";
    }
    leaf pdcchCongestMeasurePeriod {
      type eytypes:int32_range_1-30;
      default "1";
      units "s";
      description "range 1..30; Default value: 1.";
    }
    leaf diffPdcchMaxTargetBlerThres {
      type int32 {
        range "-100..250";
      }
      default "-10";
      units "dB";
      description "range -100..250; Default value: -10.";
    }
    leaf woasDualLayerEnabled {
      type boolean;
      default "false";
      description "Default value: false.";
    }
    leaf pZeroOffsetUlCa {
      type int32 {
        range "0..12 | 255";
      }
      default "255";
      units "dB";
      description "Default value: 255.";
    }
    leaf subscriptionRatioHighThresh {
      type ietfinet:ip-address;
      description "range 0..16000; Default value: 16000.";
    }
    leaf optimizedPdcchCceUtilThres {
      type eytypes:int32_range_0-100;
      default "0";
      units "percent";
      description "range 0..100; Default value: 0.";
    }
    leaf peUeToInterCellPreThrUnreg {
      type eytypes:int32_range_0-100-3;
      default "10";
      description "range 0..100; Default value: 10.";
    }
    leaf peUeToInterCellPreHyst {
      type int32 {
        range "5..100";
      }
      default "10";
      description "range 5..100; Default value: 10.";
    }
    leaf endcB1MeasGapConfig {
      type enumeration {
        enum ENABLED;
        enum DISABLED;
        enum DISABLED_FR1;
        enum DISABLED_FR2;
      }
    }
    leaf tm8SCellMuMimoEnabled {
      type boolean;
      default "false";
      description "Default value: false.";
    }
    leaf raRange {
      type eytypes:int32_range_0-100000;
      default "0";
      units "m";
      description "range 0..100000; Default value: 0.";
    }
    leaf raObsMaxRange {
      type int32 {
        range "1..120000";
      }
      config false;
      units "m";
      description "range 1..120000.";
    }
    leaf paConnCellUeReservations {
      type eytypes:int32_range_0-90;
      default "1";
      units "percent";
      description "range 0..90; Default value: 1.";
    }
    leaf zzzTemporary101 {
      type int32;
      default "-2000000000";
      description "Default value: -2000000000.";
    }
    leaf loopingEndcProtectionEnabled {
      type boolean;
      default "false";
      description "Default value: false.";
    }
    leaf loopingEndcBackoffDuration {
      type eytypes:int32_range_0-86400;
      default "100";
      units "s";
      description "range 0..86400; Default value: 100.";
    }
    leaf loopingEndcShortScgSessTime {
      type eytypes:int32_range_0-30000-33;
      default "1500";
      units "ms";
      description "range 0..30000; Default value: 1500.";
    }
    leaf loopingEndcConsecFailThr {
      type eytypes:int32_range_1-100-4;
      default "5";
      description "range 1..100; Default value: 5.";
    }
    leaf pdcchCongCtrlParamEnabled {
      type boolean;
      default "false";
      description "Default value: false.";
    }
    leaf pdcchOutLoopInitAdjCong {
      type eytypes:int32_range_-200-200;
      default "-70";
      units "dB";
      description "range -200..200; Default value: -70.";
    }
    leaf pdcchOutLoopInitAdjPCellCong {
      type eytypes:int32_range_-200-200;
      default "-70";
      units "dB";
      description "range -200..200; Default value: -70.";
    }
    leaf pdcchPowerBoostMaxCong {
      type eytypes:int32_range_0-6;
      default "0";
      units "dB";
      description "range 0..6; Default value: 0.";
    }
    leaf pdcchTargetBlerAdjStep {
      type int32 {
        range "1..10";
      }
      default "5";
      units "percent";
      description "range 1..10; Default value: 5.";
    }
    leaf ulCompUserSelSinrThr {
      type eytypes:int32_range_-150-400;
      default "400";
      units "dB";
      description "range -150..400; Default value: 400.";
    }
    leaf ulCompUserSelSinrHys {
      type eytypes:int32_range_10-50;
      default "10";
      units "dB";
      description "range 10..50; Default value: 10.";
    }
    leaf dlSrsMuMimoStrictPairing {
      type boolean;
      default "false";
      description "Default value: false.";
    }
    leaf dlSrsMuMimoLinkAdapEnh {
      type boolean;
      default "false";
      description "Default value: false.";
    }
    leaf zzzTemporary102 {
      type int32;
      status deprecated;
      default "-2000000000";
      description "Default value: -2000000000; Status info: Since 25.Q2. Replaced by interFreqHoHigherPrioSpid. Planned to be removed..";
    }
    leaf aiAdvCellSupAdjustMimoSleep {
      type boolean;
      default "true";
      description "Default value: true.";
    }
    leaf endcDistrProfileRef {
      type string;
    }
    leaf ductIntRedSuppressActPosition {
      type eytypes:int32_range_0-16;
      default "0";
      description "range 0..16; Default value: 0.";
    }
    leaf ductIntCrsMutingMode {
      type enumeration {
        enum NOT_MUTING;
        enum PARTIAL_MUTING;
        enum FULL_MUTING;
      }
    }
    leaf uttmCtrlForEndcUe {
      type enumeration {
        enum ENABLED_FOR_ALL_ENDC_UE;
        enum DISABLED_FOR_ENDC_ALLOWED_UE;
        enum DISABLED_FOR_ENDC_CONFIG_UE;
      }
    }
    leaf interFreqHoHigherPrioEnabled {
      type boolean;
      default "false";
      description "Default value: false.";
    }
    leaf minIntensityLimitForLbab {
      type eytypes:int32_range_0-32767;
      default "50";
      description "range 0..32767; Default value: 50.";
    }
    leaf dlVolteCovMobDetect {
      type enumeration {
        enum DISABLED;
        enum MEASBASEDHO;
        enum BLINDHO;
      }
    }
    leaf dlVolteCovMobWindowLen {
      type eytypes:int32_range_1-31;
      default "10";
      description "range 1..31; Default value: 10.";
    }
    leaf dlVolteCovMobThrHigh {
      type eytypes:int32_range_1-10;
      default "6";
      description "range 1..10; Default value: 6.";
    }
    leaf dlVolteCovMobThrLow {
      type eytypes:int32_range_1-10;
      default "4";
      description "range 1..10; Default value: 4.";
    }
    leaf aiSrsAllocStrategy {
      type enumeration {
        enum OFF;
        enum EVENT_TRIGGER;
        enum RECURRENT;
      }
    }
    leaf pciConflictUtvmEcgiMeas {
      type boolean;
      default "true";
      description "Default value: true.";
    }
    leaf endcSetupUlBsVolThr {
      type int32 {
        range "0..150000";
      }
      default "0";
      units "bytes";
      description "range 0..150000; Default value: 0.";
    }
    leaf restartBufMonAtMobility {
      type boolean;
      default "false";
      description "Default value: false.";
    }
    leaf nrMeasRepBlockedDuringHo {
      type boolean;
      default "false";
      description "Default value: false.";
    }
    leaf decoupledPdcchLaEnabled {
      type boolean;
      default "false";
      description "Default value: false.";
    }
    leaf pdcchUlDtxWorseThres {
      type eytypes:int32_range_0-100;
      default "5";
      units "percent";
      description "range 0..100; Default value: 5.";
    }
    leaf interFreqHoHigherPrioSnRel {
      type boolean;
      default "false";
      description "Default value: false.";
    }
    leaf interFreqHoHigherPrioRre {
      type boolean;
      default "true";
      description "Default value: true.";
    }
    leaf-list nrMobilityTriggerQciRef {
      type string;
      ordered-by user;
    }
    leaf lbUlHeavyUeDetectEnabled {
      type boolean;
      default "false";
      description "Default value: false.";
    }
    leaf pwrBoostRaMsg2Pdcch {
      type int32 {
        range "0 | 15 | 20 | 25 | 30";
      }
      default "0";
      units "dB";
      description "Default value: 0.";
    }
    leaf pwrBoostRaMsg2Pdsch {
      type int32 {
        range "0 | 15 | 20 | 25 | 30";
      }
      default "0";
      units "dB";
      description "Default value: 0.";
    }
    leaf pwrBoostRaMsg2TaThr {
      type int32 {
        range "0..1190 | 65535";
      }
      default "65535";
      description "Default value: 65535.";
    }
    leaf interFreqHoHigherPrioEndc {
      type boolean;
      default "true";
      description "Default value: true.";
    }
    leaf ulCaPrioThreshold {
      type eytypes:int32_range_0-65535-10;
      default "200";
      description "range 0..65535; Default value: 200.";
    }
    leaf lessWindow1StartTime {
      type string {
        length "5";
      }
      default "00:00";
      description "length 5..5; Default value: 00:00.";
    }
    leaf lessWindow1EndTime {
      type string {
        length "5";
      }
      default "00:00";
      description "length 5..5; Default value: 00:00.";
    }
    leaf lessWindow2StartTime {
      type string {
        length "5";
      }
      default "00:00";
      description "length 5..5; Default value: 00:00.";
    }
    leaf lessWindow2EndTime {
      type string {
        length "5";
      }
      default "00:00";
      description "length 5..5; Default value: 00:00.";
    }
    leaf lessWindow1StartTimeApplied {
      type string {
        length "5";
      }
      config false;
      description "length 5..5.";
    }
    leaf lessWindow1EndTimeApplied {
      type string {
        length "5";
      }
      config false;
      description "length 5..5.";
    }
    leaf lessWindow2StartTimeApplied {
      type string {
        length "5";
      }
      config false;
      description "length 5..5.";
    }
    leaf lessWindow2EndTimeApplied {
      type string {
        length "5";
      }
      config false;
      description "length 5..5.";
    }
    leaf lessPrbUsageThresholdWindow2 {
      type eytypes:int32_range_0-100;
      default "90";
      units "percent";
      description "range 0..100; Default value: 90.";
    }
    leaf interFreqHoHigherPrioMeas {
      type boolean;
      default "false";
      description "Default value: false.";
    }
    leaf spidUeEnhLoadMgmtThr {
      type eytypes:int32_range_0-16000;
      default "0";
      description "range 0..16000; Default value: 0.";
    }
    leaf bitRateUpRecommTimer {
      type eytypes:int32_range_2-30;
      default "5";
      units "s";
      description "range 2..30; Default value: 5.";
    }
    leaf bitRateDownRecommTimer {
      type eytypes:int32_range_2-30;
      default "3";
      units "s";
      description "range 2..30; Default value: 3.";
    }
    leaf enhVolteRateRecommEnabled {
      type boolean;
      default "false";
      description "Default value: false.";
    }
    leaf decouplePdcchDtxThres {
      type eytypes:int32_range_0-100;
      default "5";
      units "percent";
      description "range 0..100; Default value: 5.";
    }
    leaf pdcchDlOlaDtxOffset {
      type eytypes:int32_range_0-100;
      default "5";
      units "percent";
      description "range 0..100; Default value: 5.";
    }
    leaf ulCaPowerScalingMode {
      type eytypes:int32_range_0-2;
      default "0";
      description "range 0..2; Default value: 0.";
    }
    leaf ulCaFallbackPolicy {
      type eytypes:int32_range_0-2;
      default "0";
      description "range 0..2; Default value: 0.";
    }
    leaf muMimoPotentialThres {
      type eytypes:int32_range_0-1000-11;
      default "200";
      units "percent";
      description "range 0..1000; Default value: 200.";
    }
    leaf muMimoPotentialHyst {
      type int32 {
        range "1..1000";
      }
      default "50";
      units "percent";
      description "range 1..1000; Default value: 50.";
    }
    leaf servSpecficUlSchedForFcb {
      type boolean;
      default "false";
      description "Default value: false.";
    }
    leaf nomPdschRsEpreOffset {
      type eytypes:int32_range_-1-6;
      default "0";
      description "range -1..6; Default value: 0.";
    }
    leaf nomPdschRsEpreOffsetAas {
      type int32 {
        range "0 | 3";
      }
      default "3";
      description "Default value: 3.";
    }
    leaf oneCwSelectionForVolteEnabled {
      type boolean;
      default "false";
      description "Default value: false.";
    }
    leaf interFreqHoHigherPrioSpid {
      type boolean;
      default "true";
      description "Default value: true.";
    }
    leaf zzzTemporary103 {
      type int32;
      default "-2000000000";
      description "Default value: -2000000000.";
    }
    leaf ulHighInterferenceThr {
      type int32 {
        range "-120..-60";
      }
      default "-120";
      units "dBm";
      description "range -120..-60; Default value: -120.";
    }
    leaf cellMaxNoOfPagingRecords {
      type eytypes:int32_range_0-16;
      default "0";
      description "range 0..16; Default value: 0.";
    }
    leaf pdcchCceLevelUp1Thres {
      type int32 {
        range "1..5 | 255";
      }
      default "255";
      description "Default value: 255.";
    }
    leaf pdcchCceLevelUp2Thres {
      type int32 {
        range "6..10 | 255";
      }
      default "255";
      description "Default value: 255.";
    }
    leaf pdcchCceLevelUp3Thres {
      type int32 {
        range "11..15 | 255";
      }
      default "255";
      description "Default value: 255.";
    }
    leaf pdcchCceLevelDownHyst {
      type eytypes:int32_range_0-3;
      default "0";
      description "range 0..3; Default value: 0.";
    }
    leaf preambleDetectionThrOffset {
      type eytypes:int32_range_0-10;
      default "0";
      description "range 0..10; Default value: 0.";
    }
    leaf pmPdcpLatPktTransDlDrxSync {
      type uint32;
      config false;
    }
    leaf pmFlexErabEstabAttInit {
      type uint32;
      config false;
    }
    leaf pmRrcConnEstabSuccDta {
      type uint32;
      config false;
      status deprecated;
      description "MOM flags: noNotification.";
    }
    leaf pmActiveUeUlCe1Max {
      type ietfyang:mac-address;
      config false;
    }
    leaf pmA3InterFBestCellEvalReportUl {
      type ietfinet:port-number;
      config false;
    }
    leaf pmRohcUlDataDeconfiguredCid {
      type uint32;
      config false;
      status deprecated;
      description "MOM flags: noNotification.";
    }
    leaf pmHoPrepRejInDynUeAdmCtrlPaPtt {
      type uint32;
      config false;
    }
    leaf pmCellHoExeSuccLteIntraF {
      type uint32;
      config false;
    }
    leaf pmPrbRemainedUl {
      type uint32;
      config false;
      status deprecated;
      description "MOM flags: noNotification.";
    }
    leaf-list pmMacUeBitRateSelectDlVoipDistr {
      type ietfinet:ip-address;
    }
    leaf-list pmPdcpLatPktTransDlDrxNoSyncQci {
      type uint32;
    }
    leaf-list pmZtemporary80 {
      type uint32;
    }
    leaf-list pmLcgThpVolUlNs05Distr {
      type uint32;
    }
    leaf pmRrcConnReestAtt {
      type uint32;
      config false;
    }
    leaf pmCellHoPrepSuccLteInterFUl {
      type uint32;
      config false;
    }
    leaf pmRrcConnBrMax {
      type int32;
      config false;
    }
    leaf pmRrcConnEstabAttReatt {
      type uint32;
      config false;
    }
    leaf-list pmModImeisvParamSet {
      type uint32;
    }
    leaf pmRrcConnReestFailBb {
      type uint32;
      config false;
    }
    leaf-list pmPdcpLatTimeDlDrxSyncQci {
      type uint32;
    }
    leaf pmUeCtxtRelAbnormalEnbCdtAutoPnr {
      type uint32;
      config false;
    }
    leaf-list pmErabRelAbnormalEnbArp {
      type uint32;
    }
    leaf pmErabRelAbnormalEnbActTnFail {
      type uint32;
      config false;
    }
    leaf-list pmMacUeBitRateRecommDlMcPttDistr {
      type ietfyang:mac-address;
    }
    leaf-list pmPdcpPktDiscDlHoQci {
      type uint32;
    }
    leaf pmZtemporary160 {
      type uint32;
      config false;
    }
    leaf pmUeThpVolUlCa {
      type uint32;
      config false;
    }
    leaf-list pmAccessClassBarringModPlmn1Distr {
      type ietfyang:mac-address;
    }
    leaf pmFlexErabEstabFailRes {
      type uint32;
      config false;
    }
    leaf pmRadioRecInterferencePwrPrb22 {
      type uint32;
      config false;
    }
    leaf pmRadioRecInterferencePwrPrb10 {
      type uint32;
      config false;
    }
    leaf-list pmRrcConnSubsGroupSumDistr {
      type uint32;
    }
    leaf-list pmRrcConnEstabFailMpOverloadCe {
      type uint32;
    }
    leaf pmFlexSessionTimeDrb {
      type uint32;
      config false;
    }
    leaf pmZtemporary246 {
      type uint32;
      config false;
    }
    leaf pmFlexMacHarqDlDtx64qam {
      type ietfyang:mac-address;
      config false;
    }
    leaf pmRadioUeRepCqi2Subband11Sum {
      type uint32;
      config false;
    }
    leaf pmRadioRecInterferencePwrPrb46 {
      type uint32;
      config false;
    }
    leaf pmZtemporary21 {
      type uint32;
      config false;
    }
    leaf pmFlexRlcArqUlNack {
      type uint32;
      config false;
    }
    leaf pmUlGrantsShortSps {
      type uint32;
      config false;
    }
    leaf pmUeCtxtRelCsfbTdScdmaEm {
      type uint32;
      config false;
    }
    leaf pmUlGrantsTransPCellNoAck {
      type uint32;
      config false;
    }
    leaf pmMacHarqDlAckComp {
      type ietfyang:mac-address;
      config false;
    }
    leaf pmFlexErabRelAbnormalEnbAct {
      type uint32;
      config false;
    }
    leaf-list pmS1SigConnEstabAttMtaCe {
      type uint32;
    }
    leaf pmHoPrepRejInLicMob {
      type uint32;
      config false;
    }
    leaf pmErabEstabAttInitPa {
      type uint32;
      config false;
    }
    leaf-list pmCellCcePttReservation {
      type uint32;
    }
    leaf pmFlexRlcArqDlAck {
      type uint32;
      config false;
    }
    leaf pmUeCtxtRelAbnormalEnbActPe {
      type uint32;
      config false;
    }
    leaf-list pmRadioHomUeRepCqi3Distr {
      type uint32;
    }
    leaf pmFlexNonMcPttQualityRbUlNok {
      type uint32;
      config false;
    }
    leaf pmBadCovMiMultiFreqSucc {
      type uint32;
      config false;
    }
    leaf-list pmErabRelNormalEnbUserInactivityQci {
      type uint32;
    }
    leaf pmEndcPrioNonServFreq {
      type uint32;
      config false;
    }
    leaf pmPrbUsedUlSrb {
      type uint32;
      config false;
    }
    leaf pmRadioRecInterferencePwrPrb91 {
      type uint32;
      config false;
    }
    leaf pmPdcpPktPdbUlOkVoip {
      type ietfinet:ip-address;
      config false;
    }
    leaf pmZtemporary85 {
      type uint32;
      config false;
    }
    leaf-list pmRaSuccTaDistr {
      type uint32;
    }
    leaf pmRadioUeRepCqi2Subband7Sum {
      type uint32;
      config false;
    }
    leaf pmUeCtxtRelCsfbWcdmaEm {
      type uint32;
      config false;
    }
    leaf pmPucchSrCqiResCongCqi {
      type uint32;
      config false;
    }
    leaf pmMacSkipUlDtxPresched {
      type ietfinet:ip-address;
      config false;
    }
    leaf pmFlexUeCtxtEstabSucc {
      type uint32;
      config false;
    }
    leaf pmFlexMacHarqDlDtx256qam {
      type ietfyang:mac-address;
      config false;
    }
    leaf pmPrbAvailUlPucchCqi {
      type uint32;
      config false;
    }
    leaf-list pmRrcSegmentUlDistr {
      type uint32;
    }
    leaf pmErabRopEndBr {
      type uint32;
      config false;
    }
    leaf pmDynUeAdmCtrlQueueOverflow {
      type uint32;
      config false;
      status deprecated;
      description "MOM flags: noNotification.";
    }
    leaf pmZtemporary236 {
      type uint32;
      config false;
    }
    leaf pmPrbUsedUlPuschLowRegionSrb {
      type uint32;
      config false;
    }
    leaf pmPwsEtwsPrimReq {
      type uint32;
      config false;
    }
    leaf pmRrcConnEstabFailMpMem {
      type uint32;
      config false;
    }
    leaf pmRadioThpVolDl5ccPCell {
      type uint32;
      config false;
    }
    leaf pmUeExclThpDlShortDrb2 {
      type uint32;
      config false;
    }
    leaf pmErabEstabSuccInitHpa {
      type uint32;
      config false;
    }
    leaf pmRadioTbsPwrRestricted {
      type uint32;
      config false;
    }
    leaf pmRrcConnMaxEndcUnavail {
      type int32;
      config false;
    }
    leaf pmMcPttQualityRbUlNok {
      type uint32;
      config false;
    }
    leaf pmRrcConnReestSuccOthVend {
      type uint32;
      config false;
    }
    leaf pmLbEvalExpiredUe {
      type uint32;
      config false;
    }
    leaf-list pmLaaSelectedChannel {
      type uint32;
    }
    leaf pmHoPrepRejInMISigQCong {
      type uint32;
      config false;
    }
    leaf pmFlexPdcpPktTransDl {
      type uint32;
      config false;
    }
    leaf-list pmErabRelAbnormalEnbUeLostQci {
      type uint32;
    }
    leaf pmFlexMacLatTimeDlNoDrxNoSync {
      type ietfyang:mac-address;
      config false;
      status deprecated;
      description "MOM flags: noNotification.";
    }
    leaf pmEndcSetupUeSucc {
      type uint32;
      config false;
    }
    leaf pmS1SigConnEstabSucc {
      type uint32;
      config false;
    }
    leaf pmFlexZtemporary14 {
      type uint32;
      config false;
    }
    leaf pmHoPrepSuccInMfbiAdditionalPrio {
      type uint32;
      config false;
    }
    leaf pmRrcConnCe0CellLevMax {
      type int32;
      config false;
    }
    leaf pmUeThpVolUlInitial {
      type uint32;
      config false;
    }
    leaf-list pmPdschMsg2PwrBoostDistr {
      type uint32;
    }
    leaf pmRrcConnEstabFailBb {
      type uint32;
      config false;
    }
    leaf-list pmErabRelAbnormalEnbActGbrArp {
      type uint32;
    }
    leaf pmHoPrepSuccInMfbiPrimaryPrio {
      type ietfinet:ip-address;
      config false;
    }
    leaf pmLaaConfigurableDlSamp {
      type uint32;
      config false;
      status deprecated;
      description "MOM flags: noNotification.";
    }
    leaf pmHoExeSuccIntraCell {
      type uint32;
      config false;
    }
    leaf pmFlexPdcpVolDlDrbCa {
      type uint32;
      config false;
    }
    leaf pmFlexPdcpPktDiscDlStaleSdu {
      type uint32;
      config false;
    }
    leaf-list pmRrcConnCeCellLevSum {
      type uint32;
    }
    leaf pmIdleModeRelDistrMediumHighLoad {
      type uint32;
      config false;
    }
    leaf-list pmPdcpLatPktTransDlCatMNoDrxNoSyncQci {
      type uint32;
    }
    leaf pmUeCtxtRelNaccCsfbWcdma {
      type uint32;
      config false;
    }
    leaf pmPrbAvailUlPucchAckNack {
      type uint32;
      config false;
    }
    leaf pmErabEstabAttInit {
      type uint32;
      config false;
    }
    leaf pmUeCtxtRelSCNrB1ServTrigRsrp {
      type uint32;
      config false;
    }
    leaf-list pmRadioHomUeRepCqi4Distr {
      type uint32;
    }
    leaf pmUeCtxtRelSCNrA2Rsrp {
      type uint32;
      config false;
    }
    leaf pmCellHoPrepSuccLteIntraF {
      type uint32;
      config false;
    }
    leaf pmZtemporary200 {
      type uint32;
      config false;
    }
    leaf pmDlAssigsWithUnknownReceptionSCell {
      type uint32;
      config false;
    }
    leaf pmVoipQualityUeUlOk {
      type ietfinet:ip-address;
      config false;
    }
    leaf-list pmErabRelAbnormalEnbCdtQci {
      type uint32;
    }
    leaf pmRrcConnSuspend {
      type uint32;
      config false;
    }
    leaf-list pmPdcpLatTimeDlQci {
      type uint32;
    }
    leaf-list pmErabEstabAttRejAdmMsrInitPttArp {
      type uint32;
    }
    leaf pmRaSuccSrOutOfSync {
      type uint32;
      config false;
    }
    leaf-list pmZtemporary18Qci {
      type uint32;
    }
    leaf pmZtemporary112 {
      type uint32;
      config false;
    }
    leaf pmRadioRecInterferencePwrPrb28 {
      type uint32;
      config false;
    }
    leaf pmZtemporary235 {
      type uint32;
      config false;
    }
    leaf pmEndcSetupUeOverloadRej {
      type uint32;
      config false;
    }
    leaf pmS1SigConnEstabAtt {
      type uint32;
      config false;
    }
    leaf pmZtemporary243 {
      type uint32;
      config false;
    }
    leaf pmUeCtxtRetrReestFailRreEval {
      type uint32;
      config false;
    }
    leaf pmFlexMacHarqDlAck16qam {
      type ietfyang:mac-address;
      config false;
    }
    leaf pmUlGrantsTransMcPtt {
      type uint32;
      config false;
    }
    leaf pmRrcConnEstabFailMmeOvlMos {
      type uint32;
      config false;
    }
    leaf pmRrcConnMaxPlmn0 {
      type int32;
      config false;
    }
    leaf pmZtemporary239 {
      type uint32;
      config false;
    }
    leaf-list pmRachPreambleDist {
      type uint32;
    }
    leaf-list pmRrcConnQueueTimeDistr {
      type uint32;
    }
    leaf pmCaDeconfiguredLostCoverageNoA1 {
      type uint32;
      config false;
    }
    leaf pmErabEstabAttAddedCsfb {
      type uint32;
      config false;
    }
    leaf pmErabRelMmeActUserInactivity {
      type uint32;
      config false;
    }
    leaf pmPrbStartPosChgUlNewTxResFair {
      type uint32;
      config false;
    }
    leaf-list pmMacTimeDlDrxSyncSampQci {
      type ietfyang:mac-address;
      description "MOM flags: noNotification.";
    }
    leaf pmS1SigConnEstabSuccHpa {
      type uint32;
      config false;
    }
    leaf pmCaDeconfiguredSCellChange {
      type uint32;
      config false;
    }
    leaf pmB1NrServTrigEvalReportRsrp {
      type ietfinet:port-number;
      config false;
    }
    leaf pmCellHoPrepAttLteInterFUtvm {
      type uint32;
      config false;
    }
    leaf pmPftEstablishedSession {
      type uint32;
      config false;
    }
    leaf pmFastPucchAssignPft {
      type uint32;
      config false;
    }
    leaf pmEndcSetupFailNrRa {
      type uint32;
      config false;
    }
    leaf-list pmAcBarringVoiceSpecAcPlmn2Distr {
      type ietfyang:mac-address;
    }
    leaf-list pmCaConfiguredDlSum {
      type uint32;
    }
    leaf pmIdleModeRelDistrHighLoad {
      type uint32;
      config false;
    }
    leaf-list pmDrxSwitchPftDistr {
      type uint32;
    }
    leaf pmRadioRecInterferencePwrPrb88 {
      type uint32;
      config false;
    }
    leaf pmUeCtxtRelAbnormalMme {
      type uint32;
      config false;
    }
    leaf pmFlexMacHarqUlDtx16qam {
      type ietfyang:mac-address;
      config false;
    }
    leaf pmCellHoPrepSuccLteInterFHybridCsg {
      type uint32;
      config false;
    }
    leaf pmUeExclThpUlShortTimeHighVol {
      type uint32;
      config false;
    }
    leaf pmRrcConnEstabAttReattDta {
      type uint32;
      config false;
      status deprecated;
      description "MOM flags: noNotification.";
    }
    leaf pmZtemporary123 {
      type uint32;
      config false;
    }
    leaf pmRobustCallSetupDelayedEndc {
      type uint32;
      config false;
    }
    leaf pmHoPrepSuccIntraCell {
      type uint32;
      config false;
    }
    leaf pmErabRelAbnormalEnbUeLostOosPft {
      type uint32;
      config false;
    }
    leaf pmRadioRecInterferencePwrSf2 {
      type uint32;
      config false;
    }
    leaf-list pmMacTimeDlSampQci {
      type ietfyang:mac-address;
      description "MOM flags: noNotification.";
    }
    leaf pmFlexCellHoExeAttLteInterF {
      type uint32;
      config false;
    }
    leaf pmFlexUeCtxtRelSCEutra {
      type uint32;
      config false;
    }
    leaf pmUeCtxtRelAbnormalEnbAct {
      type uint32;
      config false;
    }
    leaf pmZtemporary170 {
      type uint32;
      config false;
    }
    leaf pmRrcConnEstabFailDuIntens {
      type uint32;
      config false;
    }
    leaf-list pmRrcConnReestFailInAdmMsrRpid {
      type uint32;
    }
    leaf-list pmAcBarringModSpecAcPlmn1Distr {
      type ietfyang:mac-address;
    }
    leaf pmErabRelAbnormalEnbCdtAuto {
      type uint32;
      config false;
    }
    leaf pmDlAssigsWithUnknownRecMcPtt {
      type uint32;
      config false;
    }
    leaf pmCriticalBorderEvalReportUl {
      type ietfinet:port-number;
      config false;
    }
    leaf pmDlAssigsWithDetectedHarqAckPCell {
      type uint32;
      config false;
    }
    leaf pmZtemporary64 {
      type uint32;
      config false;
    }
    leaf pmRohcEstabFailLic {
      type uint32;
      config false;
    }
    leaf pmRrcConnQueueOverflow {
      type uint32;
      config false;
    }
    leaf pmMacVolUlResUeLastTti {
      type ietfyang:mac-address;
      config false;
    }
    leaf pmPwsCmasReq {
      type uint32;
      config false;
    }
    leaf pmBestCellEvalReport {
      type ietfinet:port-number;
      config false;
    }
    leaf-list pmRrcConnReestAttCe {
      type uint32;
    }
    leaf-list pmPrbUsedMimoLayersUlDistr {
      type uint32;
    }
    leaf pmLbSubRatioSamp {
      type uint32;
      config false;
    }
    leaf pmFlexErabRelAbnormalEnbActOos {
      type uint32;
      config false;
      status deprecated;
      description "MOM flags: noNotification.";
    }
    leaf pmFlexUeCtxtEstabAtt {
      type uint32;
      config false;
    }
    leaf pmPrbUsedUlAilgTot {
      type uint32;
      config false;
    }
    leaf pmHoPrepRejInDuIntens {
      type uint32;
      config false;
    }
    leaf-list pmZtemporary232Compr {
      type uint32;
    }
    leaf-list pmZtemporary231Compr {
      type uint32;
    }
    leaf pmRadioRecInterferencePwrPrb15 {
      type uint32;
      config false;
    }
    leaf pmRadioRecInterferencePwrPrb12 {
      type uint32;
      config false;
    }
    leaf pmRrcConnCatmMax {
      type int32;
      config false;
      status deprecated;
      description "MOM flags: noNotification.";
    }
    leaf-list pmZtemporary81 {
      type uint32;
    }
    leaf pmActiveDrbDlDelayedLess {
      type ietfyang:mac-address;
      config false;
    }
    leaf-list pmCellIntensHoRrcConnReqDistr {
      type uint32;
      description "MOM flags: noNotification.";
    }
    leaf pmFlexUeCtxtRelMmeAct {
      type uint32;
      config false;
    }
    leaf-list pmAcBarringMosSpecialAcDistr {
      type ietfyang:mac-address;
    }
    leaf pmPdcpLatPktTransDl {
      type uint32;
      config false;
    }
    leaf pmBadCovOutSearchEvalReportRsrp {
      type ietfinet:port-number;
      config false;
    }
    leaf pmRadioUeRepCqiSubband12Sum {
      type uint32;
      config false;
    }
    leaf pmRrcConnEstabLowCovUeSucc {
      type uint32;
      config false;
    }
    leaf pmLaaCapableDlSamp {
      type uint32;
      config false;
    }
    leaf pmFlexZtemporary1 {
      type uint32;
      config false;
    }
    leaf pmBbUeMeasAllocSucc {
      type uint32;
      config false;
    }
    leaf pmZtemporary33 {
      type uint32;
      config false;
    }
    leaf-list pmAcBarringVideoSpecialAcDistr {
      type ietfyang:mac-address;
    }
    leaf-list pmMacUeBitRateRecommDlDistr {
      type ietfyang:mac-address;
    }
    leaf pmIdcCapableSum {
      type uint32;
      config false;
    }
    leaf pmZtemporary116 {
      type uint32;
      config false;
    }
    leaf pmUeCtxtRelSCUtranA2Rsrp {
      type uint32;
      config false;
    }
    leaf pmRrcConnSuspendFailMpMem {
      type uint32;
      config false;
    }
    leaf pmMacSkipUlDtxTxSps {
      type ietfinet:ip-address;
      config false;
    }
    leaf pmZtemporary69 {
      type uint32;
      config false;
    }
    leaf-list pmMacUeBitRateRecommUlMcPttDistr {
      type ietfyang:mac-address;
    }
    leaf pmActiveUeDlMax {
      type ietfyang:mac-address;
      config false;
    }
    leaf pmRlcPollRetxUl {
      type uint32;
      config false;
    }
    leaf pmFlexMacTimeDlNoDrxNoSyncSamp {
      type ietfyang:mac-address;
      config false;
      status deprecated;
      description "MOM flags: noNotification.";
    }
    leaf pmFlexRrcConnReestSucc {
      type uint32;
      config false;
    }
    leaf pmCellHoPrepAttLteInterFCsg {
      type uint32;
      config false;
    }
    leaf-list pmS1SigConnEstabSuccCe {
      type uint32;
    }
    leaf-list pmActiveUeUlMaxCe {
      type ietfyang:mac-address;
      description "MOM flags: noNotification.";
    }
    leaf pmPdcpLatTimeDlDrxSync {
      type uint32;
      config false;
    }
    leaf-list pmHoPrepRejInMpMemCe {
      type uint32;
      description "MOM flags: noNotification.";
    }
    leaf-list pmAcBarringCsfbSpecAcPlmn3Distr {
      type ietfyang:mac-address;
    }
    leaf-list pmRrcConnEstabFailCellIntensDLCCe {
      type uint32;
    }
    leaf pmRadioUeRepCqiSubbandSamp {
      type uint32;
      config false;
    }
    leaf pmFlexUeThpVolUlCa {
      type uint32;
      config false;
    }
    leaf pmHoPrepRejInCellLatency {
      type uint32;
      config false;
    }
    leaf-list pmErabRelMmeQci {
      type uint32;
    }
    leaf pmRrcConnEstabAtt {
      type uint32;
      config false;
    }
    leaf pmFlexPdcpPktLostUl {
      type uint32;
      config false;
    }
    leaf-list pmRrcLatencyCapEnqDistr {
      type uint32;
    }
    leaf pmUeCtxtRelSCCdmaUlSinr {
      type uint32;
      config false;
    }
    leaf pmZtemporary229 {
      type uint32;
      config false;
    }
    leaf-list pmRrcConnReestFailCellLatencyCe {
      type uint32;
    }
    leaf pmCellHoExeSuccLteInterF {
      type uint32;
      config false;
    }
    leaf pmAnrCandNrelRem {
      type uint32;
      config false;
    }
    leaf-list pmRrcConnEstabAttReattMtaCe {
      type uint32;
    }
    leaf pmPrbUsedUlPuschCenterRegionSrb {
      type uint32;
      config false;
    }
    leaf pmAcBarringEmSpecAcPlmn1 {
      type ietfyang:mac-address;
      config false;
    }
    leaf pmUeCtxtRelAbnormalEnbActUeLost {
      type uint32;
      config false;
    }
    leaf pmDrxTotalTime {
      type uint32;
      config false;
    }
    leaf-list pmLaaActivatedSum {
      type uint32;
    }
    leaf pmRlcArqUlNack {
      type uint32;
      config false;
    }
    leaf-list pmHoPrepRejInAdmMsrPttArp {
      type uint32;
    }
    leaf-list pmPdcpLatPktTransDlNoDrxNoSyncQci {
      type uint32;
    }
    leaf pmHoPrepRejInDuSwC {
      type uint32;
      config false;
    }
    leaf pmZtemporary7 {
      type uint32;
      config false;
    }
    leaf pmRaSuccCbra {
      type uint32;
      config false;
    }
    leaf pmRadioRecInterferencePwrPrb33 {
      type uint32;
      config false;
    }
    leaf pmZtemporary66 {
      type uint32;
      config false;
    }
    leaf pmPdcpBitrateUlDrbMax {
      type int32;
      config false;
    }
    leaf-list pmCellIntensRrcConnSuspendDistr {
      type uint32;
    }
    leaf pmUeThpTimeUl {
      type uint32;
      config false;
    }
    leaf pmRadioRecInterferencePwrPrb80 {
      type uint32;
      config false;
    }
    leaf pmUeCtxtFetchSuccEndcSetup {
      type uint32;
      config false;
    }
    leaf pmUlGrantsWithDetPuschNonMcPtt {
      type uint32;
      config false;
    }
    leaf pmFlexCellHoExeSuccLteInterF {
      type uint32;
      config false;
    }
    leaf pmUlGrantsTrans {
      type uint32;
      config false;
    }
    leaf pmNasTransferAttAbortDlSrb2 {
      type uint32;
      config false;
    }
    leaf pmRrcConnReestFailDynUeAdmCtrlPtt {
      type uint32;
      config false;
    }
    leaf-list pmPdcchCongestDistr {
      type uint32;
    }
    leaf-list pmPdcpPktLostUlQci {
      type uint32;
    }
    leaf pmNonMcPttQualityRbUlNok {
      type uint32;
      config false;
    }
    leaf pmDlAssigsWithUnknownReception {
      type uint32;
      config false;
    }
    leaf pmCaConfiguredMeasSucc {
      type uint32;
      config false;
    }
    leaf-list pmRadioHomUeRepRankDistr {
      type uint32;
    }
    leaf-list pmLcgThpVolUlLcg {
      type uint32;
    }
    leaf pmUeCtxtRelSrvccA2Critical1xRtt {
      type uint32;
      config false;
    }
    leaf pmRaContResOnly {
      type uint32;
      config false;
    }
    leaf pmRrcConnResumeFailLicActiveUsers {
      type uint32;
      config false;
      status deprecated;
      description "MOM flags: noNotification.";
    }
    leaf pmUeCtxtRelSrvccMeasTO1xRtt {
      type uint32;
      config false;
    }
    leaf pmUeCtxtRelSCUtranA2Rsrq {
      type uint32;
      config false;
    }
    leaf pmMacHarqDlAck256qam {
      type ietfyang:mac-address;
      config false;
    }
    leaf-list pmErabEstabAttRejAdmMsrInitRpid {
      type uint32;
    }
    leaf pmFlexErabEstabAttAdded {
      type uint32;
      config false;
    }
    leaf pmPwsEtwsSecSucc {
      type uint32;
      config false;
    }
    leaf-list pmErabEstabAttRejAdmMsrInitArp {
      type uint32;
    }
    leaf-list pmCaScheduledDl3ccSumDistr {
      type uint32;
    }
    leaf-list pmRrcLatencyConnSetupDistr {
      type uint32;
    }
    leaf pmFlexCellHoPrepSuccUtran {
      type uint32;
      config false;
    }
    leaf pmFlexCellHoExeAttNonMobLte {
      type uint32;
      config false;
    }
    leaf-list pmPuschMcsSubsGroup8Distr {
      type uint32;
    }
    leaf pmZtemporary3 {
      type uint32;
      config false;
    }
    leaf pmDlAssigsDetHarqNonMcPttNDO {
      type uint32;
      config false;
    }
    leaf pmUeCtxtEstabAttCsfb {
      type uint32;
      config false;
    }
    leaf pmFlexNonMcPttQualityRbUlOk {
      type uint32;
      config false;
    }
    leaf-list pmPrbUtilDl {
      type uint32;
    }
    leaf pmFlexCellHoExeAttUtranSrvcc {
      type uint32;
      config false;
    }
    leaf pmUeCtxtFetchAttReconfErabRel {
      type uint32;
      config false;
    }
    leaf pmMacPdschEmptySubframe {
      type ietfyang:mac-address;
      config false;
    }
    leaf pmRrcConnQueueSucc {
      type uint32;
      config false;
    }
    leaf-list pmZtemporary159Compr {
      type uint32;
    }
    leaf-list pmAcBarringMosSpecAcPlmn2Distr {
      type ietfyang:mac-address;
    }
    leaf pmFlexMacHarqUlSucc256qam {
      type ietfyang:mac-address;
      config false;
    }
    leaf pmFlexMacHarqDl4 {
      type ietfyang:mac-address;
      config false;
    }
    leaf pmPdcpVolUlDrbPlmn6 {
      type uint32;
      config false;
    }
    leaf-list pmRrcConnEstabAttMtaPagPrioDistr {
      type uint32;
    }
    leaf-list pmErabRelAbnormalEnbActHoQci {
      type uint32;
    }
    leaf pmGoodCovSearchEvalReportUl {
      type ietfinet:port-number;
      config false;
    }
    leaf pmRadioThpVolUl {
      type uint32;
      config false;
    }
    leaf pmUeCtxtFetchAttReconfUeCtxtEstab {
      type uint32;
      config false;
    }
    leaf pmFlexPdcpVolDlDrbLastTTIUeCa {
      type uint32;
      config false;
    }
    leaf-list pmErabModAttQci {
      type uint32;
    }
    leaf pmRrcConnResumeFallbackSucc {
      type uint32;
      config false;
    }
    leaf-list pmErabEstabAttAddedQci {
      type uint32;
    }
    leaf pmDuctIntPdschBlankedTti {
      type uint32;
      config false;
    }
    leaf pmFlexMacHarqDlNack256qam {
      type ietfyang:mac-address;
      config false;
    }
    leaf pmUeExclThpUlShortTimeQciLowVol {
      type uint32;
      config false;
    }
    leaf pmErabEstabFailGbrDlEnb {
      type uint32;
      config false;
    }
    leaf pmPdcpVolDlSrbTrans {
      type uint32;
      config false;
    }
    leaf-list pmUeCtxtRelSCEUtraBestCellRsrpCe {
      type uint32;
    }
    leaf-list pmPuschMcsSubsGroup4Distr {
      type uint32;
    }
    leaf-list pmErabRelAbnormalEnbActCdtAutoQci {
      type uint32;
    }
    leaf pmRadioRecInterferencePwrPrb5 {
      type uint32;
      config false;
    }
    leaf pmFlexHoPrepRejInUlThres {
      type uint32;
      config false;
      status deprecated;
      description "MOM flags: noNotification.";
    }
    leaf-list pmCellIntensRrcConnResumeReqDistr {
      type uint32;
    }
    leaf-list pmErabRelAbnormalEnbActCdtAutoPnrQci {
      type uint32;
    }
    leaf-list pmPdcpLatTimeDlNoDrxNoSyncQci {
      type uint32;
    }
    leaf-list pmTxPsdLoadUlDistr {
      type uint32;
    }
    leaf-list pmAccessClassBarringMosPlmn1Distr {
      type ietfyang:mac-address;
    }
    leaf pmErabRelAbnormalEnbUeLost {
      type uint32;
      config false;
    }
    leaf pmPdcpVolDlDrbLastTTI {
      type uint32;
      config false;
    }
    leaf pmDlAssigsTransPCell {
      type uint32;
      config false;
    }
    leaf-list pmMacLatTimeDlNoDrxSyncQci {
      type ietfyang:mac-address;
      description "MOM flags: noNotification.";
    }
    leaf pmUeCtxtRelSCGsmA2Rsrq {
      type uint32;
      config false;
    }
    leaf-list pmRrcConnEstabFailDuSwCCe {
      type uint32;
    }
    leaf pmHoPrepRejOutUlThres {
      type uint32;
      config false;
    }
    leaf pmUeCtxtRelAbnormalEnbPsFail {
      type uint32;
      config false;
    }
    leaf pmZtemporary161 {
      type uint32;
      config false;
    }
    leaf-list pmActiveUeUlSumLcg {
      type ietfyang:mac-address;
    }
    leaf-list pmDrbThpTimeDlQci {
      type uint32;
    }
    leaf pmPdcpVolUlDrbPlmn1 {
      type uint32;
      config false;
    }
    leaf-list pmPdcpVolDlHdrQci {
      type uint32;
    }
    leaf-list pmRaContResAccDistr {
      type uint32;
    }
    leaf-list pmRrcConnReestFailMpMemCe {
      type uint32;
      description "MOM flags: noNotification.";
    }
    leaf-list pmErabRelAbnormalEnbPsPartFailQci {
      type uint32;
    }
    leaf pmRadioRecInterferencePwrPrb57 {
      type uint32;
      config false;
    }
    leaf pmBadCovMiMultiFreqSel {
      type uint32;
      config false;
    }
    leaf pmZtemporary244 {
      type uint32;
      config false;
    }
    leaf-list pmCellIntensHoReqDistr {
      type uint32;
    }
    leaf pmFlexCellHoPrepSuccGeran {
      type uint32;
      config false;
    }
    leaf pmPdcpBitrateDlDrbMin {
      type int32;
      config false;
    }
    leaf pmRadioCalibAttFail {
      type uint32;
      config false;
    }
    leaf pmRrcConnEstabFailLowCovUeLic {
      type uint32;
      config false;
    }
    leaf pmRrcConnEstabFailLicActiveUsers {
      type uint32;
      config false;
      status deprecated;
      description "MOM flags: noNotification.";
    }
    leaf pmCellHoExeAttLteInterFUeMeas {
      type uint32;
      config false;
    }
    leaf pmRrcConnEstabFailDynUeAdmCtrlPa {
      type uint32;
      config false;
    }
    leaf pmVoipQualityUeUlNok {
      type ietfinet:ip-address;
      config false;
    }
    leaf pmFlexMacHarqUl5 {
      type ietfyang:mac-address;
      config false;
    }
    leaf pmUeCtxtRelAbnormalEnbActHo {
      type uint32;
      config false;
    }
    leaf pmBadCovSearchEvalReport {
      type ietfinet:port-number;
      config false;
    }
    leaf pmS1RerouteNasRequestReceived {
      type uint32;
      config false;
    }
    leaf pmAcBarringEmSpecialAc {
      type ietfyang:mac-address;
      config false;
    }
    leaf pmA2InterFHoHigherPrioConfig {
      type uint32;
      config false;
    }
    leaf pmRrcConnNs05Samp {
      type uint32;
      config false;
    }
    leaf pmRadioRecInterferencePwrPrb47 {
      type uint32;
      config false;
    }
    leaf pmPdcchTxConservative {
      type uint32;
      config false;
    }
    leaf-list pmPrbAvailUtilUlDistr {
      type uint32;
    }
    leaf pmErabEstabSuccAddedPa {
      type uint32;
      config false;
    }
    leaf pmRrcSegmentAttUl {
      type uint32;
      config false;
    }
    leaf pmZtemporary146 {
      type uint32;
      config false;
    }
    leaf-list pmPrbUsedDlDmrsMuMimoLayersDistr {
      type uint32;
    }
    leaf pmFlexCellHoPrepAttNr {
      type uint32;
      config false;
    }
    leaf pmRrcConnEstabAttReattMos {
      type uint32;
      config false;
    }
    leaf pmRadioRecInterferencePwrPrb35 {
      type uint32;
      config false;
    }
    leaf pmHoPrepRejInLicRlcUm {
      type uint32;
      config false;
    }
    leaf pmZtemporary62 {
      type uint32;
      config false;
    }
    leaf-list pmPdcpLatPktTransDlCatMNoDrxSyncQci {
      type uint32;
    }
    leaf pmMacHarqUlFail16qam {
      type ietfyang:mac-address;
      config false;
    }
    leaf-list pmRadioUeRepRankDistr {
      type uint32;
    }
    leaf pmCellSubscriptionRatioHigh {
      type ietfinet:ip-address;
      config false;
    }
    leaf pmSchedActivityUlTTI {
      type uint32;
      config false;
    }
    leaf pmPucchFailSr {
      type uint32;
      config false;
    }
    leaf-list pmMacTimeDlNoDrxNoSyncSampQci {
      type ietfyang:mac-address;
      description "MOM flags: noNotification.";
    }
    leaf pmPrbUsedDlDtchSCellEran {
      type uint32;
      config false;
    }
    leaf pmUeCtxtRelSCCdmaA2Rsrp {
      type uint32;
      config false;
    }
    leaf pmErabRelAbnormalMmeAct {
      type uint32;
      config false;
    }
    leaf-list pmRlcArqRetxDl {
      type uint32;
    }
    leaf pmPucchSrResShortUtilCell {
      type int32;
      config false;
    }
    leaf pmFlexErabRelAbnormalEnbPe {
      type uint32;
      config false;
    }
    leaf pmUeCtxtFetchAttS1HoPrepSrvccUtran {
      type uint32;
      config false;
    }
    leaf-list pmMultiUserMimoLayersDlDistr {
      type uint32;
    }
    leaf pmPdcpVolDlDrbCa {
      type uint32;
      config false;
    }
    leaf pmMacVolUlUnresUeBsrGrant {
      type ietfyang:mac-address;
      config false;
    }
    leaf pmRrcConnMaxPlmn1 {
      type int32;
      config false;
    }
    leaf-list pmCaActivatedDl5ccSumDistr {
      type uint32;
    }
    leaf-list pmRrcConnQueueSizeDistr {
      type uint32;
    }
    leaf pmZtemporary113 {
      type uint32;
      config false;
    }
    leaf-list pmPrbUsedDlMuMimoLayersDistr {
      type uint32;
    }
    leaf-list pmTaInitDistr {
      type uint32;
      description "MOM flags: noNotification.";
    }
    leaf pmCellHoPrepAttLteInterFEndcHo {
      type uint32;
      config false;
    }
    leaf-list pmMacLcgThpTimeUlLcg {
      type ietfyang:mac-address;
    }
    leaf-list pmPtmAtoMeasuredUeDistr {
      type uint32;
    }
    leaf pmPwsCmasRepReq {
      type uint32;
      config false;
    }
    leaf pmCellHoExeAttLteInterFHybridCsg {
      type uint32;
      config false;
    }
    leaf pmUeCtxtEstabAtt {
      type uint32;
      config false;
    }
    leaf-list pmDlSinrPdcchDistr {
      type uint32;
    }
    leaf pmEndcSetupScgUeAtt {
      type uint32;
      config false;
    }
    leaf pmMpdcchPrbUsed {
      type uint32;
      config false;
      status deprecated;
      description "MOM flags: noNotification.";
    }
    leaf pmFlexDrbThpTimeDl {
      type uint32;
      config false;
    }
    leaf pmFlexUeThpTimeUl {
      type uint32;
      config false;
    }
    leaf-list pmAccessClassBarringMosPlmn3Distr {
      type ietfyang:mac-address;
    }
    leaf pmCaConfiguredAiBasedSucc {
      type uint32;
      config false;
    }
    leaf pmDrxCommandPft {
      type uint32;
      config false;
    }
    leaf pmUeCtxtRelAbnormalEnbPeInterCell {
      type uint32;
      config false;
    }
    leaf pmZtemporary23 {
      type uint32;
      config false;
    }
    leaf-list pmCellIntensRrcConnReconfDistr {
      type uint32;
    }
    leaf pmRrcConnEstabFailLowCovUeAdmCtrl {
      type uint32;
      config false;
    }
    leaf-list pmMacUeBitRateSelectUlMcPttDistr {
      type ietfyang:mac-address;
    }
    leaf pmNonCaPf3ResCollision {
      type uint32;
      config false;
    }
    leaf-list pmLaaConfiguredDlSum {
      type uint32;
    }
    leaf pmEndcSetupUeAtt {
      type uint32;
      config false;
    }
    leaf pmErabRelAbnormalEnbCdt {
      type uint32;
      config false;
    }
    leaf pmMacHarqUlSucc64Qam {
      type ietfyang:mac-address;
      config false;
    }
    leaf pmRrcConnQueueSuccEm {
      type uint32;
      config false;
    }
    leaf pmRadioRecInterferencePwrPrb49 {
      type uint32;
      config false;
    }
    leaf pmSchedActivityUeUlShortSps {
      type uint32;
      config false;
    }
    leaf-list pmNonCaAssignedPf3ResDistr {
      type uint32;
    }
    leaf pmUlGrantsTransNonMcPttNoAck {
      type uint32;
      config false;
    }
    leaf pmRrcConnReconfAttNoMobEarfcnEndc {
      type uint32;
      config false;
    }
    leaf-list pmHoExeOutSuccQci {
      type uint32;
    }
    leaf pmPwsRestartIndicationSent {
      type uint32;
      config false;
    }
    leaf-list pmCellDlPrbUtilization {
      type uint32;
    }
    leaf pmFlexMcPttQualityRbUlNok {
      type uint32;
      config false;
    }
    leaf pmZtemporary167 {
      type uint32;
      config false;
    }
    leaf pmUlGrantsTransNonMcPttNDO {
      type uint32;
      config false;
    }
    leaf pmUnackedUeRelease {
      type uint32;
      config false;
    }
    leaf-list pmRrcConnReestAttQci {
      type uint32;
    }
    leaf pmFlexUeThpTimeDlCa {
      type uint32;
      config false;
    }
    leaf pmRadioRecInterferencePwrPrb51 {
      type uint32;
      config false;
    }
    leaf pmEranCompUlAvoidedNack {
      type uint32;
      config false;
    }
    leaf pmUeCtxtRelCsfbGsmEm {
      type uint32;
      config false;
    }
    leaf pmSchedTtiCellUlResFair {
      type uint32;
      config false;
      status deprecated;
      description "MOM flags: noNotification.";
    }
    leaf pmFlexUeThpTimeDl {
      type uint32;
      config false;
    }
    leaf pmActiveUeDlCe3Max {
      type ietfyang:mac-address;
      config false;
    }
    leaf pmUeCtxtFetchAttIntraEnbHoPrep {
      type uint32;
      config false;
    }
    leaf pmRrcConnReconfAttNoMobDlComp {
      type uint32;
      config false;
    }
    leaf-list pmRrcLatencyConnReconfigDistr {
      type uint32;
    }
    leaf pmCellHoPrepSuccLteInterFUtvm {
      type uint32;
      config false;
    }
    leaf-list pmPdcpLatTimeDlNoDrxSyncQci {
      type uint32;
    }
    leaf pmPdcpBitrateUlDrbMin {
      type int32;
      config false;
    }
    leaf pmFlexUeThpVolUl {
      type uint32;
      config false;
    }
    leaf pmCellDowntimeManCbrs {
      type uint32;
      config false;
    }
    leaf pmLongDrxCommandPft {
      type uint32;
      config false;
    }
    leaf pmMacHarqUlFailIuaQpsk {
      type ietfyang:mac-address;
      config false;
    }
    leaf pmRrcConnEstabAttHpa {
      type uint32;
      config false;
    }
    leaf pmErabEstabAttAdded {
      type uint32;
      config false;
    }
    leaf pmRrcConnQueueAttMoVoice {
      type uint32;
      config false;
    }
    leaf pmUlTrafficA5MeasRepUe {
      type uint32;
      config false;
    }
    leaf pmFlexZtemporary17 {
      type uint32;
      config false;
    }
    leaf-list pmErabEstabAttAddedArp {
      type uint32;
    }
    leaf pmRadioRecInterferencePwrPrb86 {
      type uint32;
      config false;
    }
    leaf pmUeCtxtRelSCUtraUlSinr {
      type uint32;
      config false;
    }
    leaf pmUeCtxtResumeSucc {
      type uint32;
      config false;
    }
    leaf pmFlexZtemporary9 {
      type uint32;
      config false;
    }
    leaf-list pmPrbUsedDlSuMimoLayersDistr {
      type uint32;
    }
    leaf pmRadioUeRepCqi2Subband4Sum {
      type uint32;
      config false;
    }
    leaf pmFlexMacHarqDlAck256qam {
      type ietfyang:mac-address;
      config false;
    }
    leaf pmSchedActivityUeUl {
      type uint32;
      config false;
    }
    leaf pmUeCtxtRelAbnormalEnbUeLostOos {
      type uint32;
      config false;
    }
    leaf pmZtemporary68 {
      type uint32;
      config false;
    }
    leaf pmCellHoExeAttLteInterFCsg {
      type uint32;
      config false;
    }
    leaf pmUeCtxtRelAbnormalEnbCdtAuto {
      type uint32;
      config false;
    }
    leaf pmRrcConnSubsGroupSamp {
      type uint32;
      config false;
    }
    leaf pmPrbUsedDlReTrans {
      type uint32;
      config false;
    }
    leaf pmFlexCellHoPrepAttGeran {
      type uint32;
      config false;
    }
    leaf pmFlexActiveUeUlPresched {
      type uint32;
      config false;
    }
    leaf pmRaContResAndRrcRsp {
      type uint32;
      config false;
    }
    leaf pmPrbUsedDlReTransCatm {
      type uint32;
      config false;
    }
    leaf pmCellHoExeSuccNrServTrig {
      type uint32;
      config false;
    }
    leaf pmCellHoExeAttLteIntraFCsg {
      type uint32;
      config false;
    }
    leaf-list pmRadioRecInterferencePwr {
      type uint32;
    }
    leaf-list pmPuschMcsVoipDistr {
      type ietfinet:ip-address;
    }
    leaf-list pmLaaChannelSelTrigger {
      type uint32;
    }
    leaf pmUeCtxtFetchAttReconf {
      type uint32;
      config false;
    }
    leaf-list pmCaSCellUpswitchDistr {
      type uint32;
    }
    leaf pmZtemporary171 {
      type uint32;
      config false;
    }
    leaf pmUeExclThpDlQciShortDrb {
      type uint32;
      config false;
    }
    leaf-list pmPrbUtilDlCellResource18Distr {
      type uint32;
      description "MOM flags: noNotification.";
    }
    leaf pmAdjustAccessDynLoadCtrl {
      type uint32;
      config false;
    }
    leaf-list pmCellIntensHoRrcConnReqResumeReqDistr {
      type uint32;
    }
    leaf-list pmCaScheduledDlSum {
      type uint32;
    }
    leaf pmErabModFailLic {
      type uint32;
      config false;
    }
    leaf pmFlexZtemporary2 {
      type uint32;
      config false;
    }
    leaf-list pmErabEstabAttRejAdmMsrAddedRpid {
      type uint32;
    }
    leaf-list pmErabRelAbnormalEnbActPeQci {
      type uint32;
    }
    leaf-list pmEranCompUlDeltaSinrPuschDistr {
      type uint32;
      description "MOM flags: noNotification.";
    }
    leaf pmUeCtxtFetchSuccS1HoExeSrvccUtran {
      type uint32;
      config false;
    }
    leaf pmUlGrantsShortSpsDetPusch {
      type uint32;
      config false;
    }
    leaf-list pmRadioUeRepCqiDistr {
      type uint32;
    }
    leaf-list pmPdcchSym3PwrUtil {
      type uint32;
    }
    leaf-list pmErabEstabSuccAddedGbrArp {
      type uint32;
    }
    leaf pmUlGrantsTransVolteNoAck {
      type uint32;
      config false;
    }
    leaf pmUeCapabilityGnss {
      type uint32;
      config false;
    }
    leaf pmRadioUeRepCqi2Subband9Sum {
      type uint32;
      config false;
    }
    leaf pmRadioUeRepCqi2SubbandSamp {
      type uint32;
      config false;
    }
    leaf pmZtemporary242 {
      type uint32;
      config false;
    }
    leaf pmActiveUeDlCe0Max {
      type ietfyang:mac-address;
      config false;
    }
    leaf pmFlexLcgThpVolUl {
      type uint32;
      config false;
    }
    leaf pmActiveUeUlCe3Max {
      type ietfyang:mac-address;
      config false;
    }
    leaf pmUeExclThpDlVolte {
      type uint32;
      config false;
      status deprecated;
      description "MOM flags: noNotification.";
    }
    leaf pmHoPrepSuccInMfbiAdditional {
      type uint32;
      config false;
    }
    leaf pmUeCtxtRelNaccSCGsm {
      type uint32;
      config false;
    }
    leaf pmRrcSegmentSuccUl {
      type uint32;
      config false;
    }
    leaf pmPrbUsedDlPcch {
      type uint32;
      config false;
    }
    leaf-list pmCellCceUtilization {
      type uint32;
    }
    leaf pmUeCtxtRelNaccCsfbGsmEm {
      type uint32;
      config false;
    }
    leaf pmUeCtxtRelAbnormalEnbPe {
      type uint32;
      config false;
    }
    leaf pmInactiveUeRelInHighLoad {
      type uint32;
      config false;
    }
    leaf pmUeCtxtFetchAttS1HoPrepSrvccGeran {
      type uint32;
      config false;
    }
    leaf-list pmErabRelAbnormalEnbHprQci {
      type uint32;
    }
    leaf pmHoPrepRejInBearerAdmissionRej {
      type uint32;
      config false;
    }
    leaf pmFlexCellHoExeSuccNr {
      type uint32;
      config false;
    }
    leaf pmEndcSetupFailNrRaProblem {
      type uint32;
      config false;
    }
    leaf pmFlexServiceTimeUe {
      type uint32;
      config false;
    }
    leaf pmMacVolUlResUe {
      type ietfyang:mac-address;
      config false;
    }
    leaf-list pmPdcchSym0PwrUtil {
      type uint32;
    }
    leaf pmSchedTtiCellUlResAllocSwitched {
      type uint32;
      config false;
    }
    leaf-list pmCellIntensRrcConnReleaseDistr {
      type uint32;
    }
    leaf pmFlexCellHoExeSuccLteIntraF {
      type uint32;
      config false;
    }
    leaf-list pmBadCovMeasTimeDistr {
      type uint32;
    }
    leaf pmEndcSetupBufMonReportUl {
      type ietfinet:port-number;
      config false;
    }
    leaf-list pmPdcpLatTimeDlCatMNoDrxSyncQci {
      type uint32;
    }
    leaf-list pmMacHarqDlAckNackModeConfig {
      type ietfyang:mac-address;
    }
    leaf pmUeCtxtRetrReestSuccEndcUe {
      type uint32;
      config false;
    }
    leaf pmRrcConnBrCellLevSamp {
      type uint32;
      config false;
    }
    leaf pmZtemporary87 {
      type uint32;
      config false;
    }
    leaf pmRrcConnQueueSuccMtaVoice {
      type uint32;
      config false;
    }
    leaf-list pmZtemporary192 {
      type uint32;
    }
    leaf pmRadioRecInterferencePwrPrb56 {
      type uint32;
      config false;
    }
    leaf pmZtemporary92 {
      type uint32;
      config false;
    }
    leaf-list pmCaActivatedDl3ccSumDistr {
      type uint32;
    }
    leaf-list pmRadioUeRepTm4Rank1PmiDistr {
      type uint32;
    }
    leaf pmRlcArqDlNack {
      type uint32;
      config false;
    }
    leaf pmFlexEndcSetupUeSucc {
      type uint32;
      config false;
    }
    leaf-list pmMacHarqUlDtxDistr {
      type ietfyang:mac-address;
    }
    leaf pmPucchCqiResLongUtilCell {
      type int32;
      config false;
    }
    leaf pmUlGrantsWithDetectedPuschVolte {
      type uint32;
      config false;
    }
    leaf pmUeCtxtRetrReestFailUnknUeCtxt {
      type uint32;
      config false;
      status deprecated;
      description "MOM flags: noNotification.";
    }
    leaf pmRadioRecInterferencePwrPrb78 {
      type uint32;
      config false;
    }
    leaf pmRrcConnEstabFailDynUeAdmCtrlPaPtt {
      type uint32;
      config false;
    }
    leaf pmMacSkipUlDtxDynamicVolte {
      type ietfinet:ip-address;
      config false;
      status deprecated;
      description "MOM flags: noNotification.";
    }
    leaf pmMacUeThpVolUl {
      type ietfyang:mac-address;
      config false;
    }
    leaf pmUeCtxtRelCsfbWcdma {
      type uint32;
      config false;
    }
    leaf pmUeCtxtRelCsfbHoPrepFail1xRttEm {
      type uint32;
      config false;
    }
    leaf pmS1SigConnEstabAttDta {
      type uint32;
      config false;
      status deprecated;
      description "MOM flags: noNotification.";
    }
    leaf pmZtemporary31 {
      type uint32;
      config false;
    }
    leaf-list pmCellDlPrbPttReservation {
      type uint32;
    }
    leaf pmPrbUsedDlAilgHighPrio {
      type uint32;
      config false;
    }
    leaf pmFlexVoipQualityRbUlNok {
      type ietfinet:ip-address;
      config false;
    }
    leaf pmFlexPrbUsedDlDtch {
      type uint32;
      config false;
    }
    leaf-list pmPrbUtilDlCellResource21Distr {
      type uint32;
      description "MOM flags: noNotification.";
    }
    leaf-list pmRrcConnEstabFailCellIntensSwCCe {
      type uint32;
    }
    leaf-list pmAccessClassBarringCsfbPlmn2Distr {
      type ietfyang:mac-address;
    }
    leaf pmPwsCmasSucc {
      type uint32;
      config false;
    }
    leaf pmZtemporary84 {
      type uint32;
      config false;
    }
    leaf pmMeasRepDiscDlComp {
      type uint32;
      config false;
    }
    leaf pmPdcchResyncSucc {
      type uint32;
      config false;
    }
    leaf pmPrbUsedDlDtchSCellIcm {
      type uint32;
      config false;
    }
    leaf pmCellDowntimeAutoCbrs {
      type uint32;
      config false;
    }
    leaf pmRadioRecInterferencePwrPrb19 {
      type uint32;
      config false;
    }
    leaf pmRrcConnEstabFailDynUeAdmCtrlPtt {
      type uint32;
      config false;
    }
    leaf pmEndcSetupScgUeOverloadRej {
      type uint32;
      config false;
    }
    leaf pmRadioThpVolTxDlSCellOffl {
      type uint32;
      config false;
    }
    leaf-list pmErabRelAbnormalMmeActQci {
      type uint32;
    }
    leaf pmCellDowntimeMan {
      type uint32;
      config false;
    }
    leaf-list pmErabEstabAttAddedHoOngoingQci {
      type uint32;
    }
    leaf pmRadioThpVolDl4ccPCell {
      type uint32;
      config false;
    }
    leaf pmZtemporary194 {
      type uint32;
      config false;
    }
    leaf pmDtdReqPft {
      type uint32;
      config false;
    }
    leaf pmHoPreventedNotInPlmnWLGeran {
      type uint32;
      config false;
    }
    leaf pmRrcConnTuneOutLevSum {
      type uint32;
      config false;
    }
    leaf pmErabEndcScgLevSum {
      type uint32;
      config false;
    }
    leaf pmAnrCandNrelX2Add {
      type uint32;
      config false;
    }
    leaf-list pmPdcpInactSecUlMcPttDistr {
      type uint32;
    }
    leaf-list pmCaActivatedDlEranSumDistr {
      type uint32;
    }
    leaf-list pmMacDrbThpTimeDlQci {
      type ietfyang:mac-address;
      description "MOM flags: noNotification.";
    }
    leaf pmFlexMacHarqUlSucc64qam {
      type ietfyang:mac-address;
      config false;
    }
    leaf pmFlexMacHarqDlNack64qam {
      type ietfyang:mac-address;
      config false;
    }
    leaf-list pmAccessClassBarringCsfbDistr {
      type ietfyang:mac-address;
    }
    leaf pmRrcConnNs05Sum {
      type uint32;
      config false;
    }
    leaf pmZtemporary90 {
      type uint32;
      config false;
    }
    leaf pmErabRelAbnormalEnbActUeLostOosPft {
      type uint32;
      config false;
    }
    leaf pmFlexZtemporary13 {
      type uint32;
      config false;
    }
    leaf-list pmPdcpPktDiscDlStaleSduQci {
      type uint32;
    }
    leaf pmFlexMacHarqDl2 {
      type ietfyang:mac-address;
      config false;
    }
    leaf pmMacSkipUlDtxPreschedVolte {
      type ietfinet:ip-address;
      config false;
      status deprecated;
      description "MOM flags: noNotification.";
    }
    leaf pmRrcConnResumeFailMISigQCong {
      type uint32;
      config false;
    }
    leaf pmRadioThpVolTxDl3ccSCell {
      type uint32;
      config false;
    }
    leaf pmZtemporary203 {
      type uint32;
      config false;
    }
    leaf-list pmErabRelAbnormalEnbActPeRpid {
      type uint32;
    }
    leaf pmFlexMacHarqDlAckComp {
      type ietfyang:mac-address;
      config false;
    }
    leaf-list pmActiveUeDlSumQci {
      type ietfyang:mac-address;
    }
    leaf pmIdcSamp {
      type uint32;
      config false;
    }
    leaf pmUeCtxtConnResumeSucc {
      type uint32;
      config false;
      status deprecated;
      description "MOM flags: noNotification.";
    }
    leaf pmActiveUeUlMax {
      type ietfyang:mac-address;
      config false;
    }
    leaf pmRrcConnEstabAttReattHpa {
      type uint32;
      config false;
    }
    leaf-list pmRadioUeRepTm4Rank4PmiDistr {
      type uint32;
    }
    leaf pmDlAssigsTransMcPtt {
      type uint32;
      config false;
    }
    leaf pmHoPreventedNotInPlmnWLUtran {
      type uint32;
      config false;
    }
    leaf pmRadioRecInterferencePwrPrb67 {
      type uint32;
      config false;
    }
    leaf pmHoPrepRejInDynUeAdmCtrl {
      type uint32;
      config false;
    }
    leaf-list pmPdcchCceAggregationUlDistr {
      type uint32;
    }
    leaf pmMacPdcchBlockingPdschTti {
      type ietfyang:mac-address;
      config false;
    }
    leaf pmRrcConnEstabFailLic {
      type uint32;
      config false;
    }
    leaf pmErabBrSum {
      type uint32;
      config false;
    }
    leaf-list pmPtmSubRatioSumDistr {
      type uint32;
    }
    leaf pmActiveUeUlCe2Max {
      type ietfyang:mac-address;
      config false;
    }
    leaf-list pmMacUeBitRateRecommDlNonMcPttDistr {
      type ietfyang:mac-address;
    }
    leaf pmPrbUsedDlDtchSCell {
      type uint32;
      config false;
    }
    leaf pmNumUlPotentialPktLossInd {
      type uint32;
      config false;
    }
    leaf pmMacHarqUlSucc256Qam {
      type ietfyang:mac-address;
      config false;
    }
    leaf-list pmErabRelAbnormalMmeGbrArp {
      type uint32;
    }
    leaf pmErabEstabAttAddedCsfbPl {
      type uint32;
      config false;
    }
    leaf pmRrcConnReestSuccHo {
      type uint32;
      config false;
    }
    leaf pmUeCtxtFetchAttIntraEnbHoExe {
      type uint32;
      config false;
    }
    leaf-list pmPrbUtilDlCellResource20Distr {
      type uint32;
      description "MOM flags: noNotification.";
    }
    leaf-list pmPdcpVolUlHdrQci {
      type uint32;
    }
    leaf pmPdcpPktReceivedUl {
      type uint32;
      config false;
    }
    leaf pmUeCtxtRelSCGsmUlSinr {
      type uint32;
      config false;
    }
    leaf-list pmPrbUsedDlSrsMuMimoLayersDistr {
      type uint32;
    }
    leaf pmRadioRecInterferencePwrPrb55 {
      type uint32;
      config false;
    }
    leaf pmHoPrepRejInMpOverload {
      type uint32;
      config false;
    }
    leaf pmRrcConnResumeAtt {
      type uint32;
      config false;
    }
    leaf pmMimoSleepOppTime {
      type uint32;
      config false;
    }
    leaf pmUeCtxtRetrReestSucc {
      type uint32;
      config false;
    }
    leaf pmPrbUsedUlDtch {
      type uint32;
      config false;
    }
    leaf-list pmRrcConnEstabFailMmeOvlModCe {
      type uint32;
    }
    leaf-list pmAccessClassBarringModPlmn3Distr {
      type ietfyang:mac-address;
    }
    leaf pmErabRelNormalEnbAct {
      type uint32;
      config false;
    }
    leaf pmRadioUeRepCqi2Subband0Sum {
      type uint32;
      config false;
    }
    leaf-list pmLaaRadarDetectionDistr {
      type uint32;
    }
    leaf pmZtemporary128 {
      type uint32;
      config false;
    }
    leaf pmPdcpVolUlDrbPlmn4 {
      type uint32;
      config false;
    }
    leaf-list pmMaxDeltaSinrDlComp {
      type uint32;
    }
    leaf pmCellHoExeSuccLteInterFUeMeas {
      type uint32;
      config false;
    }
    leaf-list pmAccessClassBarringVideoPlmn2Distr {
      type ietfyang:mac-address;
    }
    leaf pmErabEstabFailInitLic {
      type uint32;
      config false;
    }
    leaf pmUeCtxtRetrReestFailUeCtxtRel {
      type uint32;
      config false;
    }
    leaf pmRaAllocCfra {
      type uint32;
      config false;
    }
    leaf-list pmActiveUeDlMaxCe {
      type ietfyang:mac-address;
      description "MOM flags: noNotification.";
    }
    leaf-list pmMacDrbThpVolDlQci {
      type ietfyang:mac-address;
      description "MOM flags: noNotification.";
    }
    leaf pmUeCtxtRelAbnormalEnbActOos {
      type uint32;
      config false;
    }
    leaf-list pmErabEstabAttInitArp {
      type uint32;
    }
    leaf pmDlAssigsTransNonMcPttNDO {
      type uint32;
      config false;
    }
    leaf pmFlexMacHarqUlFail256qam {
      type ietfyang:mac-address;
      config false;
    }
    leaf-list pmLcgThpVolUlNonNs05Distr {
      type uint32;
    }
    leaf pmCellHoExeSuccLteInterFMbms {
      type uint32;
      config false;
    }
    leaf pmErabRelAbnormalEnbTnFail {
      type uint32;
      config false;
    }
    leaf-list pmPdcpInactSecDlNonMcPttDistr {
      type uint32;
    }
    leaf pmErabRelAbnormalEnbAct {
      type uint32;
      config false;
    }
    leaf pmOutOfSyncTimePft {
      type uint32;
      config false;
    }
    leaf pmCovCriticalZoneSamp {
      type uint32;
      config false;
    }
    leaf pmFlexMacHarqUl2 {
      type ietfyang:mac-address;
      config false;
    }
    leaf pmZtemporary125 {
      type uint32;
      config false;
    }
    leaf pmRrcConnEstabFailDynUeAdmCtrlMoVoicePtt {
      type uint32;
      config false;
    }
    leaf pmTtiNs05FullBandSch {
      type uint32;
      config false;
    }
    leaf pmFlexServiceTimeDrb {
      type uint32;
      config false;
    }
    leaf pmRadioRecInterferencePwrPrb29 {
      type uint32;
      config false;
    }
    leaf pmCellHoExeAttLteInterFDtvm {
      type uint32;
      config false;
    }
    leaf-list pmPagDiscardedCe {
      type uint32;
    }
    leaf pmZtemporary193 {
      type uint32;
      config false;
    }
    leaf-list pmPdcpInactSecUlNonMcPttDistr {
      type uint32;
    }
    leaf pmUeExclThpDlSmallVol2 {
      type uint32;
      config false;
    }
    leaf pmZtemporary119 {
      type uint32;
      config false;
    }
    leaf pmRadioRecInterferencePwrPrb50 {
      type uint32;
      config false;
    }
    leaf pmFlexErabRelAbnormalMmeAct {
      type uint32;
      config false;
    }
    leaf pmZtemporary126 {
      type uint32;
      config false;
    }
    leaf pmB1BestCellEvalReport {
      type ietfinet:port-number;
      config false;
    }
    leaf-list pmPrbUtilDlCellResource13Distr {
      type uint32;
      description "MOM flags: noNotification.";
    }
    leaf-list pmAcBarringVoiceSpecialAcDistr {
      type ietfyang:mac-address;
    }
    leaf pmRrcConnResumeFailMpMem {
      type uint32;
      config false;
    }
    leaf pmRadioRecInterferencePwrPrb100 {
      type uint32;
      config false;
    }
    leaf pmUlGrantsTransVolteNDO {
      type uint32;
      config false;
    }
    leaf pmErabRelAbnormalMmeCritCov {
      type uint32;
      config false;
    }
    leaf pmEndcHoB1MeasRepUe {
      type uint32;
      config false;
    }
    leaf pmRrcConnNs05RepeaterZoneSum {
      type uint32;
      config false;
    }
    leaf pmFlexRlcArqDlNack {
      type uint32;
      config false;
    }
    leaf pmRrcConnEstabFailCellIntensSwC {
      type uint32;
      config false;
    }
    leaf pmFlexErabRelAbnormalMmeGbr {
      type uint32;
      config false;
    }
    leaf pmFlexMacVolUlResUe {
      type ietfyang:mac-address;
      config false;
    }
    leaf pmMeasConfigB1GUtran {
      type uint32;
      config false;
      status deprecated;
      description "MOM flags: noNotification.";
    }
    leaf pmRadioThpVolTxDlSCellEran {
      type uint32;
      config false;
    }
    leaf pmRadioRecInterferencePwrPrb85 {
      type uint32;
      config false;
    }
    leaf pmErabUlRlcBufferCongHandl {
      type uint32;
      config false;
    }
    leaf pmUeCtxtRelAbnormalMmeS1Reset {
      type uint32;
      config false;
    }
    leaf pmFlexPdcpVolDlDrbLastTTIUe {
      type uint32;
      config false;
    }
    leaf pmMacHarqUlFail64Qam {
      type ietfyang:mac-address;
      config false;
    }
    leaf-list pmPdcchCceAggregationDlDistr {
      type uint32;
    }
    leaf pmRadioRecInterferencePwrPrb25 {
      type uint32;
      config false;
    }
    leaf pmRrcScgFailureArfcnNil {
      type uint32;
      config false;
    }
    leaf pmFlexZtemporary6 {
      type uint32;
      config false;
    }
    leaf pmS1SigConnEstabSuccMos {
      type uint32;
      config false;
    }
    leaf-list pmPrbUtilDlCellResource14Distr {
      type uint32;
      description "MOM flags: noNotification.";
    }
    leaf-list pmPuschMcsSubsGroup0Distr {
      type uint32;
    }
    leaf-list pmZtemporary132Compr {
      type uint32;
    }
    leaf-list pmAasSchedPrbDlVerticalDistr {
      type uint32;
    }
    leaf pmUeCapabilityLoggedMdt {
      type uint32;
      config false;
    }
    leaf pmRadioRecInterferencePwrPrb95 {
      type uint32;
      config false;
    }
    leaf-list pmErabRelAbnormalMmeQci {
      type uint32;
    }
    leaf pmRrcConnQueueAttHpa {
      type uint32;
      config false;
    }
    leaf pmUeCtxtRelSCCdma {
      type uint32;
      config false;
    }
    leaf pmRadioRecInterferencePwrPrb53 {
      type uint32;
      config false;
    }
    leaf pmRadioRecInterferencePwrSfSamp {
      type uint32;
      config false;
    }
    leaf pmFlexErabRelNormalEnbUserInactivity {
      type uint32;
      config false;
      status deprecated;
      description "MOM flags: noNotification.";
    }
    leaf pmCaDeconfiguredVolte {
      type uint32;
      config false;
    }
    leaf pmFlexCellHoExeSuccUtran {
      type uint32;
      config false;
    }
    leaf pmFlexZtemporary22 {
      type uint32;
      config false;
    }
    leaf pmRrcConnReconfSuccNoMobDlComp {
      type uint32;
      config false;
    }
    leaf pmRaFailCbraMsg1DiscOoc {
      type uint32;
      config false;
    }
    leaf-list pmPuschMcsSubsGroup5Distr {
      type uint32;
    }
    leaf-list pmSinrPucchDistr {
      type uint32;
    }
    leaf pmErabRelMmeActUnspecified {
      type uint32;
      config false;
    }
    leaf pmRadioRecInterferencePwrPrb30 {
      type uint32;
      config false;
    }
    leaf-list pmMacUeThpUlDistr {
      type ietfyang:mac-address;
    }
    leaf pmUeCtxtFetchAttEndcSetup {
      type uint32;
      config false;
    }
    leaf pmRadioThpVolDlSCellExt {
      type uint32;
      config false;
    }
    leaf pmS1SigConnEstabSuccEm {
      type uint32;
      config false;
    }
    leaf pmRrcConnEstabAttReattMod {
      type uint32;
      config false;
    }
    leaf pmActiveUeUlPresched {
      type ietfyang:mac-address;
      config false;
    }
    leaf-list pmRaFailMsg1DiscDistr {
      type uint32;
    }
    leaf pmFlexHoPrepRejOutUlThres {
      type uint32;
      config false;
    }
    leaf-list pmRrcConnEstabFailMmeOvlMosCe {
      type uint32;
    }
    leaf pmFlexPdcpPktDiscDlPelr {
      type uint32;
      config false;
    }
    leaf pmIdcUlCaMax {
      type int32;
      config false;
    }
    leaf pmInvalidPftNum {
      type uint32;
      config false;
    }
    leaf pmFlexErabRelAbnormalEnb {
      type uint32;
      config false;
    }
    leaf pmZtemporary129 {
      type uint32;
      config false;
    }
    leaf pmHoPrepRejInUlThres {
      type uint32;
      config false;
      status deprecated;
      description "MOM flags: noNotification.";
    }
    leaf pmZtemporary121 {
      type uint32;
      config false;
    }
    leaf-list pmPdcchTargetBlerLowRatioDistr {
      type uint32;
    }
    leaf pmNumDlPotentialPktLossInd {
      type uint32;
      config false;
    }
    leaf pmRadioRecInterferencePwrPrb90 {
      type uint32;
      config false;
    }
    leaf-list pmCaScheduledDlIcmSumDistr {
      type uint32;
    }
    leaf-list pmErabRelAbnormalEnbActArp {
      type uint32;
    }
    leaf pmRrcConnEstabFailLicMoVoice {
      type uint32;
      config false;
    }
    leaf pmFlexSchedActivityCellDl {
      type uint32;
      config false;
    }
    leaf-list pmCaActDlIeNbSum {
      type uint32;
    }
    leaf pmUlGrantsDetectedPuschVolteNDO {
      type uint32;
      config false;
    }
    leaf pmFlexMacHarqUlSucc16qam {
      type ietfyang:mac-address;
      config false;
    }
    leaf-list pmBitRateDownUlVoipTimeDistr {
      type ietfinet:ip-address;
    }
    leaf pmUeCtxtRelAbnormalEnbSir {
      type uint32;
      config false;
    }
    leaf pmFlexUeCtxtRelAbnormalEnb {
      type uint32;
      config false;
    }
    leaf pmUeExclThpUlRelativeQciHighVol {
      type uint32;
      config false;
    }
    leaf pmUeCtxtRelSCWcdma {
      type uint32;
      config false;
    }
    leaf-list pmMacUeBitRateSelectDlNonMcPttDistr {
      type ietfyang:mac-address;
    }
    leaf pmErabRelAbnormalEnbActPe {
      type uint32;
      config false;
    }
    leaf pmPrbUsedUlPresched {
      type uint32;
      config false;
    }
    leaf-list pmMacUeBitRateRecommDlVoipDistr {
      type ietfinet:ip-address;
    }
    leaf pmRadioUeRepCqi2Subband1Sum {
      type uint32;
      config false;
    }
    leaf pmOocNewDataUlGrants {
      type uint32;
      config false;
    }
    leaf pmZtemporary199 {
      type int32;
      config false;
    }
    leaf pmUeCtxtFetchAttReconfRrcConnReest {
      type uint32;
      config false;
    }
    leaf pmUeCtxtRelAbnormalEnbCritCov {
      type uint32;
      config false;
    }
    leaf pmUeCtxtFetchSuccNoNeighRel {
      type uint32;
      config false;
    }
    leaf pmErabRelNormalEnbUserInactivity {
      type uint32;
      config false;
    }
    leaf pmCellSleepTime {
      type uint32;
      config false;
    }
    leaf-list pmPrbUtilDlCellResource11Distr {
      type uint32;
      description "MOM flags: noNotification.";
    }
    leaf pmUlGrantsWithDetPuschMcPtt {
      type uint32;
      config false;
    }
    leaf-list pmErabRelAllEnbQci {
      type uint32;
    }
    leaf pmPrbUsedUlCatmSum {
      type uint32;
      config false;
    }
    leaf-list pmRrcConnCeCellLevMax {
      type uint32;
      description "MOM flags: noNotification.";
    }
    leaf pmRrcConnQueueAttEm {
      type uint32;
      config false;
    }
    leaf-list pmRadioUeRepCqiDistr2 {
      type uint32;
    }
    leaf-list pmErabEstabSuccAddedQci {
      type uint32;
    }
    leaf pmServiceTimeUe {
      type uint32;
      config false;
    }
    leaf pmPwrBoostSuccLowCovUe {
      type uint32;
      config false;
    }
    leaf pmErabLevSum {
      type uint32;
      config false;
    }
    leaf pmPdcpPktFwdDl {
      type uint32;
      config false;
    }
    leaf pmCellHoExeAttLteIntraFHybridCsg {
      type uint32;
      config false;
    }
    leaf pmZtemporary136 {
      type uint32;
      config false;
    }
    leaf pmFlexMacHarqUlDtxQpsk {
      type ietfyang:mac-address;
      config false;
    }
    leaf-list pmRaBackoffDistr {
      type uint32;
    }
    leaf pmRadioRecInterferencePwrPrb54 {
      type uint32;
      config false;
    }
    leaf pmFlexMacHarqDl5 {
      type ietfyang:mac-address;
      config false;
    }
    leaf pmRadioUeRepCqiSubband9Sum {
      type uint32;
      config false;
    }
    leaf pmZtemporary118 {
      type uint32;
      config false;
    }
    leaf-list pmAccessClassBarringVoiceDistr {
      type ietfyang:mac-address;
    }
    leaf pmPrbUsedUlPuschHighRegionDtch {
      type uint32;
      config false;
    }
    leaf pmUeCtxtRelSC1xRttUlSinr {
      type uint32;
      config false;
      status deprecated;
      description "MOM flags: noNotification.";
    }
    leaf-list pmAcBarringCsfbSpecAcPlmn1Distr {
      type ietfyang:mac-address;
    }
    leaf pmFlexErabRelNormalEnbGbr {
      type uint32;
      config false;
    }
    leaf pmMacHarqDlNackQpsk {
      type ietfyang:mac-address;
      config false;
    }
    leaf pmCellHoExeAttLteInterFMbms {
      type uint32;
      config false;
    }
    leaf pmFlexErabEstabSuccAddedGbr {
      type uint32;
      config false;
    }
    leaf pmMeasRepGoodCovElc {
      type uint32;
      config false;
    }
    leaf pmErabEstabFailGbrUlEnb {
      type uint32;
      config false;
    }
    leaf pmPtmHoBlocked {
      type uint32;
      config false;
    }
    leaf pmRadioRecInterferencePwrPrb66 {
      type uint32;
      config false;
    }
    leaf pmRrcConnResumeFailDynUeAdmCtrlPtt {
      type uint32;
      config false;
    }
    leaf-list pmRrcConnEstabAttReattDtaCe {
      type uint32;
    }
    leaf pmRrcConnResumeFailLic {
      type uint32;
      config false;
    }
    leaf-list pmSinrPuschDistr {
      type uint32;
    }
    leaf-list pmPdcpPktDiscDlPelrQci {
      type uint32;
    }
    leaf pmFlexMacLatTimeDl {
      type ietfyang:mac-address;
      config false;
      status deprecated;
      description "MOM flags: noNotification.";
    }
    leaf pmGoodCovSearchEvalReport {
      type ietfinet:port-number;
      config false;
    }
    leaf-list pmAasHorizontalDistr {
      type uint32;
    }
    leaf pmUeCtxtFetchSuccS1HoPrepSrvccUtran {
      type uint32;
      config false;
    }
    leaf pmUeAdmCtrlPreventivePe {
      type uint32;
      config false;
    }
    leaf pmErabRelAbnormalEnbActHpr {
      type uint32;
      config false;
    }
    leaf pmMcPttQualityRbUlLowSampl {
      type uint32;
      config false;
    }
    leaf pmUeCapabilityAsrMismatch {
      type uint32;
      config false;
    }
    leaf pmCellHoPrepSuccLteInterF {
      type uint32;
      config false;
    }
    leaf-list pmUlPathlossDistr {
      type uint32;
    }
    leaf pmRrcConnReestFailDynUeAdmCtrl {
      type uint32;
      config false;
    }
    leaf pmRrcConnReconfAttNoMobEarfcnCa {
      type uint32;
      config false;
    }
    leaf pmFlexMacHarqDl6 {
      type ietfyang:mac-address;
      config false;
    }
    leaf pmS1SigConnEstabSuccMta {
      type uint32;
      config false;
    }
    leaf-list pmRobustCallSetupGuardTimeDistr {
      type uint32;
    }
    leaf pmPdcpVolDlSrb {
      type uint32;
      config false;
    }
    leaf pmCellHoPrepAttLteInterF {
      type uint32;
      config false;
    }
    leaf pmCellHoExeAttLteInterFUeMeasRsrp {
      type uint32;
      config false;
    }
    leaf pmRrcConnMax {
      type int32;
      config false;
    }
    leaf-list pmRrcConnEstabSuccCe {
      type uint32;
    }
    leaf pmHoPrepOutS1RejInvalidIntraFCsg {
      type uint32;
      config false;
    }
    leaf pmRrcConnEstabFailMISigQCong {
      type uint32;
      config false;
    }
    leaf pmMacVolDlDataTm7Tm8Srs {
      type ietfyang:mac-address;
      config false;
    }
    leaf pmFlexMacHarqDlNackComp {
      type ietfyang:mac-address;
      config false;
    }
    leaf pmBadCovSearchEvalReportRsrp {
      type ietfinet:port-number;
      config false;
    }
    leaf-list pmRrcLatencyConnResumeDistr {
      type uint32;
    }
    leaf pmFlexZtemporary16 {
      type uint32;
      config false;
    }
    leaf pmRadioThpVolTxDlSCellIcmOffl {
      type uint32;
      config false;
    }
    leaf pmEndcRelMnMcgRelocAtt {
      type uint32;
      config false;
    }
    leaf-list pmIdcUlCaVictimOnDistr {
      type uint32;
    }
    leaf pmFlexPdcpPktReceivedUl {
      type uint32;
      config false;
    }
    leaf pmCellHoPrepAttLteIntraFHybridCsg {
      type uint32;
      config false;
    }
    leaf-list pmCaSchedDlOffloadingDistr {
      type uint32;
    }
    leaf pmPdcpPktDiscDlPelr {
      type uint32;
      config false;
    }
    leaf-list pmZtemporary17Qci {
      type uint32;
    }
    leaf-list pmErabLevRopStartQci {
      type uint32;
    }
    leaf pmUeCtxtRelSCTdScdma {
      type uint32;
      config false;
    }
    leaf pmSchedActivityCellUl {
      type uint32;
      config false;
    }
    leaf-list pmAcBarringCsfbSpecAcPlmn2Distr {
      type ietfyang:mac-address;
    }
    leaf-list pmDynUeAdmCtrlQueueTimeDistr {
      type uint32;
      description "MOM flags: noNotification.";
    }
    leaf pmErabRelAbnormalEnbPe {
      type uint32;
      config false;
    }
    leaf pmErabEstabFailAddedOngoingProc {
      type uint32;
      config false;
    }
    leaf pmRadioThpVolDl3ccPCell {
      type uint32;
      config false;
    }
    leaf pmUeCtxtRelCsfbLimitedDualRadioUeCdma {
      type uint32;
      config false;
    }
    leaf pmHoPrepRejInLicConnUsers {
      type uint32;
      config false;
    }
    leaf-list pmAccessClassBarringCsfbPlmn3Distr {
      type ietfyang:mac-address;
    }
    leaf pmCgiMeasFailAnrPciConflict {
      type uint32;
      config false;
    }
    leaf pmRrcConnQueueAttMtaHp {
      type uint32;
      config false;
    }
    leaf pmRrcConnLevSum {
      type uint32;
      config false;
    }
    leaf pmUeCtxtRelMmeActHo {
      type uint32;
      config false;
    }
    leaf pmRobustCallSetupTimerExp {
      type uint32;
      config false;
    }
    leaf pmFlexZtemporary11 {
      type uint32;
      config false;
    }
    leaf-list pmTaInitBrDistr {
      type uint32;
    }
    leaf pmRadioRecInterferencePwrPrb16 {
      type uint32;
      config false;
    }
    leaf pmRadioUeRepCqi2Subband8Sum {
      type uint32;
      config false;
    }
    leaf-list pmErabRelAbnormalEnbQci {
      type uint32;
    }
    leaf pmUeCtxtFetchSuccIntraEnbHoExe {
      type uint32;
      config false;
    }
    leaf pmGoodCovSearchEvalReportRsrp {
      type ietfinet:port-number;
      config false;
    }
    leaf pmRadioRecInterferencePwrPrb2 {
      type uint32;
      config false;
    }
    leaf pmOocUesLevSum {
      type uint32;
      config false;
    }
    leaf pmUeCtxtFetchSuccCgiMeas {
      type uint32;
      config false;
    }
    leaf-list pmAccessClassBarringVoicePlmn3Distr {
      type ietfyang:mac-address;
    }
    leaf pmEndcUaiRecOverheatingDisc {
      type uint32;
      config false;
    }
    leaf pmErabActQci5EmInactTimer {
      type uint32;
      config false;
    }
    leaf pmRaAccHarqFailAfterContRes {
      type uint32;
      config false;
    }
    leaf pmBadCovOutSearchEvalReport {
      type ietfinet:port-number;
      config false;
    }
    leaf-list pmActiveDrbDlSumQci {
      type ietfyang:mac-address;
    }
    leaf pmRrcConnEstabSuccMoVoice {
      type uint32;
      config false;
    }
    leaf pmMimoSleepTime {
      type uint32;
      config false;
    }
    leaf pmCellHoPrepAttLteInterFMbms {
      type uint32;
      config false;
    }
    leaf-list pmZtemporary131Compr {
      type uint32;
    }
    leaf-list pmErabEstabAttAddedHoOngoingArp {
      type uint32;
    }
    leaf pmUeCtxtFetchAttS1HoExeSrvccUtran {
      type uint32;
      config false;
    }
    leaf pmUeCtxtFetchSuccX2HoIn {
      type uint32;
      config false;
    }
    leaf-list pmMacTimeDlNoDrxSyncSampQci {
      type ietfyang:mac-address;
      description "MOM flags: noNotification.";
    }
    leaf pmUeExclThpUlRelativeHighVol {
      type uint32;
      config false;
    }
    leaf-list pmCaActivatedDlIcmSumDistr {
      type uint32;
    }
    leaf pmCellHoPrepAttLteIntraFCsg {
      type uint32;
      config false;
    }
    leaf pmZtemporary110 {
      type uint32;
      config false;
    }
    leaf pmZtemporary60 {
      type uint32;
      config false;
    }
    leaf-list pmCaConfiguredUlSum {
      type uint32;
    }
    leaf pmPrbUsedDlMax {
      type int32;
      config false;
    }
    leaf pmRrcConnResumeFailLowCovUeAdmCtrl {
      type uint32;
      config false;
      status deprecated;
      description "MOM flags: noNotification.";
    }
    leaf pmHoPreventedNotInPlmnWL {
      type uint32;
      config false;
    }
    leaf pmUeCtxtRetainArpHigh {
      type uint32;
      config false;
    }
    leaf pmCellHoPrepAttNrServTrig {
      type uint32;
      config false;
    }
    leaf pmEndcSetupBufMonConfig {
      type uint32;
      config false;
    }
    leaf-list pmPrbUtilUl {
      type uint32;
    }
    leaf-list pmPdcpLatPktTransDlCatMDrxNoSyncQci {
      type uint32;
    }
    leaf pmRadioRecInterferencePwrPrb14 {
      type uint32;
      config false;
    }
    leaf-list pmUeThpDlMbbFilteredDistr {
      type uint32;
      description "MOM flags: noNotification.";
    }
    leaf pmUeCtxtRelSCCdmaA2Rsrq {
      type uint32;
      config false;
    }
    leaf-list pmPrbUtilDlCellResource24Distr {
      type uint32;
      description "MOM flags: noNotification.";
    }
    leaf pmSchedTtiCellUlFreqSel {
      type uint32;
      config false;
      status deprecated;
      description "MOM flags: noNotification.";
    }
    leaf pmFlexEndcSetupUeAtt {
      type uint32;
      config false;
    }
    leaf pmZtemporary139 {
      type uint32;
      config false;
    }
    leaf pmFlexSchedActivityUeDl {
      type uint32;
      config false;
    }
    leaf pmFlexErabEstabSuccAdded {
      type uint32;
      config false;
    }
    leaf pmWifiAccessEval {
      type uint32;
      config false;
    }
    leaf pmPucchCqiResMediumUtilCell {
      type int32;
      config false;
    }
    leaf-list pmPdcchCfiUtil {
      type uint32;
    }
    leaf pmZtemporary122 {
      type uint32;
      config false;
    }
    leaf-list pmErabRelAbnormalMmeArp {
      type uint32;
    }
    leaf pmClpcUlSinr {
      type uint32;
      config false;
    }
    leaf pmPrbAvailDl {
      type uint32;
      config false;
    }
    leaf pmUeCtxtRelSCNrB2Rsrq {
      type uint32;
      config false;
    }
    leaf pmFlexPdcpPktFwdDl {
      type uint32;
      config false;
    }
    leaf-list pmCaScheduledDl2ccSumDistr {
      type uint32;
    }
    leaf pmUeCtxtFetchSuccX2HoPrep {
      type uint32;
      config false;
    }
    leaf pmFlexMacHarqDlDtxQpsk {
      type ietfyang:mac-address;
      config false;
    }
    leaf-list pmErabRelNormalEnbActArp {
      type uint32;
    }
    leaf pmRadioThpVolTxDlSCellExt {
      type uint32;
      config false;
    }
    leaf pmMacUeThpTimeUl {
      type ietfyang:mac-address;
      config false;
    }
    leaf pmFlexErabEstabAttAddedCsfb {
      type uint32;
      config false;
    }
    leaf pmUeCtxtRelMme {
      type uint32;
      config false;
    }
    leaf pmFlexMacHarqDlNack16qam {
      type ietfyang:mac-address;
      config false;
    }
    leaf pmRadioUeRepCqiSubband8Sum {
      type uint32;
      config false;
    }
    leaf pmMacVolUlUnresUePucchSrGrant {
      type ietfyang:mac-address;
      config false;
    }
    leaf pmFlexErabRelAbnormalEnbActPe {
      type uint32;
      config false;
    }
    leaf pmRadioThpVolTxDlSCellEranOffl {
      type uint32;
      config false;
    }
    leaf pmEndcNotAllowedMoVoice {
      type uint32;
      config false;
    }
    leaf pmRrcConnReconfAttNoMob {
      type uint32;
      config false;
    }
    leaf-list pmPdcchSym2PwrUtil {
      type uint32;
    }
    leaf pmUeExclThpUlRelativeQciLowVol {
      type uint32;
      config false;
    }
    leaf-list pmPrbUtilDlCellResource2Distr {
      type uint32;
      description "MOM flags: noNotification.";
    }
    leaf pmPdcpVolDlDrbTransPlmn4 {
      type uint32;
      config false;
    }
    leaf pmRadioRecInterferencePwrPrb4 {
      type uint32;
      config false;
    }
    leaf-list pmAccessClassBarringVideoDistr {
      type ietfyang:mac-address;
    }
    leaf pmErabRelAbnormalMmeS1Reset {
      type uint32;
      config false;
    }
    leaf pmEndcHoQualifiedUe {
      type uint32;
      config false;
    }
    leaf pmEndcHoA5MeasRepUe {
      type uint32;
      config false;
    }
    leaf pmFlexZtemporary23 {
      type uint32;
      config false;
    }
    leaf pmCaDeconfiguredMeasTo {
      type uint32;
      config false;
      status deprecated;
      description "MOM flags: noNotification.";
    }
    leaf-list pmPrbUtilDlCellResource3Distr {
      type uint32;
      description "MOM flags: noNotification.";
    }
    leaf pmRadioRecInterferencePwrSf1 {
      type uint32;
      config false;
    }
    leaf-list pmAccessClassBarringMosPlmn2Distr {
      type ietfyang:mac-address;
    }
    leaf pmFlexZtemporary19 {
      type uint32;
      config false;
    }
    leaf pmCellDownLockMan {
      type uint32;
      config false;
    }
    leaf pmZtemporary124 {
      type uint32;
      config false;
    }
    leaf-list pmPdcpInactSecDlVolteDistr {
      type uint32;
    }
    leaf pmUeCtxtRelAbnormalEnbActOosPft {
      type uint32;
      config false;
    }
    leaf pmZtemporary111 {
      type uint32;
      config false;
    }
    leaf pmFlexMacHarqDlDtx16qam {
      type ietfyang:mac-address;
      config false;
    }
    leaf pmRrcConnNs05RepeaterZoneSamp {
      type uint32;
      config false;
    }
    leaf pmPagEdrxReceived {
      type uint32;
      config false;
    }
    leaf pmHoPrepAttIntraCell {
      type uint32;
      config false;
    }
    leaf pmRrcConnEstabAttReattEm {
      type uint32;
      config false;
    }
    leaf pmRadioRecInterferencePwrPrb24 {
      type uint32;
      config false;
    }
    leaf pmZtemporary138 {
      type uint32;
      config false;
    }
    leaf pmUeMeasAttCsfb1xRtt {
      type uint32;
      config false;
    }
    leaf pmLbCellHighLoaded {
      type uint32;
      config false;
    }
    leaf pmUeCtxtConnResumeAtt {
      type uint32;
      config false;
      status deprecated;
      description "MOM flags: noNotification.";
    }
    leaf pmRadioUeRepCqi2Subband2Sum {
      type uint32;
      config false;
    }
    leaf pmFlexCellHoExeAttGeran {
      type uint32;
      config false;
    }
    leaf-list pmPdcpVolDlDrbTransQci {
      type uint32;
    }
    leaf pmS1SigConnEstabFailMmeOvlMos {
      type uint32;
      config false;
    }
    leaf pmUeThpTimeUlInitial {
      type uint32;
      config false;
    }
    leaf pmPdcpPktReceivedDl {
      type uint32;
      config false;
    }
    leaf pmRrcConnMaxPlmn4 {
      type int32;
      config false;
    }
    leaf pmMacHarqUlDtxQpsk {
      type ietfyang:mac-address;
      config false;
    }
    leaf-list pmRrcConnQueueAdptPullDelayDistr {
      type uint32;
    }
    leaf pmErabRelAbnormalEnbOos {
      type uint32;
      config false;
    }
    leaf pmPdcpVolDlDrbTransPlmn3 {
      type uint32;
      config false;
    }
    leaf pmA3InterFBestCellEvalReport {
      type ietfinet:port-number;
      config false;
    }
    leaf-list pmErabEstabFailUeAdmLicRejArp {
      type uint32;
    }
    leaf-list pmMacUeBitRateRecommUlDistr {
      type ietfyang:mac-address;
    }
    leaf pmFlexMacHarqUlDtx256qam {
      type ietfyang:mac-address;
      config false;
    }
    leaf pmPdcpBitrateDlDrbMax {
      type int32;
      config false;
    }
    leaf pmRaAttCfra {
      type uint32;
      config false;
    }
    leaf pmRadioRecInterferencePwrPrb41 {
      type uint32;
      config false;
    }
    leaf pmZtemporary67 {
      type uint32;
      config false;
    }
    leaf pmFlexCellHoExeAttNr {
      type uint32;
      config false;
    }
    leaf pmActiveDrbUlSum {
      type ietfyang:mac-address;
      config false;
    }
    leaf pmRrcConnMaxPlmn3 {
      type int32;
      config false;
    }
    leaf pmRrcConnEstabAttMos {
      type uint32;
      config false;
    }
    leaf pmRrcConnReestFailMISigQCong {
      type uint32;
      config false;
    }
    leaf pmRadioRecInterferencePwrPrb11 {
      type uint32;
      config false;
    }
    leaf pmUeExclThpUlShortTimeQciHighVol {
      type uint32;
      config false;
    }
    leaf pmS1SigConnEstabAttMos {
      type uint32;
      config false;
    }
    leaf pmPrbUsedUlMax {
      type int32;
      config false;
    }
    leaf pmPrbUsedDlDtch {
      type uint32;
      config false;
    }
    leaf pmFlexCellHoPrepSucc1xRttSrvcc {
      type uint32;
      config false;
    }
    leaf-list pmErabRelAbnormalEnbActTnFailQci {
      type uint32;
    }
    leaf-list pmErabRelNormalEnbQci {
      type uint32;
    }
    leaf-list pmErabRelAbnormalEnbPeQci {
      type uint32;
    }
    leaf pmRadioUeRepCqi2Subband10Sum {
      type uint32;
      config false;
    }
    leaf-list pmRadioRecEffectiveIpNPwrDistr {
      type ietfinet:ip-address;
    }
    leaf pmPrbAvailUl {
      type uint32;
      config false;
    }
    leaf pmRadioRecInterferencePwrPrb87 {
      type uint32;
      config false;
    }
    leaf pmUeCtxtRelCsfbCdma1xRtt {
      type uint32;
      config false;
    }
    leaf pmRadioRecInterferencePwrPrb68 {
      type uint32;
      config false;
    }
    leaf pmUeCtxtRelAbnormalEnbActCdt {
      type uint32;
      config false;
    }
    leaf-list pmPdcchTargetBlerHighRatioDistr {
      type uint32;
    }
    leaf pmRadioRecInterferencePwrPrb76 {
      type uint32;
      config false;
    }
    leaf pmCaConfiguredMeasAtt {
      type uint32;
      config false;
    }
    leaf pmS1SigConnEstabAttHpa {
      type uint32;
      config false;
    }
    leaf pmWifiAccessRej {
      type uint32;
      config false;
    }
    leaf pmErabRelAbnormalMmeActCritCov {
      type uint32;
      config false;
    }
    leaf pmIdcUlCaCapableSum {
      type uint32;
      config false;
    }
    leaf pmUeCtxtFetchAttNasTransferDl {
      type uint32;
      config false;
    }
    leaf pmFlexErabEstabAttAddedHoOngoing {
      type uint32;
      config false;
    }
    leaf pmFlexCellHoPrepSuccNr {
      type uint32;
      config false;
    }
    leaf pmS1SigConnEstabAttMoVoice {
      type uint32;
      config false;
    }
    leaf pmFlexMacTimeDlSamp {
      type ietfyang:mac-address;
      config false;
      status deprecated;
      description "MOM flags: noNotification.";
    }
    leaf-list pmAccessClassBarringVoicePlmn2Distr {
      type ietfyang:mac-address;
    }
    leaf pmErabRelAbnormalEnbUeLostOos {
      type uint32;
      config false;
    }
    leaf pmZtemporary27 {
      type uint32;
      config false;
    }
    leaf-list pmPdcpVolDlDrbQci {
      type uint32;
    }
    leaf-list pmZtemporary225Compr {
      type uint32;
    }
    leaf pmErabEndcScgMax {
      type int32;
      config false;
    }
    leaf pmPdcpRtpSnGapDetected {
      type uint32;
      config false;
    }
    leaf pmRadioRecInterferencePwrPrb36 {
      type uint32;
      config false;
    }
    leaf pmUeCtxtRelAbnormalEnbCdt {
      type uint32;
      config false;
    }
    leaf pmErabRelAbnormalEnbActUeLostOos {
      type uint32;
      config false;
    }
    leaf pmRadioRecInterferencePwrPrb1 {
      type uint32;
      config false;
    }
    leaf pmUlGrantsDetPuschMcPttNDO {
      type uint32;
      config false;
    }
    leaf pmFlexCellHoPrepAttUtran {
      type uint32;
      config false;
    }
    leaf pmMacHarqDlDtxQpsk {
      type ietfyang:mac-address;
      config false;
    }
    leaf pmZtemporary12 {
      type uint32;
      config false;
    }
    leaf pmPtmInhibitImp {
      type uint32;
      config false;
    }
    leaf pmPrbUsedUlCatmSamp {
      type uint32;
      config false;
    }
    leaf pmRadioThpVolDl2ccPCell {
      type uint32;
      config false;
    }
    leaf pmFlexErabRelAbnormalEnbGbr {
      type uint32;
      config false;
    }
    leaf pmRrcConnEstabAttMta {
      type uint32;
      config false;
    }
    leaf-list pmMacUeThpUlMbbLowVolDistr {
      type ietfyang:mac-address;
    }
    leaf pmMacPdschEmptySubframeForced {
      type ietfyang:mac-address;
      config false;
    }
    leaf-list pmPdcpLatPktTransDlNoDrxSyncQci {
      type uint32;
    }
    leaf-list pmRadioTxRankSCellDistr {
      type uint32;
    }
    leaf-list pmDynUeAdmCtrlQueueSizeDistr {
      type uint32;
      description "MOM flags: noNotification.";
    }
    leaf pmRaUnassignedCfraFalse {
      type uint32;
      config false;
    }
    leaf pmUeCtxtRelAbnormalEnbLic {
      type uint32;
      config false;
    }
    leaf-list pmHoExeOutAttQci {
      type uint32;
    }
    leaf pmUeCtxtFetchAttUeCapEnq {
      type uint32;
      config false;
    }
    leaf pmRrcConnQueueAtt {
      type uint32;
      config false;
    }
    leaf pmErabRelMme {
      type uint32;
      config false;
    }
    leaf pmMacHarqDlAck64qam {
      type ietfyang:mac-address;
      config false;
    }
    leaf pmClpcUlP0 {
      type uint32;
      config false;
    }
    leaf-list pmPrbAvailUtilDlDistr {
      type uint32;
    }
    leaf pmMeasRepDlComp {
      type uint32;
      config false;
    }
    leaf-list pmLcgThpTimeUlNs05Distr {
      type uint32;
    }
    leaf-list pmPdcpPktLostUlSrbTooLarge {
      type uint32;
    }
    leaf pmZtemporary247 {
      type uint32;
      config false;
    }
    leaf pmCellHoPrepSuccLteInterFEndcHo {
      type uint32;
      config false;
    }
    leaf-list pmErabEstabFailAddedErabIdInUseQci {
      type uint32;
    }
    leaf pmUeCtxtRelSCNrB1Rsrp {
      type uint32;
      config false;
    }
    leaf pmFlexCellHoExeAttNonMobIrat {
      type uint32;
      config false;
    }
    leaf pmFlexSessionTimeUe {
      type uint32;
      config false;
    }
    leaf pmRrcConnEstabSuccHpa {
      type uint32;
      config false;
    }
    leaf pmHoPrepOutS1RejInvalidInterFCsg {
      type uint32;
      config false;
    }
    leaf pmUeCtxtRelSCNr {
      type uint32;
      config false;
    }
    leaf-list pmHoPrepRejIntraCellDistr {
      type uint32;
    }
    leaf pmPrbAvailUlPucchSr {
      type uint32;
      config false;
    }
    leaf pmPucchSrCqiResAllocAtt {
      type uint32;
      config false;
    }
    leaf pmUeCtxtRelSCNrB2Rsrp {
      type uint32;
      config false;
    }
    leaf pmA5BestCellEvalReport {
      type ietfinet:port-number;
      config false;
    }
    leaf-list pmActiveUeDlSumCe {
      type ietfyang:mac-address;
    }
    leaf-list pmErabRelAllMmeQci {
      type uint32;
    }
    leaf pmPdcpPktLostUl {
      type uint32;
      config false;
    }
    leaf-list pmPdcpVolUlDrbQci {
      type uint32;
    }
    leaf-list pmPdcpInactSecDlMcPttDistr {
      type uint32;
    }
    leaf-list pmZtemporary59 {
      type uint32;
    }
    leaf pmZtemporary196 {
      type uint32;
      config false;
    }
    leaf-list pmPdcpLatTimeDlDrxNoSyncQci {
      type uint32;
    }
    leaf pmRadioRecInterferencePwrPrb93 {
      type uint32;
      config false;
    }
    leaf pmZtemporary5 {
      type uint32;
      config false;
    }
    leaf pmRadioRecInterferencePwrPrb59 {
      type uint32;
      config false;
    }
    leaf pmRaMsg2AttCbra {
      type uint32;
      config false;
    }
    leaf-list pmAccessClassBarringMosDistr {
      type ietfyang:mac-address;
    }
    leaf pmFlexErabEstabAttAddedGbr {
      type uint32;
      config false;
    }
    leaf pmPdcpVolUlDrb {
      type uint32;
      config false;
    }
    leaf pmMacVolUlUnresUePreemptGrant {
      type ietfyang:mac-address;
      config false;
    }
    leaf pmRaSuccSrOutOfSyncPft {
      type uint32;
      config false;
    }
    leaf pmPrbUsedUlDtchNs05FullBandSch {
      type uint32;
      config false;
    }
    leaf-list pmActiveUeDlSectorCarrierDistr {
      type ietfyang:mac-address;
    }
    leaf pmFlexCellHoExeAttLteIntraF {
      type uint32;
      config false;
    }
    leaf-list pmS1SigConnEstabAttDtaCe {
      type uint32;
    }
    leaf pmInvalidPftMsg {
      type uint32;
      config false;
    }
    leaf pmMultiUserMimoSchedPrbDl {
      type uint32;
      config false;
    }
    leaf pmCellHoExeAttNrServTrig {
      type uint32;
      config false;
    }
    leaf pmRaFailCbraMsg2Disc {
      type uint32;
      config false;
    }
    leaf pmUlGrantsTransMcPttNoAck {
      type uint32;
      config false;
    }
    leaf pmRadioRecInterferencePwrPrb72 {
      type uint32;
      config false;
    }
    leaf pmZtemporary9 {
      type uint32;
      config false;
    }
    leaf pmUeCtxtRelCsfbUlHoPrepTxTO1xRtt {
      type uint32;
      config false;
    }
    leaf-list pmErabRelAbnormalMmeActGbrArp {
      type uint32;
    }
    leaf pmZtemporary6 {
      type uint32;
      config false;
    }
    leaf-list pmPdcchCceAggregationDistr {
      type uint32;
    }
    leaf-list pmPrbUtilDlCellResource19Distr {
      type uint32;
      description "MOM flags: noNotification.";
    }
    leaf pmUeCtxtRetrReestFailShortMacVer {
      type ietfyang:mac-address;
      config false;
      status deprecated;
      description "MOM flags: noNotification.";
    }
    leaf pmFlexRlcDelayPktTransDl {
      type uint32;
      config false;
    }
    leaf pmRadioRecInterferencePwrPrb75 {
      type uint32;
      config false;
    }
    leaf pmRrcConnResumeFailCellIntensSwC {
      type uint32;
      config false;
    }
    leaf pmCriticalBorderEvalReportRsrp {
      type ietfinet:port-number;
      config false;
    }
    leaf pmAnrNrNoActionTooWeak {
      type uint32;
      config false;
    }
    leaf pmPdcpVolDlDrbTransPlmn1 {
      type uint32;
      config false;
    }
    leaf pmRadioRecInterferencePwrPrb92 {
      type uint32;
      config false;
    }
    leaf pmRrcConnEstabAttDta {
      type uint32;
      config false;
      status deprecated;
      description "MOM flags: noNotification.";
    }
    leaf pmRadioThpVolTxDlSCell {
      type uint32;
      config false;
    }
    leaf pmZtemporary26 {
      type uint32;
      config false;
    }
    leaf-list pmCaActivatedDl4ccSumDistr {
      type uint32;
    }
    leaf pmPtmCellReservedSubRatio {
      type uint32;
      config false;
    }
    leaf pmRadioRecInterferencePwrPrb6 {
      type uint32;
      config false;
    }
    leaf pmCellHoPrepSuccLteInterFDtvm {
      type uint32;
      config false;
    }
    leaf pmZtemporary20 {
      type uint32;
      config false;
    }
    leaf pmZtemporary142 {
      type uint32;
      config false;
    }
    leaf pmUeCtxtSuspendSucc {
      type uint32;
      config false;
    }
    leaf pmMeasRep {
      type uint32;
      config false;
    }
    leaf pmFlexErabEstabAttAddedHoOngoingGbr {
      type uint32;
      config false;
    }
    leaf pmZtemporary57 {
      type uint32;
      config false;
    }
    leaf pmActiveUeUlSum {
      type ietfyang:mac-address;
      config false;
    }
    leaf-list pmCellDlSePttReservation {
      type uint32;
    }
    leaf-list pmAccessClassBarringVideoPlmn1Distr {
      type ietfyang:mac-address;
    }
    leaf pmRlcDelayTimeDl2 {
      type uint32;
      config false;
    }
    leaf pmCovSearchZoneSum {
      type uint32;
      config false;
    }
    leaf pmErabRelAbnormalEnbHo {
      type uint32;
      config false;
    }
    leaf pmRrcConnEstabSuccGummeiNative {
      type uint32;
      config false;
    }
    leaf pmRadioRecInterferencePwrPrb97 {
      type uint32;
      config false;
    }
    leaf-list pmAasVerticalDistr {
      type uint32;
    }
    leaf pmErabRelNormalEnb {
      type uint32;
      config false;
    }
    leaf pmZtemporary240 {
      type uint32;
      config false;
    }
    leaf pmUeCtxtRelNormalEnbAct {
      type uint32;
      config false;
    }
    leaf pmOocStateExitsUeRel {
      type uint32;
      config false;
    }
    leaf pmUeCtxtFetchAttX2HoExe {
      type uint32;
      config false;
    }
    leaf-list pmRrcConnEstabSuccModCe {
      type uint32;
    }
    leaf pmUeThpTimeUlCa {
      type uint32;
      config false;
    }
    leaf pmErabRelAbnormalEnbSir {
      type uint32;
      config false;
    }
    leaf-list pmErabEstabAttAddedCsfbQci {
      type uint32;
    }
    leaf pmFlexErabEstabFailAddedErabIdInUse {
      type uint32;
      config false;
    }
    leaf pmFlexUeCtxtRelMme {
      type uint32;
      config false;
    }
    leaf pmPrbOccupiedUlShortSps {
      type uint32;
      config false;
    }
    leaf pmUeCtxtRetrReestFailOngUeProc {
      type uint32;
      config false;
    }
    leaf pmCovSearchZoneSamp {
      type uint32;
      config false;
    }
    leaf pmSchedActivityUeUlComp {
      type uint32;
      config false;
    }
    leaf pmUeCtxtRelSCGsm {
      type uint32;
      config false;
    }
    leaf pmRadioRecInterferencePwrPrb83 {
      type uint32;
      config false;
    }
    leaf pmErabRelQci1EmInactTimer {
      type uint32;
      config false;
    }
    leaf-list pmErabRelDlInactGapQci {
      type uint32;
    }
    leaf pmPwrBoostAttLowCovUe {
      type uint32;
      config false;
    }
    leaf pmFlexRrcConnSum {
      type uint32;
      config false;
    }
    leaf pmHoPrepOutS1RejInvalidInterFHybridCsg {
      type uint32;
      config false;
    }
    leaf pmCellHoExeSuccLteInterFCsg {
      type uint32;
      config false;
    }
    leaf pmEndcSetupFailUeCap {
      type uint32;
      config false;
    }
    leaf-list pmRrcConnEstabAttReattMtaPagPrioDistr {
      type uint32;
    }
    leaf pmRrcConnReestFailDynUeAdmCtrlPa {
      type uint32;
      config false;
    }
    leaf pmFlexErabRelMmeActEutra {
      type uint32;
      config false;
    }
    leaf-list pmLcgThpTimeUlLcg {
      type uint32;
    }
    leaf-list pmCaConfiguredDlIeNbSum {
      type uint32;
    }
    leaf pmUeCtxtFetchAttS1HoExe {
      type uint32;
      config false;
    }
    leaf pmFlexPdcpPktDiscDlPelrUu {
      type uint32;
      config false;
    }
    leaf pmUlGrantsWithDetectedPuschPCell {
      type uint32;
      config false;
    }
    leaf pmPwsEtwsPrimSucc {
      type uint32;
      config false;
    }
    leaf pmZtemporary88 {
      type uint32;
      config false;
    }
    leaf pmFlexZtemporary10 {
      type uint32;
      config false;
    }
    leaf-list pmUeThpDlDistr {
      type uint32;
    }
    leaf pmMacHarqDlNack256qam {
      type ietfyang:mac-address;
      config false;
    }
    leaf pmMacHarqFail {
      type ietfyang:mac-address;
      config false;
    }
    leaf pmRrcConnResumeFailDynUeAdmCtrl {
      type uint32;
      config false;
    }
    leaf pmFlexUeCtxtRelSCGsm {
      type uint32;
      config false;
    }
    leaf pmRadioRecInterferencePwrPrb38 {
      type uint32;
      config false;
    }
    leaf pmFlexPdcpVolDlDrbLastTTI {
      type uint32;
      config false;
    }
    leaf pmPrbUsedDlFirstTrans {
      type uint32;
      config false;
    }
    leaf pmSchedTtiCellDl {
      type uint32;
      config false;
    }
    leaf pmPdschBlankedSubframe {
      type uint32;
      config false;
    }
    leaf-list pmUeThpUlDistr {
      type uint32;
    }
    leaf pmErabRelAbnormalMme {
      type uint32;
      config false;
    }
    leaf pmDynUeAdmCtrlQueueTo {
      type uint32;
      config false;
      status deprecated;
      description "MOM flags: noNotification.";
    }
    leaf pmPdcpPktDiscDlPelrUu {
      type uint32;
      config false;
    }
    leaf pmZtemporary127 {
      type uint32;
      config false;
    }
    leaf pmDuctIntCharSeq {
      type uint32;
      config false;
    }
    leaf pmEndcSetupUeSuccNrRestricted {
      type uint32;
      config false;
    }
    leaf pmPdcpVolDlDrbTransPlmn6 {
      type uint32;
      config false;
    }
    leaf pmMacUeThpVolDl {
      type ietfyang:mac-address;
      config false;
      status deprecated;
      description "MOM flags: noNotification.";
    }
    leaf pmDlAssigsWithDetHarqAckMcPtt {
      type uint32;
      config false;
    }
    leaf pmRadioRecInterferencePwrPrb70 {
      type uint32;
      config false;
    }
    leaf pmRadioUeRepCqiSubband11Sum {
      type uint32;
      config false;
    }
    leaf pmRadioUeRepCqi2Subband12Sum {
      type uint32;
      config false;
    }
    leaf-list pmMacHarqDlDtxDistr {
      type ietfyang:mac-address;
    }
    leaf pmPdcpLatTimeDl {
      type uint32;
      config false;
    }
    leaf pmZtemporary86 {
      type uint32;
      config false;
    }
    leaf pmA5BestCellEvalReportUl {
      type ietfinet:port-number;
      config false;
    }
    leaf pmRadioRecInterferencePwrPrb60 {
      type uint32;
      config false;
    }
    leaf-list pmCaWaitGoodCov {
      type uint32;
    }
    leaf-list pmZtemporary134Compr {
      type uint32;
    }
    leaf pmRrcConnNs05Max {
      type int32;
      config false;
    }
    leaf pmUeExclThpUlSmallVol {
      type uint32;
      config false;
    }
    leaf-list pmCaScheduledDlIeNbSum {
      type uint32;
    }
    leaf pmFlexErabEstabFailAddedOngoingProc {
      type uint32;
      config false;
    }
    leaf pmFlexMacSkipUlDtxPresched {
      type ietfinet:ip-address;
      config false;
    }
    leaf pmFlexRrcConnReestAtt {
      type uint32;
      config false;
    }
    leaf pmZtemporary241 {
      type uint32;
      config false;
    }
    leaf-list pmPdcpPktTransDlQci {
      type uint32;
    }
    leaf pmMacHarqDlNack64qam {
      type ietfyang:mac-address;
      config false;
    }
    leaf-list pmRrcConnResumeTimeDistr {
      type uint32;
    }
    leaf-list pmPrbUtilDlCellResource9Distr {
      type uint32;
      description "MOM flags: noNotification.";
    }
    leaf-list pmAccessClassBarringVideoPlmn3Distr {
      type ietfyang:mac-address;
    }
    leaf-list pmMacLcgThpVolUlLcg {
      type ietfyang:mac-address;
    }
    leaf pmRrcConnReestFailCellLatency {
      type uint32;
      config false;
    }
    leaf pmCellHoPrepCancelGbr {
      type uint32;
      config false;
    }
    leaf pmAnrCandNrelCgiAdd {
      type uint32;
      config false;
    }
    leaf pmSchedTtiCellUlResAllocKept {
      type uint32;
      config false;
    }
    leaf pmRadioRecInterferencePwrPrb31 {
      type uint32;
      config false;
    }
    leaf pmRrcConnEstabSuccEm {
      type uint32;
      config false;
    }
    leaf pmRadioRecInterferencePwrPrb37 {
      type uint32;
      config false;
    }
    leaf pmUeCtxtRelNaccCsfbGsm {
      type uint32;
      config false;
    }
    leaf pmUeCtxtRelSCGsmB2Rsrq {
      type uint32;
      config false;
    }
    leaf pmRrcConnResumeFailBearerAdmRej {
      type uint32;
      config false;
    }
    leaf-list pmPuschMcsSubsGroup9Distr {
      type uint32;
    }
    leaf pmFlexErabRelAbnormalEnbActGbr {
      type uint32;
      config false;
    }
    leaf pmErabRelAbnormalEnbActOos {
      type uint32;
      config false;
    }
    leaf-list pmAasSchedPrbDlHorizontalDistr {
      type uint32;
    }
    leaf pmRadioUeRepCqiSubband4Sum {
      type uint32;
      config false;
    }
    leaf pmElcPdcchBlankedTti {
      type uint32;
      config false;
    }
    leaf pmDlAssigsTransMcPttNDO {
      type uint32;
      config false;
    }
    leaf pmPdcpPktDiscDlBbmLimit {
      type uint32;
      config false;
    }
    leaf pmRadioRecInterferencePwrPrb73 {
      type uint32;
      config false;
    }
    leaf pmConfigRejDlComp {
      type uint32;
      config false;
    }
    leaf pmCellHoExeAttLteInterFUtvm {
      type uint32;
      config false;
    }
    leaf pmUlGrantsTransMcPttNDO {
      type uint32;
      config false;
    }
    leaf pmFlexErabRelMme {
      type uint32;
      config false;
    }
    leaf pmActiveDrbDlSum {
      type ietfyang:mac-address;
      config false;
    }
    leaf pmUeCtxtRelCsfbGsm {
      type uint32;
      config false;
    }
    leaf-list pmPrbUtilDlCellResource10Distr {
      type uint32;
      description "MOM flags: noNotification.";
    }
    leaf pmCellHoExeAttLteIntraFAfterResync {
      type uint32;
      config false;
    }
    leaf pmActiveUeDlSum {
      type ietfyang:mac-address;
      config false;
    }
    leaf pmRrcConnReconfSuccNoMobDacc {
      type uint32;
      config false;
    }
    leaf-list pmAcBarringVoiceSpecAcPlmn1Distr {
      type ietfyang:mac-address;
    }
    leaf pmErabEstabAttInitHpa {
      type uint32;
      config false;
    }
    leaf pmZtemporary91 {
      type uint32;
      config false;
    }
    leaf pmZtemporary29 {
      type uint32;
      config false;
    }
    leaf-list pmRadioUeOutLoopAdjDistr {
      type uint32;
    }
    leaf pmFlexCellHoPrepAttUtranSrvcc {
      type uint32;
      config false;
    }
    leaf pmRateShapeTimeUl {
      type uint32;
      config false;
    }
    leaf-list pmMacUeBitRateSelectUlDistr {
      type ietfyang:mac-address;
    }
    leaf pmZtemporary24 {
      type uint32;
      config false;
    }
    leaf-list pmRadioUeRepTm4Rank3PmiDistr {
      type uint32;
    }
    leaf pmRrcConnEstabFailCellLatency {
      type uint32;
      config false;
    }
    leaf pmMacHarqUlFailIua16qam {
      type ietfyang:mac-address;
      config false;
    }
    leaf pmUeCtxtRelSCCdmaB2Rsrp {
      type uint32;
      config false;
    }
    leaf pmUeCtxtRetrReestFailEndcUe {
      type uint32;
      config false;
      status deprecated;
      description "MOM flags: noNotification.";
    }
    leaf pmPrbUsedDlBcch {
      type uint32;
      config false;
    }
    leaf-list pmPrbUtilDlCellResource16Distr {
      type uint32;
      description "MOM flags: noNotification.";
    }
    leaf pmFlexCellHoExeAttUtran {
      type uint32;
      config false;
    }
    leaf pmUeThpTimeDl {
      type uint32;
      config false;
    }
    leaf pmUeCtxtFetchAttCgiMeas {
      type uint32;
      config false;
    }
    leaf pmWifiAccessDecisionByWic {
      type uint32;
      config false;
    }
    leaf pmCellHoPrepSuccLowCovUe {
      type uint32;
      config false;
    }
    leaf-list pmErabRelMmeArp {
      type uint32;
    }
    leaf pmMacHarqDlDtx256qam {
      type ietfyang:mac-address;
      config false;
    }
    leaf pmFlexPdcpLatPktTransDl {
      type uint32;
      config false;
    }
    leaf pmFlexCellHoExeSuccGeran {
      type uint32;
      config false;
    }
    leaf pmSchedActivityCellDl {
      type uint32;
      config false;
    }
    leaf pmZtemporary14 {
      type uint32;
      config false;
    }
    leaf pmRadioRecInterferencePwrPrb42 {
      type uint32;
      config false;
    }
    leaf-list pmSinrPdcchDistr {
      type uint32;
    }
    leaf pmPdcpVolDlDrbTransPlmn0 {
      type uint32;
      config false;
    }
    leaf pmBbUeMeasAllocAtt {
      type uint32;
      config false;
    }
    leaf pmZtemporary61 {
      type uint32;
      config false;
    }
    leaf pmZtemporary89 {
      type uint32;
      config false;
    }
    leaf-list pmPrbUsedUlDtchQci {
      type uint32;
    }
    leaf pmUeCtxtRelAbnormalEnbActCdtAutoPnr {
      type uint32;
      config false;
    }
    leaf-list pmAcBarringVideoSpecAcPlmn2Distr {
      type ietfyang:mac-address;
    }
    leaf-list pmLcgThpTimeUlNonNs05Distr {
      type uint32;
    }
    leaf pmFlexCellHoPrepAttNonMobLte {
      type uint32;
      config false;
    }
    leaf pmUeCtxtRelSCEUtraBestCellRsrp {
      type uint32;
      config false;
    }
    leaf pmMacTimeUlResUe {
      type ietfyang:mac-address;
      config false;
    }
    leaf pmRaFailCfraMsg2Disc {
      type uint32;
      config false;
    }
    leaf pmFlexErabEstabSuccInitGbr {
      type uint32;
      config false;
    }
    leaf pmZtemporary130 {
      type uint32;
      config false;
    }
    leaf-list pmPrbUtilDlCellResource7Distr {
      type uint32;
      description "MOM flags: noNotification.";
    }
    leaf pmRohcEstabFailCid {
      type uint32;
      config false;
    }
    leaf pmRrcConnReestAttHo {
      type uint32;
      config false;
    }
    leaf pmFlexCellHoPrepAttLteIntraF {
      type uint32;
      config false;
    }
    leaf pmUeCtxtFetchSuccS1HoExeSrvccGeran {
      type uint32;
      config false;
    }
    leaf-list pmMacUeBitRateRecommUlVoipDistr {
      type ietfinet:ip-address;
    }
    leaf pmZtemporary28 {
      type uint32;
      config false;
    }
    leaf pmUeCapabilityGUtran {
      type uint32;
      config false;
    }
    leaf pmErabRelAbnormalEnbActUeLost {
      type uint32;
      config false;
    }
    leaf-list pmLaaCapableDlSum {
      type uint32;
    }
    leaf pmErabEndcScgLevSamp {
      type uint32;
      config false;
    }
    leaf-list pmSrGrantLatDistr {
      type uint32;
    }
    leaf pmHoPrepRejInLicLowCovUe {
      type uint32;
      config false;
    }
    leaf pmRadioUeRepCqiSubband2Sum {
      type uint32;
      config false;
    }
    leaf pmDlAssigsDetectedHarqVolteNDO {
      type uint32;
      config false;
    }
    leaf pmErabRelAbnormalEnbActCritCov {
      type uint32;
      config false;
    }
    leaf pmFlexUeCtxtRelSCWcdma {
      type uint32;
      config false;
    }
    leaf pmUeExclThpDlSmallVol {
      type uint32;
      config false;
      status deprecated;
      description "MOM flags: noNotification.";
    }
    leaf pmCellHoExeAttLteInterF {
      type uint32;
      config false;
    }
    leaf-list pmAcBarringMosSpecAcPlmn1Distr {
      type ietfyang:mac-address;
    }
    leaf pmCellHoPrepSuccLteInterFMbms {
      type uint32;
      config false;
    }
    leaf-list pmCompUlDeltaSinrPuschInterEnbDistr {
      type uint32;
    }
    leaf-list pmRrcConnEstabFailDuIntensCe {
      type uint32;
    }
    leaf pmIdleModeRelDistrLowMediumLoad {
      type uint32;
      config false;
    }
    leaf pmDynUeAdmCtrlQueueAtt {
      type uint32;
      config false;
      status deprecated;
      description "MOM flags: noNotification.";
    }
    leaf pmEndcSetupScgUeSucc {
      type uint32;
      config false;
    }
    leaf pmSessionTimeUe {
      type uint32;
      config false;
    }
    leaf-list pmUeCtxtRelSCEUtraCe {
      type uint32;
    }
    leaf pmPrbAvailUlPuschLowRegion {
      type uint32;
      config false;
    }
    leaf pmUeCtxtResumeAtt {
      type uint32;
      config false;
    }
    leaf pmPdcpVolUlDrbPlmn0 {
      type uint32;
      config false;
    }
    leaf pmUeCtxtRelAbnormalEnbActTnFail {
      type uint32;
      config false;
    }
    leaf pmIdcUlCaSum {
      type uint32;
      config false;
    }
    leaf pmUeCtxtRelAbnormalEnbOos {
      type uint32;
      config false;
    }
    leaf-list pmRrcConnEstabSuccDtaCe {
      type uint32;
    }
    leaf pmA2InterFHoHigherPrioEvalReport {
      type ietfinet:port-number;
      config false;
    }
    leaf pmPrbUsedUlPuschHighRegionSrb {
      type uint32;
      config false;
    }
    leaf pmFlexMacHarqUlFailIuaQpsk {
      type ietfyang:mac-address;
      config false;
    }
    leaf pmUeCtxtRetrReestAttEndcUe {
      type uint32;
      config false;
    }
    leaf pmPrbRemainedUsableUl {
      type uint32;
      config false;
    }
    leaf pmRrcConnResumeFailCellLatency {
      type uint32;
      config false;
    }
    leaf pmZtemporary15 {
      type uint32;
      config false;
    }
    leaf-list pmRrcConnEstabFailCellIntensStatCe {
      type uint32;
    }
    leaf pmErabRelMmeActHo {
      type uint32;
      config false;
    }
    leaf pmPdcpVolUlSrb {
      type uint32;
      config false;
    }
    leaf pmRadioRecInterferencePwrPrb69 {
      type uint32;
      config false;
    }
    leaf pmUeCtxtRelSCEUtraA2Rsrq {
      type uint32;
      config false;
    }
    leaf-list pmRadioUeRepCqiDistr3 {
      type uint32;
    }
    leaf pmUeCtxtRelSCNrB1Rsrq {
      type uint32;
      config false;
    }
    leaf-list pmErabEstabAttRejAdmMsrAddedArp {
      type uint32;
    }
    leaf-list pmPdcpVolDlDrbFiltQci {
      type uint32;
      description "MOM flags: noNotification.";
    }
    leaf pmMacHarqUlFail256Qam {
      type ietfyang:mac-address;
      config false;
    }
    leaf pmRadioRecInterferencePwrPrb65 {
      type uint32;
      config false;
    }
    leaf pmPucchSrResLongUtilCell {
      type int32;
      config false;
    }
    leaf pmRadioRecInterferencePwrPrb21 {
      type uint32;
      config false;
    }
    leaf-list pmPdcpLatTimeDlCatMDrxSyncQci {
      type uint32;
    }
    leaf pmRohcEstabFailUeCap {
      type uint32;
      config false;
    }
    leaf-list pmRaFailCbraMsg2DiscBr {
      type uint32;
    }
    leaf-list pmPrbUtilDlCellResource4Distr {
      type uint32;
      description "MOM flags: noNotification.";
    }
    leaf pmPdcpPktPdbUlOkNonMcPtt {
      type uint32;
      config false;
    }
    leaf pmCgiMeasSuccAgQci1 {
      type uint32;
      config false;
    }
    leaf pmA3InterFBestCellEvalReportRsrp {
      type ietfinet:port-number;
      config false;
    }
    leaf pmCellHoPrepSuccLteIntraFHybridCsg {
      type uint32;
      config false;
    }
    leaf pmEndcSetupUeAttNrRestricted {
      type uint32;
      config false;
    }
    leaf-list pmMimoSleepTimeDistr {
      type uint32;
    }
    leaf-list pmRaRrcRspDistr {
      type uint32;
    }
    leaf pmMacUeThpTimeDl {
      type ietfyang:mac-address;
      config false;
      status deprecated;
      description "MOM flags: noNotification.";
    }
    leaf-list pmHoPrepRejInAdmMsrRpid {
      type uint32;
    }
    leaf-list pmPdcchTargetBlerDistr {
      type uint32;
    }
    leaf-list pmZtemporary226Compr {
      type uint32;
    }
    leaf-list pmErabRelAbnormalEnbCdtAutoPnrQci {
      type uint32;
    }
    leaf-list pmCaAssignedCsSetsDistr {
      type uint32;
    }
    leaf-list pmPrbUtilDlCellResource8Distr {
      type uint32;
      description "MOM flags: noNotification.";
    }
    leaf pmAnrHoSuccLevelMedium {
      type uint32;
      config false;
    }
    leaf pmMpdcchMaxPrbAvail {
      type uint32;
      config false;
      status deprecated;
      description "MOM flags: noNotification.";
    }
    leaf pmCaConfiguredNoMeasSucc {
      type uint32;
      config false;
    }
    leaf pmRrcConnQueueSuccMtaHp {
      type uint32;
      config false;
    }
    leaf pmHoPrepRejInCellIntensDLC {
      type uint32;
      config false;
    }
    leaf pmCovGoodZoneSamp {
      type uint32;
      config false;
    }
    leaf-list pmPdcchCceUsedDlQci {
      type uint32;
    }
    leaf pmRaAccHarqFailWithinContRes {
      type uint32;
      config false;
    }
    leaf pmCellHoPrepAttLteInterFHybridCsg {
      type uint32;
      config false;
    }
    leaf-list pmPrbUtilUlMaxEstDistr {
      type uint32;
    }
    leaf pmA1InterFHoHigherPrioConfig {
      type uint32;
      config false;
    }
    leaf pmFlexCellHoPrepSuccLteInterF {
      type uint32;
      config false;
    }
    leaf pmRrcConnQueueAllocAtt {
      type uint32;
      config false;
    }
    leaf pmPrbUsedUlPuschCenterRegionDtch {
      type uint32;
      config false;
    }
    leaf pmUlGrantsWithDetectedPusch {
      type uint32;
      config false;
    }
    leaf pmRrcConnRelRlcFail {
      type uint32;
      config false;
    }
    leaf pmRadioRecInterferencePwrPrb98 {
      type uint32;
      config false;
    }
    leaf-list pmRrcConnEstabFailMpMemCe {
      type uint32;
      description "MOM flags: noNotification.";
    }
    leaf pmRrcConnResumeFailDuSwC {
      type uint32;
      config false;
    }
    leaf pmRrcConnReconfSuccNoMobUpswitch {
      type uint32;
      config false;
    }
    leaf pmUeCtxtRelCsfbMeasTO1xRttEm {
      type uint32;
      config false;
    }
    leaf pmRadioRecInterferencePwrPrb62 {
      type uint32;
      config false;
    }
    leaf-list pmCaConfDlEranSumDistr {
      type uint32;
    }
    leaf pmRadioRecInterferencePwrPrb39 {
      type uint32;
      config false;
    }
    leaf pmHoPrepRejInLicMultiErab {
      type uint32;
      config false;
    }
    leaf pmFlexVoipQualityRbUlOk {
      type ietfinet:ip-address;
      config false;
    }
    leaf pmErabRelAbnormalEnbActCdtAutoPnr {
      type uint32;
      config false;
    }
    leaf-list pmActiveUeUlSumCe {
      type ietfyang:mac-address;
    }
    leaf pmRrcConnQueueSuccMoVoice {
      type uint32;
      config false;
    }
    leaf pmPdcpVolDlDrbLastTTICa {
      type uint32;
      config false;
    }
    leaf pmS1SigConnEstabSuccMod {
      type uint32;
      config false;
    }
    leaf-list pmUeCtxtFetchSuccErabActQci {
      type uint32;
    }
    leaf pmZtemporary202 {
      type uint32;
      config false;
    }
    leaf pmUeCtxtModAttCsfb {
      type uint32;
      config false;
    }
    leaf pmRachNumContentionReport {
      type ietfinet:port-number;
      config false;
    }
    leaf pmUeCtxtFetchAtt {
      type uint32;
      config false;
    }
    leaf pmPdcpRtpSnReorderDetected {
      type uint32;
      config false;
    }
    leaf-list pmIdcUlCaVictimOffDistr {
      type uint32;
    }
    leaf pmErabRelAbnormalEnbActCdtAuto {
      type uint32;
      config false;
    }
    leaf pmUeExclThpVolte {
      type uint32;
      config false;
    }
    leaf-list pmCellIntensRrcConnReqDistr {
      type uint32;
    }
    leaf pmErabRelAbnormalEnbExtIat {
      type uint32;
      config false;
    }
    leaf pmB1NrBestCellEvalReport {
      type ietfinet:port-number;
      config false;
      status deprecated;
      description "MOM flags: noNotification.";
    }
    leaf pmUeCtxtFetchAttNoNeighRel {
      type uint32;
      config false;
    }
    leaf pmErabRelAbnormalEnbActCdt {
      type uint32;
      config false;
    }
    leaf-list pmPdcpLatTimeDlCatMNoDrxNoSyncQci {
      type uint32;
    }
    leaf pmMiMimoSleepOpp {
      type uint32;
      config false;
    }
    leaf-list pmErabRelUlInactGapQci {
      type uint32;
    }
    leaf pmNonMcPttQualityRbUlLowSampl {
      type uint32;
      config false;
    }
    leaf pmSchedTtiCellUl {
      type uint32;
      config false;
    }
    leaf pmB1NrServTrigEvalReport {
      type ietfinet:port-number;
      config false;
    }
    leaf pmErabRelMmeCellUnavail {
      type uint32;
      config false;
    }
    leaf-list pmUlSinrPdcchDistr {
      type uint32;
    }
    leaf pmHoExeAttIntraCell {
      type uint32;
      config false;
    }
    leaf-list pmRrcConnEstabAttModCe {
      type uint32;
    }
    leaf pmFlexErabRelNormalEnb {
      type uint32;
      config false;
    }
    leaf pmZtemporary148 {
      type uint32;
      config false;
    }
    leaf pmPdcchResyncFail {
      type uint32;
      config false;
      status deprecated;
      description "MOM flags: noNotification.";
    }
    leaf pmUeCtxtRelAbnormalMmeCritCov {
      type uint32;
      config false;
    }
    leaf-list pmErabRelAbnormalEnbTnFailQci {
      type uint32;
    }
    leaf pmFlexCellHoPrepSuccNonMobIrat {
      type uint32;
      config false;
    }
    leaf-list pmPrbUsedDlDtchVirtualCellsDistr {
      type uint32;
    }
    leaf pmUeCtxtRelNormalEnbTuneOut {
      type uint32;
      config false;
    }
    leaf pmPucchSrCqiResCongSr {
      type uint32;
      config false;
    }
    leaf pmDrxSleepTimePft {
      type uint32;
      config false;
    }
    leaf pmZtemporary10 {
      type uint32;
      config false;
    }
    leaf pmUeCtxtRelSCEutraUlSinr {
      type uint32;
      config false;
    }
    leaf-list pmMacLatTimeDlQci {
      type ietfyang:mac-address;
      description "MOM flags: noNotification.";
    }
    leaf pmUeCtxtRelCsfbTdScdma {
      type uint32;
      config false;
    }
    leaf pmRadioThpVolDlScellEran {
      type uint32;
      config false;
    }
    leaf pmRadioRecInterferencePwrSf8 {
      type uint32;
      config false;
    }
    leaf pmFlexMacHarqUl3 {
      type ietfyang:mac-address;
      config false;
    }
    leaf pmUePeAttInterCell {
      type uint32;
      config false;
    }
    leaf pmRadioRecInterferencePwrSf3 {
      type uint32;
      config false;
    }
    leaf pmCellHoExeAttLteInterFEndcHo {
      type uint32;
      config false;
    }
    leaf-list pmCaActivatedDlSum {
      type uint32;
    }
    leaf pmZtemporary141 {
      type uint32;
      config false;
    }
    leaf-list pmPrbUtilDlCellResource22Distr {
      type uint32;
      description "MOM flags: noNotification.";
    }
    leaf pmRobustCallSetupDelayedUtGeran {
      type uint32;
      config false;
    }
    leaf-list pmPdcchDlDtxWorseDistr {
      type uint32;
    }
    leaf-list pmAccessClassBarringVoicePlmn1Distr {
      type ietfyang:mac-address;
    }
    leaf pmTtiBundlingFailTO {
      type uint32;
      config false;
    }
    leaf-list pmRlcDelayPktTransDlQci {
      type uint32;
    }
    leaf pmRadioUeRepCqi2Subband6Sum {
      type uint32;
      config false;
    }
    leaf pmFlexMcPttQualityRbUlOk {
      type uint32;
      config false;
    }
    leaf pmRadioRecInterferencePwrPrb27 {
      type uint32;
      config false;
    }
    leaf pmUeCapabilityUlDelay {
      type uint32;
      config false;
    }
    leaf pmFlexMacHarqDlAck64qam {
      type ietfyang:mac-address;
      config false;
    }
    leaf pmErabModQci5EmInactTimer {
      type uint32;
      config false;
    }
    leaf pmRrcConnResumeFallbackAtt {
      type uint32;
      config false;
    }
    leaf-list pmPdcchCceUtil {
      type uint32;
    }
    leaf pmUeMeasAttCsfb1xRttEm {
      type uint32;
      config false;
    }
    leaf-list pmAcBarringVideoSpecAcPlmn1Distr {
      type ietfyang:mac-address;
    }
    leaf-list pmAcBarringCsfbSpecialAcDistr {
      type ietfyang:mac-address;
    }
    leaf pmRrcConnEstabFailCellIntensStat {
      type uint32;
      config false;
    }
    leaf pmRrcConnEstabAttMod {
      type uint32;
      config false;
    }
    leaf-list pmErabQciMax {
      type uint32;
    }
    leaf pmErabRelAbnormalEnbPsFail {
      type uint32;
      config false;
    }
    leaf pmRrcConnReconfAttNoMobSkipUlDyn {
      type ietfinet:ip-address;
      config false;
    }
    leaf pmUlGrantsTransNoAck {
      type uint32;
      config false;
    }
    leaf pmPrbUsedDlSum {
      type uint32;
      config false;
    }
    leaf pmLbSubRatioSum {
      type uint32;
      config false;
    }
    leaf pmPtmCellReservedMsr {
      type uint32;
      config false;
    }
    leaf pmFlexPdcpPktDiscDlRbLimit {
      type uint32;
      config false;
    }
    leaf pmMacVolUlResUeLate {
      type ietfyang:mac-address;
      config false;
    }
    leaf pmFlexZtemporary25 {
      type uint32;
      config false;
    }
    leaf pmCaDeconfigured {
      type uint32;
      config false;
    }
    leaf pmPdcchMaxCceAvailUlSf {
      type uint32;
      config false;
    }
    leaf pmUeCtxtRelSCNrA2Rsrq {
      type uint32;
      config false;
    }
    leaf pmActiveUeDrbSamp {
      type ietfyang:mac-address;
      config false;
    }
    leaf pmZtemporary189 {
      type uint32;
      config false;
    }
    leaf pmZtemporary114 {
      type uint32;
      config false;
    }
    leaf pmUeCtxtRelMmeAct {
      type uint32;
      config false;
    }
    leaf-list pmErabRelMmeActQci {
      type uint32;
    }
    leaf pmZtemporary25 {
      type uint32;
      config false;
    }
    leaf-list pmErabEstabAttRejAdmMsrAddedPttArp {
      type uint32;
    }
    leaf pmZtemporary137 {
      type uint32;
      config false;
    }
    leaf pmPdcpVolUlDrbPlmn2 {
      type uint32;
      config false;
    }
    leaf pmHoPrepRejInCellIntensSwC {
      type uint32;
      config false;
    }
    leaf pmPdcchCceUsedUlSf {
      type uint32;
      config false;
    }
    leaf pmRrcConnReconfSuccNoMobEarfcnCa {
      type uint32;
      config false;
    }
    leaf pmObsLocalEventDiscPmLoad {
      type uint32;
      config false;
    }
    leaf pmCellDownUnlockMan {
      type uint32;
      config false;
    }
    leaf pmSchedNewTxUlRsvdRegion {
      type uint32;
      config false;
    }
    leaf pmUeThpTimeDlCa {
      type uint32;
      config false;
    }
    leaf pmDlAssigsTransNDO {
      type uint32;
      config false;
    }
    leaf pmRadioRecInterferencePwrPrb9 {
      type uint32;
      config false;
    }
    leaf-list pmActiveUeUlSectorCarrierDistr {
      type ietfyang:mac-address;
    }
    leaf pmS1SigConnEstabSuccMoVoice {
      type uint32;
      config false;
    }
    leaf pmDrxSleepTime {
      type uint32;
      config false;
    }
    leaf-list pmErabEstabAttInitQci {
      type uint32;
    }
    leaf pmAcBarringEmSpecAcPlmn3 {
      type ietfyang:mac-address;
      config false;
    }
    leaf-list pmRaMsg3DtxCbraTxDistr {
      type uint32;
    }
    leaf-list pmErabEstabAttAddedCsfbArp {
      type uint32;
    }
    leaf-list pmBitRateUpUlVoipTimeDistr {
      type ietfinet:ip-address;
    }
    leaf pmRrcConnReconfAttNoMobUpswitch {
      type uint32;
      config false;
    }
    leaf pmRrcConnReestFailDynUeAdmCtrlPaPtt {
      type uint32;
      config false;
    }
    leaf pmRadioThpVolDlSCell {
      type uint32;
      config false;
    }
    leaf pmWifiAccessEvalFailLic {
      type uint32;
      config false;
    }
    leaf pmDlAssigsDetectedHarqNDO {
      type uint32;
      config false;
    }
    leaf-list pmTaInit2Distr {
      type uint32;
    }
    leaf pmDlAssigsWithUnknownReceptionPCell {
      type uint32;
      config false;
    }
    leaf-list pmMacUeBitRateRecommUlNonMcPttDistr {
      type ietfyang:mac-address;
    }
    leaf pmCaConfiguredAiBasedAtt {
      type uint32;
      config false;
    }
    leaf pmZtemporary8 {
      type uint32;
      config false;
    }
    leaf pmMacHarqDlAck16qam {
      type ietfyang:mac-address;
      config false;
    }
    leaf pmErabRelAbnormalEnbActOosPft {
      type uint32;
      config false;
    }
    leaf pmErabEstabSuccAddedHpa {
      type uint32;
      config false;
    }
    leaf-list pmPuschHomMcsDistr {
      type uint32;
    }
    leaf pmPrbUsedDlCatmMax {
      type int32;
      config false;
    }
    leaf pmRadioUeRepCqiSubband7Sum {
      type uint32;
      config false;
    }
    leaf pmDsdReqPft {
      type uint32;
      config false;
    }
    leaf pmFlexEndcSetupScgUeAtt {
      type uint32;
      config false;
    }
    leaf-list pmErabEstabAttInitGbrArp {
      type uint32;
    }
    leaf pmUeCtxtRelAbnormalEnbSirBb {
      type uint32;
      config false;
    }
    leaf pmUlGrantsDetectedPuschNDO {
      type uint32;
      config false;
    }
    leaf pmCellHoExeSuccLteInterFUeMeasRsrp {
      type uint32;
      config false;
    }
    leaf pmFlexCellHoExeSuccUtranSrvcc {
      type uint32;
      config false;
    }
    leaf-list pmErabRelAbnormalEnbActQci {
      type uint32;
    }
    leaf pmMeasGapFailLicInterFOtdoa {
      type uint32;
      config false;
    }
    leaf pmB2BestCellEvalReportRsrp {
      type ietfinet:port-number;
      config false;
    }
    leaf pmNasTransferSuccDlSrb2 {
      type uint32;
      config false;
    }
    leaf-list pmCellDlSeUtilization {
      type uint32;
    }
    leaf pmFlexMacHarqUlSuccQpsk {
      type ietfyang:mac-address;
      config false;
    }
    leaf pmPrbUsedUlCatmMax {
      type int32;
      config false;
    }
    leaf pmRadioRecInterferencePwrPrb13 {
      type uint32;
      config false;
    }
    leaf pmZtemporary22 {
      type uint32;
      config false;
    }
    leaf pmFlexZtemporary18 {
      type uint32;
      config false;
    }
    leaf pmBadCovEvalReport {
      type ietfinet:port-number;
      config false;
    }
    leaf-list pmCaCapableUlSum {
      type uint32;
    }
    leaf pmRrcConnResumeFailCellIntensStat {
      type uint32;
      config false;
    }
    leaf pmRrcConnReestFailLicMtReest {
      type uint32;
      config false;
    }
    leaf pmFlexPdcpLatTimeDl {
      type uint32;
      config false;
    }
    leaf pmS1SigConnEstabAttEm {
      type uint32;
      config false;
    }
    leaf pmFlexZtemporary4 {
      type uint32;
      config false;
    }
    leaf pmAntennaSelectionCapable {
      type uint32;
      config false;
    }
    leaf pmCellHoExeSuccLteInterFHybridCsg {
      type uint32;
      config false;
    }
    leaf pmUeCtxtRelNormalEnb {
      type uint32;
      config false;
    }
    leaf pmDlAssigsWithDetectedHarqAck {
      type uint32;
      config false;
    }
    leaf pmPdcpPktDiscDlHo {
      type uint32;
      config false;
    }
    leaf pmErabEstabAttAddedHpa {
      type uint32;
      config false;
    }
    leaf pmFlexMacSkipUlDtxDynamic {
      type ietfinet:ip-address;
      config false;
    }
    leaf-list pmZtemporary133Compr {
      type uint32;
    }
    leaf pmRrcConnMaxEndc0 {
      type int32;
      config false;
    }
    leaf pmCellHoPrepSuccNrServTrig {
      type uint32;
      config false;
    }
    leaf-list pmErabQciLevSum {
      type uint32;
    }
    leaf pmRaFailCbraMsg1DiscSched {
      type uint32;
      config false;
    }
    leaf pmMacCellThpTimeUl {
      type ietfyang:mac-address;
      config false;
    }
    leaf pmZtemporary197 {
      type uint32;
      config false;
    }
    leaf pmFlexRadioThpVolumeUl {
      type uint32;
      config false;
    }
    leaf pmSchedActivityCellUlBr {
      type uint32;
      config false;
    }
    leaf-list pmPagReceivedCe {
      type uint32;
    }
    leaf pmRaUnassignedCfraSum {
      type uint32;
      config false;
    }
    leaf pmZtemporary93 {
      type uint32;
      config false;
    }
    leaf pmEndcSetupBufMonReport {
      type ietfinet:port-number;
      config false;
    }
    leaf-list pmRrcConnEstabAttCe {
      type uint32;
    }
    leaf pmSessionTimeDrb {
      type uint32;
      config false;
    }
    leaf pmFlexSchedActivityUeUl {
      type uint32;
      config false;
    }
    leaf pmS1SigConnEstabAttMta {
      type uint32;
      config false;
    }
    leaf pmCellCaLockTimeHighLoad {
      type uint32;
      config false;
    }
    leaf-list pmMultiUserMimoUlPrbUtil {
      type uint32;
    }
    leaf pmUeCtxtRelSCCdmaB2Rsrq {
      type uint32;
      config false;
    }
    leaf pmRrcConnEstabAttReattMta {
      type uint32;
      config false;
    }
    leaf pmZtemporary19 {
      type uint32;
      config false;
    }
    leaf pmMacHarqDlDtx64qam {
      type ietfyang:mac-address;
      config false;
    }
    leaf pmPucchSrMax {
      type int32;
      config false;
    }
    leaf pmCellSleepFailUeCap {
      type uint32;
      config false;
    }
    leaf pmFlexRadioThpVolumeDl {
      type uint32;
      config false;
    }
    leaf pmDlAssigsTransNonMcPtt {
      type uint32;
      config false;
    }
    leaf pmCgiMeasSuccDrx {
      type uint32;
      config false;
    }
    leaf pmRrcConnReconfSuccNoMob {
      type uint32;
      config false;
    }
    leaf pmRrcConnEstabSucc {
      type uint32;
      config false;
    }
    leaf pmFlexUeCtxtRelSCNr {
      type uint32;
      config false;
    }
    leaf pmCellHoExeSuccLteInterFEndcHo {
      type uint32;
      config false;
    }
    leaf pmRrcConnMaxEndc1 {
      type int32;
      config false;
    }
    leaf pmRadioRecInterferencePwrPrb96 {
      type uint32;
      config false;
    }
    leaf pmRadioRecInterferencePwrPrb17 {
      type uint32;
      config false;
    }
    leaf-list pmRaContResRejDistr {
      type uint32;
    }
    leaf pmRadioThpResDl {
      type uint32;
      config false;
    }
    leaf pmZtemporary71 {
      type uint32;
      config false;
    }
    leaf pmRrcConnMaxPlmn2 {
      type int32;
      config false;
    }
    leaf pmRrcConnMaxEndc2 {
      type int32;
      config false;
    }
    leaf pmRadioRecInterferencePwrPrb32 {
      type uint32;
      config false;
    }
    leaf pmMacHarqUlFailQpsk {
      type ietfyang:mac-address;
      config false;
    }
    leaf pmRadioUeRepCqiSubband1Sum {
      type uint32;
      config false;
    }
    leaf pmFlexCellHoExeSuccNonMobIrat {
      type uint32;
      config false;
    }
    leaf pmRadioRecInterferencePwrPrb23 {
      type uint32;
      config false;
    }
    leaf pmPtmStopIncomingIflb {
      type uint32;
      config false;
    }
    leaf pmRrcConnReestFailMpMem {
      type uint32;
      config false;
    }
    leaf-list pmZtemporary82 {
      type uint32;
    }
    leaf-list pmAcBarringModSpecAcPlmn3Distr {
      type ietfyang:mac-address;
    }
    leaf pmZtemporary227 {
      type int32;
      config false;
    }
    leaf pmCaConfiguredNoMeasAtt {
      type uint32;
      config false;
    }
    leaf pmErabRelAbnormalEnbCritCov {
      type uint32;
      config false;
    }
    leaf-list pmRrcConnEstabAttMtaCe {
      type uint32;
    }
    leaf pmRadioRecInterferencePwrPrb8 {
      type uint32;
      config false;
    }
    leaf pmRohcUlDataFailedMaxCid {
      type uint32;
      config false;
    }
    leaf pmRrcConnMaxPlmn5 {
      type int32;
      config false;
    }
    leaf pmFlexMacLatTimeDlNoDrxSync {
      type ietfyang:mac-address;
      config false;
      status deprecated;
      description "MOM flags: noNotification.";
    }
    leaf pmZtemporary145 {
      type uint32;
      config false;
    }
    leaf-list pmSessionTimeDrbQci {
      type uint32;
    }
    leaf pmFlexMacHarqUlFail64qam {
      type ietfyang:mac-address;
      config false;
    }
    leaf pmRrcConnEstabFailDynUeAdmCtrl {
      type uint32;
      config false;
    }
    leaf pmZtemporary149 {
      type uint32;
      config false;
    }
    leaf pmFlexMacTimeUlResUe {
      type ietfyang:mac-address;
      config false;
    }
    leaf pmCellHoPrepAttLteInterFDtvm {
      type uint32;
      config false;
    }
    leaf pmRadioRecInterferencePwrPrb84 {
      type uint32;
      config false;
    }
    leaf pmRaRejHarqFailWithinContRes {
      type uint32;
      config false;
    }
    leaf pmCriticalBorderEvalReport {
      type ietfinet:port-number;
      config false;
    }
    leaf pmZtemporary147 {
      type uint32;
      config false;
    }
    leaf pmPdcpVolUlDrbPlmn5 {
      type uint32;
      config false;
    }
    leaf pmEndcSetupScgUeAttBufDl {
      type uint32;
      config false;
    }
    leaf pmHoPrepOutS1RejInvalidIntraFHybridCsg {
      type uint32;
      config false;
    }
    leaf pmFlexErabRelNormalEnbAct {
      type uint32;
      config false;
      status deprecated;
      description "MOM flags: noNotification.";
    }
    leaf pmRadioRecInterferencePwrPrb18 {
      type uint32;
      config false;
    }
    leaf pmZtemporary117 {
      type uint32;
      config false;
    }
    leaf pmRrcConnTuneOutLevSamp {
      type uint32;
      config false;
    }
    leaf pmFlexErabEstabAttInitGbr {
      type uint32;
      config false;
    }
    leaf pmUeCtxtRelSCUtranB2Rsrp {
      type uint32;
      config false;
    }
    leaf pmMacHarqDlAckQpsk {
      type ietfyang:mac-address;
      config false;
    }
    leaf pmUeExclThpUlShortTimeLowVol {
      type uint32;
      config false;
    }
    leaf pmRadioRecInterferencePwrPrb20 {
      type uint32;
      config false;
    }
    leaf-list pmUeThp2UlDistr {
      type uint32;
    }
    leaf pmPrbUsedUlSum {
      type uint32;
      config false;
    }
    leaf pmErabMax {
      type int32;
      config false;
    }
    leaf pmPrbUsedDlCatmSum {
      type uint32;
      config false;
      status deprecated;
      description "MOM flags: noNotification.";
    }
    leaf pmZtemporary228 {
      type uint32;
      config false;
    }
    leaf pmFlexCellHoPrepSuccLteIntraF {
      type uint32;
      config false;
    }
    leaf pmZtemporary198 {
      type uint32;
      config false;
    }
    leaf pmRadioRecInterferencePwrPrb52 {
      type uint32;
      config false;
    }
    leaf-list pmZtemporary158Compr {
      type uint32;
    }
    leaf pmUeCtxtRelAbnormalEnbUeLost {
      type uint32;
      config false;
    }
    leaf pmErabResumeArpLow {
      type uint32;
      config false;
    }
    leaf-list pmS1SigConnEstabSuccDtaCe {
      type uint32;
    }
    leaf pmZtemporary13 {
      type uint32;
      config false;
    }
    leaf pmMeasConfigB1Endc {
      type uint32;
      config false;
    }
    leaf-list pmPrbUtilDlCellResource6Distr {
      type uint32;
      description "MOM flags: noNotification.";
    }
    leaf pmUeCtxtRelSCEUtraA2Rsrp {
      type uint32;
      config false;
    }
    leaf-list pmMacHarqNonCaDlAnModeMuxDistr {
      type ietfyang:mac-address;
    }
    leaf-list pmPdcpVolUlCmpHdrQci {
      type uint32;
    }
    leaf-list pmRrcConnReestFailDynUeAdmCtrlPttCe {
      type uint32;
    }
    leaf pmPdcchCceActivity {
      type uint32;
      config false;
    }
    leaf-list pmPrbUtilDlCellResource1Distr {
      type uint32;
      description "MOM flags: noNotification.";
    }
    leaf pmPrbUsedUlPuschLowRegionDtch {
      type uint32;
      config false;
    }
    leaf pmRrcConnLevSamp {
      type uint32;
      config false;
    }
    leaf pmDrxTotalTimePft {
      type uint32;
      config false;
    }
    leaf pmFlexZtemporary3 {
      type uint32;
      config false;
    }
    leaf pmPdcpVolDlDrb {
      type uint32;
      config false;
    }
    leaf pmUeCtxtFetchSuccS1HoPrepSrvccGeran {
      type uint32;
      config false;
    }
    leaf pmIdleModeRelDistrLowLoad {
      type uint32;
      config false;
    }
    leaf pmZtemporary172 {
      type uint32;
      config false;
    }
    leaf pmFlexMacSkipUlDtxTxSps {
      type ietfinet:ip-address;
      config false;
    }
    leaf-list pmRlcDelayTimeDl2Qci {
      type uint32;
    }
    leaf-list pmErabEstabAttAddedGbrArp {
      type uint32;
    }
    leaf pmFlexMacHarqDlAckQpsk {
      type ietfyang:mac-address;
      config false;
    }
    leaf pmFlexCellHoPrepAttNonMobIrat {
      type uint32;
      config false;
    }
    leaf-list pmCaScheduledDlIcmSum {
      type uint32;
      description "MOM flags: noNotification.";
    }
    leaf-list pmPdcpLatPktTransDlQci {
      type uint32;
    }
    leaf-list pmErabRelAbnormalEnbGbrArp {
      type uint32;
    }
    leaf pmFlexMacHarqUlFail16qam {
      type ietfyang:mac-address;
      config false;
    }
    leaf pmRadioUeRepCqiSubband10Sum {
      type uint32;
      config false;
    }
    leaf-list pmPdcpPktLostUlRohcFail2Qci {
      type uint32;
    }
    leaf-list pmRrcConnEstabAttDtaCe {
      type uint32;
    }
    leaf pmFlexErabEstabFailResGbr {
      type uint32;
      config false;
    }
    leaf pmRrcConnEstabSuccMos {
      type uint32;
      config false;
    }
    leaf pmB2BestCellEvalReportUl {
      type ietfinet:port-number;
      config false;
    }
    leaf-list pmPdcpLatTimeDlCatMDrxNoSyncQci {
      type uint32;
    }
    leaf pmPdcpPktLostUlLimitations {
      type uint32;
      config false;
    }
    leaf pmZtemporary63 {
      type uint32;
      config false;
    }
    leaf pmRobustCallSetupTimerQci1 {
      type uint32;
      config false;
    }
    leaf-list pmCaScheduledDl4ccSumDistr {
      type uint32;
    }
    leaf-list pmPdcpPktDiscDlPelrUuQci {
      type uint32;
    }
    leaf pmUeCtxtFetchSuccReconf {
      type uint32;
      config false;
    }
    leaf pmUeCtxtFetchAttIntraEnbHoIn {
      type uint32;
      config false;
    }
    leaf pmPrbUsedDlAilgTot {
      type uint32;
      config false;
    }
    leaf pmRadioThpResUl {
      type uint32;
      config false;
    }
    leaf pmZtemporary245 {
      type uint32;
      config false;
    }
    leaf pmRadioThpVolTxDl4ccSCell {
      type uint32;
      config false;
    }
    leaf pmNonMcPttQualityRbUlOk {
      type uint32;
      config false;
    }
    leaf-list pmPdcchCceUsedUlQci {
      type uint32;
    }
    leaf pmRrcConnQueueTo {
      type uint32;
      config false;
    }
    leaf pmPrbUsedDlCatmSamp {
      type uint32;
      config false;
    }
    leaf pmPrbUsedDlSamp {
      type uint32;
      config false;
    }
    leaf pmPrioFreqBandConfigured {
      type uint32;
      config false;
    }
    leaf-list pmPrbUtilUlDistr {
      type uint32;
    }
    leaf pmUeCtxtEstabSucc {
      type uint32;
      config false;
    }
    leaf pmUlGrantsTransNonMcPtt {
      type uint32;
      config false;
    }
    leaf-list pmPdcpPktReceivedDlQci {
      type uint32;
    }
    leaf-list pmMacUeThpUlMbbHighVolQciDistr {
      type ietfyang:mac-address;
    }
    leaf pmZtemporary30 {
      type uint32;
      config false;
    }
    leaf pmRrcConnMaxPlmn6 {
      type int32;
      config false;
    }
    leaf pmCellHoExeSuccLteIntraFAfterResync {
      type uint32;
      config false;
    }
    leaf pmErabBrSamp {
      type uint32;
      config false;
    }
    leaf pmAnrNeighbrelAdd {
      type uint32;
      config false;
    }
    leaf pmWifiAccessAllowed {
      type uint32;
      config false;
    }
    leaf pmUeCtxtRelCsfbUlHoPrepTxTO1xRttEm {
      type uint32;
      config false;
    }
    leaf-list pmCaScheduledDl5ccSumDistr {
      type uint32;
    }
    leaf pmFlexZtemporary5 {
      type uint32;
      config false;
    }
    leaf pmMeasRepBadCovElc {
      type uint32;
      config false;
    }
    leaf pmMacPdcchBlockingPuschTti {
      type ietfyang:mac-address;
      config false;
    }
    leaf-list pmMacUeThpDlDistr {
      type ietfyang:mac-address;
      description "MOM flags: noNotification.";
    }
    leaf pmConfirmedUeRelReqPft {
      type uint32;
      config false;
    }
    leaf pmRadioRecInterferencePwrPrb82 {
      type uint32;
      config false;
    }
    leaf-list pmBwAssignedDistr {
      type uint32;
    }
    leaf pmFlexMacHarqUl1 {
      type ietfyang:mac-address;
      config false;
    }
    leaf-list pmErabEstabSuccInitGbrArp {
      type uint32;
    }
    leaf-list pmErabRelAbnormalEnbActCdtQci {
      type uint32;
    }
    leaf pmRaFailCfraMsg1DiscOoc {
      type uint32;
      config false;
    }
    leaf-list pmPrbUtilUlNonRetransDistr {
      type uint32;
    }
    leaf-list pmPdcpPktDiscDlAqmQci {
      type uint32;
    }
    leaf pmSchedActivityCellDlBr {
      type uint32;
      config false;
    }
    leaf-list pmBadCovMeasTimeActDistr {
      type uint32;
    }
    leaf pmMacHarqUlSucc16qam {
      type ietfyang:mac-address;
      config false;
    }
    leaf pmCellHoExeSuccLteInterFUlTraffic {
      type uint32;
      config false;
    }
    leaf pmS1SigConnEstabSuccDta {
      type uint32;
      config false;
      status deprecated;
      description "MOM flags: noNotification.";
    }
    leaf pmFlexMacHarqDl3 {
      type ietfyang:mac-address;
      config false;
    }
    leaf pmFlexMacHarqDlNackQpsk {
      type ietfyang:mac-address;
      config false;
    }
    leaf pmUeCtxtFetchSuccReconfErabEstab {
      type uint32;
      config false;
    }
    leaf-list pmMacUeBitRateSelectDlDistr {
      type ietfyang:mac-address;
    }
    leaf pmFlexMacLatTimeDlDrxSync {
      type ietfyang:mac-address;
      config false;
      status deprecated;
      description "MOM flags: noNotification.";
    }
    leaf pmZtemporary11 {
      type uint32;
      config false;
    }
    leaf pmErabRelMmeActEutra {
      type uint32;
      config false;
    }
    leaf pmRetransPostponedNs05FullBandSch {
      type uint32;
      config false;
    }
    leaf-list pmHoPrepRejInAdmMsrArp {
      type uint32;
    }
    leaf pmIdleModeRelDistrMediumLoad {
      type uint32;
      config false;
    }
    leaf pmFlexZtemporary21 {
      type uint32;
      config false;
    }
    leaf pmRlcPollRetxDl {
      type uint32;
      config false;
    }
    leaf pmRadioRecInterferencePwrPrb63 {
      type uint32;
      config false;
    }
    leaf pmUeCtxtRelCsfbCdma1xRttEm {
      type uint32;
      config false;
    }
    leaf pmZtemporary234 {
      type uint32;
      config false;
    }
    leaf pmFlexEndcSetupScgUeSucc {
      type uint32;
      config false;
    }
    leaf pmUeCtxtFetchSuccReconfRrcConnReest {
      type uint32;
      config false;
    }
    leaf pmHoPrepRejInDynUeAdmCtrlPa {
      type uint32;
      config false;
    }
    leaf-list pmErabEstabFailAddedErabIdInUseArp {
      type uint32;
    }
    leaf-list pmZtemporary83 {
      type uint32;
    }
    leaf-list pmErabReestAttRejAdmMsrPttArp {
      type uint32;
    }
    leaf-list pmMacHarqNonCaDlAnModePf3Distr {
      type ietfyang:mac-address;
    }
    leaf pmZtemporary32 {
      type uint32;
      config false;
    }
    leaf pmFlexMacTimeDlDrxSyncSamp {
      type ietfyang:mac-address;
      config false;
      status deprecated;
      description "MOM flags: noNotification.";
    }
    leaf pmCovCriticalZoneSum {
      type uint32;
      config false;
    }
    leaf pmUlGrantsTransPCell {
      type uint32;
      config false;
    }
    leaf pmUeCtxtFetchAttReconfErabEstab {
      type uint32;
      config false;
    }
    leaf pmRaRejHarqFailAfterContRes {
      type uint32;
      config false;
    }
    leaf pmErabRelMmeAct {
      type uint32;
      config false;
    }
    leaf pmMacHarqUlSuccQpsk {
      type ietfyang:mac-address;
      config false;
    }
    leaf-list pmErabRelNormalEnbGbrArp {
      type uint32;
    }
    leaf pmRadioUeRepCqiSubband0Sum {
      type uint32;
      config false;
    }
    leaf pmRadioRecInterferencePwrPrb7 {
      type uint32;
      config false;
    }
    leaf pmEndcCapableUeInitSetup {
      type uint32;
      config false;
      status deprecated;
      description "MOM flags: noNotification.";
    }
    leaf pmErabRelAbnormalEnb {
      type uint32;
      config false;
    }
    leaf pmFlexUeCtxtRelAbnormalEnbPe {
      type uint32;
      config false;
    }
    leaf pmRrcConnEstabSuccMta {
      type uint32;
      config false;
    }
    leaf-list pmPrbUtilDlCellResource12Distr {
      type uint32;
      description "MOM flags: noNotification.";
    }
    leaf pmHoPrepRejOutUlThresCaRedirect {
      type uint32;
      config false;
    }
    leaf pmRaAttCbra {
      type uint32;
      config false;
    }
    leaf pmUeCtxtRelAbnormalEnbActUeLostOosPft {
      type uint32;
      config false;
    }
    leaf pmInSyncTimePft {
      type uint32;
      config false;
    }
    leaf pmHoPrepRejInUlThresCaRedirect {
      type uint32;
      config false;
      status deprecated;
      description "MOM flags: noNotification.";
    }
    leaf pmUeCtxtRelSCGsmA2Rsrp {
      type uint32;
      config false;
    }
    leaf pmHoPrepRejInDynUeAdmCtrlPtt {
      type uint32;
      config false;
    }
    leaf pmFlexErabRelAbnormalEnbPeGbr {
      type uint32;
      config false;
    }
    leaf pmUeCtxtFetchSuccX2HoExe {
      type uint32;
      config false;
    }
    leaf-list pmUeThp2DlDistr {
      type uint32;
    }
    leaf pmCriticalBorderEvalReportAct {
      type ietfinet:port-number;
      config false;
    }
    leaf pmFlexUeCtxtRelNormalEnb {
      type uint32;
      config false;
    }
    leaf pmHoPrepRejInPtm {
      type uint32;
      config false;
    }
    leaf pmFlexMacHarqUl4 {
      type ietfyang:mac-address;
      config false;
    }
    leaf pmRadioRecInterferencePwrPrb79 {
      type uint32;
      config false;
    }
    leaf pmVoipQualityUeUlLowSampl {
      type ietfinet:ip-address;
      config false;
    }
    leaf pmDlAssigsTrans {
      type uint32;
      config false;
    }
    leaf-list pmPuschMcsSubsGroup7Distr {
      type uint32;
    }
    leaf pmRrcConnQueueAllocSucc {
      type uint32;
      config false;
    }
    leaf pmFlexPrbUsedUlDtch {
      type uint32;
      config false;
    }
    leaf pmZtemporary143 {
      type uint32;
      config false;
    }
    leaf pmVoipQualityRbUlLowSampl {
      type ietfinet:ip-address;
      config false;
    }
    leaf-list pmMiMimoModelAccuracyDistr {
      type uint32;
    }
    leaf pmErabEstabSuccAdded {
      type uint32;
      config false;
    }
    leaf pmFlexMacHarqDl1 {
      type ietfyang:mac-address;
      config false;
    }
    leaf pmRrcConnEstabAttReattMoVoice {
      type uint32;
      config false;
    }
    leaf pmEndcRelMnMcgRelocSucc {
      type uint32;
      config false;
    }
    leaf pmRrcConnEstabSuccMod {
      type uint32;
      config false;
    }
    leaf pmRrcConnReconfAttNoMobSkipUlIua {
      type ietfinet:ip-address;
      config false;
    }
    leaf pmFlexErabModFailOngoingProc {
      type uint32;
      config false;
    }
    leaf pmRrcConnResumeFailLowCovUeLic {
      type uint32;
      config false;
      status deprecated;
      description "MOM flags: noNotification.";
    }
    leaf-list pmRadioUeRepTm4Rank2PmiDistr {
      type uint32;
    }
    leaf pmBadCovMiMultiFreqTo {
      type uint32;
      config false;
    }
    leaf pmRrcConnEstabAttEm {
      type uint32;
      config false;
    }
    leaf pmUlGrantsTransNDO {
      type uint32;
      config false;
    }
    leaf pmMacHarqDlDtx16qam {
      type ietfyang:mac-address;
      config false;
    }
    leaf pmZtemporary238 {
      type uint32;
      config false;
    }
    leaf pmPdschBlankedSubframeLess {
      type uint32;
      config false;
    }
    leaf pmZtemporary204 {
      type uint32;
      config false;
    }
    leaf-list pmS1SigConnEstabAttModCe {
      type uint32;
    }
    leaf-list pmAdjustAccessDynLoadCtrlDistr {
      type uint32;
    }
    leaf pmFlexMacTimeDlNoDrxSyncSamp {
      type ietfyang:mac-address;
      config false;
      status deprecated;
      description "MOM flags: noNotification.";
    }
    leaf pmUeCtxtRelAbnormalEnbTuneOut {
      type uint32;
      config false;
    }
    leaf pmRadioRecInterferencePwrPrb71 {
      type uint32;
      config false;
    }
    leaf pmUeExclThpUlRelativeLowVol {
      type uint32;
      config false;
    }
    leaf pmRobustCallSetupDelayedNr {
      type uint32;
      config false;
    }
    leaf pmOocStateEntries {
      type uint32;
      config false;
    }
    leaf pmCovGoodZoneSum {
      type uint32;
      config false;
    }
    leaf pmSchedAdpReTxUlRsvdRegion {
      type uint32;
      config false;
    }
    leaf-list pmEranUlCompDeltaSinrPuschDistr {
      type uint32;
    }
    leaf pmRrcConnReconfAttNoMobDacc {
      type uint32;
      config false;
    }
    leaf pmZtemporary144 {
      type uint32;
      config false;
    }
    leaf pmCgiMeasSuccAg {
      type uint32;
      config false;
    }
    leaf-list pmUeCategoryDlUlCombDistr {
      type uint32;
    }
    leaf pmErabRelAbnormalEnbOosPft {
      type uint32;
      config false;
    }
    leaf pmMacCellThpTimeDl {
      type ietfyang:mac-address;
      config false;
      status deprecated;
      description "MOM flags: noNotification.";
    }
    leaf pmRrcConnCe1CellLevMax {
      type int32;
      config false;
    }
    leaf-list pmPrbUtilDlCellResource17Distr {
      type uint32;
      description "MOM flags: noNotification.";
    }
    leaf pmDlAssigsTransVolteNDO {
      type uint32;
      config false;
    }
    leaf pmFlexPdcpPktReceivedDl {
      type uint32;
      config false;
    }
    leaf pmFlexMacHarqUl7 {
      type ietfyang:mac-address;
      config false;
    }
    leaf pmRrcConnEstabFailDuSwC {
      type uint32;
      config false;
    }
    leaf pmUeCtxtRelAbnormalEnbUeLostOosPft {
      type uint32;
      config false;
    }
    leaf pmFlexPdcpVolDlDrbTrans {
      type uint32;
      config false;
    }
    leaf pmEranCompUlNack {
      type uint32;
      config false;
    }
    leaf-list pmRrcConnEstabFailMtaDynUeAdmCtrlPagPrioDistr {
      type uint32;
    }
    leaf pmPdcpPktPdbUlOkMcPtt {
      type uint32;
      config false;
    }
    leaf-list pmCaCapableDlSum {
      type uint32;
    }
    leaf pmUeCtxtRelNaccSCWcdma {
      type uint32;
      config false;
    }
    leaf pmFlexMacHarqUlFail {
      type ietfyang:mac-address;
      config false;
    }
    leaf pmMacDelayTimeDl {
      type ietfyang:mac-address;
      config false;
    }
    leaf-list pmPtmIfoMeasuredUeDistr {
      type uint32;
    }
    leaf-list pmRrcConnEstabFailDynUeAdmCtrlPttCe {
      type uint32;
    }
    leaf pmErabEstabAttAddedPa {
      type uint32;
      config false;
    }
    leaf pmEndcRelScgUeOverheating {
      type uint32;
      config false;
    }
    leaf pmMeasConfigB1EndcDistribution {
      type uint32;
      config false;
    }
    leaf pmErabBrMax {
      type int32;
      config false;
    }
    leaf pmRadioRecInterferencePwrPrb74 {
      type uint32;
      config false;
    }
    leaf pmHoPrepRejInBb {
      type uint32;
      config false;
    }
    leaf pmRadioRecInterferencePwrPrb3 {
      type uint32;
      config false;
    }
    leaf pmRrcConnResumeFailMpOverload {
      type uint32;
      config false;
    }
    leaf-list pmPuschMcsSubsGroup1Distr {
      type uint32;
    }
    leaf pmCellDowntimeAuto {
      type uint32;
      config false;
    }
    leaf pmFlexZtemporary12 {
      type uint32;
      config false;
    }
    leaf-list pmErabEstabSuccInitQci {
      type uint32;
    }
    leaf pmDlAssigsTransSCell {
      type uint32;
      config false;
    }
    leaf-list pmAcBarringModSpecialAcDistr {
      type ietfyang:mac-address;
    }
    leaf pmUeCtxtRetrReestAtt {
      type uint32;
      config false;
    }
    leaf-list pmPdcpVolDlCmpHdrQci {
      type uint32;
    }
    leaf pmB1MeasRepEndcConfig {
      type uint32;
      config false;
    }
    leaf-list pmAcBarringMosSpecAcPlmn3Distr {
      type ietfyang:mac-address;
    }
    leaf pmActiveUeDlCe1Max {
      type ietfyang:mac-address;
      config false;
    }
    leaf pmRadioRecInterferencePwrPrb81 {
      type uint32;
      config false;
    }
    leaf-list pmErabRelNormalEnbArp {
      type uint32;
    }
    leaf-list pmPdcpLatPktTransDlCatMDrxSyncQci {
      type uint32;
    }
    leaf pmRrcConnQueueAttMtaVoice {
      type uint32;
      config false;
    }
    leaf-list pmZtemporary191 {
      type uint32;
    }
    leaf pmRrcConnResumeFailDuIntens {
      type uint32;
      config false;
    }
    leaf pmRrcConnLevSumUlOutOfSync {
      type uint32;
      config false;
    }
    leaf-list pmErabRelAbnormalEnbPeRpid {
      type uint32;
    }
    leaf pmAnrNeighbrelRem {
      type uint32;
      config false;
    }
    leaf pmZtemporary115 {
      type uint32;
      config false;
    }
    leaf pmCellHoExeAttLteIntraF {
      type uint32;
      config false;
    }
    leaf pmErabEstabSuccInitPa {
      type uint32;
      config false;
    }
    leaf pmFlexPdcpVolUlDrb {
      type uint32;
      config false;
    }
    leaf-list pmRrcLatencySecModeCmdDistr {
      type uint32;
    }
    leaf pmPwsCmasRepSucc {
      type uint32;
      config false;
    }
    leaf pmErabLevSamp {
      type uint32;
      config false;
    }
    leaf-list pmUlSinrDistr {
      type uint32;
    }
    leaf-list pmMacUeBitRateSelectUlNonMcPttDistr {
      type ietfyang:mac-address;
    }
    leaf pmPdcpPktTransDl {
      type uint32;
      config false;
    }
    leaf pmCellHoExeSuccLteIntraFHybridCsg {
      type uint32;
      config false;
    }
    leaf-list pmRrcConnReestFailDynUeAdmCtrlCe {
      type uint32;
    }
    leaf pmRohcUlDataDeconfigSucc {
      type uint32;
      config false;
    }
    leaf-list pmErabReestAttRejAdmMsrArp {
      type uint32;
    }
    leaf pmRadioRecInterferencePwrPrb44 {
      type uint32;
      config false;
    }
    leaf pmRadioThpVolUlSCell {
      type uint32;
      config false;
    }
    leaf pmUeCtxtRelAbnormalMmeActCritCov {
      type uint32;
      config false;
    }
    leaf-list pmAcBarringVideoSpecAcPlmn3Distr {
      type ietfyang:mac-address;
    }
    leaf pmErabModFailOngoingProc {
      type uint32;
      config false;
    }
    leaf pmErabRelAbnormalEnbHpr {
      type uint32;
      config false;
    }
    leaf pmCellHoPrepAttLowCovUe {
      type uint32;
      config false;
    }
    leaf pmCellHoPrepAttLteInterFUl {
      type uint32;
      config false;
    }
    leaf pmB1BestCellEvalReportRsrp {
      type ietfinet:port-number;
      config false;
    }
    leaf-list pmPdcpLatPktTransDlDrxSyncQci {
      type uint32;
    }
    leaf pmAnrHoSuccLevelLow {
      type uint32;
      config false;
    }
    leaf pmVoipQualityRbUlNok {
      type ietfinet:ip-address;
      config false;
    }
    leaf pmDynUeAdmCtrlQueueSucc {
      type uint32;
      config false;
      status deprecated;
      description "MOM flags: noNotification.";
    }
    leaf pmErabEstabQci5EmInactTimer {
      type uint32;
      config false;
    }
    leaf pmHoPrepRejInOffloadAdmission {
      type uint32;
      config false;
    }
    leaf-list pmMacLatTimeDlNoDrxNoSyncQci {
      type ietfyang:mac-address;
      description "MOM flags: noNotification.";
    }
    leaf pmCellHoExeAttLteIntraFTuneOut {
      type uint32;
      config false;
    }
    leaf pmUeCtxtFetchAttReconfErabMod {
      type uint32;
      config false;
    }
    leaf-list pmRadioUeRepRankAggrDistr {
      type uint32;
      description "MOM flags: noNotification.";
    }
    leaf pmUeCtxtFetchAttX2HoIn {
      type uint32;
      config false;
    }
    leaf-list pmPdcpPktDiscDlRbLimitQci {
      type uint32;
    }
    leaf pmLbtDrsSucc {
      type uint32;
      config false;
    }
    leaf pmActiveUeDownlinkMax {
      type ietfyang:mac-address;
      config false;
    }
    leaf-list pmPrbUtilDlCellResource15Distr {
      type uint32;
      description "MOM flags: noNotification.";
    }
    leaf pmMacHarqUlDtx16qam {
      type ietfyang:mac-address;
      config false;
    }
    leaf pmPrbUsedDlDtchSCellExt {
      type uint32;
      config false;
    }
    leaf-list pmPrbUtilDlNonRetransDistr {
      type uint32;
    }
    leaf pmUeCtxtRelCsfbMeasTO1xRtt {
      type uint32;
      config false;
    }
    leaf pmIdcUlCaCapableMax {
      type int32;
      config false;
    }
    leaf-list pmDeltaSinrDlComp {
      type uint32;
    }
    leaf-list pmZtemporary224Compr {
      type uint32;
    }
    leaf pmCellHoExeSuccLteInterFUl {
      type uint32;
      config false;
    }
    leaf pmUeCtxtFetchSuccIntraEnbHoIn {
      type uint32;
      config false;
    }
    leaf pmUeCtxtRelSCNrB1ServTrigRsrq {
      type uint32;
      config false;
    }
    leaf pmRadioThpVolDlSCellIcm {
      type uint32;
      config false;
    }
    leaf pmRadioRecInterferencePwrPrb34 {
      type uint32;
      config false;
    }
    leaf-list pmRrcConnEstabAttReattModCe {
      type uint32;
    }
    leaf pmPucchSrResMediumUtilCell {
      type int32;
      config false;
    }
    leaf pmElcOffBadCov {
      type uint32;
      config false;
    }
    leaf pmZtemporary140 {
      type uint32;
      config false;
    }
    leaf-list pmPdcpInactSecUlVolteDistr {
      type uint32;
    }
    leaf pmUeCtxtRelSCGsmB2Rsrp {
      type uint32;
      config false;
    }
    leaf pmRadioUeRepCqiSubband5Sum {
      type uint32;
      config false;
    }
    leaf pmRrcConnEstabFailDynUeAdmCtrlMoVoice {
      type uint32;
      config false;
    }
    leaf pmEndcPrioServFreq {
      type uint32;
      config false;
    }
    leaf pmFlexErabEstabSuccInit {
      type uint32;
      config false;
    }
    leaf-list pmRrcConnEstabFailDynUeAdmCtrlCe {
      type uint32;
    }
    leaf pmFlexZtemporary8 {
      type uint32;
      config false;
    }
    leaf pmPdcchMaxCceAvail {
      type uint32;
      config false;
    }
    leaf pmDlAssigsWithUnknownRecNonMcPtt {
      type uint32;
      config false;
    }
    leaf pmRrcConnCe3CellLevMax {
      type int32;
      config false;
    }
    leaf pmUeCtxtFetchAttX2HoPrep {
      type uint32;
      config false;
    }
    leaf-list pmS1SigConnEstabFailMmeOvlMosCe {
      type uint32;
    }
    leaf pmFlexRlcDelayTimeDl {
      type uint32;
      config false;
      status deprecated;
      description "MOM flags: noNotification.";
    }
    leaf pmLbtDrsAtt {
      type uint32;
      config false;
    }
    leaf-list pmServiceTimeDrbQci {
      type uint32;
    }
    leaf-list pmMacUeBitRateSelectDlMcPttDistr {
      type ietfyang:mac-address;
    }
    leaf pmRadioUeRepCqiSubband6Sum {
      type uint32;
      config false;
    }
    leaf pmDlAssigsWithUnknownReceptionVolte {
      type uint32;
      config false;
    }
    leaf pmCellHoPrepSuccLteIntraFCsg {
      type uint32;
      config false;
    }
    leaf pmRadioThpVolDl {
      type uint32;
      config false;
    }
    leaf pmZtemporary195 {
      type uint32;
      config false;
    }
    leaf-list pmAccessClassBarringModPlmn2Distr {
      type ietfyang:mac-address;
    }
    leaf pmRadioUeRepCqiSubband3Sum {
      type uint32;
      config false;
    }
    leaf-list pmCaAssignedPf3ResDistr {
      type uint32;
    }
    leaf-list pmPuschMcsSubsGroup3Distr {
      type uint32;
    }
    leaf-list pmDrxReqPftDistr {
      type uint32;
    }
    leaf pmZtemporary120 {
      type uint32;
      config false;
    }
    leaf pmFlexRlcArqUlAck {
      type uint32;
      config false;
    }
    leaf pmB2BestCellEvalReport {
      type ietfinet:port-number;
      config false;
    }
    leaf pmCellHoPrepSuccLteInterFCsg {
      type uint32;
      config false;
    }
    leaf-list pmTm9CapableDistr {
      type uint32;
    }
    leaf pmUeCtxtRelAbnormalEnbOosPft {
      type uint32;
      config false;
    }
    leaf pmErabRelAbnormalEnbCdtAutoPnr {
      type uint32;
      config false;
    }
    leaf pmZtemporary173 {
      type uint32;
      config false;
    }
    leaf pmRrcConnSamp {
      type uint32;
      config false;
    }
    leaf pmNasTransferFailPnrDlSrb2 {
      type uint32;
      config false;
    }
    leaf pmPdcpVolDlDrbTransPlmn2 {
      type uint32;
      config false;
    }
    leaf pmA5InterFHigherPrioEvalReport {
      type ietfinet:port-number;
      config false;
    }
    leaf pmFlexErabRelAbnormalMmeActGbr {
      type uint32;
      config false;
    }
    leaf pmUeCtxtFetchSuccUeCapEnq {
      type uint32;
      config false;
    }
    leaf-list pmRlcDelayTimeDlQci {
      type uint32;
      description "MOM flags: noNotification.";
    }
    leaf pmRadioRecInterferencePwrPrb64 {
      type uint32;
      config false;
    }
    leaf-list pmMacUeBitRateSelectUlVoipDistr {
      type ietfinet:ip-address;
    }
    leaf pmDlAssigsWithDetHarqAckNonMcPtt {
      type uint32;
      config false;
    }
    leaf pmCgiMeasSuccAnrPciConflict {
      type uint32;
      config false;
    }
    leaf pmUeCtxtRelMmeHo {
      type uint32;
      config false;
    }
    leaf pmRadioUeRepCqi2Subband5Sum {
      type uint32;
      config false;
    }
    leaf pmRlcDelayPktTransDl {
      type uint32;
      config false;
    }
    leaf pmActiveUeDlCe2Max {
      type ietfyang:mac-address;
      config false;
    }
    leaf-list pmMeasGapDurationDistr {
      type uint32;
    }
    leaf-list pmZtemporary190 {
      type uint32;
    }
    leaf pmRrcConnEstabFailMmeOvlMod {
      type uint32;
      config false;
    }
    leaf-list pmCaScheduledUlSum {
      type uint32;
    }
    leaf pmRrcConnReestSucc {
      type uint32;
      config false;
    }
    leaf pmPdcpVolUlDrbPlmn3 {
      type uint32;
      config false;
    }
    leaf pmUeCtxtFetchAttS1HoExeSrvccGeran {
      type uint32;
      config false;
    }
    leaf pmUeCategoryDowngraded {
      type uint32;
      config false;
    }
    leaf pmErabEstabFailAddedLic {
      type uint32;
      config false;
    }
    leaf pmFlexPdcpVolDlDrb {
      type uint32;
      config false;
    }
    leaf-list pmCellUlSeUtilization {
      type uint32;
    }
    leaf pmRadioRecInterferencePwrPrb26 {
      type uint32;
      config false;
    }
    leaf pmHoPrepSuccInMfbiPrimary {
      type ietfinet:ip-address;
      config false;
    }
    leaf-list pmZtemporary135Compr {
      type uint32;
    }
    leaf-list pmZtemporary233Compr {
      type uint32;
    }
    leaf pmFlexCellHoPrepAttLteInterF {
      type uint32;
      config false;
    }
    leaf pmCellHoExeSuccLteIntraFTuneOut {
      type uint32;
      config false;
    }
    leaf pmEndcSetupUeAttBufUl {
      type uint32;
      config false;
    }
    leaf-list pmErabModSuccQci {
      type uint32;
    }
    leaf pmPdcpVolDlDrbTransPlmn5 {
      type uint32;
      config false;
    }
    leaf pmUeCtxtRelSCUtranB2Rsrq {
      type uint32;
      config false;
    }
    leaf pmCellHoExeSuccLteInterFDtvm {
      type uint32;
      config false;
    }
    leaf pmNasTransferAttDlSrb2 {
      type uint32;
      config false;
    }
    leaf pmRadioRecInterferencePwrPrb89 {
      type uint32;
      config false;
    }
    leaf pmHoPreventedProblematicCell {
      type uint32;
      config false;
    }
    leaf pmErabRelMmeHo {
      type uint32;
      config false;
    }
    leaf pmZtemporary65 {
      type uint32;
      config false;
    }
    leaf pmMeasMissingNeighRel {
      type uint32;
      config false;
    }
    leaf pmPucchSr {
      type uint32;
      config false;
    }
    leaf pmCpriExtDelayChange {
      type uint32;
      config false;
    }
    leaf pmRaSuccCfra {
      type uint32;
      config false;
    }
    leaf pmUeCtxtFetchSucc {
      type uint32;
      config false;
    }
    leaf pmDlAssigsTransVolte {
      type uint32;
      config false;
    }
    leaf pmRrcConnEstabAttMoVoice {
      type uint32;
      config false;
    }
    leaf pmZtemporary237 {
      type uint32;
      config false;
    }
    leaf pmRlcArqDlAck {
      type uint32;
      config false;
    }
    leaf pmSchedActivityUeDl {
      type uint32;
      config false;
    }
    leaf pmPdcchResyncAtt {
      type uint32;
      config false;
    }
    leaf-list pmZtemporary230Compr {
      type uint32;
    }
    leaf-list pmPdcchCceUtilDistr {
      type uint32;
    }
    leaf pmUeCtxtSuspendAtt {
      type uint32;
      config false;
    }
    leaf pmZtemporary4 {
      type uint32;
      config false;
    }
    leaf pmRadioRecInterferencePwrPrb43 {
      type uint32;
      config false;
    }
    leaf-list pmUeCategoryDistr {
      type uint32;
    }
    leaf pmFlexRlcDelayTimeDl2 {
      type uint32;
      config false;
    }
    leaf pmCellHoExeAttLteInterFUl {
      type uint32;
      config false;
    }
    leaf pmDlAssigsWithDetectedHarqAckVolte {
      type uint32;
      config false;
    }
    leaf pmUeCtxtRelAbnormalEnbActCritCov {
      type uint32;
      config false;
    }
    leaf pmRadioUeRepCqi2Subband3Sum {
      type uint32;
      config false;
    }
    leaf pmErabEstabSuccInit {
      type uint32;
      config false;
    }
    leaf pmFlexMacHarqUlFailIua16qam {
      type ietfyang:mac-address;
      config false;
    }
    leaf pmUeCtxtRelAbnormalEnb {
      type uint32;
      config false;
    }
    leaf-list pmPrbUtilDlCellResource23Distr {
      type uint32;
      description "MOM flags: noNotification.";
    }
    leaf-list pmInhibitImeisvFeature {
      type uint32;
    }
    leaf pmPrbUsedUlSamp {
      type uint32;
      config false;
    }
    leaf pmPrbUsedDlSrbFirstTrans {
      type uint32;
      config false;
    }
    leaf pmFlexMacHarqDlAllDtx {
      type ietfyang:mac-address;
      config false;
    }
    leaf pmPrbAvailUlPuschCenterRegion {
      type uint32;
      config false;
    }
    leaf pmRrcConnCe2CellLevMax {
      type int32;
      config false;
    }
    leaf pmErabRelAbnormalEnbPsPartFail {
      type uint32;
      config false;
    }
    leaf pmTtiBundlingDisable {
      type uint32;
      config false;
    }
    leaf pmCellHoPrepSuccLteInterFUlTraffic {
      type uint32;
      config false;
    }
    leaf pmFlexUeThpTimeUlCa {
      type uint32;
      config false;
    }
    leaf pmRrcConnQueueSuccHpa {
      type uint32;
      config false;
    }
    leaf pmPagReceived {
      type uint32;
      config false;
    }
    leaf pmUeCtxtRelAbnormalEnbHo {
      type uint32;
      config false;
    }
    leaf-list pmAccessClassBarringCsfbPlmn1Distr {
      type ietfyang:mac-address;
    }
    leaf pmUeCtxtRelAbnormalEnbPeSrResPa {
      type uint32;
      config false;
    }
    leaf pmRrcConnEstabFailMpOverload {
      type uint32;
      config false;
    }
    leaf pmBadCovSearchEvalReportUl {
      type ietfinet:port-number;
      config false;
    }
    leaf pmRrcConnEstabLowCovUeAtt {
      type uint32;
      config false;
    }
    leaf pmTtiBundlingEnable {
      type uint32;
      config false;
    }
    leaf pmFlexErabRelMmeAct {
      type uint32;
      config false;
    }
    leaf pmActiveUeUlCe0Max {
      type ietfyang:mac-address;
      config false;
    }
    leaf pmUeExclThpDlShortDrb {
      type uint32;
      config false;
      status deprecated;
      description "MOM flags: noNotification.";
    }
    leaf pmA5BestCellEvalReportRsrp {
      type ietfinet:port-number;
      config false;
    }
    leaf pmEndcNotAllowedExpiredMoVoice {
      type uint32;
      config false;
    }
    leaf-list pmCompUlDeltaSinrPuschDistr {
      type uint32;
    }
    leaf pmMcPttQualityRbUlOk {
      type uint32;
      config false;
    }
    leaf-list pmRaAttTaDistr {
      type uint32;
    }
    leaf-list pmErabRelMmeGbrArp {
      type uint32;
    }
    leaf pmRrcConnReconfNoDrxMoVoice {
      type uint32;
      config false;
    }
    leaf pmCellDownLockAuto {
      type uint32;
      config false;
    }
    leaf pmCaCapableDlSamp {
      type uint32;
      config false;
    }
    leaf pmUeCtxtFetchSuccNasTransferDl {
      type uint32;
      config false;
    }
    leaf pmPwsEtwsSecReq {
      type uint32;
      config false;
    }
    leaf pmFlexErabRelAbnormalMme {
      type uint32;
      config false;
    }
    leaf-list pmErabEstabSuccAddedArp {
      type uint32;
    }
    leaf pmRadioRecInterferencePwrPrb48 {
      type uint32;
      config false;
    }
    leaf pmUeCtxtFetchSuccS1HoExe {
      type uint32;
      config false;
    }
    leaf pmRohcUlDataDeconfigAtt {
      type uint32;
      config false;
    }
    leaf-list pmPuschMcsSubsGroup6Distr {
      type uint32;
    }
    leaf pmS1InitialUeMsgSendBack {
      type uint32;
      config false;
    }
    leaf pmZtemporary205 {
      type uint32;
      config false;
    }
    leaf pmDlAssigsDetHarqMcPttNDO {
      type uint32;
      config false;
    }
    leaf pmMiMimoSleepIn {
      type uint32;
      config false;
    }
    leaf-list pmMacUeThpUlMbbHighVolDistr {
      type ietfyang:mac-address;
    }
    leaf-list pmRrcConnReestSuccQci {
      type uint32;
    }
    leaf pmErabRelAbnormalEnbSirBb {
      type uint32;
      config false;
    }
    leaf pmEndcSetupScgUeAttBufUl {
      type uint32;
      config false;
    }
    leaf pmRadioRecInterferencePwrPrb58 {
      type uint32;
      config false;
    }
    leaf pmCellDowntime {
      type uint32;
      config false;
    }
    leaf-list pmRrcConnEstabAttReattCe {
      type uint32;
    }
    leaf pmHoPrepRejInMpMem {
      type uint32;
      config false;
    }
    leaf pmCellHoPrepAttLteIntraF {
      type uint32;
      config false;
    }
    leaf-list pmMultiUserMimoUlUePairsDistr {
      type uint32;
    }
    leaf pmMacVolDlDataTotal {
      type ietfyang:mac-address;
      config false;
    }
    leaf pmCgiMeasSuccDrxQci1 {
      type uint32;
      config false;
    }
    leaf pmPdcchCceUsedUl {
      type uint32;
      config false;
    }
    leaf pmFlexZtemporary20 {
      type uint32;
      config false;
    }
    leaf pmHoPrepRejInCellIntensStat {
      type uint32;
      config false;
    }
    leaf pmUeCtxtFetchAttEndcRel {
      type uint32;
      config false;
    }
    leaf pmCellHoExeAttLteInterFUlTraffic {
      type uint32;
      config false;
    }
    leaf pmUeCtxtFetchAttReconfUeCtxtEstabReconfFail {
      type uint32;
      config false;
    }
    leaf pmUlGrantsTransVolte {
      type uint32;
      config false;
    }
    leaf pmB1MeasRepEndcConfigRestart {
      type uint32;
      config false;
    }
    leaf-list pmCaScheduledDlEranSumDistr {
      type uint32;
    }
    leaf pmFlexSchedActivityCellUl {
      type uint32;
      config false;
    }
    leaf-list pmPdcpPktLostUlMissingPdus2Qci {
      type uint32;
    }
    leaf pmPrbAvailDlMbms {
      type uint32;
      config false;
    }
    leaf pmFlexRadioThpVolUl {
      type uint32;
      config false;
      status deprecated;
      description "MOM flags: noNotification.";
    }
    leaf pmMiMimoSleepTerm {
      type uint32;
      config false;
    }
    leaf pmUeCtxtFetchAttS1HoPrep {
      type uint32;
      config false;
    }
    leaf pmMiMimoSleepOut {
      type uint32;
      config false;
    }
    leaf pmPdcpUeThpTimeDl {
      type uint32;
      config false;
      status deprecated;
      description "MOM flags: noNotification.";
    }
    leaf pmFlexCellHoExeCancelUtranSrvcc {
      type uint32;
      config false;
    }
    leaf pmFlexUeCtxtRelAbnormalEnbActPe {
      type uint32;
      config false;
    }
    leaf pmUeCtxtFetchSuccS1HoPrep {
      type uint32;
      config false;
    }
    leaf-list pmErabRelAbnormalEnbActHprQci {
      type uint32;
    }
    leaf pmUlTrafficQualifiedUe {
      type uint32;
      config false;
    }
    leaf pmRadioThpVolTxDlSCellIcm {
      type uint32;
      config false;
    }
    leaf-list pmS1SigConnEstabSuccModCe {
      type uint32;
    }
    leaf pmServiceTimeDrb {
      type uint32;
      config false;
    }
    leaf pmZtemporary201 {
      type uint32;
      config false;
    }
    leaf pmErabEstabFailAddedErabIdInUse {
      type uint32;
      config false;
    }
    leaf pmFlexZtemporary15 {
      type uint32;
      config false;
    }
    leaf pmUeCtxtRelSCEUtraBestCellRsrq {
      type uint32;
      config false;
    }
    leaf-list pmAccessClassBarringModDistr {
      type ietfyang:mac-address;
    }
    leaf pmErabRelAbnormalEnbActHo {
      type uint32;
      config false;
    }
    leaf-list pmErabRelAbnormalMmeActArp {
      type uint32;
    }
    leaf-list pmRadioRecInterferencePwrPucch {
      type uint32;
    }
    leaf pmRrcConnResumeFailCellIntensDLC {
      type uint32;
      config false;
    }
    leaf pmMacHarqUlDtx64Qam {
      type ietfyang:mac-address;
      config false;
    }
    leaf-list pmCaConfDlIcmSumDistr {
      type uint32;
    }
    leaf-list pmPrbUtilDlCellResource5Distr {
      type uint32;
      description "MOM flags: noNotification.";
    }
    leaf pmFlexPdcpPktDiscDlAqm {
      type uint32;
      config false;
    }
    leaf pmA1InterFHoHigherPrioEvalReport {
      type ietfinet:port-number;
      config false;
    }
    leaf-list pmPdcpPktReceivedUlQci {
      type uint32;
    }
    leaf-list pmPdcpVolDlDrbLastTTIQci {
      type uint32;
    }
    leaf-list pmPrbUsedDlDtchFirstTransQci {
      type uint32;
    }
    leaf-list pmRaMsg2AttCbraBr {
      type uint32;
    }
    leaf pmMacHarqDlNackComp {
      type ietfyang:mac-address;
      config false;
    }
    leaf pmPrbUsedDlFirstTransCatm {
      type uint32;
      config false;
    }
    leaf pmEndcSetupUeAttBufDl {
      type uint32;
      config false;
    }
    leaf pmFlexRadioThpVolDl {
      type uint32;
      config false;
      status deprecated;
      description "MOM flags: noNotification.";
    }
    leaf-list pmRaSuccCbraBr {
      type uint32;
    }
    leaf pmUeThpVolUl {
      type uint32;
      config false;
    }
    leaf pmUeCtxtRelCsfbHoPrepFail1xRtt {
      type uint32;
      config false;
    }
    leaf-list pmCellUlPrbUtilization {
      type uint32;
    }
    leaf pmFlexCellHoPrepSuccNonMobLte {
      type uint32;
      config false;
    }
    leaf-list pmErabRelAbnormalEnbActUeLostQci {
      type uint32;
    }
    leaf pmS1SigConnEstabAttMod {
      type uint32;
      config false;
    }
    leaf pmPagEdrxDiscarded {
      type uint32;
      config false;
    }
    leaf pmFlexZtemporary7 {
      type uint32;
      config false;
    }
    leaf pmRadioRecInterferencePwrPrb77 {
      type uint32;
      config false;
    }
    leaf-list pmErabRelNormalEnbActQci {
      type uint32;
    }
    leaf-list pmPdcchSym1PwrUtil {
      type uint32;
    }
    leaf pmMacHarqDlNack16qam {
      type ietfyang:mac-address;
      config false;
    }
    leaf-list pmPuschMcsSubsGroup2Distr {
      type uint32;
    }
    leaf pmFlexPdcpPktDiscDlHo {
      type uint32;
      config false;
    }
    leaf pmErabEstabAttAddedCsfbSinr {
      type uint32;
      config false;
    }
    leaf pmCaDeconfiguredLostCoverage {
      type uint32;
      config false;
    }
    leaf pmRadioRecInterferencePwrPrb45 {
      type uint32;
      config false;
    }
    leaf-list pmUeThpDlMbbFilteredQciDistr {
      type uint32;
    }
    leaf pmRadioThpVolTxDl5ccSCell {
      type uint32;
      config false;
    }
    leaf pmEndcUaiRecOverheating {
      type uint32;
      config false;
    }
    leaf pmRlcArqUlAck {
      type uint32;
      config false;
    }
    leaf-list pmPdcchUlDtxWorseDistr {
      type uint32;
    }
    leaf pmFlexCellHoExeSuccNonMobLte {
      type uint32;
      config false;
    }
    leaf pmErabEstabAttAddedHoOngoing {
      type uint32;
      config false;
    }
    leaf pmUeCtxtRelAbnormalMmeAct {
      type uint32;
      config false;
    }
    leaf-list pmS1SigConnEstabAttCe {
      type uint32;
    }
    leaf pmFlexMacHarqUlDtx64qam {
      type ietfyang:mac-address;
      config false;
    }
    leaf pmFlexMacHarqDl7 {
      type ietfyang:mac-address;
      config false;
    }
    leaf pmCellHoPrepAttLteInterFUlTraffic {
      type uint32;
      config false;
    }
    leaf pmRadioThpVolTxDl2ccSCell {
      type uint32;
      config false;
    }
    leaf-list pmRrcConnEstabSuccMtaCe {
      type uint32;
    }
    leaf pmZtemporary70 {
      type uint32;
      config false;
    }
    leaf pmRrcConnResumeSucc {
      type uint32;
      config false;
    }
    leaf pmVoipQualityRbUlOk {
      type ietfinet:ip-address;
      config false;
    }
    leaf pmOocStateExits {
      type uint32;
      config false;
    }
    leaf-list pmPdcchMsg2PwrBoostDistr {
      type uint32;
    }
    leaf-list pmZtemporary16Qci {
      type uint32;
    }
    leaf pmFlexCellHoPrepAtt1xRttSrvcc {
      type uint32;
      config false;
    }
    leaf-list pmAcBarringModSpecAcPlmn2Distr {
      type ietfyang:mac-address;
    }
    leaf-list pmRadioUeRepCqiDistr4 {
      type uint32;
    }
    leaf pmRadioTbsPwrUnrestricted {
      type uint32;
      config false;
    }
    leaf pmEndcUaiRecOverheatingMiti {
      type uint32;
      config false;
    }
    leaf-list pmLaaConfigurableDlSum {
      type uint32;
      description "MOM flags: noNotification.";
    }
    leaf pmRadioRecInterferencePwrSf6 {
      type uint32;
      config false;
    }
    leaf pmPagDiscarded {
      type uint32;
      config false;
    }
    leaf pmRadioRecInterferencePwrPrb40 {
      type uint32;
      config false;
    }
    leaf pmZtemporary2 {
      type uint32;
      config false;
    }
    leaf pmUeCtxtRelAbnormalEnbActUeLostOos {
      type uint32;
      config false;
    }
    leaf pmRrcConnEstabFailCellIntensDLC {
      type uint32;
      config false;
    }
    leaf-list pmRaMsg3NackCbraTxDistr {
      type uint32;
    }
    leaf-list pmS1SigConnEstabSuccMtaCe {
      type uint32;
    }
    leaf pmUeCtxtFetchSuccEndcRel {
      type uint32;
      config false;
    }
    leaf pmCellHoExeSuccLteInterFUtvm {
      type uint32;
      config false;
    }
    leaf pmFlexMacHarqUlAllDtx {
      type ietfyang:mac-address;
      config false;
    }
    leaf pmLbtPdschSucc {
      type uint32;
      config false;
    }
    leaf pmFlexMacHarqUlFailQpsk {
      type ietfyang:mac-address;
      config false;
    }
    leaf-list pmRaAttCbraBr {
      type uint32;
    }
    leaf pmFlexLcgThpTimeUl {
      type uint32;
      config false;
    }
    leaf-list pmMacUeThpUlMbbLowVolQciDistr {
      type ietfyang:mac-address;
    }
    leaf pmUeCtxtRelNaccCsfbWcdmaEm {
      type uint32;
      config false;
    }
    leaf pmZtemporary150 {
      type uint32;
      config false;
    }
    leaf pmRadioRecInterferencePwrPrb94 {
      type uint32;
      config false;
    }
    leaf pmUeCtxtFetchSuccIntraEnbHoPrep {
      type uint32;
      config false;
    }
    leaf pmPucchCqiResShortUtilCell {
      type int32;
      config false;
    }
    leaf pmRadioRecInterferencePwrSf7 {
      type uint32;
      config false;
    }
    leaf pmAdjustAccessMpLoadCtrl {
      type uint32;
      config false;
    }
    leaf pmDlAssigsWithDetectedHarqAckSCell {
      type uint32;
      config false;
    }
    leaf-list pmRadioHomUeRepCqi2Distr {
      type uint32;
    }
    leaf-list pmCaActivatedDl2ccSumDistr {
      type uint32;
    }
    leaf pmRobustCallSetupDelayedIntraLte {
      type uint32;
      config false;
    }
    leaf pmActiveUeUlPreschedData {
      type ietfyang:mac-address;
      config false;
    }
    leaf-list pmUeThpDlMbbFiltered2Distr {
      type uint32;
    }
    leaf-list pmRlcPduBufferUtilUlCellDistr {
      type uint32;
    }
    leaf pmRaFailCfraMsg1DiscSched {
      type uint32;
      config false;
    }
    leaf pmUlGrantsDetPuschNonMcPttNDO {
      type uint32;
      config false;
    }
    leaf pmRadioRecInterferencePwrPrb99 {
      type uint32;
      config false;
    }
    leaf pmRlcDelayTimeDl {
      type uint32;
      config false;
      status deprecated;
      description "MOM flags: noNotification.";
    }
    leaf pmIdcCapableMax {
      type int32;
      config false;
    }
    leaf pmPrbAvailUlPuschHighRegion {
      type uint32;
      config false;
    }
    leaf pmPdcchCceUsedUlPresched {
      type uint32;
      config false;
    }
    leaf pmLbtPdschAtt {
      type uint32;
      config false;
    }
    leaf-list pmRadioTxRankDistr {
      type uint32;
    }
    leaf-list pmCaActivatedDlIcmSum {
      type uint32;
      description "MOM flags: noNotification.";
    }
    leaf pmFlexMacHarqUl6 {
      type ietfyang:mac-address;
      config false;
    }
    leaf-list pmErabRelAbnormalEnbCdtAutoQci {
      type uint32;
    }
    leaf pmCellHoExeSuccLteIntraFCsg {
      type uint32;
      config false;
    }
    leaf pmAcBarringEmSpecAcPlmn2 {
      type ietfyang:mac-address;
      config false;
    }
    leaf pmRrcConnReconfSuccNoMobEarfcnEndc {
      type uint32;
      config false;
    }
    leaf pmLaaConfiguredDlSamp {
      type uint32;
      config false;
    }
    leaf pmUeCtxtRelSCEUtra {
      type uint32;
      config false;
    }
    leaf-list pmPrbUtilDlDistr {
      type uint32;
    }
    leaf-list pmRadioHomUeRepCqiDistr {
      type uint32;
    }
    leaf pmRaSuccSrInSync {
      type uint32;
      config false;
    }
    leaf-list pmMacLatTimeDlDrxSyncQci {
      type ietfyang:mac-address;
      description "MOM flags: noNotification.";
    }
    leaf pmFlexCellHoPrepSuccUtranSrvcc {
      type uint32;
      config false;
    }
    leaf pmUeExclThpDlVolteMbb {
      type uint32;
      config false;
      status deprecated;
      description "MOM flags: noNotification.";
    }
    leaf-list pmRrcConnEstabSuccMtaPagPrioDistr {
      type uint32;
    }
    leaf pmElcPdschBlankedTti {
      type uint32;
      config false;
    }
    leaf pmFlexErabRelMmeGbr {
      type uint32;
      config false;
    }
    leaf pmEndcCapableUe {
      type uint32;
      config false;
    }
    leaf-list pmRrcConnEstabFailCellLatencyCe {
      type uint32;
    }
    leaf-list pmPuschMcsDistr {
      type uint32;
    }
    leaf-list pmErabEstabSuccInitArp {
      type uint32;
    }
    leaf pmUeCtxtRelAbnormalEnbActCdtAuto {
      type uint32;
      config false;
    }
    leaf pmPdcpPktDiscDlAqm {
      type uint32;
      config false;
    }
    leaf pmMacHarqUlDtx256Qam {
      type ietfyang:mac-address;
      config false;
    }
    leaf-list pmErabVolteTimeDistr {
      type uint32;
    }
    leaf pmUePeAttSrResPa {
      type uint32;
      config false;
    }
    leaf pmPdcchTxAggressive {
      type uint32;
      config false;
    }
    leaf pmHoPrepRejInSl {
      type uint32;
      config false;
    }
    leaf pmRrcConnEstabFailBearerAdmissionRej {
      type uint32;
      config false;
    }
    leaf pmZtemporary1 {
      type uint32;
      config false;
    }
    leaf pmFlexZtemporary24 {
      type uint32;
      config false;
    }
    leaf pmRadioRecInterferencePwrPrb61 {
      type uint32;
      config false;
    }
    leaf pmMacSkipUlDtxDynamic {
      type ietfinet:ip-address;
      config false;
    }
    leaf-list pmErabRelAbnormalEnbHoQci {
      type uint32;
    }
    leaf pmS1InitialUeMsgReroute {
      type uint32;
      config false;
    }
    leaf-list pmZtemporary58 {
      type uint32;
    }
    leaf pmErabRelAbnormalMmeExtIat {
      type uint32;
      config false;
    }
    leaf-list pmAcBarringVoiceSpecAcPlmn3Distr {
      type ietfyang:mac-address;
    }
    leaf pmMacVolUlUnresUe {
      type ietfyang:mac-address;
      config false;
    }
    leaf pmCaConfiguredDlSamp {
      type uint32;
      config false;
    }
    leaf pmUeCtxtRelAbnormalEnbDataStall {
      type uint32;
      config false;
    }
    leaf-list pmPrbUsedMimoLayersDlDistr {
      type uint32;
    }
  }
  grouping EUtraNetwork-attributes {
    leaf eUtraNetworkId {
      type string;
      mandatory true;
    }
    leaf userLabel {
      type string {
        length "1..128";
      }
      description "length 1..128.";
    }
  }
  grouping EUtranFreqRelation-attributes {
    leaf eUtranFreqRelationId {
      type string;
      mandatory true;
    }
    leaf userLabel {
      type string {
        length "1..128";
      }
      description "length 1..128.";
    }
    leaf eutranFrequencyRef {
      type string;
      mandatory true;
    }
    leaf qRxLevMin {
      type eytypes:int32_range_-140--44;
      default "-140";
      units "dBm";
      description "range -140..-44; Default value: -140.";
    }
    leaf pMax {
      type int32 {
        range "-30..33 | 1000";
      }
      default "1000";
      units "dBm";
      description "Default value: 1000.";
    }
    leaf tReselectionEutra {
      type eytypes:int32_range_0-7-9;
      default "2";
      units "s";
      description "range 0..7; Default value: 2.";
    }
    leaf tReselectionEutraSfHigh {
      type eytypes:int32_range_25-100-26;
      default "100";
      units "percent";
      description "range 25..100; Default value: 100.";
    }
    leaf tReselectionEutraSfMedium {
      type eytypes:int32_range_25-100-26;
      default "100";
      units "percent";
      description "range 25..100; Default value: 100.";
    }
    leaf cellReselectionPriority {
      type eytypes:int32_range_-1-7;
      default "7";
      description "range -1..7; Default value: 7.";
    }
    leaf threshXHigh {
      type eytypes:int32_range_0-62;
      default "4";
      units "dB";
      description "range 0..62; Default value: 4.";
    }
    leaf threshXLow {
      type eytypes:int32_range_0-62;
      default "0";
      units "dB";
      description "range 0..62; Default value: 0.";
    }
    leaf allowedMeasBandwidth {
      type int32 {
        range "6 | 15 | 25 | 50 | 75 | 100";
      }
      default "6";
      units "Number of PRBs";
      description "Default value: 6.";
    }
    leaf qOffsetFreq {
      type int32 {
        range "-24 | -22 | -20 | -18 | -16 | -14 | -12 | -10 | -8 | -6..6 | 8 | 10 | 12 | 14 | 16 | 18 | 20 | 22 | 24";
      }
      default "0";
      units "dB";
      description "Default value: 0.";
    }
    leaf presenceAntennaPort1 {
      type ietfinet:port-number;
      description "Default value: false.";
    }
    list allowedPlmnList {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf connectedModeMobilityPrio {
      type eytypes:int32_range_-1-7;
      default "7";
      description "range -1..7; Default value: 7.";
    }
    leaf mobilityAction {
      type enumeration {
        enum RELEASE_WITH_REDIRECT;
        enum HANDOVER;
      }
    }
    leaf createdBy {
      type enumeration {
        enum ANR;
        enum X2;
        enum OPERATOR;
      }
      config false;
    }
    leaf timeOfCreation {
      type string {
        length "0..19";
      }
      config false;
      description "length 0..19.";
    }
    leaf lastModification {
      type enumeration {
        enum ANR_MODIFICATION;
        enum X2_MODIFICATION;
        enum OPERATOR_MODIFICATION;
        enum ANR_DELETE;
        enum X2_DELETE;
        enum OPERATOR_DELETE;
        enum NOT_MODIFIED;
        enum MRO_MODIFICATION;
        enum PCI_MODIFICATION;
        enum MLB_MODIFICATION;
        enum RACH_OPT_MODIFICATION;
        enum LM_MODIFICATION;
      }
      config false;
    }
    leaf timeOfLastModification {
      type string {
        length "0..19";
      }
      config false;
      description "length 0..19.";
    }
    leaf threshXHighQ {
      type eytypes:int32_range_0-31;
      default "2";
      units "dB";
      description "range 0..31; Default value: 2.";
    }
    leaf threshXLowQ {
      type eytypes:int32_range_0-31;
      default "0";
      units "dB";
      description "range 0..31; Default value: 0.";
    }
    leaf qQualMin {
      type int32 {
        range "-34..-3 | 0";
      }
      default "0";
      units "dB";
      description "Default value: 0.";
    }
    leaf neighCellConfig {
      type enumeration {
        enum DIFF_MBSFN_SUBFRAMES;
        enum SAME_MBSFN_SUBFRAMES;
        enum NO_MBSFN_SUBFRAMES;
        enum DIFF_UL_DL_ALLOCATION;
      }
    }
    leaf voicePrio {
      type eytypes:int32_range_-1-7;
      default "0";
      description "range -1..7; Default value: 0.";
    }
    list blackListEntry {
      key "id";
      leaf id {
        type uint32;
        description "Synthetic key for struct sequence entry.";
      }
      container attributes {
      leaf physicalLayerCellIdGroup {
        type int32 {
          range "-1..167";
        }
        default "-1";
        description "range -1..167; Default value: -1.";
      }
      leaf physicalLayerSubCellId {
        type int32 {
          range "-1..2";
        }
        default "-1";
        description "range -1..2; Default value: -1.";
      }
      leaf range {
        type int32;
        default "1";
        description "Default value: 1.";
      }
      }
    }
    leaf interFreqMeasType {
      type enumeration {
        enum EVENT_A5;
        enum EVENT_A3;
      }
    }
    list eutranFreqToQciProfileRelation {
      key "id";
      leaf id {
        type uint32;
        description "Synthetic key for struct sequence entry.";
      }
      container attributes {
      leaf lbQciProfileHandling {
        type ietfinet:ip-address;
      }
      leaf qciProfileRef {
        type ietfinet:ip-address;
      }
      leaf lbA5Threshold2RsrpOffset {
        type eytypes:int32_range_0-24;
        default "0";
        description "range 0..24; Default value: 0.";
      }
      leaf lbA5Threshold2RsrqOffset {
        type int32 {
          range "0..240";
        }
        default "0";
        units "dB";
        description "range 0..240; Default value: 0.";
      }
      leaf a5Thr1RsrpFreqQciOffset {
        type eytypes:int32_range_-100-100;
        default "0";
        units "dB";
        description "range -100..100; Default value: 0.";
      }
      leaf a5Thr1RsrqFreqQciOffset {
        type eytypes:int32_range_-240-240;
        default "0";
        units "dB";
        description "range -240..240; Default value: 0.";
      }
      leaf a5Thr2RsrpFreqQciOffset {
        type eytypes:int32_range_-100-100;
        default "0";
        units "dB";
        description "range -100..100; Default value: 0.";
      }
      leaf a5Thr2RsrqFreqQciOffset {
        type eytypes:int32_range_-240-240;
        default "0";
        units "dB";
        description "range -240..240; Default value: 0.";
      }
      leaf atoThresh1QciProfileHandling {
        type ietfinet:ip-address;
      }
      leaf atoThresh2QciProfileHandling {
        type ietfinet:ip-address;
      }
      leaf a3RsrpFreqQciOffsetAdjustment {
        type eytypes:int32_range_-150-150;
        default "0";
        units "dB";
        description "range -150..150; Default value: 0.";
      }
      leaf a3RsrqFreqQciOffsetAdjustment {
        type eytypes:int32_range_-150-150;
        default "0";
        units "dB";
        description "range -150..150; Default value: 0.";
      }
      leaf timeToTriggerA3 {
        type int32;
        default "-1";
        units "ms";
        description "Default value: -1.";
      }
      leaf timeToTriggerA3Rsrq {
        type int32;
        default "-1";
        units "ms";
        description "Default value: -1.";
      }
      }
    }
    list blackListEntryIdleMode {
      key "id";
      leaf id {
        type uint32;
        description "Synthetic key for struct sequence entry.";
      }
      container attributes {
      leaf physicalLayerCellIdGroup {
        type int32 {
          range "-1..167";
        }
        default "-1";
        description "range -1..167; Default value: -1.";
      }
      leaf physicalLayerSubCellId {
        type int32 {
          range "-1..2";
        }
        default "-1";
        description "range -1..2; Default value: -1.";
      }
      leaf range {
        type int32;
        default "1";
        description "Default value: 1.";
      }
      }
    }
    leaf lbBnrPolicy {
      type enumeration {
        enum NOT_ALLOWED;
        enum AUTO;
        enum LB_ONLY;
        enum OFFLOAD_ONLY;
        enum IFO_AND_IFLB;
      }
    }
    leaf anrMeasOn {
      type boolean;
      default "true";
      description "Default value: true.";
    }
    leaf lbActivationThreshold {
      type eytypes:int32_range_0-16000;
      default "0";
      description "range 0..16000; Default value: 0.";
    }
    leaf caTriggeredRedirectionActive {
      type boolean;
      default "true";
      description "Default value: true.";
    }
    leaf arpPrio {
      type eytypes:int32_range_-1-7;
      default "0";
      description "range -1..7; Default value: 0.";
    }
    leaf nonPlannedPhysCellId {
      type int32 {
        range "0..503 | 1000";
      }
      default "1000";
      description "Default value: 1000.";
    }
    leaf nonPlannedPhysCellIdRange {
      type int32 {
        range "1..504";
      }
      default "1";
      description "range 1..504; Default value: 1.";
    }
    leaf nonPlannedPciCIO {
      type int32 {
        range "-24 | -22 | -20 | -18 | -16 | -14 | -12 | -10 | -8 | -6..6 | 8 | 10 | 12 | 14 | 16 | 18 | 20 | 22 | 24";
      }
      default "0";
      units "dB";
      description "Default value: 0.";
    }
    leaf nonPlannedPciTargetIdType {
      type enumeration {
        enum MACRO_ENODEB_ID;
        enum HOME_ENODEB_ID;
      }
    }
    list candNeighborRel {
      config false;
      container attributes {
      leaf physicalLayerSubCellId {
        type eytypes:int32_range_0-2;
        description "range 0..2.";
      }
      leaf physicalLayerCellIdGroup {
        type eytypes:int32_range_0-167;
        description "range 0..167.";
      }
      leaf cellId {
        type eytypes:int32_range_0-255;
        description "range 0..255.";
      }
      leaf enbId {
        type eytypes:int32_range_0-1048575;
        description "range 0..1048575.";
      }
      leaf mcc {
        type eytypes:int32_range_0-999;
        description "range 0..999.";
      }
      leaf mnc {
        type eytypes:int32_range_0-999;
        description "range 0..999.";
      }
      leaf mncLength {
        type eytypes:int32_range_2-3;
        description "range 2..3.";
      }
      leaf tac {
        type eytypes:int32_range_0-65535-10;
        description "range 0..65535.";
      }
      leaf mobilityStatusReason {
        type enumeration {
          enum NONE;
          enum PROBLEMATIC_CELL;
          enum PLMN_NOT_SUPPORTED;
          enum PLMN_BLOCKLISTED;
        }
      }
      leaf blockedPlmnCell {
        type string;
      }
      }
    }
    leaf a5Thr1RsrpFreqOffset {
      type eytypes:int32_range_-100-100;
      default "0";
      units "dB";
      description "range -100..100; Default value: 0.";
    }
    leaf a5Thr1RsrqFreqOffset {
      type eytypes:int32_range_-240-240;
      default "0";
      units "dB";
      description "range -240..240; Default value: 0.";
    }
    leaf a5Thr2RsrpFreqOffset {
      type eytypes:int32_range_-100-100;
      default "0";
      units "dB";
      description "range -100..100; Default value: 0.";
    }
    leaf a5Thr2RsrqFreqOffset {
      type eytypes:int32_range_-240-240;
      default "0";
      units "dB";
      description "range -240..240; Default value: 0.";
    }
    leaf atoAllowed {
      type boolean;
      default "false";
      description "Default value: false.";
    }
    leaf cellSleepCovCellMeasOn {
      type boolean;
      default "true";
      description "Default value: true.";
    }
    leaf interFreqMeasTypeUlSinr {
      type enumeration {
        enum EVENT_A5;
        enum EVENT_A3;
      }
    }
    leaf csgPhysCellId {
      type int32 {
        range "0..503 | 1000";
      }
      default "1000";
      description "Default value: 1000.";
    }
    leaf csgPhysCellIdRange {
      type int32 {
        range "1 | 4 | 8 | 12 | 16 | 24 | 32 | 48 | 64 | 84 | 96 | 128 | 168 | 252 | 504";
      }
      default "1";
      description "Default value: 1.";
    }
    leaf hybridCsgPhysCellId {
      type int32 {
        range "0..503 | 1000";
      }
      default "1000";
      description "Default value: 1000.";
    }
    leaf hybridCsgPhysCellIdRange {
      type int32 {
        range "1..504";
      }
      default "1";
      description "range 1..504; Default value: 1.";
    }
    leaf csgCellTargetIdType {
      type enumeration {
        enum MACRO_ENODEB_ID;
        enum HOME_ENODEB_ID;
      }
    }
    leaf amoAllowed {
      type boolean;
      default "true";
      description "Default value: true.";
    }
    leaf lbA5Thr1RsrpFreqOffset {
      type eytypes:int32_range_0-100-6;
      default "0";
      units "dB";
      description "range 0..100; Default value: 0.";
    }
    leaf caFreqPriority {
      type eytypes:int32_range_-1-7;
      default "4";
      description "range -1..7; Default value: 4.";
    }
    leaf caFreqProportion {
      type ietfinet:port-number;
      default "100";
      description "range 0..100; Default value: 100.";
    }
    leaf tReselectionEutraCe {
      type int32 {
        range "0..15";
      }
      default "2";
      units "s";
      description "range 0..15; Default value: 2.";
    }
    leaf qRxLevMinCe {
      type eytypes:int32_range_-140--44;
      default "-140";
      units "dBm";
      description "range -140..-44; Default value: -140.";
    }
    leaf qQualMinRsrqCe {
      type int32 {
        range "-34..-3 | 0";
      }
      default "0";
      units "dB";
      description "Default value: 0.";
    }
    leaf csmUeCapMonitorEnabled {
      type boolean;
      default "false";
      description "Default value: false.";
    }
    leaf csmUeCapMonitorTime {
      type int32 {
        range "0..1440";
      }
      default "60";
      units "min";
      description "range 0..1440; Default value: 60.";
    }
    leaf mdtMeasOn {
      type boolean;
      default "true";
      description "Default value: true.";
    }
    list a5OffsetPerPC {
      key "id";
      leaf id {
        type uint32;
        description "Synthetic key for struct sequence entry.";
      }
      container attributes {
      leaf powerClass {
        type enumeration {
          enum PC_1;
          enum PC_2;
        }
      }
      leaf a5Thr1RsrpPCOffset {
        type eytypes:int32_range_-100-100;
        default "0";
        units "dB";
        description "range -100..100; Default value: 0.";
      }
      leaf a5Thr1RsrqPCOffset {
        type eytypes:int32_range_-240-240;
        default "0";
        units "dB";
        description "range -240..240; Default value: 0.";
      }
      leaf a5Thr2RsrpPCOffset {
        type eytypes:int32_range_-100-100;
        default "0";
        units "dB";
        description "range -100..100; Default value: 0.";
      }
      leaf a5Thr2RsrqPCOffset {
        type eytypes:int32_range_-240-240;
        default "0";
        units "dB";
        description "range -240..240; Default value: 0.";
      }
      }
    }
    leaf cioQci1Enabled {
      type boolean;
      default "false";
      description "Default value: false.";
    }
    leaf connectedModeMobilityPrioBr {
      type eytypes:int32_range_-1-7;
      default "7";
      description "range -1..7; Default value: 7.";
    }
    leaf voicePrioBr {
      type eytypes:int32_range_-1-7;
      default "0";
      description "range -1..7; Default value: 0.";
    }
    leaf mobilityActionBr {
      type enumeration {
        enum RELEASE_WITH_REDIRECT;
        enum HANDOVER;
      }
    }
    leaf a3RsrpFreqOffsetAdjustment {
      type eytypes:int32_range_-150-150;
      default "0";
      units "dB";
      description "range -150..150; Default value: 0.";
    }
    leaf a3RsrqFreqOffsetAdjustment {
      type eytypes:int32_range_-150-150;
      default "0";
      units "dB";
      description "range -150..150; Default value: 0.";
    }
    leaf zzzTemporary1 {
      type int32;
      default "-2000000000";
      description "Default value: -2000000000.";
    }
    leaf zzzTemporary2 {
      type int32;
      default "-2000000000";
      description "Default value: -2000000000.";
    }
    leaf zzzTemporary3 {
      type string;
    }
    leaf endcHoFreqPriority {
      type eytypes:int32_range_-1-7;
      default "7";
      description "range -1..7; Default value: 7.";
    }
    leaf zzzTemporary4 {
      type int32;
      default "-2000000000";
      description "Default value: -2000000000.";
    }
    leaf zzzTemporary5 {
      type int32;
      default "-2000000000";
      description "Default value: -2000000000.";
    }
    leaf zzzTemporary6 {
      type int32;
      default "-2000000000";
      description "Default value: -2000000000.";
    }
    leaf asmSCellDetection {
      type enumeration {
        enum OFF;
        enum LOCAL;
        enum EXTERNAL;
        enum EXTERNAL_AND_LOCAL;
      }
    }
    leaf asmHitRateAddThreshold {
      type eytypes:int32_range_0-100;
      default "15";
      units "percent";
      description "range 0..100; Default value: 15.";
    }
    leaf asmHitRateRemoveThreshold {
      type eytypes:int32_range_0-100;
      default "5";
      units "percent";
      description "range 0..100; Default value: 5.";
    }
    leaf caOffloadingEnabled {
      type boolean;
      default "true";
      description "Default value: true.";
    }
    leaf endcAwareIdleModePriority {
      type eytypes:int32_range_-1-7;
      default "7";
      description "range -1..7; Default value: 7.";
    }
    list nonPlannedPciAllowedPlmnList {
      key "id";
      leaf id {
        type uint32;
        description "Synthetic key for struct sequence entry.";
      }
      ordered-by user;
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf eUtraFreqRelProfileSetRef {
      type string;
    }
    leaf interFreqHoHigherPrioAllowed {
      type boolean;
      default "false";
      description "Default value: false.";
    }
    leaf sCellPriorityLocal {
      type eytypes:int32_range_-1-7;
      default "7";
      description "range -1..7; Default value: 7.";
    }
    leaf sCellPriorityExtCoSited {
      type eytypes:int32_range_-1-7;
      default "7";
      description "range -1..7; Default value: 7.";
    }
    leaf sCellPriorityExtNonCoSited {
      type eytypes:int32_range_-1-7;
      default "7";
      description "range -1..7; Default value: 7.";
    }
    leaf ulCaFreqProportion {
      type ietfinet:port-number;
      default "100";
      description "range 0..100; Default value: 100.";
    }
    leaf ulCaFreqPriority {
      type eytypes:int32_range_-1-7;
      default "4";
      description "range -1..7; Default value: 4.";
    }
    leaf interFreqHoHigherPrioControl {
      type enumeration {
        enum PRIO_ENDC;
        enum PRIO_LTE;
      }
    }
    leaf a5Thr1RsrpVolteMobFreqOffset {
      type eytypes:int32_range_-100-100;
      default "0";
      units "dB";
      description "range -100..100; Default value: 0.";
    }
    leaf a5Thr1RsrqVolteMobFreqOffset {
      type eytypes:int32_range_-240-240;
      default "0";
      units "dB";
      description "range -240..240; Default value: 0.";
    }
    leaf a5Thr2RsrpVolteMobFreqOffset {
      type eytypes:int32_range_-100-100;
      default "0";
      units "dB";
      description "range -100..100; Default value: 0.";
    }
    leaf a5Thr2RsrqVolteMobFreqOffset {
      type eytypes:int32_range_-240-240;
      default "0";
      units "dB";
      description "range -240..240; Default value: 0.";
    }
    leaf pmMbmsInterestIndication {
      type uint32;
      config false;
    }
    leaf pmCaRedirectMeasuredUe {
      type uint32;
      config false;
    }
    leaf pmLbMeasuredUe {
      type uint32;
      config false;
    }
    leaf pmBadCovMiFreqSel {
      type uint32;
      config false;
    }
    leaf pmSpifhoMeasuredUe {
      type uint32;
      config false;
    }
    leaf pmTm9PrioritizedUe {
      type uint32;
      config false;
    }
    leaf pmAtoMeasuredUe {
      type uint32;
      config false;
    }
    leaf pmIdleModeRelDistrPrioFreq {
      type uint32;
      config false;
    }
    leaf pmEndcPrioritizedUe {
      type uint32;
      config false;
    }
    leaf pmBadCovMiFreqSucc {
      type uint32;
      config false;
    }
    leaf pmMbmsInterestIndicationPCell {
      type uint32;
      config false;
    }
    leaf pmMbmsInterestIndicationNonServ {
      type uint32;
      config false;
    }
    leaf pmMbmsInterestIndicationSCell {
      type uint32;
      config false;
    }
    leaf pmBadCovMiFreqTo {
      type uint32;
      config false;
    }
  }
  grouping EUtranFreqRelationUnlicensed-attributes {
    leaf eUtranFreqRelationUnlicensedId {
      type string;
      mandatory true;
    }
    leaf allowedMeasBandwidth {
      type int32 {
        range "6 | 15 | 25 | 50 | 75 | 100";
      }
      default "100";
      units "Number of PRBs";
      description "Default value: 100.";
    }
    list allowedPlmnList {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf caFreqPriority {
      type eytypes:int32_range_-1-7;
      default "7";
      description "range -1..7; Default value: 7.";
    }
    leaf caFreqProportion {
      type ietfinet:port-number;
      default "100";
      description "range 0..100; Default value: 100.";
    }
    leaf band46UnlicensedProfileRef {
      type string;
    }
    leaf userLabel {
      type string {
        length "1..128";
      }
      description "length 1..128.";
    }
    leaf unlicensedBandProfileRef {
      type string;
    }
    leaf caOffloadingEnabled {
      type boolean;
      default "true";
      description "Default value: true.";
    }
  }
  grouping EUtranFrequency-attributes {
    leaf eUtranFrequencyId {
      type string;
      mandatory true;
    }
    leaf-list reservedBy {
      type string;
    }
    leaf userLabel {
      type string {
        length "1..128";
      }
      description "length 1..128.";
    }
    leaf arfcnValueEUtranDl {
      type int32 {
        range "0..17999 | 36000..262143";
      }
      mandatory true;
    }
    leaf-list additionalFreqBandList {
      type eytypes:int32_range_1-256;
    }
    leaf-list excludeAdditionalFreqBandList {
      type eytypes:int32_range_1-256;
    }
    leaf freqBand {
      type eytypes:int32_range_1-256;
      config false;
      description "range 1..256.";
    }
    leaf-list prioAdditionalFreqBandList {
      type eytypes:int32_range_1-256;
    }
    leaf mfbiFreqBandIndPrio {
      type boolean;
      default "false";
      description "Default value: false.";
    }
    leaf-list zzzTemporaryList1 {
      type int32;
    }
    leaf zzzTemporary1 {
      type int32;
      default "-2000000000";
      description "Default value: -2000000000.";
    }
    leaf zzzTemporary2 {
      type int32;
      default "-2000000000";
      description "Default value: -2000000000.";
    }
    leaf zzzTemporary3 {
      type string;
    }
    list extEndcAllowedPlmnListPolicy {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf zzzTemporary4 {
      type int32;
      default "-2000000000";
      description "Default value: -2000000000.";
    }
    leaf zzzTemporary5 {
      type int32;
      default "-2000000000";
      description "Default value: -2000000000.";
    }
    leaf zzzTemporary6 {
      type int32;
      default "-2000000000";
      description "Default value: -2000000000.";
    }
    leaf caOffloadingEnabled {
      type boolean;
      default "false";
      description "Default value: false.";
    }
  }
  grouping ExternalBroadcastPLMNInfo-attributes {
    list pLMNIdList {
      key "id";
      leaf id {
        type uint32;
        description "Synthetic key for struct sequence entry.";
      }
      ordered-by user;
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf nRTAC {
      type eytypes:int32_range_-1-16777215;
      description "range -1..16777215.";
    }
    leaf externalBroadcastPLMNInfoId {
      type string;
      mandatory true;
    }
    leaf createdBy {
      type enumeration {
        enum ANR;
        enum X2;
        enum OPERATOR;
      }
      config false;
    }
  }
  grouping ExternalCdma20001xRttCell-attributes {
    leaf externalCdma20001xRttCellId {
      type string;
      mandatory true;
    }
    leaf pnOffset {
      type eytypes:int32_range_0-511;
      mandatory true;
      description "range 0..511.";
    }
    leaf-list reservedBy {
      type string;
    }
    leaf acBarring1xRttForMoDataPresent {
      type boolean;
      default "false";
      description "Default value: false.";
    }
    list mscIdentifier {
      key "id";
      leaf id {
        type uint32;
        description "Synthetic key for struct entry.";
      }
      container attributes {
      leaf marketId {
        type eytypes:int32_range_0-65535-10;
        description "range 0..65535.";
      }
      leaf switchNumber {
        type eytypes:int32_range_0-255;
        description "range 0..255.";
      }
      }
    }
    leaf sid {
      type eytypes:int32_range_0-32768;
      mandatory true;
      description "range 0..32768.";
    }
    leaf nid {
      type eytypes:int32_range_0-65535-10;
      mandatory true;
      description "range 0..65535.";
    }
    list cellIdentifier {
      key "id";
      leaf id {
        type uint32;
        description "Synthetic key for struct entry.";
      }
      container attributes {
      leaf cellId {
        type eytypes:int32_range_0-4095;
        description "range 0..4095.";
      }
      leaf sectorNumber {
        type eytypes:int32_range_0-15;
        description "range 0..15.";
      }
      }
    }
    list acBarring1xRttMoData {
      key "id";
      leaf id {
        type uint32;
        description "Synthetic key for struct entry.";
      }
      container attributes {
      leaf acBarring0to9R9 {
        type eytypes:int32_range_0-63;
        default "0";
        description "range 0..63; Default value: 0.";
      }
      leaf acBarring10R9 {
        type eytypes:int32_range_0-7;
        default "0";
        description "range 0..7; Default value: 0.";
      }
      leaf acBarring11R9 {
        type eytypes:int32_range_0-7;
        default "0";
        description "range 0..7; Default value: 0.";
      }
      leaf acBarring12R9 {
        type eytypes:int32_range_0-7;
        default "0";
        description "range 0..7; Default value: 0.";
      }
      leaf acBarring13R9 {
        type eytypes:int32_range_0-7;
        default "0";
        description "range 0..7; Default value: 0.";
      }
      leaf acBarring14R9 {
        type eytypes:int32_range_0-7;
        default "0";
        description "range 0..7; Default value: 0.";
      }
      leaf acBarring15R9 {
        type eytypes:int32_range_0-7;
        default "0";
        description "range 0..7; Default value: 0.";
      }
      leaf acBarringMsgR9 {
        type eytypes:int32_range_0-7;
        default "0";
        description "range 0..7; Default value: 0.";
      }
      leaf acBarringRegR9 {
        type eytypes:int32_range_0-7;
        default "0";
        description "range 0..7; Default value: 0.";
      }
      leaf acBarringEmgR9 {
        type eytypes:int32_range_0-7;
        default "0";
        description "range 0..7; Default value: 0.";
      }
      }
    }
    list csfbRegParams1xRttMoData {
      key "id";
      leaf id {
        type uint32;
        description "Synthetic key for struct entry.";
      }
      container attributes {
      leaf multipleSid {
        type ietfinet:ip-address;
        description "Default value: false.";
      }
      leaf multipleNid {
        type ietfinet:ip-address;
        description "Default value: false.";
      }
      leaf homeReg {
        type boolean;
        default "true";
        description "Default value: true.";
      }
      leaf foreignSidReg {
        type boolean;
        default "true";
        description "Default value: true.";
      }
      leaf foreignNidReg {
        type boolean;
        default "true";
        description "Default value: true.";
      }
      leaf parameterReg {
        type boolean;
        default "true";
        description "Default value: true.";
      }
      leaf powerUpReg {
        type boolean;
        default "true";
        description "Default value: true.";
      }
      leaf registrationPeriod {
        type int32;
        default "80";
        units "second = 2^(reg_prd/4) x 0.08";
        description "Default value: 80.";
      }
      leaf registrationZone {
        type eytypes:int32_range_0-4095;
        default "0";
        description "range 0..4095; Default value: 0.";
      }
      leaf totalZone {
        type eytypes:int32_range_0-7;
        default "0";
        description "range 0..7; Default value: 0.";
      }
      leaf zoneTimer {
        type int32;
        default "1";
        units "min";
        description "Default value: 1.";
      }
      leaf powerDownRegR9 {
        type boolean;
        default "true";
        description "Default value: true.";
      }
      }
    }
    list mobilityParams1xRttMoData {
      key "id";
      leaf id {
        type uint32;
        description "Synthetic key for struct entry.";
      }
      container attributes {
      leaf protocolRev {
        type eytypes:int32_range_0-255;
        default "0";
        description "range 0..255; Default value: 0.";
      }
      leaf minProtocolRev {
        type eytypes:int32_range_0-255;
        default "3";
        description "range 0..255; Default value: 3.";
      }
      leaf authenticationEnabled {
        type boolean;
        default "false";
        description "Default value: false.";
      }
      leaf maxNumAltServiceOption {
        type eytypes:int32_range_0-7;
        default "0";
        description "range 0..7; Default value: 0.";
      }
      leaf preferredMsidType {
        type enumeration {
          enum EMSIS_ESN;
          enum IMSI_OR_TMSI;
          enum IMSI_ESN_OR_TMSI;
        }
      }
      leaf mcc {
        type eytypes:int32_range_0-1023-23;
        default "0";
        description "range 0..1023; Default value: 0.";
      }
      leaf imsiBit11and12 {
        type eytypes:int32_range_0-127;
        default "0";
        description "range 0..127; Default value: 0.";
      }
      leaf imsiTSupported {
        type ietfinet:port-number;
        description "Default value: false.";
      }
      leaf fchFchInitSetupRc3 {
        type eytypes:int32_range_8-255;
        default "56";
        units "dB";
        description "range 8..255; Default value: 56.";
      }
      leaf fchFchInitSetupRc4 {
        type eytypes:int32_range_8-255;
        default "64";
        units "dB";
        description "range 8..255; Default value: 64.";
      }
      leaf fchFchInitSetupRc5 {
        type eytypes:int32_range_8-255;
        default "56";
        units "dB";
        description "range 8..255; Default value: 56.";
      }
      leaf fchFchInitSetupRc11 {
        type eytypes:int32_range_8-255;
        default "64";
        units "dB";
        description "range 8..255; Default value: 64.";
      }
      leaf fchFchInitSetupRc12 {
        type eytypes:int32_range_8-255;
        default "64";
        units "dB";
        description "range 8..255; Default value: 64.";
      }
      leaf localTimeOffset {
        type int32 {
          range "-24..23";
        }
        default "0";
        units "hr";
        description "range -24..23; Default value: 0.";
      }
      leaf dayLightSaving {
        type boolean;
        default "false";
        description "Default value: false.";
      }
      leaf gcsnaL2AckTimer {
        type int32 {
          range "1..255";
        }
        default "3";
        units "ms";
        description "range 1..255; Default value: 3.";
      }
      leaf gcsnaSequenceContextTimer {
        type int32 {
          range "1..255";
        }
        default "5";
        units "ms";
        description "range 1..255; Default value: 5.";
      }
      leaf pilotIncrement {
        type eytypes:int32_range_1-15-8;
        default "4";
        description "range 1..15; Default value: 4.";
      }
      }
    }
    leaf userLabel {
      type string {
        length "1..128";
      }
      description "length 1..128.";
    }
    leaf srvccCapability {
      type enumeration {
        enum NOT_SUPPORTED;
        enum CS_ONLY_SUPPORTED;
        enum PS_AND_CS_SUPPORTED;
      }
    }
  }
  grouping ExternalCdma2000Cell-attributes {
    leaf externalCdma2000CellId {
      type string;
      mandatory true;
    }
    leaf pnOffset {
      type eytypes:int32_range_0-511;
      mandatory true;
      description "range 0..511.";
    }
    leaf userLabel {
      type string {
        length "1..128";
      }
      description "length 1..128.";
    }
    leaf cellGlobalIdHrpd {
      type string;
      mandatory true;
    }
    leaf-list reservedBy {
      type string;
    }
  }
  grouping ExternalENodeBFunction-attributes {
    list eNodeBPlmnId {
      key "id";
      leaf id {
        type uint32;
        description "Synthetic key for struct entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf externalENodeBFunctionId {
      type string;
      mandatory true;
    }
    leaf eNBId {
      type eytypes:int32_range_0-1048575;
      mandatory true;
      description "range 0..1048575.";
    }
    list gUGroupIdList {
      config false;
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      leaf mmeGI {
        type eytypes:int32_range_0-65535-10;
        description "range 0..65535.";
      }
      }
    }
    leaf userLabel {
      type string {
        length "1..128";
      }
      description "length 1..128.";
    }
    leaf masterEnbFunctionId {
      type string {
        length "0..128";
      }
      description "length 0..128.";
    }
    leaf createdBy {
      type enumeration {
        enum ANR;
        enum X2;
        enum OPERATOR;
      }
      config false;
    }
    leaf timeOfCreation {
      type string {
        length "0..19";
      }
      config false;
      description "length 0..19.";
    }
    leaf lastModification {
      type enumeration {
        enum ANR_MODIFICATION;
        enum X2_MODIFICATION;
        enum OPERATOR_MODIFICATION;
        enum ANR_DELETE;
        enum X2_DELETE;
        enum OPERATOR_DELETE;
        enum NOT_MODIFIED;
        enum MRO_MODIFICATION;
        enum PCI_MODIFICATION;
        enum MLB_MODIFICATION;
        enum RACH_OPT_MODIFICATION;
        enum LM_MODIFICATION;
      }
      config false;
    }
    leaf timeOfLastModification {
      type string {
        length "0..19";
      }
      config false;
      description "length 0..19.";
    }
    leaf mfbiSupport {
      type ietfinet:port-number;
      description "Default value: false.";
    }
    leaf ulTrigHoSupport {
      type ietfinet:port-number;
    }
    leaf ulTrigSupport {
      type ietfinet:port-number;
      config false;
    }
    leaf eSCellCapacityScaling {
      type eytypes:int32_range_0-100;
      default "100";
      units "percent";
      description "range 0..100; Default value: 100.";
    }
    leaf interENodeBCAInteractionMode {
      type enumeration {
        enum NONE;
        enum ERAN;
        enum IENBCA;
      }
      status deprecated;
      default "IENBCA";
      description "Default value: IENBCA; Takes effect: Next MO unlock; Status info: Since 21.Q2. Has no functional behavior. Planned to be removed..";
      reference "Takes effect: Next MO unlock.";
    }
    leaf eranVlanPortRef {
      type ietfinet:port-number;
    }
    leaf eranUlCompVlanPortRef {
      type ietfinet:port-number;
    }
    leaf eranLinkMaxRttDelay {
      type int32 {
        range "20 | 60 | 160";
      }
      default "60";
      units "microseconds";
      description "Default value: 60.";
    }
    leaf zzzTemporary1 {
      type int32;
      status deprecated;
      default "-2000000000";
      description "Default value: -2000000000; Status info: Since 20.Q4. Replaced by eranPrioritizationDisabled. Planned to be removed..";
    }
    leaf zzzTemporary2 {
      type int32;
      default "-2000000000";
      description "Default value: -2000000000.";
    }
    leaf zzzTemporary3 {
      type string;
    }
    leaf zzzTemporary7 {
      type int32;
      default "-2000000000";
      description "Default value: -2000000000.";
    }
    leaf zzzTemporary4 {
      type int32;
      default "-2000000000";
      description "Default value: -2000000000.";
    }
    leaf zzzTemporary5 {
      type int32;
      default "-2000000000";
      description "Default value: -2000000000.";
    }
    leaf zzzTemporary6 {
      type int32;
      default "-2000000000";
      description "Default value: -2000000000.";
    }
    leaf zzzTemporary8 {
      type int32;
      default "-2000000000";
      description "Default value: -2000000000.";
    }
    leaf eranPrioritizationDisabled {
      type boolean;
      default "false";
      description "Default value: false.";
    }
    leaf zzzTemporary9 {
      type int32;
      default "-2000000000";
      description "Default value: -2000000000.";
    }
    leaf eranPimVlanPortRef {
      type ietfinet:port-number;
    }
    leaf pimDetectionCandidateRate {
      type eytypes:int32_range_0-100-3;
      config false;
      description "range 0..100.";
    }
    leaf pimDetectionRemoteSelected {
      type boolean;
      default "false";
      description "Default value: false.";
    }
    leaf coSited {
      type boolean;
      default "false";
      description "Default value: false.";
    }
    leaf pmHoPrepRejOutTargetFail {
      type uint32;
      config false;
    }
    leaf pmZtemporary206 {
      type uint32;
      config false;
    }
    leaf pmEenbPktLostDlCa {
      type uint32;
      config false;
    }
    leaf pmEranCaPartnerBlock {
      type uint32;
      config false;
    }
    leaf pmEenbPktRecDlCa {
      type uint32;
      config false;
    }
    leaf pmCaCrntiUnavail {
      type uint32;
      config false;
    }
    leaf pmEranUlCompServSendReq {
      type uint32;
      config false;
    }
    leaf pmEranUlCompServReceiveRsp {
      type uint32;
      config false;
    }
    leaf pmZtemporary223 {
      type uint32;
      config false;
    }
    leaf pmEenbPktLateDlCa {
      type uint32;
      config false;
    }
    leaf pmEenbPktTransDlCa {
      type uint32;
      config false;
    }
    leaf pmEranUlCompCoopSendRsp {
      type uint32;
      config false;
    }
    leaf pmZtemporary222 {
      type uint32;
      config false;
    }
    leaf-list pmEranUlCompCoopSinrPuschDistr {
      type uint32;
    }
    leaf pmEenbPktDiscDlCa {
      type uint32;
      config false;
    }
    leaf pmEranUlCompCoopReceiveReq {
      type uint32;
      config false;
    }
  }
  grouping ExternalEUtranCellFDD-attributes {
    leaf externalEUtranCellFDDId {
      type string;
      mandatory true;
    }
    leaf localCellId {
      type eytypes:int32_range_0-255;
      mandatory true;
      description "range 0..255.";
    }
    leaf physicalLayerCellIdGroup {
      type eytypes:int32_range_0-167;
      mandatory true;
      description "range 0..167.";
    }
    leaf physicalLayerSubCellId {
      type eytypes:int32_range_0-2;
      mandatory true;
      description "range 0..2.";
    }
    leaf-list reservedBy {
      type string;
    }
    leaf userLabel {
      type string {
        length "1..128";
      }
      description "length 1..128.";
    }
    leaf tac {
      type eytypes:int32_range_0-65535-10;
      mandatory true;
      description "range 0..65535.";
    }
    leaf dlChannelBandwidth {
      type int32 {
        range "0 | 1400 | 3000 | 5000 | 10000 | 15000 | 20000";
      }
      config false;
      units "kHz";
    }
    leaf isRemoveAllowed {
      type boolean;
      default "false";
      description "Default value: false.";
    }
    leaf masterEUtranCellFDDId {
      type string {
        length "0..128";
      }
      description "length 0..128.";
    }
    leaf ulChannelBandwidth {
      type int32 {
        range "0 | 1400 | 3000 | 5000 | 10000 | 15000 | 20000";
      }
      config false;
      units "kHz";
    }
    leaf eutranFrequencyRef {
      type string;
      mandatory true;
    }
    list activePlmnList {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf createdBy {
      type enumeration {
        enum ANR;
        enum X2;
        enum OPERATOR;
      }
      config false;
    }
    leaf timeOfCreation {
      type string {
        length "0..19";
      }
      config false;
      description "length 0..19.";
    }
    leaf lastModification {
      type enumeration {
        enum ANR_MODIFICATION;
        enum X2_MODIFICATION;
        enum OPERATOR_MODIFICATION;
        enum ANR_DELETE;
        enum X2_DELETE;
        enum OPERATOR_DELETE;
        enum NOT_MODIFIED;
        enum MRO_MODIFICATION;
        enum PCI_MODIFICATION;
        enum MLB_MODIFICATION;
        enum RACH_OPT_MODIFICATION;
        enum LM_MODIFICATION;
      }
      config false;
    }
    leaf timeOfLastModification {
      type string {
        length "0..19";
      }
      config false;
      description "length 0..19.";
    }
    leaf-list pciConflict {
      type enumeration {
        enum NO;
        enum NO_CONFLICTING_CELL;
        enum YES;
        enum YES_CONFLICTING_CELL;
      }
    }
    list pciConflictCell {
      key "id";
      leaf id {
        type uint32;
        description "Synthetic key for struct sequence entry.";
      }
      container attributes {
      leaf enbId {
        type eytypes:int32_range_0-1048575;
        default "0";
        description "range 0..1048575; Default value: 0.";
      }
      leaf cellId {
        type eytypes:int32_range_0-255;
        default "0";
        description "range 0..255; Default value: 0.";
      }
      leaf mcc {
        type eytypes:int32_range_0-999;
        default "1";
        description "range 0..999; Default value: 1.";
      }
      leaf mnc {
        type eytypes:int32_range_0-999;
        default "1";
        description "range 0..999; Default value: 1.";
      }
      leaf mncLength {
        type eytypes:int32_range_2-3;
        default "2";
        description "range 2..3; Default value: 2.";
      }
      }
    }
    list pciDetectingCell {
      key "id";
      leaf id {
        type uint32;
        description "Synthetic key for struct sequence entry.";
      }
      container attributes {
      leaf enbId {
        type eytypes:int32_range_0-1048575;
        default "0";
        description "range 0..1048575; Default value: 0.";
      }
      leaf cellId {
        type eytypes:int32_range_0-255;
        default "0";
        description "range 0..255; Default value: 0.";
      }
      leaf mcc {
        type eytypes:int32_range_0-999;
        default "1";
        description "range 0..999; Default value: 1.";
      }
      leaf mnc {
        type eytypes:int32_range_0-999;
        default "1";
        description "range 0..999; Default value: 1.";
      }
      leaf mncLength {
        type eytypes:int32_range_2-3;
        default "2";
        description "range 2..3; Default value: 2.";
      }
      }
    }
    leaf-list activeServiceAreaId {
      type eytypes:int32_range_0-65535-10;
    }
    leaf lbEUtranCellOffloadCapacity {
      type eytypes:int32_range_0-1000000-18;
      default "1000";
      description "range 0..1000000; Default value: 1000.";
    }
    leaf-list additionalFreqBandList {
      type eytypes:int32_range_1-256;
    }
    leaf freqBand {
      type eytypes:int32_range_1-256;
      config false;
      description "range 1..256.";
    }
    leaf noOfTxAntennas {
      type int32 {
        range "1..2 | 4";
      }
      default "2";
      description "Default value: 2.";
    }
    list mbsfnSubframeAlloc {
      config false;
      container attributes {
      leaf radioframeAllocationPeriod {
        type int32;
      }
      leaf radioframeAllocationOffset {
        type eytypes:int32_range_0-7;
        description "range 0..7.";
      }
      leaf subframeAllocation {
        type int32;
      }
      leaf subframeAllocationOneFrame {
        type string {
          length "6";
        }
        description "length 6..6.";
      }
      leaf subframeAllocationFourFrame {
        type string {
          length "24";
        }
        description "length 24..24.";
      }
      }
    }
    leaf remoteCellState {
      type enumeration {
        enum DISABLED;
        enum ENABLED;
      }
      config false;
    }
    leaf zzzTemporaryExt1 {
      type int32;
      default "-2000000000";
      description "Default value: -2000000000.";
    }
    leaf zzzTemporaryExt2 {
      type int32;
      default "-2000000000";
      description "Default value: -2000000000.";
    }
    leaf zzzTemporaryExt3 {
      type int32;
      default "-2000000000";
      description "Default value: -2000000000.";
    }
    leaf zzzTemporaryExt4 {
      type int32;
      default "-2000000000";
      description "Default value: -2000000000.";
    }
    leaf zzzTemporaryExt5 {
      type int32;
      default "-2000000000";
      description "Default value: -2000000000.";
    }
    leaf remoteCellStateInterEnbUlComp {
      type enumeration {
        enum DISABLED;
        enum ENABLED;
      }
      config false;
    }
    list commonSFAllocList {
      config false;
      container attributes {
      leaf radioframeAllocationPeriod {
        type int32;
      }
      leaf radioframeAllocationOffset {
        type eytypes:int32_range_0-7;
        description "range 0..7.";
      }
      leaf subframeAllocation {
        type int32;
      }
      leaf subframeAllocationOneFrame {
        type string;
      }
      leaf subframeAllocationFourFrame {
        type string;
      }
      leaf sfAllocationFourFrame {
        type eytypes:int32_range_0-16777215;
        description "range 0..16777215.";
      }
      leaf sfAllocationOneFrame {
        type eytypes:int32_range_0-63;
        description "range 0..63.";
      }
      }
    }
    leaf physicalLayerCellId {
      type eytypes:int32_range_0-503;
      config false;
      description "range 0..503.";
    }
    leaf remoteCellStateEranUlComp {
      type enumeration {
        enum DISABLED;
        enum ENABLED;
      }
      config false;
      status deprecated;
      description "Status info: Since 20.Q2. Planned to be removed..";
    }
    leaf mfbiFreqBandIndPrioExt {
      type enumeration {
        enum NOT_BROADCASTED;
        enum BROADCASTED;
        enum NOT_SUPPORTED;
        enum UNDEFINED_VALUE;
      }
      config false;
    }
    leaf caLockDueToHighLoad {
      type boolean;
      config false;
    }
    leaf plmnListVerifiedByX2OrCgi {
      type boolean;
      config false;
    }
    list endcAllowedPlmnList {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf pimcuId {
      type int32;
      config false;
    }
    leaf tandemPimcuId {
      type int32;
      config false;
    }
    leaf pimDetectionRole {
      type enumeration {
        enum AGGRESSOR;
        enum VICTIM;
        enum VICTIM_AND_AGGRESSOR;
      }
      config false;
    }
  }
  grouping ExternalEUtranCellTDD-attributes {
    leaf channelBandwidth {
      type int32 {
        range "0 | 1400 | 3000 | 5000 | 10000 | 15000 | 20000";
      }
      config false;
      units "kHz";
    }
    leaf eutranFrequencyRef {
      type string;
      mandatory true;
    }
    leaf externalEUtranCellTDDId {
      type string;
      mandatory true;
    }
    leaf localCellId {
      type eytypes:int32_range_0-255;
      mandatory true;
      description "range 0..255.";
    }
    leaf physicalLayerCellIdGroup {
      type eytypes:int32_range_0-167;
      mandatory true;
      description "range 0..167.";
    }
    leaf physicalLayerSubCellId {
      type eytypes:int32_range_0-2;
      mandatory true;
      description "range 0..2.";
    }
    leaf-list reservedBy {
      type string;
    }
    leaf tac {
      type eytypes:int32_range_0-65535-10;
      mandatory true;
      description "range 0..65535.";
    }
    leaf userLabel {
      type string {
        length "1..128";
      }
      description "length 1..128.";
    }
    leaf isRemoveAllowed {
      type boolean;
      default "false";
      description "Default value: false.";
    }
    leaf masterEUtranCellTDDId {
      type string {
        length "0..128";
      }
      description "length 0..128.";
    }
    list activePlmnList {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf createdBy {
      type enumeration {
        enum ANR;
        enum X2;
        enum OPERATOR;
      }
      config false;
    }
    leaf timeOfCreation {
      type string {
        length "0..19";
      }
      config false;
      description "length 0..19.";
    }
    leaf lastModification {
      type enumeration {
        enum ANR_MODIFICATION;
        enum X2_MODIFICATION;
        enum OPERATOR_MODIFICATION;
        enum ANR_DELETE;
        enum X2_DELETE;
        enum OPERATOR_DELETE;
        enum NOT_MODIFIED;
        enum MRO_MODIFICATION;
        enum PCI_MODIFICATION;
        enum MLB_MODIFICATION;
        enum RACH_OPT_MODIFICATION;
        enum LM_MODIFICATION;
      }
      config false;
    }
    leaf timeOfLastModification {
      type string {
        length "0..19";
      }
      config false;
      description "length 0..19.";
    }
    leaf zzzTemporary1 {
      type string;
    }
    leaf zzzTemporary2 {
      type string;
    }
    leaf zzzTemporary3 {
      type string;
    }
    leaf zzzTemporary4 {
      type string;
    }
    leaf-list pciConflict {
      type enumeration {
        enum NO;
        enum NO_CONFLICTING_CELL;
        enum YES;
        enum YES_CONFLICTING_CELL;
      }
    }
    list pciConflictCell {
      key "id";
      leaf id {
        type uint32;
        description "Synthetic key for struct sequence entry.";
      }
      container attributes {
      leaf enbId {
        type eytypes:int32_range_0-1048575;
        default "0";
        description "range 0..1048575; Default value: 0.";
      }
      leaf cellId {
        type eytypes:int32_range_0-255;
        default "0";
        description "range 0..255; Default value: 0.";
      }
      leaf mcc {
        type eytypes:int32_range_0-999;
        default "1";
        description "range 0..999; Default value: 1.";
      }
      leaf mnc {
        type eytypes:int32_range_0-999;
        default "1";
        description "range 0..999; Default value: 1.";
      }
      leaf mncLength {
        type eytypes:int32_range_2-3;
        default "2";
        description "range 2..3; Default value: 2.";
      }
      }
    }
    list pciDetectingCell {
      key "id";
      leaf id {
        type uint32;
        description "Synthetic key for struct sequence entry.";
      }
      container attributes {
      leaf enbId {
        type eytypes:int32_range_0-1048575;
        default "0";
        description "range 0..1048575; Default value: 0.";
      }
      leaf cellId {
        type eytypes:int32_range_0-255;
        default "0";
        description "range 0..255; Default value: 0.";
      }
      leaf mcc {
        type eytypes:int32_range_0-999;
        default "1";
        description "range 0..999; Default value: 1.";
      }
      leaf mnc {
        type eytypes:int32_range_0-999;
        default "1";
        description "range 0..999; Default value: 1.";
      }
      leaf mncLength {
        type eytypes:int32_range_2-3;
        default "2";
        description "range 2..3; Default value: 2.";
      }
      }
    }
    leaf zzzTemporary55 {
      type int32;
      default "-2000000000";
      description "Default value: -2000000000.";
    }
    leaf zzzTemporary56 {
      type int32;
      default "-2000000000";
      description "Default value: -2000000000.";
    }
    leaf zzzTemporary57 {
      type int32;
      default "-2000000000";
      description "Default value: -2000000000.";
    }
    leaf-list activeServiceAreaId {
      type eytypes:int32_range_0-65535-10;
    }
    leaf lbEUtranCellOffloadCapacity {
      type eytypes:int32_range_0-1000000-18;
      default "1000";
      description "range 0..1000000; Default value: 1000.";
    }
    leaf-list additionalFreqBandList {
      type eytypes:int32_range_1-256;
    }
    leaf freqBand {
      type eytypes:int32_range_1-256;
      config false;
      description "range 1..256.";
    }
    leaf subframeAssignment {
      type eytypes:int32_range_-1-6;
      config false;
      description "range -1..6.";
    }
    leaf remoteCellState {
      type enumeration {
        enum DISABLED;
        enum ENABLED;
      }
      config false;
    }
    leaf remoteCellStateInterEnbUlComp {
      type enumeration {
        enum DISABLED;
        enum ENABLED;
      }
      config false;
    }
    list commonSFAllocList {
      config false;
      container attributes {
      leaf radioframeAllocationPeriod {
        type int32;
      }
      leaf radioframeAllocationOffset {
        type eytypes:int32_range_0-7;
        description "range 0..7.";
      }
      leaf subframeAllocation {
        type int32;
      }
      leaf subframeAllocationOneFrame {
        type string;
      }
      leaf subframeAllocationFourFrame {
        type string;
      }
      leaf sfAllocationFourFrame {
        type eytypes:int32_range_0-16777215;
        description "range 0..16777215.";
      }
      leaf sfAllocationOneFrame {
        type eytypes:int32_range_0-63;
        description "range 0..63.";
      }
      }
    }
    leaf physicalLayerCellId {
      type eytypes:int32_range_0-503;
      config false;
      description "range 0..503.";
    }
    leaf specialSubframePattern {
      type int32 {
        range "-1..8";
      }
      config false;
      description "range -1..8.";
    }
    leaf remoteCellStateEranUlComp {
      type enumeration {
        enum DISABLED;
        enum ENABLED;
      }
      config false;
      status deprecated;
      description "Status info: Since 20.Q2. Planned to be removed..";
    }
    leaf mfbiFreqBandIndPrioExt {
      type enumeration {
        enum NOT_BROADCASTED;
        enum BROADCASTED;
        enum NOT_SUPPORTED;
        enum UNDEFINED_VALUE;
      }
      config false;
    }
    leaf caLockDueToHighLoad {
      type boolean;
      config false;
    }
    leaf plmnListVerifiedByX2OrCgi {
      type boolean;
      config false;
    }
    list endcAllowedPlmnList {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
  }
  grouping ExternalEUtranCellUnlicensed-attributes {
    leaf externalEUtranCellUnlicensedId {
      type string;
      mandatory true;
    }
    leaf freqBand {
      type eytypes:int32_range_1-256;
      config false;
      description "range 1..256.";
    }
    leaf localCellId {
      type eytypes:int32_range_0-255;
      mandatory true;
      description "range 0..255.";
    }
    leaf physicalLayerCellId {
      type eytypes:int32_range_0-503;
      config false;
      description "range 0..503.";
    }
    leaf physicalLayerCellIdGroup {
      type eytypes:int32_range_0-167;
      mandatory true;
      description "range 0..167.";
    }
    leaf physicalLayerSubCellId {
      type eytypes:int32_range_0-2;
      mandatory true;
      description "range 0..2.";
    }
    leaf remoteCellState {
      type enumeration {
        enum DISABLED;
        enum ENABLED;
      }
      config false;
    }
    leaf-list reservedBy {
      type string;
    }
    leaf timeOfCreation {
      type string {
        length "0..19";
      }
      config false;
      description "length 0..19.";
    }
    leaf timeOfLastModification {
      type string {
        length "0..19";
      }
      config false;
      description "length 0..19.";
    }
    leaf uniqueCellId {
      type int32 {
        range "0..268435455";
      }
      config false;
      description "range 0..268435455.";
    }
    leaf userLabel {
      type string {
        length "1..128";
      }
      description "length 1..128.";
    }
    leaf zzzTemporaryExt1 {
      type string;
    }
    leaf zzzTemporaryExt2 {
      type string;
    }
    leaf zzzTemporaryExt3 {
      type string;
    }
    leaf lastModification {
      type enumeration {
        enum ANR_MODIFICATION;
        enum X2_MODIFICATION;
        enum OPERATOR_MODIFICATION;
        enum ANR_DELETE;
        enum X2_DELETE;
        enum OPERATOR_DELETE;
        enum NOT_MODIFIED;
        enum MRO_MODIFICATION;
        enum PCI_MODIFICATION;
        enum MLB_MODIFICATION;
        enum RACH_OPT_MODIFICATION;
        enum LM_MODIFICATION;
      }
      config false;
    }
  }
  grouping ExternalGeranCell-attributes {
    leaf externalGeranCellId {
      type string;
      mandatory true;
    }
    leaf-list reservedBy {
      type string;
    }
    list plmnIdentity {
      key "id";
      leaf id {
        type uint32;
        description "Synthetic key for struct entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf lac {
      type int32 {
        range "1..65533 | 65535";
      }
      mandatory true;
    }
    leaf cellIdentity {
      type eytypes:int32_range_0-65535-10;
      mandatory true;
      description "range 0..65535.";
    }
    leaf bcc {
      type eytypes:int32_range_0-7;
      mandatory true;
      description "range 0..7.";
    }
    leaf ncc {
      type eytypes:int32_range_0-7;
      mandatory true;
      description "range 0..7.";
    }
    leaf userLabel {
      type string {
        length "1..128";
      }
      description "length 1..128.";
    }
    leaf createdBy {
      type enumeration {
        enum OPERATOR;
        enum ANR;
      }
      config false;
    }
    leaf timeOfCreation {
      type string {
        length "0..19";
      }
      config false;
      description "length 0..19.";
    }
    leaf masterGeranCellId {
      type string {
        length "0..128";
      }
      description "length 0..128.";
    }
    leaf rimCapable {
      type enumeration {
        enum RIM_CAPABLE;
        enum RIM_INCAPABLE;
        enum RIM_CAPABILITY_UNKNOWN;
      }
    }
    leaf rimAssociationStatus {
      type enumeration {
        enum RIM_ACTIVE;
        enum RIM_INACTIVE;
        enum RIM_STOPPED;
      }
      config false;
    }
    leaf zzzTemporary1 {
      type string;
    }
    leaf zzzTemporary2 {
      type string;
    }
    leaf zzzTemporary3 {
      type string;
    }
    leaf zzzTemporary4 {
      type string;
    }
    leaf zzzTemporary5 {
      type int32;
      default "-2000000000";
      description "Default value: -2000000000.";
    }
    leaf isRemoveAllowed {
      type boolean;
      default "true";
      description "Default value: true.";
    }
    leaf lastModification {
      type enumeration {
        enum ANR_MODIFICATION;
        enum OPERATOR_MODIFICATION;
        enum NOT_MODIFIED;
        enum ANR_DELETE;
        enum OPERATOR_DELETE;
      }
      config false;
    }
    leaf timeOfLastModification {
      type string {
        length "0..19";
      }
      config false;
      description "length 0..19.";
    }
    leaf rac {
      type eytypes:int32_range_-1-255;
      default "-1";
      description "range -1..255; Default value: -1.";
    }
    leaf dtmSupport {
      type ietfinet:port-number;
    }
    leaf geranFrequencyRef {
      type string;
    }
    leaf zzzTemporary8 {
      type int32;
      default "-2000000000";
      description "Default value: -2000000000.";
    }
    leaf zzzTemporary9 {
      type int32;
      default "-2000000000";
      description "Default value: -2000000000.";
    }
    leaf zzzTemporary10 {
      type int32;
      default "-2000000000";
      description "Default value: -2000000000.";
    }
    leaf zzzTemporary11 {
      type int32;
      default "-2000000000";
      description "Default value: -2000000000.";
    }
    leaf zzzTemporary12 {
      type int32;
      default "-2000000000";
      description "Default value: -2000000000.";
    }
    leaf pmRimAssocSucc {
      type uint32;
      config false;
    }
    leaf pmZtemporary99 {
      type uint32;
      config false;
    }
    leaf pmZtemporary98 {
      type uint32;
      config false;
    }
    leaf pmRimAssocAtt {
      type uint32;
      config false;
    }
    leaf pmRimAssocTO {
      type uint32;
      config false;
    }
    leaf pmRimUpdateReceived {
      type uint32;
      config false;
    }
    leaf pmRimUpdateAckSent {
      type uint32;
      config false;
    }
    leaf pmRimReportErr {
      type ietfinet:port-number;
      config false;
    }
    leaf pmRimAssocRemoved {
      type uint32;
      config false;
    }
    leaf pmRimAssocAttRetry {
      type uint32;
      config false;
    }
  }
  grouping ExternalGNodeBDuPartner-attributes {
    leaf externalGNodeBDuPartnerId {
      type string;
      mandatory true;
    }
    leaf gNBDuPartnerId {
      type eytypes:int64_range_0-68719476735;
      config false;
      description "range 0..68719476735.";
    }
    leaf gNBDuPartnerName {
      type string {
        length "0..256";
      }
      config false;
      description "length 0..256.";
    }
  }
  grouping ExternalGNodeBFunction-attributes {
    leaf externalGNodeBFunctionId {
      type string;
      mandatory true;
    }
    leaf userLabel {
      type string {
        length "1..128";
      }
      description "length 1..128.";
    }
    leaf gNBId {
      type eytypes:int32_range_-1-1048575;
      status deprecated;
      default "-1";
      description "range -1..1048575; Default value: -1; MOM flags: restricted; Status info: Since 18.Q3. Planned to be removed..";
    }
    list gNodeBPlmnId {
      key "id";
      leaf id {
        type uint32;
        description "Synthetic key for struct entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf gNodeBIdLength {
      type eytypes:int32_range_22-32;
      default "22";
      description "range 22..32; Default value: 22.";
    }
    leaf gNodeBId {
      type eytypes:int64_range_0-4294967295;
      mandatory true;
      description "range 0..4294967295.";
    }
    leaf createdBy {
      type enumeration {
        enum ANR;
        enum X2;
        enum OPERATOR;
      }
      config false;
    }
    leaf timeOfCreation {
      type string {
        length "0..19";
      }
      config false;
      description "length 0..19.";
    }
    leaf eNBVlanPortRef {
      type ietfinet:port-number;
    }
    leaf dirDataPathAvail {
      type boolean;
      default "true";
      description "Default value: true.";
    }
    leaf independentGapConfigSupported {
      type ietfinet:port-number;
      description "Default value: false.";
    }
    leaf pimDetectionCandidateRate {
      type eytypes:int32_range_0-100-3;
      config false;
      description "range 0..100.";
    }
    leaf pimDetectionRemoteSelected {
      type boolean;
      default "false";
      description "Default value: false.";
    }
  }
  grouping ExternalGUtranCell-attributes {
    leaf externalGUtranCellId {
      type string;
      mandatory true;
    }
    leaf-list reservedBy {
      type string;
    }
    leaf gUtranSyncSignalFrequencyRef {
      type string;
    }
    leaf physicalLayerCellIdGroup {
      type int32 {
        range "0..335";
      }
      mandatory true;
      description "range 0..335.";
    }
    leaf physicalLayerSubCellId {
      type eytypes:int32_range_0-2;
      mandatory true;
      description "range 0..2.";
    }
    leaf localCellId {
      type eytypes:int32_range_0-16383;
      mandatory true;
      description "range 0..16383.";
    }
    leaf absTimeOffset {
      type int32 {
        range "0..999999";
      }
      default "0";
      units "ns";
      description "range 0..999999; Default value: 0.";
    }
    leaf absSubFrameOffset {
      type int32 {
        range "0..10239";
      }
      default "0";
      units "ms";
      description "range 0..10239; Default value: 0.";
    }
    leaf pointAArfcnDl {
      type int32 {
        range "-1..3279165";
      }
      config false;
      description "range -1..3279165.";
    }
    leaf pointAArfcnUl {
      type int32 {
        range "-1..3279165";
      }
      config false;
      description "range -1..3279165.";
    }
    list transmissionBwDl {
      config false;
      container attributes {
      leaf noOfResourceBlocks {
        type int32;
      }
      leaf subCarrierSpacing {
        type int32;
        units "kHz";
      }
      }
    }
    list transmissionBwUl {
      config false;
      container attributes {
      leaf noOfResourceBlocks {
        type int32;
      }
      leaf subCarrierSpacing {
        type int32;
        units "kHz";
      }
      }
    }
    leaf serviceStatus {
      type enumeration {
        enum OUT_OF_SERVICE;
        enum IN_SERVICE;
      }
      config false;
    }
    leaf cellState {
      type enumeration {
        enum IDLE;
        enum INACTIVE;
        enum ACTIVE;
      }
      config false;
    }
    leaf-list bandList {
      type eytypes:int32_range_1-1024;
    }
    list plmnIdList {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf isRemoveAllowed {
      type boolean;
      default "false";
      description "Default value: false.";
    }
    leaf createdBy {
      type enumeration {
        enum ANR;
        enum X2;
        enum OPERATOR;
      }
      config false;
    }
    leaf timeOfCreation {
      type string {
        length "0..19";
      }
      config false;
      description "length 0..19.";
    }
    leaf configuredTAC {
      type int32 {
        range "-1..65535";
      }
      config false;
      description "range -1..65535.";
    }
    leaf nRTAC {
      type eytypes:int32_range_-1-16777215;
      description "range -1..16777215.";
    }
    leaf nRPCI {
      type int32;
      config false;
    }
    leaf smtcDuration {
      type eytypes:int32_range_0-5-32;
      default "0";
      units "ms";
      description "range 0..5; Default value: 0.";
    }
    leaf smtcOffset {
      type int32 {
        range "-1..159";
      }
      default "-1";
      units "ms";
      description "range -1..159; Default value: -1.";
    }
    leaf smtcPeriodicity {
      type int32 {
        range "0 | 5 | 10 | 20 | 40 | 80 | 160";
      }
      default "0";
      units "ms";
      description "Default value: 0.";
    }
    leaf b1ThrRsrpCellOffset {
      type eytypes:int32_range_-30-30;
      default "0";
      units "dB";
      description "range -30..30; Default value: 0.";
    }
    leaf b1ThrRsrqCellOffset {
      type eytypes:int32_range_-230-230;
      default "0";
      units "dB";
      description "range -230..230; Default value: 0.";
    }
    leaf-list pciConflict {
      type enumeration {
        enum NO;
        enum NO_CONFLICTING_CELL;
        enum YES;
        enum YES_CONFLICTING_CELL;
      }
    }
    list pciConflictCell {
      config false;
      container attributes {
      leaf nrCellId {
        type eytypes:int32_range_0-16383;
        default "0";
        description "range 0..16383; Default value: 0.";
      }
      leaf gNodeBId {
        type eytypes:int64_range_0-4294967295;
        default "0";
        description "range 0..4294967295; Default value: 0.";
      }
      leaf gNodeBIdLength {
        type eytypes:int32_range_22-32;
        default "22";
        description "range 22..32; Default value: 22.";
      }
      leaf mcc {
        type eytypes:int32_range_0-999;
        default "1";
        description "range 0..999; Default value: 1.";
      }
      leaf mnc {
        type eytypes:int32_range_0-999;
        default "1";
        description "range 0..999; Default value: 1.";
      }
      leaf mncLength {
        type eytypes:int32_range_2-3;
        default "2";
        description "range 2..3; Default value: 2.";
      }
      }
    }
    list pciDetectingCell {
      config false;
      container attributes {
      leaf enbId {
        type eytypes:int32_range_0-1048575;
        default "0";
        description "range 0..1048575; Default value: 0.";
      }
      leaf cellId {
        type eytypes:int32_range_0-255;
        default "0";
        description "range 0..255; Default value: 0.";
      }
      leaf mcc {
        type eytypes:int32_range_0-999;
        default "1";
        description "range 0..999; Default value: 1.";
      }
      leaf mnc {
        type eytypes:int32_range_0-999;
        default "1";
        description "range 0..999; Default value: 1.";
      }
      leaf mncLength {
        type eytypes:int32_range_2-3;
        default "2";
        description "range 2..3; Default value: 2.";
      }
      }
    }
    leaf pimDetectionRole {
      type enumeration {
        enum AGGRESSOR;
        enum VICTIM;
        enum VICTIM_AND_AGGRESSOR;
      }
      config false;
    }
    leaf pmCellBarredBackoffTimer {
      type uint32;
      config false;
    }
  }
  grouping ExternalPimFunction-attributes {
    leaf externalPimFunctionId {
      type string;
      mandatory true;
      status deprecated;
      description "MOM flags: restricted, noNotification; Status info: Since 24.Q1. Planned to be removed..";
    }
    leaf remoteAggressorAllowed {
      type boolean;
      status deprecated;
      default "false";
      description "Default value: false; Status info: Since 24.Q1. Replaced by ExternalENodeBFunction::pimDetectionRemoteSelected. Planned to be removed..";
    }
    leaf operationalState {
      type enumeration {
        enum DISABLED;
        enum ENABLED;
      }
      config false;
      status deprecated;
      description "MOM flags: noNotification; Status info: Since 24.Q1. Planned to be removed.; Specification: ITU-T Rec. X.731.";
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
      description "MOM flags: noNotification; Status info: Since 24.Q1. Planned to be removed.; Specification: ITU-T Rec. X.731.";
    }
  }
  grouping ExternalUtranCellFDD-attributes {
    leaf externalUtranCellFDDId {
      type string;
      mandatory true;
    }
    leaf physicalCellIdentity {
      type eytypes:int32_range_0-511;
      mandatory true;
      description "range 0..511.";
    }
    list cellIdentity {
      key "id";
      leaf id {
        type uint32;
        description "Synthetic key for struct entry.";
      }
      container attributes {
      leaf rncId {
        type int32 {
          range "1..4095";
        }
        description "range 1..4095.";
      }
      leaf cId {
        type eytypes:int32_range_0-65535-10;
        description "range 0..65535.";
      }
      }
    }
    list plmnIdentity {
      key "id";
      leaf id {
        type uint32;
        description "Synthetic key for struct entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf-list reservedBy {
      type string;
    }
    leaf userLabel {
      type string {
        length "1..128";
      }
      description "length 1..128.";
    }
    leaf createdBy {
      type enumeration {
        enum OPERATOR;
        enum ANR;
      }
      config false;
    }
    leaf timeOfCreation {
      type string {
        length "0..19";
      }
      config false;
      description "length 0..19.";
    }
    leaf masterUtranCellId {
      type string {
        length "0..128";
      }
      description "length 0..128.";
    }
    leaf lac {
      type int32 {
        range "0..65533 | 65535";
      }
      default "0";
      description "Default value: 0.";
    }
    leaf rac {
      type eytypes:int32_range_-1-255;
      default "-1";
      description "range -1..255; Default value: -1.";
    }
    leaf lastModification {
      type enumeration {
        enum ANR_MODIFICATION;
        enum OPERATOR_MODIFICATION;
        enum NOT_MODIFIED;
        enum ANR_DELETE;
        enum OPERATOR_DELETE;
        enum LM_MODIFICATION;
      }
      config false;
    }
    leaf timeOfLastModification {
      type string {
        length "0..19";
      }
      config false;
      description "length 0..19.";
    }
    leaf rimCapable {
      type enumeration {
        enum RIM_CAPABLE;
        enum RIM_INCAPABLE;
        enum RIM_CAPABILITY_UNKNOWN;
      }
    }
    leaf rimAssociationStatus {
      type enumeration {
        enum RIM_ACTIVE;
        enum RIM_INACTIVE;
        enum RIM_STOPPED;
      }
      config false;
    }
    leaf isRemoveAllowed {
      type boolean;
      default "false";
      description "Default value: false.";
    }
    leaf srvccCapability {
      type enumeration {
        enum NOT_SUPPORTED;
        enum CS_ONLY_SUPPORTED;
        enum PS_AND_CS_SUPPORTED;
      }
    }
    leaf lbUtranCellOffloadCapacity {
      type eytypes:int32_range_0-1000000-18;
      default "1000";
      description "range 0..1000000; Default value: 1000.";
    }
    leaf zzzTemporary1 {
      type int32;
      default "-2000000000";
      description "Default value: -2000000000.";
    }
    leaf zzzTemporary2 {
      type int32;
      default "-2000000000";
      description "Default value: -2000000000.";
    }
    leaf zzzTemporary3 {
      type int32;
      default "-2000000000";
      description "Default value: -2000000000.";
    }
    leaf zzzTemporary4 {
      type int32;
      default "-2000000000";
      description "Default value: -2000000000.";
    }
    leaf zzzTemporary5 {
      type int32;
      default "-2000000000";
      description "Default value: -2000000000.";
    }
    leaf zzzTemporaryExt1 {
      type int32;
      default "-2000000000";
      description "Default value: -2000000000.";
    }
    leaf zzzTemporaryExt2 {
      type int32;
      default "-2000000000";
      description "Default value: -2000000000.";
    }
    leaf zzzTemporaryExt3 {
      type int32;
      default "-2000000000";
      description "Default value: -2000000000.";
    }
    leaf zzzTemporaryExt4 {
      type int32;
      default "-2000000000";
      description "Default value: -2000000000.";
    }
    leaf zzzTemporaryExt5 {
      type int32;
      default "-2000000000";
      description "Default value: -2000000000.";
    }
    leaf pmZtemporary100 {
      type uint32;
      config false;
    }
    leaf pmRimAssocRemoved {
      type uint32;
      config false;
    }
    leaf pmRimUpdateReceived {
      type uint32;
      config false;
    }
    leaf pmRimAssocTO {
      type uint32;
      config false;
    }
    leaf pmRimAssocAttRetry {
      type uint32;
      config false;
    }
    leaf pmRimAssocAtt {
      type uint32;
      config false;
    }
    leaf pmRimAssocSucc {
      type uint32;
      config false;
    }
    leaf pmRimUpdateAckSent {
      type uint32;
      config false;
    }
    leaf pmRimReportErr {
      type ietfinet:port-number;
      config false;
    }
    leaf pmZtemporary101 {
      type uint32;
      config false;
    }
  }
  grouping ExternalUtranCellTDD-attributes {
    leaf lac {
      type int32 {
        range "0..65533 | 65535";
      }
      default "0";
      description "Default value: 0.";
    }
    leaf rac {
      type eytypes:int32_range_-1-255;
      default "-1";
      description "range -1..255; Default value: -1.";
    }
    leaf lastModification {
      type enumeration {
        enum ANR_MODIFICATION;
        enum OPERATOR_MODIFICATION;
        enum NOT_MODIFIED;
        enum ANR_DELETE;
        enum OPERATOR_DELETE;
        enum LM_MODIFICATION;
      }
      config false;
    }
    leaf timeOfLastModification {
      type string {
        length "0..19";
      }
      config false;
      description "length 0..19.";
    }
    leaf timeOfCreation {
      type string {
        length "0..19";
      }
      config false;
      description "length 0..19.";
    }
    leaf masterUtranCellId {
      type string {
        length "0..128";
      }
      description "length 0..128.";
    }
    leaf createdBy {
      type enumeration {
        enum OPERATOR;
        enum ANR;
      }
      config false;
    }
    leaf externalUtranCellTDDId {
      type string;
      mandatory true;
    }
    leaf physicalCellIdentity {
      type eytypes:int32_range_0-127;
      mandatory true;
      description "range 0..127.";
    }
    list cellIdentity {
      key "id";
      leaf id {
        type uint32;
        description "Synthetic key for struct entry.";
      }
      container attributes {
      leaf rncId {
        type int32 {
          range "1..4095";
        }
        description "range 1..4095.";
      }
      leaf cId {
        type eytypes:int32_range_0-65535-10;
        description "range 0..65535.";
      }
      }
    }
    list plmnIdentity {
      key "id";
      leaf id {
        type uint32;
        description "Synthetic key for struct entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf-list reservedBy {
      type string;
    }
    leaf userLabel {
      type string {
        length "1..128";
      }
      description "length 1..128.";
    }
    leaf rimCapable {
      type enumeration {
        enum RIM_CAPABLE;
        enum RIM_INCAPABLE;
        enum RIM_CAPABILITY_UNKNOWN;
      }
    }
    leaf rimAssociationStatus {
      type enumeration {
        enum RIM_ACTIVE;
        enum RIM_INACTIVE;
        enum RIM_STOPPED;
      }
      config false;
    }
    leaf zzzTemporary1 {
      type string;
    }
    leaf zzzTemporary2 {
      type string;
    }
    leaf zzzTemporary3 {
      type string;
    }
    leaf zzzTemporary4 {
      type string;
    }
    leaf zzzTemporary5 {
      type int32;
      default "-2000000000";
      description "Default value: -2000000000.";
    }
    leaf zzzTemporary6 {
      type int32;
      default "-2000000000";
      description "Default value: -2000000000.";
    }
    leaf zzzTemporary7 {
      type int32;
      default "-2000000000";
      description "Default value: -2000000000.";
    }
    leaf isRemoveAllowed {
      type boolean;
      default "false";
      description "Default value: false.";
    }
    leaf zzzTemporary8 {
      type int32;
      default "-2000000000";
      description "Default value: -2000000000.";
    }
    leaf zzzTemporary9 {
      type int32;
      default "-2000000000";
      description "Default value: -2000000000.";
    }
  }
  grouping FastCoordinationGroup-attributes {
    leaf fastCoordinationGroupId {
      type string;
      mandatory true;
    }
    leaf eranFeatureName {
      type enumeration {
        enum ULCOMP;
        enum DL_CA;
      }
      config false;
    }
    list activeList {
      config false;
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      leaf enbId {
        type eytypes:int32_range_0-1048575;
        description "range 0..1048575.";
      }
      }
    }
    list candidateList {
      config false;
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      leaf enbId {
        type eytypes:int32_range_0-1048575;
        description "range 0..1048575.";
      }
      }
    }
    leaf-list pmEranThpVolDlRecDistr {
      type uint32;
    }
    leaf-list pmEranThpVolDlTransDistr {
      type uint32;
    }
  }
  grouping FlexibleQoSFunction-attributes {
    leaf flexibleQoSFunctionId {
      type string;
      mandatory true;
    }
  }
  grouping FlexibleQoSGroup-attributes {
    leaf flexibleQoSGroupId {
      type string;
      mandatory true;
    }
    leaf qciProfileRef {
      type ietfinet:ip-address;
      mandatory true;
    }
  }
  grouping FlexibleQoSGroupMember-attributes {
    leaf flexibleQoSGroupMemberId {
      type string;
      mandatory true;
    }
    leaf userProfileRef {
      type string;
      mandatory true;
    }
    leaf sciProfileRef {
      type ietfinet:ip-address;
      mandatory true;
    }
  }
  grouping FreqPrioEUtra-attributes {
    leaf endcHoFreqPriority {
      type int32 {
        range "-1000 | -1..7";
      }
      default "-1000";
      description "Default value: -1000.";
    }
    leaf freqPrioEUtraId {
      type string;
      mandatory true;
    }
    leaf interFreqHoHigherPrioAllowed {
      type boolean;
      default "false";
      description "Default value: false.";
    }
    leaf interFreqHoHigherPrioControl {
      type enumeration {
        enum PRIO_ENDC;
        enum PRIO_LTE;
      }
    }
  }
  grouping FreqPrioNR-attributes {
    leaf freqPrioNRId {
      type string;
      mandatory true;
    }
    leaf arfcnValueNRDl {
      type int32 {
        range "-1000 | 0..3279165";
      }
      default "-1000";
      description "Default value: -1000.";
    }
    leaf cellReselectionPrio {
      type int32 {
        range "-1000 | 0..7";
      }
      default "-1000";
      description "Default value: -1000.";
    }
    leaf connModeMobilityPrio {
      type int32 {
        range "-1000 | -1..7";
      }
      default "-1000";
      description "Default value: -1000.";
    }
    leaf voicePrio {
      type int32 {
        range "-1000 | -1..7";
      }
      default "-1000";
      description "Default value: -1000.";
    }
    leaf endcB1MeasPriority {
      type int32 {
        range "-1000 | -1..7";
      }
      default "-1000";
      description "Default value: -1000.";
    }
    leaf cellReselectionSubPrio {
      type int32 {
        range "0 | 2 | 4 | 6 | 8";
      }
      default "0";
      description "Default value: 0.";
    }
  }
  grouping GeranCellRelation-attributes {
    leaf geranCellRelationId {
      type string;
      mandatory true;
    }
    leaf createdBy {
      type enumeration {
        enum OPERATOR;
        enum ANR;
      }
      config false;
    }
    leaf timeOfCreation {
      type string {
        length "0..19";
      }
      config false;
      description "length 0..19.";
    }
    leaf coverageIndicator {
      type enumeration {
        enum NONE;
        enum COVERS;
        enum OVERLAP;
        enum CONTAINED_IN;
      }
    }
    leaf isRemoveAllowed {
      type boolean;
      default "false";
      description "Default value: false.";
    }
    leaf lastModification {
      type enumeration {
        enum ANR_MODIFICATION;
        enum OPERATOR_MODIFICATION;
        enum NOT_MODIFIED;
        enum ANR_DELETE;
        enum OPERATOR_DELETE;
      }
      config false;
    }
    leaf timeOfLastModification {
      type string {
        length "0..19";
      }
      config false;
      description "length 0..19.";
    }
    leaf isHoAllowed {
      type boolean;
      default "true";
      description "Default value: true.";
    }
    leaf extGeranCellRef {
      type string;
    }
    list mobilityStatus {
      config false;
      container attributes {
      leaf available {
        type string;
      }
      leaf reason {
        type string;
      }
      }
    }
    leaf hoSuccLevel {
      type enumeration {
        enum OFF;
        enum HIGH;
        enum MEDIUM;
        enum LOW;
      }
      config false;
    }
    leaf pmHoExeCancel {
      type uint32;
      config false;
    }
    leaf pmHoPrepSucc {
      type uint32;
      config false;
    }
    leaf pmZtemporary95 {
      type uint32;
      config false;
    }
    leaf pmHoPrepAtt {
      type uint32;
      config false;
    }
    leaf pmHoPrepCancel {
      type uint32;
      config false;
    }
    leaf pmZtemporary94 {
      type uint32;
      config false;
    }
    leaf pmHoExeSucc {
      type uint32;
      config false;
    }
    leaf pmHoExeAtt {
      type uint32;
      config false;
    }
    leaf pmHoPrepCancelReest {
      type uint32;
      config false;
    }
  }
  grouping GeraNetwork-attributes {
    leaf geraNetworkId {
      type string;
      mandatory true;
    }
    leaf userLabel {
      type string {
        length "1..128";
      }
      description "length 1..128.";
    }
  }
  grouping GeranFreqGroup-attributes {
    leaf geranFreqGroupId {
      type string;
      mandatory true;
    }
    leaf userLabel {
      type string {
        length "1..128";
      }
      description "length 1..128.";
    }
    leaf-list reservedBy {
      type string;
    }
    leaf frequencyGroupId {
      type int32 {
        range "0..1024";
      }
      mandatory true;
      description "range 0..1024.";
    }
  }
  grouping GeranFreqGroupRelation-attributes {
    leaf geranFreqGroupRelationId {
      type string;
      mandatory true;
    }
    leaf userLabel {
      type string {
        length "1..128";
      }
      description "length 1..128.";
    }
    leaf geranFreqGroupRef {
      type string;
      mandatory true;
    }
    leaf qRxLevMin {
      type int32 {
        range "-115..-25";
      }
      default "-115";
      units "dBm";
      description "range -115..-25; Default value: -115.";
    }
    leaf pMaxGeran {
      type int32 {
        range "0..39 | 1000";
      }
      default "1000";
      description "Default value: 1000.";
    }
    leaf threshXHigh {
      type eytypes:int32_range_0-62-22;
      default "4";
      description "range 0..62; Default value: 4.";
    }
    leaf threshXLow {
      type eytypes:int32_range_0-62-22;
      default "0";
      description "range 0..62; Default value: 0.";
    }
    leaf nccPermitted {
      type string {
        length "8";
      }
      default "11111111";
      description "length 8..8; Default value: 11111111.";
    }
    leaf cellReselectionPriority {
      type eytypes:int32_range_0-7;
      default "5";
      description "range 0..7; Default value: 5.";
    }
    list allowedPlmnList {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf csFallbackPrio {
      type eytypes:int32_range_-1-7;
      default "0";
      description "range -1..7; Default value: 0.";
    }
    leaf connectedModeMobilityPrio {
      type eytypes:int32_range_-1-7;
      default "5";
      description "range -1..7; Default value: 5.";
    }
    leaf qOffsetFreq {
      type eytypes:int32_range_-15-15;
      default "0";
      units "dB";
      description "range -15..15; Default value: 0.";
    }
    leaf csFallbackPrioEC {
      type eytypes:int32_range_-1-7;
      default "0";
      description "range -1..7; Default value: 0.";
    }
    leaf mobilityActionCsfb {
      type enumeration {
        enum RELEASE_WITH_REDIRECT;
        enum RELEASE_WITH_REDIRECT_NACC;
      }
    }
    leaf mobilityAction {
      type enumeration {
        enum RELEASE_WITH_REDIRECT;
        enum RELEASE_WITH_REDIRECT_NACC;
      }
    }
    leaf anrMeasOn {
      type boolean;
      default "true";
      description "Default value: true.";
    }
    leaf voicePrio {
      type eytypes:int32_range_-1-7;
      default "0";
      description "range -1..7; Default value: 0.";
    }
    leaf altCsfbTargetPrio {
      type eytypes:int32_range_-1-7;
      default "0";
      description "range -1..7; Default value: 0.";
    }
    leaf altCsfbTargetPrioEc {
      type eytypes:int32_range_-1-7;
      default "0";
      description "range -1..7; Default value: 0.";
    }
    leaf b2Thr1RsrpGeranFreqOffset {
      type eytypes:int32_range_-100-100;
      default "0";
      units "dB";
      description "range -100..100; Default value: 0.";
    }
    leaf b2Thr1RsrqGeranFreqOffset {
      type eytypes:int32_range_-240-240;
      default "0";
      units "dB";
      description "range -240..240; Default value: 0.";
    }
    leaf b2Thr2GeranFreqOffset {
      type eytypes:int32_range_-24-24;
      default "0";
      units "dB";
      description "range -24..24; Default value: 0.";
    }
    list qciB2ThrOffsets {
      key "id";
      leaf id {
        type uint32;
        description "Synthetic key for struct sequence entry.";
      }
      container attributes {
      leaf qciProfileRef {
        type ietfinet:ip-address;
      }
      leaf b2Thr1RsrpGeranFreqQciOffset {
        type eytypes:int32_range_-100-100;
        default "0";
        units "dB";
        description "range -100..100; Default value: 0.";
      }
      leaf b2Thr1RsrqGeranFreqQciOffset {
        type eytypes:int32_range_-240-240;
        default "0";
        units "dB";
        description "range -240..240; Default value: 0.";
      }
      leaf b2Thr2GeranFreqQciOffset {
        type eytypes:int32_range_-24-24;
        default "0";
        units "dB";
        description "range -24..24; Default value: 0.";
      }
      }
    }
    list b2GeranOffsetPerPC {
      key "id";
      leaf id {
        type uint32;
        description "Synthetic key for struct sequence entry.";
      }
      container attributes {
      leaf powerClass {
        type enumeration {
          enum PC_1;
          enum PC_2;
        }
      }
      leaf b2Thr1RsrpGeranPCOffset {
        type eytypes:int32_range_-100-100;
        default "0";
        units "dB";
        description "range -100..100; Default value: 0.";
      }
      leaf b2Thr1RsrqGeranPCOffset {
        type eytypes:int32_range_-240-240;
        default "0";
        units "dB";
        description "range -240..240; Default value: 0.";
      }
      }
    }
  }
  grouping GeranFrequency-attributes {
    leaf geranFrequencyId {
      type string;
      mandatory true;
    }
    leaf userLabel {
      type string {
        length "1..128";
      }
      description "length 1..128.";
    }
    leaf bandIndicator {
      type enumeration {
        enum DCS_1800;
        enum PCS_1900;
      }
    }
    leaf arfcnValueGeranDl {
      type eytypes:int32_range_0-1023-23;
      mandatory true;
      description "range 0..1023.";
    }
    leaf-list geranFreqGroupRef {
      type string;
    }
    leaf-list reservedBy {
      type string;
    }
  }
  grouping GtpPath-attributes {
    leaf remoteIpAddress {
      type ietfinet:ip-address;
      config false;
      description "length 2..39.";
    }
    leaf localIpAddress {
      type ietfinet:ip-address;
      config false;
      description "length 2..39.";
    }
    leaf samplingInterval {
      type int32;
      config false;
      units "ms";
    }
    leaf echoPeerStatus {
      type enumeration {
        enum UNKNOWN;
        enum REACHABLE;
        enum UNREACHABLE;
      }
      config false;
    }
    leaf operationalState {
      type enumeration {
        enum DISABLED;
        enum ENABLED;
      }
      config false;
    }
    leaf gtpPathId {
      type string;
      mandatory true;
    }
    leaf pmPDVFwdMax {
      type int32;
      config false;
    }
    leaf pmRTDMax {
      type int32;
      config false;
    }
    leaf pmRTDMin {
      type int32;
      config false;
    }
    leaf pmEchoRespAccRcvd {
      type uint32;
      config false;
    }
    leaf pmRTD99p {
      type int32;
      config false;
    }
    leaf-list pmRTDDistr {
      type uint32;
    }
    leaf pmEchoRespNotRcvd {
      type uint32;
      config false;
    }
    leaf pmEchoReqSent {
      type uint32;
      config false;
    }
    leaf pmPDVFwdAvg {
      type int32;
      config false;
    }
    leaf pmRTDAvg {
      type int32;
      config false;
    }
    leaf pmEchoRespRejRcvd {
      type uint32;
      config false;
    }
    leaf pmPDVFwd99p {
      type int32;
      config false;
    }
  }
  grouping GtpuApplicationTunnel-attributes {
    leaf gtpuApplicationTunnelId {
      type string;
      mandatory true;
    }
  }
  grouping GUtraFreqRelProfile-attributes {
    leaf-list ueProfileFilterRefList {
      type string;
      ordered-by user;
    }
    leaf cellReselectionPrio {
      type int32 {
        range "-1000 | -1..7";
      }
      default "-1000";
      description "Default value: -1000.";
    }
    leaf connModeMobilityPrio {
      type int32 {
        range "-1000 | -1..7";
      }
      default "-1000";
      description "Default value: -1000.";
    }
    leaf endcB1MeasPriority {
      type int32 {
        range "-1000 | -1..7";
      }
      default "-1000";
      description "Default value: -1000.";
    }
    leaf gUtraFreqRelProfileId {
      type string;
      mandatory true;
    }
    leaf voicePrio {
      type int32 {
        range "-1000 | -1..7";
      }
      default "-1000";
      description "Default value: -1000.";
    }
    leaf-list ueProfileFilterRef {
      type string;
      ordered-by user;
    }
    leaf cellReselectionSubPrio {
      type int32 {
        range "0 | 2 | 4 | 6 | 8";
      }
      default "0";
      description "Default value: 0.";
    }
  }
  grouping GUtraFreqRelProfileSet-attributes {
    leaf gUtraFreqRelProfileSetId {
      type string;
      mandatory true;
    }
    leaf-list reservedBy {
      type string;
    }
  }
  grouping GUtranCellRelation-attributes {
    leaf createdBy {
      type enumeration {
        enum ANR;
        enum X2;
        enum OPERATOR;
      }
      config false;
    }
    leaf gUtranCellRelationId {
      type string;
      mandatory true;
    }
    leaf isRemoveAllowed {
      type boolean;
      default "false";
      description "Default value: false.";
    }
    leaf neighborCellRef {
      type string;
      mandatory true;
    }
    leaf userLabel {
      type string {
        length "1..128";
      }
      description "length 1..128.";
    }
    leaf essEnabled {
      type boolean;
      default "false";
      description "Default value: false.";
    }
    leaf timeOfCreation {
      type string {
        length "0..19";
      }
      config false;
      description "length 0..19.";
    }
    leaf-list reservedBy {
      type string;
    }
    list essCellScPairs {
      config false;
      container attributes {
      leaf eNBessLocalScId {
        type int32 {
          range "0..99999";
        }
        description "range 0..99999.";
      }
      leaf gNBessLocalScId {
        type int32 {
          range "0..99999";
        }
        description "range 0..99999.";
      }
      leaf essScPairId {
        type int64 {
          range "0..9223372036854775807";
        }
        description "range 0..9223372036854775807.";
      }
      }
    }
    leaf isHoAllowed {
      type boolean;
      default "true";
      description "Default value: true.";
    }
    list mobilityStatusNR {
      config false;
      container attributes {
      leaf available {
        type boolean;
        default "true";
        description "Default value: true.";
      }
      leaf reason {
        type string;
      }
      }
    }
    leaf isVoiceHoAllowed {
      type boolean;
      default "true";
      description "Default value: true.";
    }
    leaf isEndcAllowed {
      type boolean;
      default "true";
      description "Default value: true.";
    }
    leaf coverageIndicator {
      type enumeration {
        enum NONE;
        enum COVERS;
        enum OVERLAP;
        enum CONTAINED_IN;
      }
    }
    leaf pmHoPrepAtt {
      type uint32;
      config false;
    }
    leaf pmHoPrepSucc {
      type uint32;
      config false;
    }
    leaf pmHoExeAtt {
      type uint32;
      config false;
    }
    leaf pmEndcSetupNStrCellUeSucc {
      type uint32;
      config false;
    }
    leaf pmEndcSetupScgUeAtt {
      type uint32;
      config false;
    }
    leaf pmHoExeSucc {
      type uint32;
      config false;
    }
    leaf pmEndcSetupFailUeCap {
      type uint32;
      config false;
    }
    leaf pmEndcSetupFailNrRa {
      type uint32;
      config false;
    }
    leaf pmEndcSetupUeAtt {
      type uint32;
      config false;
    }
    leaf pmEndcSetupNStrCellUeAtt {
      type uint32;
      config false;
    }
    leaf pmEndcSetupScgUeSucc {
      type uint32;
      config false;
    }
    leaf pmEndcRelShortScgSession {
      type uint32;
      config false;
    }
    leaf pmEndcSetupUeSucc {
      type uint32;
      config false;
    }
  }
  grouping GUtraNetwork-attributes {
    leaf userLabel {
      type string {
        length "1..128";
      }
      description "length 1..128.";
    }
    leaf gUtraNetworkId {
      type string;
      mandatory true;
    }
    leaf simpleGUtranFreqSmtc {
      type boolean;
    }
  }
  grouping GUtranFreqRelation-attributes {
    leaf gUtranFreqRelationId {
      type string;
      mandatory true;
    }
    leaf gUtranSyncSignalFrequencyRef {
      type string;
      mandatory true;
    }
    leaf cellReselectionPriority {
      type eytypes:int32_range_-1-7;
      default "2";
      description "range -1..7; Default value: 2.";
    }
    leaf threshXHigh {
      type eytypes:int32_range_0-62;
      default "4";
      units "dB";
      description "range 0..62; Default value: 4.";
    }
    leaf threshXLow {
      type eytypes:int32_range_0-62;
      default "0";
      units "dB";
      description "range 0..62; Default value: 0.";
    }
    leaf threshXHighQ {
      type eytypes:int32_range_0-31;
      default "0";
      units "dB";
      description "range 0..31; Default value: 0.";
    }
    leaf threshXLowQ {
      type eytypes:int32_range_0-31;
      default "0";
      units "dB";
      description "range 0..31; Default value: 0.";
    }
    leaf qRxLevMin {
      type eytypes:int32_range_-140--44;
      default "-140";
      units "dBm";
      description "range -140..-44; Default value: -140.";
    }
    leaf pMaxNR {
      type int32 {
        range "-30..33";
      }
      default "33";
      units "dBm";
      description "range -30..33; Default value: 33.";
    }
    leaf qQualMin {
      type int32 {
        range "-43..-3 | 0";
      }
      default "0";
      units "dB";
      description "Default value: 0.";
    }
    leaf deriveSsbIndexFromCell {
      type boolean;
      default "false";
      description "Default value: false.";
    }
    leaf connectedModeMobilityPrio {
      type eytypes:int32_range_-1-7;
      default "6";
      description "range -1..7; Default value: 6.";
    }
    leaf qOffsetFreq {
      type eytypes:int32_range_-15-15;
      default "0";
      units "dB";
      description "range -15..15; Default value: 0.";
    }
    list allowedPlmnList {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf reportConfigB1Ref {
      type ietfinet:port-number;
      status deprecated;
      description "Takes effect: New connection; MOM flags: isNillable=true; Status info: Since 19.Q4. Has no functional behavior. Planned to be removed..";
      reference "Takes effect: New connection.";
    }
    leaf reportConfigB1EndcRef {
      type ietfinet:port-number;
      status deprecated;
      description "Takes effect: New connection; MOM flags: isNillable=true; Status info: Since 19.Q4. Has no functional behavior. Planned to be removed..";
      reference "Takes effect: New connection.";
    }
    leaf endcB1MeasPriority {
      type eytypes:int32_range_-1-7;
      default "4";
      description "range -1..7; Default value: 4.";
    }
    leaf b1ThrRsrpFreqOffset {
      type eytypes:int32_range_-30-30;
      default "0";
      units "dB";
      description "range -30..30; Default value: 0.";
    }
    leaf b1ThrRsrqFreqOffset {
      type eytypes:int32_range_-230-230;
      default "0";
      units "dB";
      description "range -230..230; Default value: 0.";
    }
    leaf anrMeasOn {
      type boolean;
      default "true";
      description "Default value: true.";
    }
    leaf cellReselectionSubPriority {
      type int32 {
        range "0 | 2 | 4 | 6 | 8";
      }
      default "0";
      description "Default value: 0.";
    }
    leaf timeToTriggerB1Override {
      type int32 {
        range "-1000 | 0 | 40 | 64 | 80 | 100 | 128 | 160 | 256 | 320 | 480 | 512 | 640 | 1024 | 1280 | 2560 | 5120";
      }
      default "-1000";
      units "ms";
      description "Default value: -1000.";
    }
    leaf triggerQuantityGUtraOverride {
      type enumeration {
        enum NO_OVERRIDE;
        enum SS_RSRP;
        enum SS_RSRQ;
      }
    }
    leaf triggerQuantityB1Override {
      type enumeration {
        enum NO_OVERRIDE;
        enum SS_RSRP;
        enum SS_RSRQ;
      }
    }
    leaf timeToTriggerNrB1Override {
      type int32 {
        range "-1000 | 0 | 40 | 64 | 80 | 100 | 128 | 160 | 256 | 320 | 480 | 512 | 640 | 1024 | 1280 | 2560 | 5120";
      }
      status deprecated;
      default "-1000";
      units "ms";
      description "Default value: -1000; Takes effect: New connection; Status info: Since 23.Q4. Replaced by timeToTriggerNrB1B2Override. Planned to be removed..";
      reference "Takes effect: New connection.";
    }
    leaf voicePrio {
      type eytypes:int32_range_-1-7;
      default "0";
      description "range -1..7; Default value: 0.";
    }
    leaf gUtraFreqRelProfileSetRef {
      type string;
    }
    leaf mobilityAction {
      type enumeration {
        enum RELEASE_WITH_REDIRECT;
        enum HANDOVER;
      }
    }
    leaf-list endcNotAllowedEUtranFreqRef {
      type string;
      ordered-by user;
    }
    leaf cellAddRsrpThrNROverride {
      type int32 {
        range "-1000 | -156..-29";
      }
      default "-1000";
      units "dBm";
      description "Default value: -1000.";
    }
    leaf cellAddRsrqThrNROverride {
      type int32 {
        range "-1000 | -435..200";
      }
      default "-1000";
      units "dB";
      description "Default value: -1000.";
    }
    leaf timeToTriggerNrB1B2Override {
      type int32 {
        range "-1000 | 0 | 40 | 64 | 80 | 100 | 128 | 160 | 256 | 320 | 480 | 512 | 640 | 1024 | 1280 | 2560 | 5120";
      }
      default "-1000";
      units "ms";
      description "Default value: -1000.";
    }
    leaf pmEndcFreqBlocklistUeCapFail {
      type uint32;
      config false;
    }
    leaf pmConnModeMobilityExcluded {
      type uint32;
      config false;
    }
    leaf pmAnrNrNoActionTooWeak {
      type uint32;
      config false;
    }
    leaf pmEndcFreqBlocklistRaFail {
      type uint32;
      config false;
    }
    leaf pmIdleModeMobilityExcluded {
      type uint32;
      config false;
    }
    leaf pmEndcDistrFreqSel {
      type uint32;
      config false;
    }
  }
  grouping GUtranSyncSignalFrequency-attributes {
    leaf gUtranSyncSignalFrequencyId {
      type string;
      mandatory true;
    }
    leaf userLabel {
      type string {
        length "1..128";
      }
      description "length 1..128.";
    }
    leaf-list reservedBy {
      type string;
    }
    leaf gscn {
      type int32 {
        range "1..28557";
      }
      config false;
      description "range 1..28557.";
    }
    leaf band {
      type int32 {
        range "-1 | 1..512";
      }
      default "-1";
      description "Default value: -1.";
    }
    leaf arfcn {
      type eytypes:int32_range_0-3279165;
      default "630000";
      description "range 0..3279165; Default value: 630000.";
    }
    leaf smtcPeriodicity {
      type int32 {
        range "5 | 10 | 20 | 40 | 80 | 160";
      }
      default "20";
      units "subframe";
      description "Default value: 20.";
    }
    leaf smtcOffset {
      type int32 {
        range "0..159";
      }
      default "0";
      units "subframe";
      description "range 0..159; Default value: 0.";
    }
    leaf smtcDuration {
      type int32 {
        range "1..5";
      }
      default "5";
      units "subframe";
      description "range 1..5; Default value: 5.";
    }
    leaf smtcScs {
      type int32 {
        range "15 | 30 | 120 | 240";
      }
      default "30";
      units "kHz";
      description "Default value: 30.";
    }
    leaf-list bandList {
      type eytypes:int32_range_1-1024;
    }
  }
  grouping HoWhiteList-attributes {
    leaf-list spidList {
      type int32 {
        range "-1000 | 1..256";
      }
    }
    leaf hoWhiteListId {
      type string;
      mandatory true;
    }
    leaf userLabel {
      type string {
        length "1..128";
      }
      description "length 1..128.";
    }
  }
  grouping IdleModePrioAtRelease-attributes {
    leaf idleModePrioAtReleaseId {
      type string;
      mandatory true;
    }
    leaf-list reservedBy {
      type string;
    }
    leaf lowLoadThreshold {
      type eytypes:int32_range_0-16000;
      default "0";
      description "range 0..16000; Default value: 0.";
    }
    leaf lowMediumLoadThreshold {
      type eytypes:int32_range_0-16000;
      default "200";
      description "range 0..16000; Default value: 200.";
    }
    leaf mediumLoadThreshold {
      type eytypes:int32_range_0-16000;
      default "400";
      description "range 0..16000; Default value: 400.";
    }
    leaf mediumHighLoadThreshold {
      type eytypes:int32_range_0-16000;
      default "600";
      description "range 0..16000; Default value: 600.";
    }
    leaf highLoadThreshold {
      type eytypes:int32_range_0-16000;
      default "800";
      description "range 0..16000; Default value: 800.";
    }
    list lowLoadDistributionInfo {
      key "id";
      leaf id {
        type uint32;
        description "Synthetic key for struct entry.";
      }
      container attributes {
      leaf eUtranFreqRefList {
        type string;
      }
      leaf freqDistributionList {
        type string;
      }
      }
    }
    list lowMediumLoadDistributionInfo {
      key "id";
      leaf id {
        type uint32;
        description "Synthetic key for struct entry.";
      }
      container attributes {
      leaf eUtranFreqRefList {
        type string;
      }
      leaf freqDistributionList {
        type string;
      }
      }
    }
    list mediumLoadDistributionInfo {
      key "id";
      leaf id {
        type uint32;
        description "Synthetic key for struct entry.";
      }
      container attributes {
      leaf eUtranFreqRefList {
        type string;
      }
      leaf freqDistributionList {
        type string;
      }
      }
    }
    list mediumHighLoadDistributionInfo {
      key "id";
      leaf id {
        type uint32;
        description "Synthetic key for struct entry.";
      }
      container attributes {
      leaf eUtranFreqRefList {
        type string;
      }
      leaf freqDistributionList {
        type string;
      }
      }
    }
    list highLoadDistributionInfo {
      key "id";
      leaf id {
        type uint32;
        description "Synthetic key for struct entry.";
      }
      container attributes {
      leaf eUtranFreqRefList {
        type string;
      }
      leaf freqDistributionList {
        type string;
      }
      }
    }
    list catmFreqDistributionInfo {
      key "id";
      leaf id {
        type uint32;
        description "Synthetic key for struct entry.";
      }
      container attributes {
      leaf eUtranFreqRefList {
        type string;
      }
      leaf freqDistributionList {
        type string;
      }
      }
    }
  }
  grouping ImeisvProfile-attributes {
    list listOfTacSvSns {
      key "id";
      leaf id {
        type uint32;
        description "Synthetic key for struct sequence entry.";
      }
      container attributes {
      leaf tac {
        type int32 {
          range "-1..99999999";
        }
        default "-1";
        description "range -1..99999999; Default value: -1.";
      }
      leaf minSv {
        type int32 {
          range "0..98";
        }
        default "0";
        description "range 0..98; Default value: 0.";
      }
      leaf maxSv {
        type int32 {
          range "0..98";
        }
        default "98";
        description "range 0..98; Default value: 98.";
      }
      leaf minSn {
        type eytypes:int32_range_0-99;
        default "0";
        description "range 0..99; Default value: 0.";
      }
      leaf maxSn {
        type eytypes:int32_range_0-99;
        default "99";
        description "range 0..99; Default value: 99.";
      }
      }
    }
    leaf imeisvProfileId {
      type string;
      mandatory true;
    }
    leaf-list listOfFeaturesToTurnOff {
      type enumeration {
        enum FEATURE_NAME1;
        enum FEATURE_NAME2;
        enum FEATURE_NAME3;
        enum FEATURE_NAME4;
        enum FEATURE_NAME5;
        enum FEATURE_NAME6;
        enum FEATURE_NAME7;
        enum FEATURE_NAME8;
        enum FEATURE_NAME9;
        enum FEATURE_NAME10;
        enum FEATURE_NAME11;
        enum FEATURE_NAME12;
        enum FEATURE_NAME13;
        enum FEATURE_NAME14;
        enum FEATURE_NAME15;
      }
    }
    leaf-list listOfFeaturesToTurnOn {
      type enumeration {
        enum FEATURE_NAME1;
        enum FEATURE_NAME2;
        enum FEATURE_NAME3;
        enum FEATURE_NAME4;
        enum FEATURE_NAME5;
        enum FEATURE_NAME6;
        enum FEATURE_NAME7;
        enum FEATURE_NAME8;
        enum FEATURE_NAME9;
        enum FEATURE_NAME10;
        enum FEATURE_NAME11;
        enum FEATURE_NAME12;
        enum FEATURE_NAME13;
        enum FEATURE_NAME14;
        enum FEATURE_NAME15;
      }
    }
    leaf voiceDrxProfileRef {
      type string;
    }
    leaf nonVoiceDrxProfileRef {
      type string;
    }
    leaf elcPreHeatingLength {
      type eytypes:int32_range_1-7;
      default "1";
      description "range 1..7; Default value: 1.";
    }
    leaf elcPostHeatingLength {
      type eytypes:int32_range_0-8;
      default "0";
      description "range 0..8; Default value: 0.";
    }
    leaf elc320msDrxEnabled {
      type boolean;
      default "false";
      description "Default value: false.";
    }
    leaf unsupportedFreqProfileRef {
      type ietfinet:port-number;
    }
  }
  grouping ImeisvTable-attributes {
    leaf imeisvTableId {
      type string;
      mandatory true;
    }
    leaf-list listOfFeaturesDefaultOff {
      type enumeration {
        enum FEATURE_NAME1;
        enum FEATURE_NAME2;
        enum FEATURE_NAME3;
        enum FEATURE_NAME4;
        enum FEATURE_NAME5;
        enum FEATURE_NAME6;
        enum FEATURE_NAME7;
        enum FEATURE_NAME8;
        enum FEATURE_NAME9;
        enum FEATURE_NAME10;
        enum FEATURE_NAME11;
        enum FEATURE_NAME12;
        enum FEATURE_NAME13;
        enum FEATURE_NAME14;
        enum FEATURE_NAME15;
      }
    }
    leaf-list listOfFeaturesDefaultOn {
      type enumeration {
        enum FEATURE_NAME1;
        enum FEATURE_NAME2;
        enum FEATURE_NAME3;
        enum FEATURE_NAME4;
        enum FEATURE_NAME5;
        enum FEATURE_NAME6;
        enum FEATURE_NAME7;
        enum FEATURE_NAME8;
        enum FEATURE_NAME9;
        enum FEATURE_NAME10;
        enum FEATURE_NAME11;
        enum FEATURE_NAME12;
        enum FEATURE_NAME13;
        enum FEATURE_NAME14;
        enum FEATURE_NAME15;
      }
    }
  }
  grouping InstantUplinkAccess-attributes {
    leaf instantUplinkAccessId {
      type string;
      mandatory true;
    }
    leaf iuaEnabled {
      type boolean;
      default "false";
      description "Default value: false.";
    }
    leaf iuaCellResourceLimit {
      type int32 {
        range "1..80";
      }
      default "20";
      units "percent";
      description "range 1..80; Default value: 20.";
    }
    leaf iuaInterval {
      type enumeration {
        enum LOAD_BASED_SELECTION;
        enum INTERVAL_1MS;
        enum INTERVAL_2MS;
        enum INTERVAL_4MS;
        enum INTERVAL_5MS;
      }
      status deprecated;
      default "INTERVAL_1MS";
      description "Default value: INTERVAL_1MS; Status info: Since 19.Q2. Replaced by iuaIntervalTdd and iuaIntervalFdd. Planned to be removed.; Specification: 3GPP 36.331.";
    }
    leaf iuaUePrbLimit {
      type eytypes:int32_range_1-100-4;
      default "3";
      description "range 1..100; Default value: 3.";
    }
    leaf iuaTargetBufferSize {
      type int32 {
        range "1..5000";
      }
      default "86";
      units "Bytes";
      description "range 1..5000; Default value: 86.";
    }
    leaf iuaTargetBufferEmptyTime {
      type int32 {
        range "1..10";
      }
      default "4";
      units "ms";
      description "range 1..10; Default value: 4.";
    }
    leaf iuaSinrThreshold {
      type eytypes:int32_range_-10-20;
      default "5";
      units "dB";
      description "range -10..20; Default value: 5.";
    }
    leaf iuaSinrDeactHyst {
      type eytypes:int32_range_0-50;
      default "20";
      units "dB";
      description "range 0..50; Default value: 20.";
    }
    leaf iuaLoadThreshold {
      type eytypes:int32_range_1-100;
      default "80";
      units "percent";
      description "range 1..100; Default value: 80.";
    }
    leaf iuaDuration {
      type int32 {
        range "5..10000";
      }
      default "1050";
      units "ms";
      description "range 5..10000; Default value: 1050.";
    }
    leaf iuaInactivityTimer {
      type eytypes:int32_range_0-500;
      default "100";
      units "ms";
      description "range 0..500; Default value: 100.";
    }
    leaf iuaDeactTimer {
      type eytypes:int32_range_0-500;
      default "10";
      units "ms";
      description "range 0..500; Default value: 10.";
    }
    leaf iuaCoscheduleDynamic {
      type boolean;
      default "false";
      description "Default value: false.";
    }
    leaf iuaDeactPdcchMargin {
      type eytypes:int32_range_0-6;
      default "3";
      units "dB";
      description "range 0..6; Default value: 3.";
    }
    leaf iuaIntervalFdd {
      type enumeration {
        enum LOAD_BASED_SELECTION;
        enum INTERVAL_1MS;
        enum INTERVAL_2MS;
        enum INTERVAL_4MS;
      }
    }
    leaf iuaIntervalTdd {
      type enumeration {
        enum LOAD_BASED_SELECTION;
        enum INTERVAL_1MS;
        enum INTERVAL_5MS;
      }
    }
  }
  grouping InterMeLink-attributes {
    leaf interMeLinkId {
      type string;
      mandatory true;
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf operationalState {
      type enumeration {
        enum DISABLED;
        enum ENABLED;
      }
      config false;
    }
    leaf localEndPoint {
      type string {
        length "2..39";
      }
      config false;
      description "length 2..39.";
    }
    leaf remoteEndPoint {
      type string {
        length "2..39";
      }
      config false;
      description "length 2..39.";
    }
    leaf vLanId {
      type eytypes:int32_range_0-2147483647;
      config false;
      description "range 0..2147483647.";
    }
    leaf linkLatency15min {
      type eytypes:int32_range_0-1000000-47;
      config false;
      units "microseconds";
      description "range 0..1000000.";
    }
    leaf linkLatency1min {
      type eytypes:int32_range_0-1000000-47;
      config false;
      units "microseconds";
      description "range 0..1000000.";
    }
    leaf linkLatency24h {
      type eytypes:int32_range_0-1000000-47;
      config false;
      units "microseconds";
      description "range 0..1000000.";
    }
  }
  grouping IuaProfile-attributes {
    leaf iuaInterval {
      type enumeration {
        enum LOAD_BASED_SELECTION;
        enum INTERVAL_1MS;
        enum INTERVAL_2MS;
        enum INTERVAL_4MS;
        enum INTERVAL_5MS;
      }
      status deprecated;
      default "INTERVAL_1MS";
      description "Default value: INTERVAL_1MS; Status info: Since 19.Q2. Replaced by iuaIntervalTdd and iuaIntervalFdd. Planned to be removed.; Specification: 3GPP 36.331.";
    }
    leaf iuaUePrbLimit {
      type eytypes:int32_range_1-100-4;
      default "3";
      description "range 1..100; Default value: 3.";
    }
    leaf iuaTargetBufferSize {
      type int32 {
        range "1..5000";
      }
      default "86";
      units "Bytes";
      description "range 1..5000; Default value: 86.";
    }
    leaf iuaTargetBufferEmptyTime {
      type int32 {
        range "1..10";
      }
      default "4";
      units "ms";
      description "range 1..10; Default value: 4.";
    }
    leaf iuaSinrThreshold {
      type eytypes:int32_range_-10-20;
      default "5";
      units "dB";
      description "range -10..20; Default value: 5.";
    }
    leaf iuaSinrDeactHyst {
      type eytypes:int32_range_0-50;
      default "20";
      units "dB";
      description "range 0..50; Default value: 20.";
    }
    leaf iuaDuration {
      type int32 {
        range "5..10000";
      }
      default "1050";
      units "ms";
      description "range 5..10000; Default value: 1050.";
    }
    leaf iuaInactivityTimer {
      type eytypes:int32_range_0-500;
      default "100";
      units "ms";
      description "range 0..500; Default value: 100.";
    }
    leaf iuaDeactTimer {
      type eytypes:int32_range_0-500;
      default "10";
      units "ms";
      description "range 0..500; Default value: 10.";
    }
    leaf iuaProfileId {
      type string;
      mandatory true;
    }
    leaf-list reservedBy {
      type string;
    }
    leaf iuaIntervalFdd {
      type enumeration {
        enum LOAD_BASED_SELECTION;
        enum INTERVAL_1MS;
        enum INTERVAL_2MS;
        enum INTERVAL_4MS;
      }
    }
    leaf iuaIntervalTdd {
      type enumeration {
        enum LOAD_BASED_SELECTION;
        enum INTERVAL_1MS;
        enum INTERVAL_5MS;
      }
    }
  }
  grouping LoadBalancingFunction-attributes {
    leaf loadBalancingFunctionId {
      type string;
      mandatory true;
    }
    leaf lbThreshold {
      type eytypes:int32_range_0-1000-2;
      default "30";
      description "range 0..1000; Default value: 30.";
    }
    leaf lbCeiling {
      type int32 {
        range "10..2000";
      }
      default "200";
      description "range 10..2000; Default value: 200.";
    }
    leaf lbRateOffsetCoefficient {
      type eytypes:int32_range_0-1000-2;
      default "320";
      description "range 0..1000; Default value: 320.";
    }
    leaf lbUtranOffloadBackoffTime {
      type int32 {
        range "30..600";
      }
      default "60";
      units "s";
      description "range 30..600; Default value: 60.";
    }
    leaf lbEUtranOffloadBackoffTime {
      type int32 {
        range "30..600";
      }
      default "60";
      units "s";
      description "range 30..600; Default value: 60.";
    }
    leaf lbCauseCodeS1SourceTriggersOffload {
      type enumeration {
        enum REDUCE_LOAD_IN_SERVING_CELL;
        enum RESOURCE_OPTIMSATION_HANDOVER;
        enum LOAD_BALANCING;
        enum TEMPORARY1;
        enum TEMPORARY2;
      }
    }
    leaf lbCauseCodeS1TargetAcceptsOffload {
      type enumeration {
        enum REDUCE_LOAD_IN_SERVING_CELL;
        enum RESOURCE_OPTIMSATION_HANDOVER;
        enum LOAD_BALANCING;
        enum TEMPORARY1;
        enum TEMPORARY2;
      }
    }
    leaf lbCauseCodeX2SourceTriggersOffload {
      type enumeration {
        enum REDUCE_LOAD_IN_SERVING_CELL;
        enum RESOURCE_OPTIMSATION_HANDOVER;
        enum LOAD_BALANCING;
        enum TEMPORARY1;
        enum TEMPORARY2;
      }
    }
    leaf lbCauseCodeX2TargetAcceptsOffload {
      type enumeration {
        enum REDUCE_LOAD_IN_SERVING_CELL;
        enum RESOURCE_OPTIMSATION_HANDOVER;
        enum LOAD_BALANCING;
        enum TEMPORARY1;
        enum TEMPORARY2;
      }
    }
    leaf lbHitRateEUtranMeasUeThreshold {
      type eytypes:int32_range_1-1000-7;
      default "10";
      description "range 1..1000; Default value: 10.";
    }
    leaf lbHitRateUtranMeasUeThreshold {
      type eytypes:int32_range_1-1000-7;
      default "200";
      description "range 1..1000; Default value: 200.";
    }
    leaf lbHitRateEUtranMeasUeIntensity {
      type eytypes:int32_range_1-100-4;
      default "10";
      description "range 1..100; Default value: 10.";
    }
    leaf lbHitRateUtranMeasUeIntensity {
      type eytypes:int32_range_1-100-4;
      default "1";
      description "range 1..100; Default value: 1.";
    }
    leaf lbHitRateEUtranAddThreshold {
      type eytypes:int32_range_1-100-4;
      default "15";
      description "range 1..100; Default value: 15.";
    }
    leaf lbHitRateUtranAddThreshold {
      type eytypes:int32_range_1-100-4;
      default "15";
      description "range 1..100; Default value: 15.";
    }
    leaf lbHitRateEUtranRemoveThreshold {
      type eytypes:int32_range_0-99;
      default "2";
      description "range 0..99; Default value: 2.";
    }
    leaf lbHitRateUtranRemoveThreshold {
      type eytypes:int32_range_0-99;
      default "2";
      description "range 0..99; Default value: 2.";
    }
    leaf txPwrForOverlaidCellDetect {
      type int32 {
        range "0..540";
      }
      default "370";
      units "dBm";
      description "range 0..540; Default value: 370.";
    }
    leaf ocdMaxNoHighHitRateCells {
      type eytypes:int32_range_1-10;
      default "3";
      description "range 1..10; Default value: 3.";
    }
    leaf ocdMinHighHitThresh {
      type eytypes:int32_range_1-100-4;
      default "15";
      description "range 1..100; Default value: 15.";
    }
    leaf lbMeasScalingLimit {
      type eytypes:int32_range_1-100-4;
      default "30";
      description "range 1..100; Default value: 30.";
    }
    leaf lbHitRateFilterCoeffCalm {
      type int32 {
        range "10..2400";
      }
      default "200";
      description "range 10..2400; Default value: 200.";
    }
    leaf lbDiffCaOffset {
      type eytypes:int32_range_0-1000-2;
      default "100";
      description "range 0..1000; Default value: 100.";
    }
    leaf lbRateOffsetLoadThreshold {
      type eytypes:int32_range_0-16000;
      default "500";
      description "range 0..16000; Default value: 500.";
    }
    leaf lbCaThreshold {
      type eytypes:int32_range_0-16000;
      default "800";
      description "range 0..16000; Default value: 800.";
    }
    leaf lbCaHysteresis {
      type eytypes:int32_range_0-1000-2;
      default "50";
      description "range 0..1000; Default value: 50.";
    }
    leaf lbCaCapHysteresis {
      type eytypes:int32_range_0-100-3;
      default "20";
      description "range 0..100; Default value: 20.";
    }
    leaf lbUeEvaluationTimer {
      type int32 {
        range "0..360";
      }
      default "90";
      units "s";
      description "range 0..360; Default value: 90.";
    }
    leaf isUlEvalAllowedAtTpLbHo {
      type boolean;
      default "false";
      description "Default value: false.";
    }
    leaf isUlEvalAllowedAtCaTrHo {
      type boolean;
      default "false";
      description "Default value: false.";
    }
    leaf lbAllowedForEndcUe {
      type boolean;
      status deprecated;
      default "false";
      description "Default value: false; Takes effect: New connection; Status info: Since 22.Q2. Replaced by EUtranCellFDD/EUtranCellTDD::lbActionForEndcUe. Planned to be removed..";
      reference "Takes effect: New connection.";
    }
    leaf lbCycle {
      type int32 {
        range "5..15";
      }
      default "5";
      units "s";
      description "range 5..15; Default value: 5.";
    }
    leaf lbSubCycle {
      type int32 {
        range "30..80";
      }
      default "50";
      units "ms";
      description "range 30..80; Default value: 50.";
    }
    leaf targetLoadAwareLbdar {
      type boolean;
      default "false";
      description "Default value: false.";
    }
    leaf coverageAwareLbdar {
      type boolean;
      default "false";
      description "Default value: false.";
    }
  }
  grouping LoggedMdt-attributes {
    leaf loggedMdtConfigEnabled {
      type boolean;
      default "false";
      description "Default value: false.";
    }
    leaf numberOfMdtConfigUes {
      type eytypes:int32_range_0-1000-2;
      default "10";
      description "range 0..1000; Default value: 10.";
    }
    leaf loggedMdtReportEnabled {
      type ietfinet:port-number;
      description "Default value: false.";
    }
    leaf loggedMdtGnssCheck {
      type boolean;
      default "false";
      description "Default value: false.";
    }
    leaf traceId {
      type int32 {
        range "1..16777215";
      }
      default "1";
      description "range 1..16777215; Default value: 1.";
    }
    leaf tceId {
      type eytypes:int32_range_1-255;
      default "1";
      description "range 1..255; Default value: 1.";
    }
    leaf traceRecSessionReference {
      type eytypes:int32_range_1-65535;
      default "1";
      description "range 1..65535; Default value: 1.";
    }
    leaf areaScopeType {
      type enumeration {
        enum NOT_PRESENT;
        enum TYPE_CGI;
        enum TYPE_TAC;
      }
    }
    list areaScopeCgiList {
      key "id";
      leaf id {
        type uint32;
        description "Synthetic key for struct sequence entry.";
      }
      container attributes {
      leaf enbId {
        type eytypes:int32_range_0-1048575;
        default "0";
        description "range 0..1048575; Default value: 0.";
      }
      leaf cellId {
        type eytypes:int32_range_0-255;
        default "0";
        description "range 0..255; Default value: 0.";
      }
      leaf mcc {
        type eytypes:int32_range_0-999;
        default "1";
        description "range 0..999; Default value: 1.";
      }
      leaf mnc {
        type eytypes:int32_range_0-999;
        default "1";
        description "range 0..999; Default value: 1.";
      }
      leaf mncLength {
        type eytypes:int32_range_2-3;
        default "2";
        description "range 2..3; Default value: 2.";
      }
      }
    }
    leaf-list areaScopeTacList {
      type eytypes:int32_range_0-65535-10;
    }
    leaf loggingInterval {
      type enumeration {
        enum MS_1280;
        enum MS_2560;
        enum MS_5120;
        enum MS_10240;
        enum MS_20480;
        enum MS_30720;
        enum MS_40960;
        enum MS_61440;
      }
    }
    leaf loggingDuration {
      type enumeration {
        enum MIN_10;
        enum MIN_20;
        enum MIN_40;
        enum MIN_60;
        enum MIN_90;
        enum MIN_120;
      }
    }
    list mdtPlmnList {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf loggedMdtId {
      type string;
      mandatory true;
    }
  }
  grouping LogicalChannelGroup-attributes {
    leaf logicalChannelGroupId {
      type string;
      mandatory true;
    }
    leaf userLabel {
      type string {
        length "1..128";
      }
      description "length 1..128.";
    }
    leaf-list reservedBy {
      type string;
    }
  }
  grouping MACConfiguration-attributes {
    leaf dlMaxHARQTx {
      type int32 {
        range "1..8 | 10 | 12 | 16 | 20 | 24 | 28";
      }
      default "4";
      description "Default value: 4.";
    }
    leaf ulMaxHARQTx {
      type eytypes:int32_range_1-7;
      default "4";
      description "range 1..7; Default value: 4.";
    }
    leaf mACConfigurationId {
      type ietfyang:mac-address;
      mandatory true;
    }
    leaf dlMaxHARQMsg4Tx {
      type eytypes:int32_range_0-4;
      default "0";
      description "range 0..4; Default value: 0.";
    }
    leaf ulTtiBundlingMaxHARQTx {
      type eytypes:int32_range_1-7;
      default "4";
      description "range 1..7; Default value: 4.";
    }
  }
  grouping Mbms-attributes {
    leaf mbmsId {
      type string;
      mandatory true;
    }
    leaf userLabel {
      type string {
        length "1..128";
      }
      description "length 1..128.";
    }
    leaf synchPeriodLength {
      type int32 {
        range "80..593920";
      }
      default "593920";
      units "ms";
      description "range 80..593920; Default value: 593920.";
    }
    leaf tMbmsAuditTimer {
      type int32 {
        range "60..86400";
      }
      default "180";
      units "second";
      description "range 60..86400; Default value: 180.";
    }
    leaf m1IpInterfaceRef {
      type ietfinet:ip-address;
    }
  }
  grouping MbmsService-attributes {
    leaf mbmsServiceId {
      type string;
      mandatory true;
    }
    leaf userLabel {
      type string {
        length "1..128";
      }
      description "length 1..128.";
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf operationalState {
      type enumeration {
        enum DISABLED;
        enum ENABLED;
      }
      config false;
    }
    list tmgiList {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      leaf serviceId {
        type eytypes:int32_range_0-16777215;
        description "range 0..16777215.";
      }
      }
    }
    leaf logicalChannelIdentity {
      type int32 {
        range "1..28";
      }
      mandatory true;
      description "range 1..28.";
    }
    leaf createdBy {
      type enumeration {
        enum SYSTEM;
        enum OPERATOR;
      }
      config false;
    }
    leaf pmMbmsPktDiscSynchPayloadTooMuch {
      type uint32;
      config false;
    }
    leaf pmMbmsPktLostSynchPayload {
      type uint32;
      config false;
    }
    leaf pmZtemporary55 {
      type uint32;
      config false;
    }
    leaf pmMbmsPktDiscSynchPayloadMuted {
      type uint32;
      config false;
    }
    leaf pmMbmsPktRecSynchCtrl {
      type uint32;
      config false;
    }
    leaf pmMbmsVolTrans {
      type uint32;
      config false;
    }
    leaf pmMbmsVolReceived {
      type uint32;
      config false;
    }
    leaf pmMbmsPktDiscSynchPayloadTooOld {
      type uint32;
      config false;
    }
    leaf pmMbmsPktRecSynchPayload {
      type uint32;
      config false;
    }
  }
  grouping MbsfnArea-attributes {
    leaf mbsfnAreaId {
      type string;
      mandatory true;
    }
    leaf userLabel {
      type string {
        length "1..128";
      }
      description "length 1..128.";
    }
    leaf mbsfnAreaIdentity {
      type eytypes:int32_range_0-255;
      mandatory true;
      description "range 0..255.";
    }
    leaf nonMbsfnRegionLength {
      type eytypes:int32_range_1-2;
      default "2";
      description "range 1..2; Default value: 2.";
    }
    leaf mcchRepetitionPeriod {
      type int32 {
        range "32 | 64 | 128 | 256";
      }
      default "32";
      description "Default value: 32.";
    }
    leaf mcchModificationPeriod {
      type int32 {
        range "512 | 1024";
      }
      default "512";
      description "Default value: 512.";
    }
    leaf signallingMCS {
      type int32 {
        range "2 | 7 | 13 | 19";
      }
      mandatory true;
    }
    leaf commonSFAllocPeriod {
      type int32 {
        range "4 | 8 | 16 | 32 | 64 | 128 | 256";
      }
      default "32";
      description "Default value: 32.";
    }
    leaf administrativeState {
      type enumeration {
        enum LOCKED;
        enum UNLOCKED;
        enum SHUTTINGDOWN;
      }
    }
    leaf-list serviceAreaId {
      type eytypes:int32_range_0-65535-10;
    }
    list commonSFAllocList {
      key "id";
      leaf id {
        type uint32;
        description "Synthetic key for struct sequence entry.";
      }
      container attributes {
      leaf radioframeAllocationPeriod {
        type int32;
        default "1";
        description "Default value: 1.";
      }
      leaf radioframeAllocationOffset {
        type eytypes:int32_range_0-7;
        default "0";
        description "range 0..7; Default value: 0.";
      }
      leaf subframeAllocation {
        type int32;
        default "1";
        description "Default value: 1.";
      }
      leaf subframeAllocationOneFrame {
        type string;
        default "000000";
        description "Default value: 000000.";
      }
      leaf subframeAllocationFourFrame {
        type string;
        default "000000000000000000000000";
        description "Default value: 000000000000000000000000.";
      }
      leaf sfAllocationFourFrame {
        type eytypes:int32_range_0-16777215;
        default "0";
        description "range 0..16777215; Default value: 0.";
      }
      leaf sfAllocationOneFrame {
        type eytypes:int32_range_0-63;
        default "0";
        description "range 0..63; Default value: 0.";
      }
      }
    }
  }
  grouping MbsfnAreaCellRelation-attributes {
    leaf mbsfnAreaCellRelationId {
      type string;
      mandatory true;
    }
    leaf userLabel {
      type string {
        length "1..128";
      }
      description "length 1..128.";
    }
    leaf mbsfnAreaCellRef {
      type string;
      mandatory true;
    }
    leaf isReservedCell {
      type boolean;
      default "false";
      description "Default value: false.";
    }
    leaf mbsfnAreaCellStatus {
      type enumeration {
        enum NOT_ACTIVATED;
        enum ACTIVATED;
        enum FAILED;
        enum CELL_DISABLED;
        enum RESERVED;
      }
      config false;
    }
  }
  grouping MdtConfiguration-attributes {
    leaf mdtConfigurationId {
      type string;
      mandatory true;
    }
    leaf reportingTrigger {
      type ietfinet:port-number;
    }
    leaf reportIntervalMdt {
      type ietfinet:port-number;
    }
    leaf reportAmountMdt {
      type ietfinet:port-number;
      default "16";
      description "Default value: 16.";
    }
    leaf a2ThresholdRsrpMdt {
      type eytypes:int32_range_-140--44;
      default "-140";
      units "dBm";
      description "range -140..-44; Default value: -140.";
    }
    leaf a2ThresholdRsrqMdt {
      type eytypes:int32_range_-195--30;
      default "-195";
      units "dB";
      description "range -195..-30; Default value: -195.";
    }
    leaf positioningMethod {
      type enumeration {
        enum NONE;
        enum GNSS;
      }
    }
    leaf hysteresisA2Mdt {
      type eytypes:int32_range_0-150;
      default "10";
      units "dB";
      description "range 0..150; Default value: 10.";
    }
    leaf timeToTriggerA2Mdt {
      type int32 {
        range "0 | 40 | 64 | 80 | 100 | 128 | 160 | 256 | 320 | 480 | 512 | 640 | 1024 | 1280 | 2560 | 5120";
      }
      default "640";
      units "ms";
      description "Default value: 640.";
    }
    leaf maxReportCellsA2Mdt {
      type ietfinet:port-number;
      default "4";
      description "range 1..8; Default value: 4.";
    }
    leaf reportQuantityA2Mdt {
      type ietfinet:port-number;
    }
    leaf triggerQuantityA2Mdt {
      type enumeration {
        enum RSRP;
        enum RSRQ;
      }
    }
    leaf measGapAllowedMdt {
      type boolean;
      default "true";
      description "Default value: true.";
    }
    leaf rlfReportEnabled {
      type ietfinet:port-number;
      description "Default value: false.";
    }
    leaf rcefReportEnabled {
      type ietfinet:port-number;
      description "Default value: false.";
    }
    leaf immediateMdtGnssCheck {
      type boolean;
      default "false";
      description "Default value: false.";
    }
    leaf delayThresholdMdtM6 {
      type int32 {
        range "30 | 40 | 50 | 60 | 70 | 80 | 90 | 100 | 150 | 300 | 500 | 750";
      }
      default "100";
      units "ms";
      description "Default value: 100.";
    }
    leaf reportAmountMdtM6 {
      type ietfinet:port-number;
      default "16";
      description "Default value: 16.";
    }
    leaf reportIntervalMdtM6 {
      type ietfinet:port-number;
      default "10240";
      units "ms";
      description "Default value: 10240.";
    }
  }
  grouping MeasCellGroup-attributes {
    leaf measCellGroupId {
      type string;
      mandatory true;
    }
    leaf groupId {
      type eytypes:int32_range_0-24;
      default "0";
      description "range 0..24; Default value: 0.";
    }
    leaf groupPrbUnit {
      type int32 {
        range "1..600";
      }
      default "5";
      description "range 1..600; Default value: 5.";
    }
    leaf-list reservedBy {
      type string;
    }
    list plmnList {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf-list spidList {
      type eytypes:int32_range_0-256;
    }
    leaf pmMeasCellGroupPrbUnit {
      type int32;
      config false;
    }
    leaf-list pmMeasCellGroupUeThp2UlDistr {
      type uint32;
    }
    leaf-list pmMeasCellGroupUeThp2DlDistr {
      type uint32;
    }
    leaf-list pmMeasCellGroupDlPrbUsedDistr {
      type uint32;
    }
  }
  grouping MimoSleepFunction-attributes {
    leaf mimoSleepFunctionId {
      type string;
      mandatory true;
    }
    leaf sleepMode {
      type enumeration {
        enum OFF;
        enum DETECTION;
        enum SOFT_SWITCH;
        enum SWITCH;
        enum ADVANCED_SWITCH;
        enum MI_DETECTION;
        enum MI_SWITCH;
      }
    }
    leaf sleepState {
      type enumeration {
        enum ACTIVATED;
        enum DEACTIVATED;
      }
      config false;
    }
    leaf sleepStartTime {
      type string {
        length "5";
      }
      default "02:00";
      description "length 5..5; Default value: 02:00.";
    }
    leaf sleepEndTime {
      type string {
        length "5";
      }
      default "05:00";
      description "length 5..5; Default value: 05:00.";
    }
    leaf switchDownMonitorDurTimer {
      type eytypes:int32_range_1-120;
      default "30";
      units "minutes";
      description "range 1..120; Default value: 30.";
    }
    leaf switchDownPrbThreshold {
      type eytypes:int32_range_0-90;
      default "10";
      units "percent";
      description "range 0..90; Default value: 10.";
    }
    leaf switchDownRrcConnThreshold {
      type eytypes:int32_range_0-500-43;
      default "5";
      description "range 0..500; Default value: 5.";
    }
    leaf switchUpMonitorDurTimer {
      type eytypes:int32_range_1-120;
      default "5";
      units "minutes";
      description "range 1..120; Default value: 5.";
    }
    leaf switchUpPrbThreshold {
      type int32 {
        range "1..90";
      }
      default "30";
      units "percent";
      description "range 1..90; Default value: 30.";
    }
    leaf switchUpRrcConnThreshold {
      type eytypes:int32_range_0-500-43;
      default "50";
      description "range 0..500; Default value: 50.";
    }
    leaf sleepPowerControl {
      type enumeration {
        enum USE_MAX_POWER;
        enum RETAIN_SAME_POWER;
      }
    }
    leaf portMergingEnabled {
      type ietfinet:port-number;
      description "Default value: false.";
    }
    leaf portMerging4TxOpMode {
      type ietfinet:port-number;
    }
    leaf portMergingOptionFor4TxTo2Tx {
      type ietfinet:port-number;
    }
    leaf sleepStartTimeApplied {
      type string {
        length "0..5";
      }
      config false;
      description "length 0..5.";
    }
    leaf sleepEndTimeApplied {
      type string {
        length "0..5";
      }
      config false;
      description "length 0..5.";
    }
    leaf modelAccuracyThreshold {
      type int32 {
        range "0 | 50..90";
      }
      default "90";
      units "percent";
      description "Default value: 90.";
    }
    leaf rank2Enabled {
      type boolean;
      default "false";
      description "Default value: false.";
    }
    leaf switchDown1TxPrbThreshold {
      type eytypes:int32_range_0-90;
      default "5";
      units "percent";
      description "range 0..90; Default value: 5.";
    }
    leaf switchDown1TxRrcConnThreshold {
      type eytypes:int32_range_0-500-43;
      default "3";
      description "range 0..500; Default value: 3.";
    }
    leaf switchUp1TxPrbThreshold {
      type int32 {
        range "1..90";
      }
      default "8";
      units "percent";
      description "range 1..90; Default value: 8.";
    }
    leaf switchUp1TxRrcConnThreshold {
      type eytypes:int32_range_0-500-43;
      default "4";
      description "range 0..500; Default value: 4.";
    }
    leaf mimoSleep4TxOpMode {
      type enumeration {
        enum OP_MODE_4TX_TO_2TX;
        enum OP_MODE_4TX_TO_2TX_TO_1TX;
      }
    }
  }
  grouping NbIdleModeLoadDistr-attributes {
    leaf nbIdleModeLoadDistrId {
      type string;
      mandatory true;
    }
    leaf-list nbCarrierFreqList {
      type eytypes:int32_range_0-262143;
    }
    leaf-list nbFreqDistributionList {
      type eytypes:int32_range_0-100;
    }
  }
  grouping NbIotCell-attributes {
    leaf nbIotCellType {
      type enumeration {
        enum NBIOT_INBAND;
        enum NBIOT_GUARDBAND;
        enum NBIOT_STANDALONE;
        enum NBIOT_INBAND_NOT_SAME_PCI;
      }
      mandatory true;
    }
    leaf eutranCellRef {
      type string;
    }
    leaf-list sectorCarrierRef {
      type string;
    }
    leaf administrativeState {
      type enumeration {
        enum LOCKED;
        enum UNLOCKED;
        enum SHUTTINGDOWN;
      }
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf cellBarred {
      type enumeration {
        enum BARRED;
        enum NOT_BARRED;
      }
    }
    leaf cellId {
      type eytypes:int32_range_0-255;
      mandatory true;
      description "range 0..255.";
    }
    leaf nbIotCellId {
      type string;
      mandatory true;
    }
    leaf operationalState {
      type enumeration {
        enum DISABLED;
        enum ENABLED;
      }
      config false;
    }
    leaf prbIndex {
      type int32 {
        range "-10..110 | 255";
      }
      status deprecated;
      default "255";
      description "Default value: 255; Takes effect: Next cell unlock; Status info: Since 17.Q3. Planned to be removed..";
      reference "Takes effect: Next cell unlock.";
    }
    leaf tac {
      type eytypes:int32_range_0-65535-10;
      mandatory true;
      description "range 0..65535.";
    }
    leaf physicalLayerCellId {
      type eytypes:int32_range_0-503;
      mandatory true;
      description "range 0..503.";
    }
    leaf earfcndl {
      type int32 {
        range "-1..17999 | 46590..262143";
      }
      default "-1";
      description "Default value: -1.";
    }
    leaf pZeroNominalNPusch {
      type eytypes:int32_range_-126-24;
      default "-110";
      units "dBm";
      description "range -126..24; Default value: -110.";
    }
    leaf earfcnul {
      type int32 {
        range "-1..0 | 18000..35999 | 46590..262143";
      }
      default "-1";
      description "Default value: -1.";
    }
    leaf qRxLevMin {
      type int32 {
        range "-156..-44";
      }
      default "-140";
      units "dBm";
      description "range -156..-44; Default value: -140.";
    }
    leaf qQualMin {
      type int32 {
        range "-34..-3 | 0";
      }
      default "-34";
      units "dB";
      description "Default value: -34.";
    }
    leaf pMax {
      type int32 {
        range "-30..33 | 1000";
      }
      default "1000";
      units "dBm";
      description "Default value: 1000.";
    }
    leaf qHyst {
      type eytypes:int32_range_0-24-29;
      default "4";
      units "dB";
      description "range 0..24; Default value: 4.";
    }
    list mappingInfo {
      key "id";
      leaf id {
        type uint32;
        description "Synthetic key for struct entry.";
      }
      container attributes {
      leaf mappingInfoNbSIB3 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoNbSIB4 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoNbSIB5 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoNbSIB14 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      leaf mappingInfoNbSIB16 {
        type enumeration {
          enum NOT_MAPPED;
          enum MAPPED_SI_1;
          enum MAPPED_SI_2;
          enum MAPPED_SI_3;
          enum MAPPED_SI_4;
          enum MAPPED_SI_5;
          enum MAPPED_SI_6;
          enum MAPPED_SI_7;
          enum MAPPED_SI_8;
          enum MAPPED_SI_9;
          enum MAPPED_SI_10;
        }
      }
      }
    }
    leaf siWindowLength {
      type int32 {
        range "160 | 320 | 480 | 640 | 960 | 1280 | 1600";
      }
      default "160";
      units "ms";
      description "Default value: 160.";
    }
    list siPeriodicity {
      key "id";
      leaf id {
        type uint32;
        description "Synthetic key for struct entry.";
      }
      container attributes {
      leaf siPeriodicitySI1 {
        type ietfinet:ip-address;
        units "rf (radioframe)";
        description "Default value: 64.";
      }
      leaf siPeriodicitySI2 {
        type ietfinet:ip-address;
        units "rf (radioframe)";
        description "Default value: 512.";
      }
      leaf siPeriodicitySI3 {
        type ietfinet:ip-address;
        units "rf (radioframe)";
        description "Default value: 512.";
      }
      leaf siPeriodicitySI4 {
        type ietfinet:ip-address;
        units "rf (radioframe)";
        description "Default value: 512.";
      }
      leaf siPeriodicitySI5 {
        type ietfinet:ip-address;
        units "rf (radioframe)";
        description "Default value: 512.";
      }
      leaf siPeriodicitySI14 {
        type ietfinet:ip-address;
        units "rf (radioframe)";
        description "Default value: 512.";
      }
      leaf siPeriodicitySI116 {
        type ietfinet:ip-address;
        units "rf (radioframe)";
        description "Default value: 512.";
      }
      leaf siPeriodicitySI6 {
        type ietfinet:ip-address;
        units "1 rf";
        description "Default value: 512.";
      }
      leaf siPeriodicitySI7 {
        type ietfinet:ip-address;
        units "1 rf";
        description "Default value: 512.";
      }
      }
    }
    list siRepetition {
      key "id";
      leaf id {
        type uint32;
        description "Synthetic key for struct entry.";
      }
      container attributes {
      leaf siRepetitionSI1 {
        type int32;
        default "4";
        units "rf (radioframe)";
        description "Default value: 4.";
      }
      leaf siRepetitionSI2 {
        type int32;
        default "4";
        units "rf (radioframe)";
        description "Default value: 4.";
      }
      leaf siRepetitionSI3 {
        type int32;
        default "4";
        units "rf (radioframe)";
        description "Default value: 4.";
      }
      leaf siRepetitionSI4 {
        type int32;
        default "4";
        units "rf (radioframe)";
        description "Default value: 4.";
      }
      leaf siRepetitionSI5 {
        type int32;
        default "4";
        units "rf (radioframe)";
        description "Default value: 4.";
      }
      leaf siRepetitionSI14 {
        type int32;
        default "4";
        units "rf (radioframe)";
        description "Default value: 4.";
      }
      leaf siRepetitionSI16 {
        type int32;
        default "4";
        units "rf (radioframe)";
        description "Default value: 4.";
      }
      }
    }
    list frequencyInfo {
      key "id";
      leaf id {
        type uint32;
        description "Synthetic key for struct sequence entry.";
      }
      container attributes {
      leaf qRxLevMin {
        type int32 {
          range "-156..-44";
        }
        default "-140";
        units "dBm";
        description "range -156..-44; Default value: -140.";
      }
      leaf pMax {
        type int32;
        default "1000";
        units "dBm";
        description "Default value: 1000.";
      }
      leaf qQualMin {
        type int32;
        default "0";
        units "dB";
        description "Default value: 0.";
      }
      leaf qOffsetFreq {
        type int32;
        default "0";
        units "dB";
        description "Default value: 0.";
      }
      leaf tReselection {
        type eytypes:int32_range_0-7-9;
        default "2";
        units "s";
        description "range 0..7; Default value: 2.";
      }
      leaf freqOffset {
        type enumeration {
          enum V_10;
          enum V_9;
          enum V_8;
          enum V_7;
          enum V_6;
          enum V_5;
          enum V_4;
          enum V_3;
          enum V_2;
          enum V_1;
          enum V_05;
          enum V0;
          enum V05;
          enum V1;
          enum V2;
          enum V3;
          enum V4;
          enum V5;
          enum V6;
          enum V7;
          enum V8;
          enum V9;
        }
      }
      leaf carrierFreq {
        type eytypes:int32_range_0-262143;
        default "0";
        description "range 0..262143; Default value: 0.";
      }
      leaf tReselectionNb {
        type int32;
        default "6";
        units "s";
        description "Default value: 6.";
      }
      leaf freqBandList {
        type string;
      }
      }
    }
    leaf allocatedPrbIndex {
      type int32 {
        range "-10..110 | 255";
      }
      config false;
      status deprecated;
      description "Status info: Since 18.Q3. Replaced by dlAllocatedPrb. Planned to be removed..";
    }
    list plmnList {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf-list plmnReservedList {
      type boolean;
    }
    leaf-list attachWithoutPDNConnectivityList {
      type boolean;
    }
    leaf freqBand {
      type eytypes:int32_range_1-256;
      config false;
      description "range 1..256.";
    }
    leaf modificationPeriodCoeff {
      type int32 {
        range "16 | 32 | 64 | 128";
      }
    }
    leaf sIntraSearchThreshold {
      type eytypes:int32_range_0-62;
      default "62";
      units "dB";
      description "range 0..62; Default value: 62.";
    }
    leaf sInterSearchThreshold {
      type eytypes:int32_range_0-62;
      default "0";
      units "dB";
      description "range 0..62; Default value: 0.";
    }
    leaf allocatedUlPrb {
      type int32 {
        range "-10..110 | 255";
      }
      config false;
      status deprecated;
      description "Status info: Since 18.Q3. Replaced by ulAllocatedPrb. Planned to be removed.; Specification: 3GPP TS 36.331 Rel-13.";
    }
    leaf coverageEnhancementLevel {
      type enumeration {
        enum CE_0;
        enum CE_1;
        enum CE_2;
      }
      status deprecated;
      default "CE_0";
      description "Default value: CE_0; Takes effect: Next cell unlock; Status info: Since 17.Q2. Has no functional behavior. Planned to be removed.; Specification: 3GPP TS 36.331 Rel-13.";
      reference "Takes effect: Next cell unlock.";
    }
    leaf zzzTemporary1 {
      type int32;
    }
    leaf zzzTemporary2 {
      type int32;
    }
    leaf zzzTemporary3 {
      type int32;
    }
    leaf zzzTemporary4 {
      type int32;
    }
    leaf zzzTemporary5 {
      type int32;
    }
    leaf zzzTemporary6 {
      type int32;
    }
    leaf zzzTemporary7 {
      type int32;
    }
    leaf zzzTemporary8 {
      type int32;
    }
    leaf zzzTemporary9 {
      type int32;
    }
    leaf zzzTemporary10 {
      type int32;
    }
    leaf eDrxAllowed {
      type boolean;
    }
    list activePlmnList {
      config false;
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf-list plmnAlarmSupprList {
      type boolean;
    }
    leaf cmcIndex {
      type eytypes:int32_range_0-2;
      description "range 0..2.";
    }
    leaf hostingDigitalUnitRef {
      type string;
      config false;
    }
    list intraFrequencyInfo {
      key "id";
      leaf id {
        type uint32;
        description "Synthetic key for struct entry.";
      }
      container attributes {
      leaf pMax {
        type int32;
        default "1000";
        units "dBm";
        description "Default value: 1000.";
      }
      leaf qQualMin {
        type int32;
        default "0";
        units "dB";
        description "Default value: 0.";
      }
      leaf qRxLevMin {
        type int32 {
          range "-156..-44";
        }
        default "-140";
        units "dBm";
        description "range -156..-44; Default value: -140.";
      }
      leaf tReselection {
        type int32;
        default "6";
        units "s";
        description "Default value: 6.";
      }
      }
    }
    leaf zzzTemporary11 {
      type int32;
    }
    leaf zzzTemporary12 {
      type int32;
    }
    leaf zzzTemporary13 {
      type int32;
    }
    leaf zzzTemporary14 {
      type int32;
    }
    leaf zzzTemporary15 {
      type int32;
    }
    leaf zzzTemporary16 {
      type int32;
    }
    leaf zzzTemporary17 {
      type string;
    }
    leaf zzzTemporary18 {
      type string;
    }
    list plmnIdList {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf zzzTemporary19 {
      type int32;
    }
    leaf zzzTemporary20 {
      type int32;
    }
    leaf ceLevelNumber {
      type eytypes:int32_range_1-3;
      default "3";
      description "range 1..3; Default value: 3.";
    }
    leaf zzzTemporary21 {
      type int32;
      status deprecated;
      default "-2000000000";
      description "Default value: -2000000000; Status info: Since 25.Q1. Replaced by NbIotCell::connEstFailOffset. Planned to be removed..";
    }
    leaf gbPrbIndexDl {
      type int32 {
        range "-1 | 1";
      }
      status deprecated;
      default "1";
      description "Default value: 1; Takes effect: Next cell unlock; Status info: Since 18.Q3. Replaced by dlAnchPrbIndex. Planned to be removed..";
      reference "Takes effect: Next cell unlock.";
    }
    leaf gbPrbIndexUl {
      type int32 {
        range "-6..-1 | 1..6";
      }
      status deprecated;
      default "1";
      description "Default value: 1; Takes effect: Next cell unlock; Status info: Since 18.Q3. Replaced by ulAnchPrbIndex. Planned to be removed..";
      reference "Takes effect: Next cell unlock.";
    }
    leaf-list additionalFreqBandList {
      type eytypes:int32_range_1-256;
    }
    leaf-list additionalSpectrumEmissionValues {
      type enumeration {
        enum NS_01;
        enum NS_03;
        enum NS_04;
        enum NS_05;
        enum NS_06;
        enum NS_07;
        enum NS_08;
        enum NS_09;
        enum NS_10;
        enum NS_11;
        enum NS_12;
        enum NS_13;
        enum NS_14;
        enum NS_15;
        enum NS_16;
        enum NS_17;
        enum NS_18;
        enum NS_19;
        enum NS_20;
        enum NS_21;
        enum NS_22;
        enum NS_23;
        enum NS_24;
        enum NS_25;
        enum NS_26;
        enum NS_27;
        enum NS_28;
        enum NS_29;
        enum NS_30;
        enum NS_31;
        enum NS_32;
        enum NS_35;
      }
    }
    list spectrumEmissionReqMapping {
      key "id";
      leaf id {
        type uint32;
        description "Synthetic key for struct sequence entry.";
      }
      container attributes {
      leaf freqBand {
        type eytypes:int32_range_1-256;
        default "1";
        description "range 1..256; Default value: 1.";
      }
      leaf spectrumEmissionReq {
        type enumeration {
          enum NS_01;
          enum NS_03;
          enum NS_04;
          enum NS_05;
          enum NS_06;
          enum NS_07;
          enum NS_08;
          enum NS_09;
          enum NS_10;
          enum NS_11;
          enum NS_12;
          enum NS_13;
          enum NS_14;
          enum NS_15;
          enum NS_16;
          enum NS_17;
          enum NS_18;
          enum NS_19;
          enum NS_20;
          enum NS_21;
          enum NS_22;
          enum NS_23;
          enum NS_24;
          enum NS_25;
          enum NS_26;
          enum NS_27;
          enum NS_28;
          enum NS_29;
          enum NS_30;
          enum NS_31;
          enum NS_32;
          enum NS_35;
        }
      }
      }
    }
    leaf networkSignallingValue {
      type enumeration {
        enum NS_01;
        enum NS_03;
        enum NS_04;
        enum NS_05;
        enum NS_06;
        enum NS_07;
        enum NS_08;
        enum NS_09;
        enum NS_10;
        enum NS_11;
        enum NS_12;
        enum NS_13;
        enum NS_14;
        enum NS_15;
        enum NS_16;
        enum NS_17;
        enum NS_18;
        enum NS_19;
        enum NS_20;
        enum NS_21;
        enum NS_22;
        enum NS_23;
        enum NS_24;
        enum NS_25;
        enum NS_26;
        enum NS_27;
        enum NS_28;
        enum NS_29;
        enum NS_30;
        enum NS_31;
        enum NS_32;
        enum NS_35;
      }
    }
    leaf enableMfbi {
      type boolean;
      default "false";
      description "Default value: false.";
    }
    leaf zzzTemporary22 {
      type int32;
      default "-2000000000";
      description "Default value: -2000000000.";
    }
    leaf cellRange {
      type int32 {
        range "1..120";
      }
      default "10";
      units "km";
      description "range 1..120; Default value: 10.";
    }
    leaf tTatDedicatedNbCe0 {
      type int32 {
        range "0 | 500 | 750 | 1280 | 1920 | 2560 | 5120 | 10240";
      }
      default "0";
      units "ms";
      description "Default value: 0.";
    }
    leaf tTatDedicatedNbCe1 {
      type int32 {
        range "0 | 500 | 750 | 1280 | 1920 | 2560 | 5120 | 10240";
      }
      default "0";
      units "ms";
      description "Default value: 0.";
    }
    leaf tTatDedicatedNbCe2 {
      type int32 {
        range "0 | 500 | 750 | 1280 | 1920 | 2560 | 5120 | 10240";
      }
      default "0";
      units "ms";
      description "Default value: 0.";
    }
    leaf useHostCellPci {
      type boolean;
      default "true";
      description "Default value: true.";
    }
    leaf rsrpThreshold1 {
      type int32 {
        range "-140..-44 | -1";
      }
      default "-1";
      units "dBm";
      description "Default value: -1.";
    }
    leaf rsrpThreshold2 {
      type int32 {
        range "-140..-44 | -1";
      }
      default "-1";
      units "dBm";
      description "Default value: -1.";
    }
    leaf preambleIniRecTargetPower {
      type eytypes:int32_range_-120--90;
      default "-114";
      units "dBm";
      description "range -120..-90; Default value: -114.";
    }
    leaf alpha {
      type int32 {
        range "0 | 4..10";
      }
      default "10";
      description "Default value: 10.";
    }
    leaf nprachCapMode4RxEnabled {
      type boolean;
      default "false";
      description "Default value: false.";
    }
    leaf userLabel {
      type string {
        length "1..128";
      }
      description "length 1..128.";
    }
    leaf primaryFreqBand {
      type int32 {
        range "-1 | 1..256";
      }
      default "-1";
      description "Default value: -1.";
    }
    leaf anchPowerBoostGainIndex {
      type enumeration {
        enum ANCHOR_POWER_RATIO_1_1;
        enum ANCHOR_POWER_RATIO_2_1;
        enum ANCHOR_POWER_RATIO_3_1;
        enum ANCHOR_POWER_RATIO_4_1;
      }
    }
    leaf dlAnchPrbIndex {
      type int32 {
        range "-10..110 | 255";
      }
      default "255";
      description "Default value: 255.";
    }
    leaf ulAnchPrbIndex {
      type int32 {
        range "-10..110 | 255";
      }
      default "255";
      description "Default value: 255.";
    }
    leaf dlNonAnchPrbNum {
      type eytypes:int32_range_0-7;
      default "0";
      description "range 0..7; Default value: 0.";
    }
    leaf ulNonAnchPrbNum {
      type eytypes:int32_range_0-7;
      default "0";
      description "range 0..7; Default value: 0.";
    }
    leaf-list dlAllocatedPrb {
      type int32 {
        range "-10..110 | 255";
      }
    }
    leaf-list ulAllocatedPrb {
      type int32 {
        range "-10..110 | 255";
      }
    }
    leaf nbDlSinrAdjust {
      type eytypes:int32_range_-200-200;
      default "0";
      units "dB";
      description "range -200..200; Default value: 0.";
    }
    leaf-list dlNonAnchPrbIndex {
      type int32 {
        range "-3..102";
      }
    }
    leaf-list ulNonAnchPrbIndex {
      type int32 {
        range "-3..102";
      }
    }
    leaf tRrcConnReest {
      type eytypes:int32_range_1-60;
      default "15";
      units "s";
      description "range 1..60; Default value: 15.";
    }
    leaf tWaitForMmeCpRelocInd {
      type eytypes:int32_range_1-60;
      default "15";
      units "s";
      description "range 1..60; Default value: 15.";
    }
    leaf latitude {
      type eytypes:int32_range_-90000000-90000000;
      default "0";
      units "degrees";
      description "range -90000000..90000000; Default value: 0.";
    }
    leaf longitude {
      type eytypes:int32_range_-180000000-180000000;
      default "0";
      units "degrees";
      description "range -180000000..180000000; Default value: 0.";
    }
    leaf raiEnabled {
      type boolean;
      default "false";
      description "Default value: false.";
    }
    list nbIotCellPolygon {
      key "id";
      leaf id {
        type uint32;
        description "Synthetic key for struct sequence entry.";
      }
      container attributes {
      leaf cornerLatitude {
        type eytypes:int32_range_-90000000-90000000;
        default "0";
        units "degrees";
        description "range -90000000..90000000; Default value: 0.";
      }
      leaf cornerLongitude {
        type eytypes:int32_range_-180000000-180000000;
        default "0";
        units "degrees";
        description "range -180000000..180000000; Default value: 0.";
      }
      }
    }
    list nbIotCellCoverage {
      key "id";
      leaf id {
        type uint32;
        description "Synthetic key for struct entry.";
      }
      container attributes {
      leaf posCellRadius {
        type eytypes:int32_range_0-200000;
        default "0";
        units "meter";
        description "range 0..200000; Default value: 0.";
      }
      leaf posCellOpeningAngle {
        type eytypes:int32_range_-1-3599;
        default "-1";
        units "degrees";
        description "range -1..3599; Default value: -1.";
      }
      leaf posCellBearing {
        type eytypes:int32_range_-1-3599;
        default "-1";
        units "degrees";
        description "range -1..3599; Default value: -1.";
      }
      }
    }
    leaf raiReleaseDelayTimer {
      type int32 {
        range "0..600";
      }
      default "5";
      units "s";
      description "range 0..600; Default value: 5.";
    }
    leaf npuschGroupHopConfig {
      type enumeration {
        enum GROUP_HOP_DISABLED;
        enum GROUP_HOP_ENABLED;
      }
    }
    leaf nprachAllocConfig {
      type enumeration {
        enum BASIC_CONFIG;
        enum OPTIMIZED_CONFIG_1;
        enum OPTIMIZED_CONFIG_2;
      }
    }
    leaf maxRrcConnectedUsers {
      type int32 {
        range "1..96";
      }
      default "32";
      description "range 1..96; Default value: 32.";
    }
    leaf ulAnchPrbUtilThr {
      type eytypes:int32_range_0-100;
      default "55";
      units "percent";
      description "range 0..100; Default value: 55.";
    }
    leaf dlAnchPrbUtilThr {
      type eytypes:int32_range_0-100;
      default "65";
      units "percent";
      description "range 0..100; Default value: 65.";
    }
    leaf ulNonAnchPrbUtilThr {
      type eytypes:int32_range_0-100;
      default "70";
      units "percent";
      description "range 0..100; Default value: 70.";
    }
    leaf dlNonAnchPrbUtilThr {
      type eytypes:int32_range_0-100;
      default "70";
      units "percent";
      description "range 0..100; Default value: 70.";
    }
    leaf raBackoffNbCe0 {
      type enumeration {
        enum NO_BACKOFF;
        enum STATIC_BACKOFF_256MS;
        enum STATIC_BACKOFF_512MS;
        enum STATIC_BACKOFF_1024MS;
        enum STATIC_BACKOFF_2048MS;
        enum STATIC_BACKOFF_4096MS;
        enum STATIC_BACKOFF_8192MS;
        enum STATIC_BACKOFF_16384MS;
        enum STATIC_BACKOFF_32768MS;
        enum STATIC_BACKOFF_65536MS;
        enum STATIC_BACKOFF_131072MS;
        enum STATIC_BACKOFF_262144MS;
        enum STATIC_BACKOFF_524288MS;
        enum DYNAMIC_BACKOFF;
      }
    }
    leaf raBackoffNbCe1 {
      type enumeration {
        enum NO_BACKOFF;
        enum STATIC_BACKOFF_256MS;
        enum STATIC_BACKOFF_512MS;
        enum STATIC_BACKOFF_1024MS;
        enum STATIC_BACKOFF_2048MS;
        enum STATIC_BACKOFF_4096MS;
        enum STATIC_BACKOFF_8192MS;
        enum STATIC_BACKOFF_16384MS;
        enum STATIC_BACKOFF_32768MS;
        enum STATIC_BACKOFF_65536MS;
        enum STATIC_BACKOFF_131072MS;
        enum STATIC_BACKOFF_262144MS;
        enum STATIC_BACKOFF_524288MS;
        enum DYNAMIC_BACKOFF;
      }
    }
    leaf raBackoffNbCe2 {
      type enumeration {
        enum NO_BACKOFF;
        enum STATIC_BACKOFF_256MS;
        enum STATIC_BACKOFF_512MS;
        enum STATIC_BACKOFF_1024MS;
        enum STATIC_BACKOFF_2048MS;
        enum STATIC_BACKOFF_4096MS;
        enum STATIC_BACKOFF_8192MS;
        enum STATIC_BACKOFF_16384MS;
        enum STATIC_BACKOFF_32768MS;
        enum STATIC_BACKOFF_65536MS;
        enum STATIC_BACKOFF_131072MS;
        enum STATIC_BACKOFF_262144MS;
        enum STATIC_BACKOFF_524288MS;
        enum DYNAMIC_BACKOFF;
      }
    }
    leaf nbIotAcPresence {
      type enumeration {
        enum OFF;
        enum ON;
      }
    }
    leaf largeRmaxUeDlAnchThr {
      type eytypes:int32_range_0-1000-2;
      status deprecated;
      default "100";
      description "range 0..1000; Default value: 100; Takes effect: Next cell unlock; Status info: Since 21.Q1. Replaced by largeRmaxUeAnchThr. Planned to be removed..";
      reference "Takes effect: Next cell unlock.";
    }
    leaf largeRmaxUeUlAnchThr {
      type eytypes:int32_range_0-1000-2;
      status deprecated;
      default "100";
      description "range 0..1000; Default value: 100; Takes effect: Next cell unlock; Status info: Since 21.Q1. Replaced by largeRmaxUeAnchThr. Planned to be removed..";
      reference "Takes effect: Next cell unlock.";
    }
    leaf nonPolledReleaseCfg {
      type enumeration {
        enum OFF_FOR_ALL_UE;
        enum ON_FOR_ALL_UE;
        enum ON_FOR_REL14_AND_LATER_UE;
      }
    }
    list msg3CqiAdjustFactorCe {
      key "id";
      leaf id {
        type uint32;
        description "Synthetic key for struct entry.";
      }
      container attributes {
      leaf ceLevel0 {
        type eytypes:int32_range_-4-4;
        default "0";
        description "range -4..4; Default value: 0.";
      }
      leaf ceLevel1 {
        type eytypes:int32_range_-4-4;
        default "0";
        description "range -4..4; Default value: 0.";
      }
      leaf ceLevel2 {
        type eytypes:int32_range_-4-4;
        default "2";
        description "range -4..4; Default value: 2.";
      }
      }
    }
    leaf msg3CqiReportEnabled {
      type ietfinet:port-number;
      description "Default value: true.";
    }
    leaf msg5MeasReportEnabled {
      type ietfinet:port-number;
      description "Default value: false.";
    }
    leaf abPresence {
      type enumeration {
        enum OFF;
        enum AUTO;
        enum MANUAL;
      }
    }
    leaf activeAbCategory {
      type enumeration {
        enum CATEGORY_A;
        enum CATEGORY_B;
        enum CATEGORY_C;
        enum OFF;
      }
      config false;
    }
    leaf activeAbBitmap {
      type int32 {
        range "-1..1023";
      }
      config false;
      description "range -1..1023.";
    }
    leaf activeAbBarringBitmapSpec {
      type int32 {
        range "-1..31";
      }
      config false;
      description "range -1..31.";
    }
    leaf activeAbException {
      type enumeration {
        enum FALSE;
        enum TRUE;
        enum OFF;
      }
      config false;
    }
    leaf activeAbPerNrsrp {
      type enumeration {
        enum OFF;
        enum THRESH1;
        enum THRESH2;
      }
      config false;
    }
    leaf abThreshRejectHigh {
      type int32 {
        range "1..1000";
      }
      default "10";
      units "percent";
      description "range 1..1000; Default value: 10.";
    }
    leaf abThreshRejectLow {
      type eytypes:int32_range_0-1000-11;
      default "5";
      units "percent";
      description "range 0..1000; Default value: 5.";
    }
    leaf abThreshTimeHigh {
      type int32 {
        range "5..4095";
      }
      default "30";
      units "s";
      description "range 5..4095; Default value: 30.";
    }
    leaf abThreshTimeLow {
      type int32 {
        range "5..4095";
      }
      default "30";
      units "s";
      description "range 5..4095; Default value: 30.";
    }
    leaf abMinIntensityThreshold {
      type eytypes:int32_range_0-32767;
      default "50";
      description "range 0..32767; Default value: 50.";
    }
    leaf abIntensityObsrvPeriod {
      type eytypes:int32_range_1-4095;
      default "120";
      units "s";
      description "range 1..4095; Default value: 120.";
    }
    leaf-list abConfProfileRef {
      type string;
    }
    leaf abContConfFromLastProfile {
      type boolean;
      default "false";
      description "Default value: false.";
    }
    list dataInactivityTimer {
      key "id";
      leaf id {
        type uint32;
        description "Synthetic key for struct entry.";
      }
      container attributes {
      leaf dataInactivityTimerCe0 {
        type int32;
        default "200";
        units "s";
        description "Default value: 200.";
      }
      leaf dataInactivityTimerCe1 {
        type int32;
        default "400";
        units "s";
        description "Default value: 400.";
      }
      leaf dataInactivityTimerCe2 {
        type int32;
        default "600";
        units "s";
        description "Default value: 600.";
      }
      }
    }
    list inactivitySupervisionTimer {
      key "id";
      leaf id {
        type uint32;
        description "Synthetic key for struct entry.";
      }
      container attributes {
      leaf inactivitySupervisionTimerCe0 {
        type eytypes:int32_range_0-2000-24;
        default "50";
        units "s";
        description "range 0..2000; Default value: 50.";
      }
      leaf inactivitySupervisionTimerCe1 {
        type eytypes:int32_range_0-2000-24;
        default "100";
        units "s";
        description "range 0..2000; Default value: 100.";
      }
      leaf inactivitySupervisionTimerCe2 {
        type eytypes:int32_range_0-2000-24;
        default "200";
        units "s";
        description "range 0..2000; Default value: 200.";
      }
      }
    }
    list raDlSinrAdjustCe {
      key "id";
      leaf id {
        type uint32;
        description "Synthetic key for struct entry.";
      }
      container attributes {
      leaf raDlSinrAdjustCe0 {
        type eytypes:int32_range_-300-300;
        default "30";
        units "dB";
        description "range -300..300; Default value: 30.";
      }
      leaf raDlSinrAdjustCe1 {
        type eytypes:int32_range_-300-300;
        default "0";
        units "dB";
        description "range -300..300; Default value: 0.";
      }
      leaf raDlSinrAdjustCe2 {
        type eytypes:int32_range_-300-300;
        default "30";
        units "dB";
        description "range -300..300; Default value: 30.";
      }
      }
    }
    leaf dlLaIpnAbsolute {
      type ietfinet:ip-address;
      units "dBm";
      description "range -1500..-500; Default value: -1233.";
    }
    leaf nbIotDynOverloadDlAnchThr {
      type eytypes:int32_range_0-100;
      default "50";
      units "percent";
      description "range 0..100; Default value: 50.";
    }
    leaf nbIotDynOverloadDlNonAnchThr {
      type eytypes:int32_range_0-100;
      default "75";
      units "percent";
      description "range 0..100; Default value: 75.";
    }
    leaf nbIotDynOverloadUlAnchThr {
      type eytypes:int32_range_0-100;
      default "45";
      units "percent";
      description "range 0..100; Default value: 45.";
    }
    leaf nbIotDynOverloadUlNonAnchThr {
      type eytypes:int32_range_0-100;
      default "75";
      units "percent";
      description "range 0..100; Default value: 75.";
    }
    leaf zzzTemporary23 {
      type int32;
      default "-2000000000";
      description "Default value: -2000000000.";
    }
    leaf zzzTemporary24 {
      type int32;
      default "-2000000000";
      description "Default value: -2000000000.";
    }
    leaf zzzTemporary25 {
      type int32;
      default "-2000000000";
      description "Default value: -2000000000.";
    }
    leaf zzzTemporary26 {
      type int32;
      default "-2000000000";
      description "Default value: -2000000000.";
    }
    leaf minNumLargeRmaxUes {
      type eytypes:int32_range_0-10;
      default "2";
      description "range 0..10; Default value: 2.";
    }
    leaf largeRmaxUeAnchThr {
      type eytypes:int32_range_0-1000-2;
      default "100";
      description "range 0..1000; Default value: 100.";
    }
    list raNprachSinrAdjustCe {
      key "id";
      leaf id {
        type uint32;
        description "Synthetic key for struct entry.";
      }
      container attributes {
      leaf raNprachSinrAdjustCe0 {
        type eytypes:int32_range_-300-300;
        default "-60";
        units "dB";
        description "range -300..300; Default value: -60.";
      }
      leaf raNprachSinrAdjustCe1 {
        type eytypes:int32_range_-300-300;
        default "-110";
        units "dB";
        description "range -300..300; Default value: -110.";
      }
      leaf raNprachSinrAdjustCe2 {
        type eytypes:int32_range_-300-300;
        default "-40";
        units "dB";
        description "range -300..300; Default value: -40.";
      }
      }
    }
    list raNpuschSinrAdjustCe {
      key "id";
      leaf id {
        type uint32;
        description "Synthetic key for struct entry.";
      }
      container attributes {
      leaf raNpuschSinrAdjustCe0 {
        type eytypes:int32_range_-300-300;
        default "0";
        units "dB";
        description "range -300..300; Default value: 0.";
      }
      leaf raNpuschSinrAdjustCe1 {
        type eytypes:int32_range_-300-300;
        default "0";
        units "dB";
        description "range -300..300; Default value: 0.";
      }
      leaf raNpuschSinrAdjustCe2 {
        type eytypes:int32_range_-300-300;
        default "0";
        units "dB";
        description "range -300..300; Default value: 0.";
      }
      }
    }
    leaf actualRsrpThreshold1 {
      type int32 {
        range "-140..-44 | -1";
      }
      config false;
      units "dBm";
    }
    leaf actualRsrpThreshold2 {
      type int32 {
        range "-140..-44 | -1";
      }
      config false;
      units "dBm";
    }
    leaf nprachSubcarrierForStMsg3Ce0 {
      type enumeration {
        enum ZERO;
        enum ONE_THIRD;
        enum TWO_THIRD;
        enum ONE;
      }
    }
    leaf nprachSubcarrierForStMsg3Ce1 {
      type enumeration {
        enum ZERO;
        enum ONE_THIRD;
        enum TWO_THIRD;
        enum ONE;
      }
    }
    leaf nprachSubcarrierForStMsg3Ce2 {
      type enumeration {
        enum ZERO;
        enum ONE_THIRD;
        enum TWO_THIRD;
        enum ONE;
      }
    }
    leaf rachPreambleTransMaxNb {
      type int32 {
        range "3..8 | 10 | 20 | 50 | 100 | 200";
      }
      default "8";
      description "Default value: 8.";
    }
    leaf maxNumPreambleAttemptNbCe0 {
      type int32 {
        range "3..8 | 10";
      }
      default "5";
      description "Default value: 5.";
    }
    leaf maxNumPreambleAttemptNbCe1 {
      type int32 {
        range "3..8 | 10";
      }
      default "5";
      description "Default value: 5.";
    }
    leaf maxNumPreambleAttemptNbCe2 {
      type int32 {
        range "3..8 | 10";
      }
      default "5";
      description "Default value: 5.";
    }
    leaf sIntraSearchDeltaP {
      type int32 {
        range "0 | 6 | 9 | 12 | 15";
      }
      default "0";
      units "dB";
      description "Default value: 0.";
    }
    leaf npbchRrmConfigEnabled {
      type boolean;
      default "false";
      description "Default value: false.";
    }
    leaf nsssRrmConfigEnabled {
      type boolean;
      default "false";
      description "Default value: false.";
    }
    leaf-list nsssRrmConfigInterFreq {
      type eytypes:int32_range_0-262143;
    }
    leaf enhancedRaPowerCtrl {
      type boolean;
      default "true";
      description "Default value: true.";
    }
    leaf enhancedPhr {
      type boolean;
      default "true";
      description "Default value: true.";
    }
    leaf preambleIniRecTargetPowerR14 {
      type int32 {
        range "-130..-122 | -88..-80 | 0";
      }
      default "0";
      units "dBm";
      description "Default value: 0.";
    }
    leaf preambleIniRecTargetPowerCe1 {
      type int32 {
        range "-130..-80";
      }
      default "-114";
      units "dBm";
      description "range -130..-80; Default value: -114.";
    }
    leaf-list nprachPeriodicity {
      type int32 {
        range "40 | 80 | 160 | 320 | 640 | 1280 | 2560 | 5120";
      }
    }
    leaf-list nprachStartTimeCe {
      type int32 {
        range "8 | 16 | 32 | 64 | 128 | 256 | 512 | 1024";
      }
    }
    leaf-list nprachSubcarrierOffsetCe {
      type int32 {
        range "0 | 2 | 12 | 18 | 24 | 34 | 36";
      }
    }
    leaf-list numRepNprach {
      type int32 {
        range "1..2 | 4 | 8 | 16 | 32 | 64 | 128";
      }
    }
    leaf-list cssRmaxForRa {
      type int32 {
        range "1..2 | 4 | 8 | 16 | 32 | 64 | 128 | 256 | 512 | 1024 | 2048";
      }
    }
    leaf-list ackNackNumRepMsg4 {
      type int32 {
        range "1..2 | 4 | 8 | 16 | 32 | 64 | 128";
      }
    }
    leaf microSleepTxPattern {
      type enumeration {
        enum ALL_ANTENNAS_ON;
        enum MAX_TWO_ANTENNAS_ON;
      }
    }
    list cDrxEnabled {
      key "id";
      leaf id {
        type uint32;
        description "Synthetic key for struct entry.";
      }
      container attributes {
      leaf cDrxEnabled0 {
        type boolean;
        default "false";
        description "Default value: false.";
      }
      leaf cDrxEnabled1 {
        type boolean;
        default "false";
        description "Default value: false.";
      }
      leaf cDrxEnabled2 {
        type boolean;
        default "false";
        description "Default value: false.";
      }
      }
    }
    leaf preschedUlGrantDelay {
      type eytypes:int32_range_0-100-12;
      default "5";
      units "ms";
      description "range 0..100; Default value: 5.";
    }
    leaf rlcStatusPduDelayDl {
      type eytypes:int32_range_0-100-12;
      default "5";
      units "ms";
      description "range 0..100; Default value: 5.";
    }
    leaf dvFactorForMsg5 {
      type eytypes:int32_range_0-100;
      default "75";
      units "percent";
      description "range 0..100; Default value: 75.";
    }
    list logicalChannelSrProhibitTimer {
      key "id";
      leaf id {
        type uint32;
        description "Synthetic key for struct entry.";
      }
      container attributes {
      leaf srProhibitTimer0 {
        type int32;
        default "32";
        description "Default value: 32.";
      }
      leaf srProhibitTimer1 {
        type int32;
        default "32";
        description "Default value: 32.";
      }
      leaf srProhibitTimer2 {
        type int32;
        default "2";
        description "Default value: 2.";
      }
      }
    }
    list periodicBsrTimerDedicated {
      key "id";
      leaf id {
        type uint32;
        description "Synthetic key for struct entry.";
      }
      container attributes {
      leaf periodicBsrTimer0 {
        type int32;
        default "8";
        description "Default value: 8.";
      }
      leaf periodicBsrTimer1 {
        type int32;
        default "4";
        description "Default value: 4.";
      }
      leaf periodicBsrTimer2 {
        type int32;
        default "2";
        description "Default value: 2.";
      }
      }
    }
    list retxBsrTimerDedicated {
      key "id";
      leaf id {
        type uint32;
        description "Synthetic key for struct entry.";
      }
      container attributes {
      leaf retxBsrTimer0 {
        type int32;
        default "128";
        description "Default value: 128.";
      }
      leaf retxBsrTimer1 {
        type int32;
        default "64";
        description "Default value: 64.";
      }
      leaf retxBsrTimer2 {
        type int32;
        default "16";
        description "Default value: 16.";
      }
      }
    }
    leaf dlGapEnabled {
      type boolean;
      default "true";
      description "Default value: true.";
    }
    leaf dlGapThreshold {
      type int32 {
        range "-1 | 32 | 64 | 128 | 256";
      }
      default "-1";
      description "Default value: -1.";
    }
    list dlLaNpdcchTargetBler {
      key "id";
      leaf id {
        type uint32;
        description "Synthetic key for struct entry.";
      }
      container attributes {
      leaf dlLaNpdcchTargetBlerCe0 {
        type eytypes:int32_range_0-20;
        default "10";
        description "range 0..20; Default value: 10.";
      }
      leaf dlLaNpdcchTargetBlerCe1 {
        type eytypes:int32_range_0-20;
        default "10";
        description "range 0..20; Default value: 10.";
      }
      leaf dlLaNpdcchTargetBlerCe2 {
        type eytypes:int32_range_0-20;
        default "10";
        description "range 0..20; Default value: 10.";
      }
      }
    }
    leaf maxNumRarMultiplexing {
      type ietfinet:ip-address;
      description "range 1..2; Default value: 2.";
    }
    leaf nprachPeriodCe0 {
      type int32 {
        range "-1 | 40 | 80 | 160 | 320 | 640";
      }
      default "-1";
      units "ms";
      description "Default value: -1.";
    }
    leaf nprachPeriodCe1 {
      type int32 {
        range "-1 | 160 | 320 | 640 | 1280";
      }
      default "-1";
      units "ms";
      description "Default value: -1.";
    }
    leaf nprachPeriodCe2 {
      type int32 {
        range "-1 | 640 | 1280 | 2560";
      }
      default "-1";
      units "ms";
      description "Default value: -1.";
    }
    leaf pagingMaxSinr {
      type int32 {
        range "-30..6";
      }
      default "3";
      units "dB";
      description "range -30..6; Default value: 3.";
    }
    leaf pagingOlaSinrDownStepSize {
      type eytypes:int32_range_0-12;
      default "3";
      units "dB";
      description "range 0..12; Default value: 3.";
    }
    leaf pagingInitSinrNoAssistData {
      type int32 {
        range "-30..6";
      }
      default "-3";
      units "dB";
      description "range -30..6; Default value: -3.";
    }
    leaf dlChannelRasterOffset {
      type int32 {
        range "-75 | -25 | 0 | 25 | 75";
      }
      default "0";
      units "kHz";
      description "Default value: 0.";
    }
    leaf ulChannelRasterOffset {
      type int32 {
        range "-50 | 0 | 50";
      }
      default "0";
      units "kHz";
      description "Default value: 0.";
    }
    leaf connEstFailOffset {
      type int32 {
        range "-1..15";
      }
      default "0";
      description "range -1..15; Default value: 0.";
    }
    leaf zzzTemporary27 {
      type int32;
      default "-2000000000";
      description "Default value: -2000000000.";
    }
    leaf zzzTemporary28 {
      type int32;
      default "-2000000000";
      description "Default value: -2000000000.";
    }
    leaf zzzTemporary29 {
      type int32;
      default "-2000000000";
      description "Default value: -2000000000.";
    }
    leaf zzzTemporary30 {
      type int32;
      default "-2000000000";
      description "Default value: -2000000000.";
    }
    leaf zzzTemporary31 {
      type int32;
      default "-2000000000";
      description "Default value: -2000000000.";
    }
    leaf rachPowerRampingStep {
      type int32 {
        range "0 | 2 | 4 | 6";
      }
      default "2";
      units "dB";
      description "Default value: 2.";
    }
    leaf maxNumOfDlInfoTrans {
      type eytypes:int32_range_1-100-4;
      default "20";
      description "range 1..100; Default value: 20.";
    }
    list validDlSubframes {
      key "id";
      leaf id {
        type uint32;
        description "Synthetic key for struct entry.";
      }
      container attributes {
      leaf subframesBitmap0 {
        type eytypes:int32_range_561-1023;
        default "1023";
        description "range 561..1023; Default value: 1023.";
      }
      leaf subframesBitmap1 {
        type eytypes:int32_range_561-1023;
        default "1023";
        description "range 561..1023; Default value: 1023.";
      }
      leaf subframesBitmap2 {
        type eytypes:int32_range_561-1023;
        default "1023";
        description "range 561..1023; Default value: 1023.";
      }
      leaf subframesBitmap3 {
        type eytypes:int32_range_561-1023;
        default "1023";
        description "range 561..1023; Default value: 1023.";
      }
      }
    }
    list usedValidDlSubframes {
      config false;
      container attributes {
      leaf subframesBitmap0 {
        type eytypes:int32_range_561-1023;
        default "1023";
        description "range 561..1023; Default value: 1023.";
      }
      leaf subframesBitmap1 {
        type eytypes:int32_range_561-1023;
        default "1023";
        description "range 561..1023; Default value: 1023.";
      }
      leaf subframesBitmap2 {
        type eytypes:int32_range_561-1023;
        default "1023";
        description "range 561..1023; Default value: 1023.";
      }
      leaf subframesBitmap3 {
        type eytypes:int32_range_561-1023;
        default "1023";
        description "range 561..1023; Default value: 1023.";
      }
      }
    }
    leaf pmRrcConnCe2Max {
      type int32;
      config false;
    }
    leaf-list pmRrcConnEstabFailDuIntensCe {
      type uint32;
    }
    leaf-list pmRaMsg4HarqDtxDistr {
      type uint32;
    }
    leaf pmS1SigConnEstabFailMmeOvlMos {
      type uint32;
      config false;
      status deprecated;
      description "MOM flags: noNotification.";
    }
    leaf pmUeReleasePendingDataCe2 {
      type uint32;
      config false;
    }
    leaf-list pmRrcConnEstabFailMmeOvlMtaCe {
      type uint32;
    }
    leaf-list pmRrcConnEstabSuccUlCe2Distr {
      type uint32;
      description "MOM flags: noNotification.";
    }
    leaf-list pmUeMeasNrsrqMsg5Distr {
      type uint32;
    }
    leaf pmUeCtxtRelAbnormalEnbAct {
      type uint32;
      config false;
      status deprecated;
      description "MOM flags: noNotification.";
    }
    leaf pmPendingDataCheckCe2 {
      type uint32;
      config false;
    }
    leaf-list pmRrcConnTimeCe2Distr {
      type uint32;
    }
    leaf-list pmAcBarringNrsrpDistr {
      type ietfyang:mac-address;
    }
    leaf-list pmUeSessionVolDlCe0Distr {
      type uint32;
    }
    leaf-list pmMacEnhancedPhrCe1Distr {
      type ietfyang:mac-address;
    }
    leaf-list pmRrcConnEstabAttMtaCe {
      type uint32;
    }
    leaf pmErabEstabAttInit {
      type uint32;
      config false;
      status deprecated;
      description "MOM flags: noNotification.";
    }
    leaf pmRrcConnLevSamp {
      type uint32;
      config false;
      status deprecated;
      description "MOM flags: noNotification.";
    }
    leaf-list pmRrcFastReturnMmeMtTimeDistr {
      type uint32;
    }
    leaf-list pmRrcConnSetupTimeCe2Distr {
      type uint32;
    }
    leaf-list pmRaSuccFreqOffsetDistr {
      type uint32;
    }
    leaf pmRrcConnReestFailMpMem {
      type uint32;
      config false;
    }
    leaf-list pmNpdschUtilDistr {
      type uint32;
    }
    leaf pmUeCtxtRelAbnormalMme {
      type uint32;
      config false;
      status deprecated;
      description "MOM flags: noNotification.";
    }
    leaf-list pmRaMsg3ThreeToneDistr {
      type uint32;
    }
    leaf-list pmRaBackoffNbCe2Distr {
      type uint32;
    }
    leaf-list pmRrcConnEstabSuccDlCe1Distr {
      type uint32;
      description "MOM flags: noNotification.";
    }
    leaf pmCellDowntimeAuto {
      type uint32;
      config false;
    }
    leaf-list pmRrcConnEstabSuccDtaCe {
      type uint32;
    }
    leaf-list pmRaMsg4HarqFailDistr {
      type uint32;
    }
    leaf-list pmRrcConnEstabSuccMosCe {
      type uint32;
    }
    leaf-list pmMacHarqUlDtxBpskCe {
      type ietfyang:mac-address;
    }
    leaf-list pmMacHarqUlMaxTxQpskCe {
      type ietfyang:mac-address;
    }
    leaf-list pmRrcConnEstabFailUeAcMtaCe {
      type uint32;
    }
    leaf-list pmNbUeCe1UlCarrierDistr {
      type uint32;
    }
    leaf-list pmRrcConnEstabAttModCe {
      type uint32;
    }
    leaf-list pmNpuschSingleToneDistr {
      type uint32;
    }
    leaf-list pmRrcConnEstabFailMmeOvlMoedCe {
      type uint32;
    }
    leaf-list pmZTemporary218 {
      type uint32;
    }
    leaf-list pmZTemporary221 {
      type uint32;
    }
    leaf-list pmNpdcchRmaxUssCe1Distr {
      type uint32;
    }
    leaf pmUeCapabilityInterferRand {
      type uint32;
      config false;
    }
    leaf-list pmUeSessionVolDlCe1Distr {
      type uint32;
    }
    leaf pmUeCapabilityMixOperMode {
      type uint32;
      config false;
    }
    leaf pmUeCapabilitySingleTone {
      type uint32;
      config false;
    }
    leaf pmUeCtxtRelAbnormalEnb {
      type uint32;
      config false;
      status deprecated;
      description "MOM flags: noNotification.";
    }
    leaf-list pmRrcConnEstabFailUeAcMoedCe {
      type uint32;
    }
    leaf-list pmUeCtxtRelAbnormalEnbCe {
      type uint32;
    }
    leaf-list pmAcBarringCatBDistr {
      type ietfyang:mac-address;
    }
    leaf-list pmNpuschF2RepCe2Distr {
      type uint32;
    }
    leaf-list pmRrcConnMax {
      type uint32;
      description "MOM flags: noNotification.";
    }
    leaf-list pmMacHarqUlFailBpskCe {
      type ietfyang:mac-address;
    }
    leaf-list pmRrcConnEstabFailUeAcAnchCe {
      type uint32;
    }
    leaf-list pmUeCtxtRelMmeActCe {
      type uint32;
    }
    leaf-list pmRrcConnEstabFailCellIntensDLCCe {
      type uint32;
    }
    leaf pmZTemporary216 {
      type uint32;
      config false;
    }
    leaf pmZTemporary212 {
      type uint32;
      config false;
    }
    leaf-list pmNbUeCe2UlCarrierDistr {
      type uint32;
    }
    leaf pmCellDownLockMan {
      type uint32;
      config false;
    }
    leaf-list pmUeCapabilityAsrNbDistr {
      type uint32;
    }
    leaf-list pmRrcConnEstabFailUeAcModCe {
      type uint32;
    }
    leaf-list pmRrcConnReestFailMmeCe {
      type uint32;
    }
    leaf-list pmRaAttCbraNbCe2Distr {
      type uint32;
    }
    leaf-list pmMacHarqUlDtxQpskCe {
      type ietfyang:mac-address;
    }
    leaf pmPagReceivedNb {
      type uint32;
      config false;
    }
    leaf-list pmUeCtxtRelNormalEnbRaiCe {
      type uint32;
    }
    leaf-list pmRrcConnEstabSuccCe {
      type uint32;
    }
    leaf-list pmUeCtxtRelNormalEnbCe {
      type uint32;
    }
    leaf pmMacHarqDlNackQpsk {
      type ietfyang:mac-address;
      config false;
      status deprecated;
      description "MOM flags: noNotification.";
    }
    leaf pmPendingDataCheckCe1 {
      type uint32;
      config false;
    }
    leaf-list pmNpuschTbsDistr {
      type uint32;
    }
    leaf-list pmMacHarqUlMaxTxBpskCe {
      type ietfyang:mac-address;
    }
    leaf-list pmUeCtxtRelMmeCe {
      type uint32;
    }
    leaf-list pmRrcConnEstabFailCellIntensSwCCe {
      type uint32;
    }
    leaf pmNpdcchResyncSucc {
      type uint32;
      config false;
    }
    leaf-list pmRrcConnEstabFailDuSwCCe {
      type uint32;
    }
    leaf-list pmNpuschF2RepCe0Distr {
      type uint32;
    }
    leaf-list pmRrcFastReturnRaiMoTimeDistr {
      type uint32;
    }
    leaf-list pmRaMsg4HarqNackDistr {
      type uint32;
    }
    leaf-list pmS1SigConnEstabAttCe {
      type uint32;
    }
    leaf-list pmNpuschMcsSixToneDistr {
      type uint32;
    }
    leaf pmZTemporary209 {
      type uint32;
      config false;
    }
    leaf pmPagReceived {
      type uint32;
      config false;
      status deprecated;
      description "MOM flags: noNotification.";
    }
    leaf-list pmSinrNpuschDistr {
      type uint32;
    }
    leaf-list pmDrxSleepTimeRateDistr1 {
      type uint32;
    }
    leaf pmNasNonDeliveryIndTrans {
      type uint32;
      config false;
    }
    leaf-list pmRrcConnReestFailUeAcAnchCe {
      type uint32;
    }
    leaf-list pmRrcConnTimeCe1Distr {
      type uint32;
    }
    leaf-list pmRaAttCbraNbCe1Distr {
      type uint32;
    }
    leaf-list pmUeCtxtRelAbnormalEnbActCdtCe {
      type uint32;
    }
    leaf-list pmRaAttCbraNbCe0Distr {
      type uint32;
    }
    leaf-list pmUeSessionVolUlCe0Distr {
      type uint32;
    }
    leaf pmRrcConnCe2Sum {
      type uint32;
      config false;
    }
    leaf-list pmNbUeCe0UlCarrierDistr {
      type uint32;
    }
    leaf-list pmMacHarqDlMaxTxQpskCe {
      type ietfyang:mac-address;
    }
    leaf-list pmRrcConnReestAttCe {
      type uint32;
    }
    leaf-list pmRrcConnSetupTimeCe0Distr {
      type uint32;
    }
    leaf pmRadioThpVolDl {
      type uint32;
      config false;
      status deprecated;
      description "MOM flags: noNotification.";
    }
    leaf pmZTemporary207 {
      type int32;
      config false;
    }
    leaf-list pmNpuschRuSixToneDistr {
      type uint32;
    }
    leaf-list pmPrbUtilDlCe2Distr {
      type uint32;
    }
    leaf pmRrcConnCeSamp {
      type uint32;
      config false;
    }
    leaf pmRrcConnEstabAttReatt {
      type uint32;
      config false;
      status deprecated;
      description "MOM flags: noNotification.";
    }
    leaf pmUeCapabilityTwoHarq {
      type uint32;
      config false;
    }
    leaf pmPendingDataCheckCe0 {
      type uint32;
      config false;
    }
    leaf pmNpdcchTimeUl {
      type uint32;
      config false;
    }
    leaf pmRrcConnCe0Max {
      type int32;
      config false;
    }
    leaf-list pmNpuschSessionDistr {
      type uint32;
    }
    leaf-list pmDrxSleepTimeRateDistr0 {
      type uint32;
    }
    leaf pmPagEdrxReceived {
      type uint32;
      config false;
    }
    leaf-list pmUeCtxtRelAbnormalEnbActUeLostCe {
      type uint32;
    }
    leaf-list pmNpuschRuSingleToneDistr {
      type uint32;
    }
    leaf-list pmRrcConnEstabSuccUlCe0Distr {
      type uint32;
      description "MOM flags: noNotification.";
    }
    leaf-list pmMacPhrCe2Distr {
      type ietfyang:mac-address;
    }
    leaf-list pmNpuschMcsSingleToneDistr {
      type uint32;
    }
    leaf-list pmRrcConnEstabFailDynUeAdmCtrlCe {
      type uint32;
    }
    leaf-list pmRrcConnReestFailUeCe {
      type uint32;
    }
    leaf-list pmNpdcchRmaxUssCe2Distr {
      type uint32;
    }
    leaf-list pmUeMeasCqiMsg3Ce0Distr {
      type uint32;
    }
    leaf-list pmMacHarqUlFailQpskCe {
      type ietfyang:mac-address;
    }
    leaf-list pmMacHarqUlSuccQpskCe {
      type ietfyang:mac-address;
    }
    leaf pmZTemporary210 {
      type uint32;
      config false;
    }
    leaf pmUeCapabilityMultiCarrPag {
      type uint32;
      config false;
    }
    leaf-list pmRrcFastReturnMmeMoTimeDistr {
      type uint32;
    }
    leaf pmRrcConnEstabAtt {
      type uint32;
      config false;
      status deprecated;
      description "MOM flags: noNotification.";
    }
    leaf-list pmNpuschRuTwelveToneDistr {
      type uint32;
    }
    leaf pmRrcConnCe0Sum {
      type uint32;
      config false;
    }
    leaf-list pmRaMsg3SingleToneDistr {
      type uint32;
    }
    leaf-list pmRaFailSrCe {
      type uint32;
    }
    leaf pmNpdcchResyncFail {
      type uint32;
      config false;
    }
    leaf pmMacHarqUlSuccQpsk {
      type ietfyang:mac-address;
      config false;
      status deprecated;
      description "MOM flags: noNotification.";
    }
    leaf-list pmRrcConnEstabAttReattCe {
      type uint32;
    }
    leaf pmUeReleasePendingDataCe1 {
      type uint32;
      config false;
    }
    leaf-list pmPrbUtilDlCe0Distr {
      type uint32;
    }
    leaf-list pmMacHarqUlSuccBpskCe {
      type ietfyang:mac-address;
    }
    leaf-list pmZTemporary217 {
      type uint32;
    }
    leaf-list pmMacHarqDlAckQpskCe {
      type ietfyang:mac-address;
    }
    leaf-list pmRrcConnReestFailUeAcUnkStmsiCe {
      type uint32;
    }
    leaf pmRrcConnEstabFailMmeOvlMos {
      type uint32;
      config false;
      status deprecated;
      description "MOM flags: noNotification.";
    }
    leaf-list pmRrcConnEstabAttReattMtaCe {
      type uint32;
    }
    leaf-list pmPrbUtilUlCe0Distr {
      type uint32;
    }
    leaf-list pmMacPhrCe1Distr {
      type ietfyang:mac-address;
    }
    leaf pmZTemporary215 {
      type uint32;
      config false;
    }
    leaf-list pmUeCapabilityPowerClassDistr {
      type uint32;
    }
    leaf pmMacHarqUlSuccBpsk {
      type ietfyang:mac-address;
      config false;
      status deprecated;
      description "MOM flags: noNotification.";
    }
    leaf-list pmPagReceivedCe {
      type uint32;
      description "MOM flags: noNotification.";
    }
    leaf-list pmRaFailCbraMsg2DiscCe {
      type uint32;
    }
    leaf-list pmNpuschMcsTwelveToneDistr {
      type uint32;
    }
    leaf pmRrcConnCe1Max {
      type int32;
      config false;
    }
    leaf-list pmRaMsg3SixToneDistr {
      type uint32;
    }
    leaf-list pmPrbUtilUlCe2Distr {
      type uint32;
    }
    leaf pmRrcConnEstabSucc {
      type uint32;
      config false;
      status deprecated;
      description "MOM flags: noNotification.";
    }
    leaf-list pmRaMsg3NackCbraTxCe2Distr {
      type uint32;
    }
    leaf-list pmRrcFastReturnInactMoTimeDistr {
      type uint32;
    }
    leaf pmRrcConnReestFailUeAcLargeRmax {
      type uint32;
      config false;
    }
    leaf pmCellDownLockAuto {
      type uint32;
      config false;
    }
    leaf pmNpdcchCceAggregationLevel1 {
      type uint32;
      config false;
    }
    leaf pmUeCtxtRelAbnormalEnbUeLost {
      type uint32;
      config false;
      status deprecated;
      description "MOM flags: noNotification.";
    }
    leaf-list pmRrcConnLevSum {
      type uint32;
      description "MOM flags: noNotification.";
    }
    leaf-list pmPagRecordNbDistr {
      type uint32;
    }
    leaf-list pmRrcConnTimeCe0Distr {
      type uint32;
    }
    leaf-list pmUeCtxtRelAbnormalEnbCdtCe {
      type uint32;
    }
    leaf-list pmZTemporary219 {
      type uint32;
    }
    leaf-list pmRrcConnRelDeliveryFailCe {
      type uint32;
    }
    leaf-list pmPagDiscardedCe {
      type uint32;
      description "MOM flags: noNotification.";
    }
    leaf-list pmRrcConnEstabFailMmeOvlDtaCe {
      type uint32;
    }
    leaf-list pmRrcConnReestFailUeAdmCtrlCe {
      type uint32;
    }
    leaf pmCellDowntimeMan {
      type uint32;
      config false;
    }
    leaf-list pmNpuschSingleToneRepDistr {
      type uint32;
    }
    leaf-list pmRrcConnEstabSuccModCe {
      type uint32;
    }
    leaf-list pmUeMeasCqiMsg3Ce1Distr {
      type uint32;
    }
    leaf-list pmUeCategoryNbDistr {
      type uint32;
    }
    leaf pmRrcConnEstabFailUeAcLargeRmax {
      type uint32;
      config false;
    }
    leaf-list pmUeCtxtRelAbnormalMmeCe {
      type uint32;
    }
    leaf-list pmMacEnhancedPhrCe0Distr {
      type ietfyang:mac-address;
    }
    leaf-list pmRrcConnEstabFailUeAcDtaCe {
      type uint32;
    }
    leaf-list pmAcBarringCatADistr {
      type ietfyang:mac-address;
    }
    leaf-list pmRaFailCbraMsg1DiscSchedCe {
      type uint32;
    }
    leaf-list pmNpdschMcsDistr {
      type uint32;
    }
    leaf-list pmSchedDlTwoHarqDistr {
      type uint32;
    }
    leaf-list pmRaMultipleRarCe0Distr {
      type ietfinet:ip-address;
    }
    leaf-list pmRrcConnEstabFailUeAcMosCe {
      type uint32;
    }
    leaf pmZTemporary208 {
      type uint32;
      config false;
    }
    leaf-list pmNpuschThreeToneRepDistr {
      type uint32;
    }
    leaf-list pmRaAttTaDistr {
      type uint32;
    }
    leaf-list pmNpdcchRmaxUssCe0Distr {
      type uint32;
    }
    leaf-list pmRrcFastReturnInactMtTimeDistr {
      type uint32;
    }
    leaf-list pmRrcConnReestFailUeAcKnStmsiCe {
      type uint32;
    }
    leaf-list pmRrcConnEstabSuccDlCe0Distr {
      type uint32;
      description "MOM flags: noNotification.";
    }
    leaf-list pmRaAttNbCbra {
      type uint32;
    }
    leaf-list pmNpdschSfDistr {
      type uint32;
    }
    leaf-list pmNpuschUtilDistr {
      type uint32;
    }
    leaf-list pmS1SigConnEstabFailMmeOvlMosCe {
      type uint32;
    }
    leaf-list pmRaMultipleRarCe2Distr {
      type ietfinet:ip-address;
    }
    leaf-list pmMacTransLatencyUlDistr {
      type ietfyang:mac-address;
    }
    leaf-list pmRrcConnEstabSuccMoedCe {
      type uint32;
    }
    leaf-list pmRaMultipleRarCe1Distr {
      type ietfinet:ip-address;
    }
    leaf-list pmUeSessionVolDlCe2Distr {
      type uint32;
    }
    leaf pmPagEdrxDiscarded {
      type uint32;
      config false;
    }
    leaf-list pmNbUeCe1DlCarrierDistr {
      type uint32;
    }
    leaf pmRrcConnEstabFailMpMem {
      type uint32;
      config false;
    }
    leaf pmUeCapabilityMultiCarrNprach {
      type uint32;
      config false;
    }
    leaf pmUeCapabilityRai {
      type uint32;
      config false;
    }
    leaf pmMacHarqUlFailQpsk {
      type ietfyang:mac-address;
      config false;
      status deprecated;
      description "MOM flags: noNotification.";
    }
    leaf-list pmRrcConnRopEndCe {
      type uint32;
    }
    leaf-list pmMacHarqDlNackQpskCe {
      type ietfyang:mac-address;
    }
    leaf-list pmRrcConnEstabAttReattMoedCe {
      type uint32;
    }
    leaf pmRrcConnCe1Sum {
      type uint32;
      config false;
    }
    leaf-list pmNpdcchRepDistr {
      type uint32;
    }
    leaf-list pmRrcConnEstabSuccMtaCe {
      type uint32;
    }
    leaf pmRrcConnEstabSuccSingleCarr {
      type uint32;
      config false;
      status deprecated;
      description "MOM flags: noNotification.";
    }
    leaf pmCellDownUnlockMan {
      type uint32;
      config false;
    }
    leaf-list pmUeMeasCqiMsg3Ce2Distr {
      type uint32;
    }
    leaf pmMacHarqUlFailBpsk {
      type ietfyang:mac-address;
      config false;
      status deprecated;
      description "MOM flags: noNotification.";
    }
    leaf-list pmRaMsg3DtxCbraTxCe2Distr {
      type uint32;
    }
    leaf-list pmNpuschThreeToneDistr {
      type uint32;
    }
    leaf-list pmNpdschRepDistr {
      type uint32;
    }
    leaf-list pmRrcConnEstabSuccDlCe2Distr {
      type uint32;
      description "MOM flags: noNotification.";
    }
    leaf-list pmRaMsg3DtxCbraTxCe1Distr {
      type uint32;
    }
    leaf pmNbUeCapSingleCarrier {
      type uint32;
      config false;
    }
    leaf-list pmRaMsg3DeltaPwrCe1Distr {
      type uint32;
    }
    leaf-list pmRaSuccTaDistr {
      type uint32;
    }
    leaf-list pmNpdschTbsDistr {
      type uint32;
    }
    leaf-list pmRrcConnEstabAttReattMosCe {
      type uint32;
    }
    leaf-list pmZTemporary220 {
      type uint32;
    }
    leaf-list pmNpuschTwelveToneRepDistr {
      type uint32;
    }
    leaf-list pmRrcConnSetupTimeCe1Distr {
      type uint32;
    }
    leaf-list pmRaBackoffNbCe1Distr {
      type uint32;
    }
    leaf-list pmUeCtxtRelAbnormalMmeActCe {
      type uint32;
    }
    leaf-list pmNpuschF2RepCe1Distr {
      type uint32;
    }
    leaf-list pmUeMeasNrsrpMsg5Distr {
      type uint32;
    }
    leaf-list pmRaMsg4HarqAckDistr {
      type uint32;
    }
    leaf-list pmRaSuccNbCbra {
      type uint32;
    }
    leaf pmNpdcchResyncAtt {
      type uint32;
      config false;
    }
    leaf-list pmNbUeCe0DlCarrierDistr {
      type uint32;
    }
    leaf-list pmRadioThpVolUlCe {
      type uint32;
    }
    leaf-list pmRaMsg3TwelveToneDistr {
      type uint32;
    }
    leaf-list pmSchedUlTwoHarqDistr {
      type uint32;
    }
    leaf-list pmRrcConnEstabAttReattModCe {
      type uint32;
    }
    leaf-list pmS1SigConnEstabSuccCe {
      type uint32;
    }
    leaf pmUeReleasePendingDataCe0 {
      type uint32;
      config false;
    }
    leaf-list pmNpuschRuThreeToneDistr {
      type uint32;
    }
    leaf-list pmRaMsg5HarqDtxDistr {
      type uint32;
    }
    leaf-list pmRaMsg3NackCbraTxCe0Distr {
      type uint32;
    }
    leaf-list pmRadioRecInterferencePwr {
      type uint32;
    }
    leaf-list pmRrcConnEstabAttDtaCe {
      type uint32;
    }
    leaf-list pmPrbUtilDlCe1Distr {
      type uint32;
    }
    leaf pmRadioThpVolUl {
      type uint32;
      config false;
      status deprecated;
      description "MOM flags: noNotification.";
    }
    leaf-list pmMacActiveSessionNbDistr {
      type ietfyang:mac-address;
    }
    leaf-list pmNpuschSixToneDistr {
      type uint32;
    }
    leaf pmUeCtxtRelAbnormalEnbActUeLost {
      type uint32;
      config false;
      status deprecated;
      description "MOM flags: noNotification.";
    }
    leaf pmS1SigConnEstabAtt {
      type uint32;
      config false;
      status deprecated;
      description "MOM flags: noNotification.";
    }
    leaf pmZTemporary211 {
      type uint32;
      config false;
    }
    leaf-list pmRrcConnEstabAttReattDtaCe {
      type uint32;
    }
    leaf-list pmRrcConnEstabSuccUlCe1Distr {
      type uint32;
      description "MOM flags: noNotification.";
    }
    leaf-list pmUeCtxtRelAbnormalEnbUeLostCe {
      type uint32;
    }
    leaf-list pmNbUeCe2DlCarrierDistr {
      type uint32;
    }
    leaf-list pmRrcFastReturnRaiMtTimeDistr {
      type uint32;
    }
    leaf-list pmUeCtxtRelNormalEnbActCe {
      type uint32;
    }
    leaf-list pmRrcConnEstabAttCe {
      type uint32;
    }
    leaf-list pmMacPhrCe0Distr {
      type ietfyang:mac-address;
    }
    leaf-list pmAcBarringCatCDistr {
      type ietfyang:mac-address;
    }
    leaf-list pmMacTransLatencyDlDistr {
      type ietfyang:mac-address;
    }
    leaf-list pmRrcConnEstabAttMosCe {
      type uint32;
    }
    leaf pmRrcConnEstabFailMmeOvlMod {
      type uint32;
      config false;
      status deprecated;
      description "MOM flags: noNotification.";
    }
    leaf pmUeCtxtRelNormalEnb {
      type uint32;
      config false;
      status deprecated;
      description "MOM flags: noNotification.";
    }
    leaf-list pmDrxSleepTimeRateDistr2 {
      type uint32;
    }
    leaf pmUeCtxtRelNormalEnbAct {
      type uint32;
      config false;
      status deprecated;
      description "MOM flags: noNotification.";
    }
    leaf-list pmRrcConnEstabFailMmeOvlMosCe {
      type uint32;
    }
    leaf pmUeCtxtRelAbnormalMmeAct {
      type uint32;
      config false;
      status deprecated;
      description "MOM flags: noNotification.";
    }
    leaf-list pmNpdcchCceUtil {
      type uint32;
    }
    leaf-list pmUeCtxtRelAbnormalEnbActCe {
      type uint32;
    }
    leaf-list pmRrcConnEstabAttMoedCe {
      type uint32;
    }
    leaf-list pmRaMsg2AttNbCbra {
      type uint32;
    }
    leaf pmPagDiscardedNb {
      type uint32;
      config false;
    }
    leaf-list pmRaSuccSrCe {
      type uint32;
    }
    leaf-list pmPrbUtilUlCe1Distr {
      type uint32;
    }
    leaf pmUeCtxtRelMme {
      type uint32;
      config false;
      status deprecated;
      description "MOM flags: noNotification.";
    }
    leaf pmMacHarqDlNackBpsk {
      type ietfyang:mac-address;
      config false;
      status deprecated;
      description "MOM flags: noNotification.";
    }
    leaf-list pmUeSessionVolUlCe1Distr {
      type uint32;
    }
    leaf-list pmRrcConnReestSuccCe {
      type uint32;
    }
    leaf pmRruEmptySubframeDl {
      type uint32;
      config false;
    }
    leaf pmErabEstabSuccInit {
      type uint32;
      config false;
      status deprecated;
      description "MOM flags: noNotification.";
    }
    leaf pmPagDiscarded {
      type uint32;
      config false;
      status deprecated;
      description "MOM flags: noNotification.";
    }
    leaf-list pmRaMsg3DeltaPwrCe2Distr {
      type uint32;
    }
    leaf pmMacHarqDlAckBpsk {
      type ietfyang:mac-address;
      config false;
      status deprecated;
      description "MOM flags: noNotification.";
    }
    leaf-list pmUeSessionVolUlCe2Distr {
      type uint32;
    }
    leaf-list pmRadioThpVolDlCe {
      type uint32;
    }
    leaf-list pmMacHarqDlDtxQpskCe {
      type ietfyang:mac-address;
    }
    leaf pmUeCapabilityDataInactMon {
      type uint32;
      config false;
    }
    leaf-list pmPagAttemptCountDistr {
      type uint32;
    }
    leaf pmZTemporary214 {
      type uint32;
      config false;
    }
    leaf-list pmRaMsg3NackCbraTxCe1Distr {
      type uint32;
    }
    leaf-list pmMacEnhancedPhrCe2Distr {
      type ietfyang:mac-address;
    }
    leaf pmZTemporary213 {
      type uint32;
      config false;
    }
    leaf-list pmUlPathlossNbDistr {
      type uint32;
    }
    leaf-list pmRaMsg3DtxCbraTxCe0Distr {
      type uint32;
    }
    leaf-list pmRaBackoffNbCe0Distr {
      type uint32;
    }
    leaf-list pmNpuschSixToneRepDistr {
      type uint32;
    }
    leaf-list pmRrcConnEstabFailCellIntensStatCe {
      type uint32;
    }
    leaf-list pmRrcConnEstabFailMpOverloadCe {
      type uint32;
    }
    leaf-list pmNpuschTwelveToneDistr {
      type uint32;
    }
    leaf-list pmNpuschMcsThreeToneDistr {
      type uint32;
    }
    leaf-list pmRrcConnEstabFailResCe {
      type uint32;
    }
    leaf-list pmRrcConnEstabFailMmeOvlModCe {
      type uint32;
    }
    leaf pmNpdcchTimeDl {
      type uint32;
      config false;
    }
    leaf pmUeCtxtRelMmeAct {
      type uint32;
      config false;
      status deprecated;
      description "MOM flags: noNotification.";
    }
    leaf pmMacHarqDlAckQpsk {
      type ietfyang:mac-address;
      config false;
      status deprecated;
      description "MOM flags: noNotification.";
    }
    leaf pmS1SigConnEstabSucc {
      type uint32;
      config false;
      status deprecated;
      description "MOM flags: noNotification.";
    }
  }
  grouping NodePerformance-attributes {
    leaf nodePerformanceId {
      type string;
      mandatory true;
    }
    leaf zzzTemporary1 {
      type int32;
      default "-2000000000";
      description "Default value: -2000000000.";
    }
    leaf zzzTemporary2 {
      type int32;
      default "-2000000000";
      description "Default value: -2000000000.";
    }
    leaf zzzTemporary3 {
      type int32;
      default "-2000000000";
      description "Default value: -2000000000.";
    }
    leaf zzzTemporary4 {
      type int32;
      default "-2000000000";
      description "Default value: -2000000000.";
    }
    leaf zzzTemporary5 {
      type int32;
      default "-2000000000";
      description "Default value: -2000000000.";
    }
    leaf zzzTemporary6 {
      type int32;
      default "-2000000000";
      description "Default value: -2000000000.";
    }
    leaf zzzTemporary7 {
      type int32;
      default "-2000000000";
      description "Default value: -2000000000.";
    }
    leaf zzzTemporary8 {
      type int32;
      default "-2000000000";
      description "Default value: -2000000000.";
    }
  }
  grouping NonPlannedPciDrxProfile-attributes {
    leaf nonPlannedPciDrxProfileId {
      type ietfinet:ip-prefix;
      mandatory true;
    }
    leaf nonPlannedPciDrxInactivityTimer {
      type ietfinet:ip-prefix;
    }
    leaf nonPlannedPciLongDrxCycle {
      type enumeration {
        enum SF10;
        enum SF20;
        enum SF32;
        enum SF40;
        enum SF64;
        enum SF80;
        enum SF128;
        enum SF160;
        enum SF256;
        enum SF320;
        enum SF512;
        enum SF640;
        enum SF1024;
        enum SF1280;
        enum SF2048;
        enum SF2560;
      }
    }
    leaf nonPlannedPciOnDurationTimer {
      type enumeration {
        enum PSF1;
        enum PSF2;
        enum PSF3;
        enum PSF4;
        enum PSF5;
        enum PSF6;
        enum PSF8;
        enum PSF10;
        enum PSF20;
        enum PSF30;
        enum PSF40;
        enum PSF50;
        enum PSF60;
        enum PSF80;
        enum PSF100;
        enum PSF200;
      }
    }
  }
  grouping Paging-attributes {
    leaf pagingId {
      type string;
      mandatory true;
    }
    leaf maxNoOfPagingRecords {
      type eytypes:int32_range_1-16;
      default "3";
      description "range 1..16; Default value: 3.";
    }
    leaf defaultPagingCycle {
      type int32 {
        range "32 | 64 | 128 | 256";
      }
      default "128";
      description "Default value: 128.";
    }
    leaf nB {
      type enumeration {
        enum T4;
        enum T2;
        enum T;
        enum T1_2;
        enum T1_4;
        enum T1_8;
        enum T1_16;
        enum T1_32;
      }
    }
    leaf pagingDiscardTimer {
      type eytypes:int32_range_1-30;
      units "s";
      description "range 1..30.";
    }
    leaf noOfDefPagCyclPrim {
      type eytypes:int32_range_1-16;
      default "8";
      description "range 1..16; Default value: 8.";
    }
    leaf nBBr {
      type enumeration {
        enum NOT_PRESENT;
        enum T1_64;
        enum T1_128;
        enum T1_256;
        enum T;
        enum T1_2T;
        enum T1_4T;
        enum T1_8T;
        enum T1_16T;
        enum T1_32T;
      }
    }
    leaf defaultPagingCycleNbIot {
      type int32 {
        range "128 | 256 | 512 | 1024";
      }
      default "256";
      description "Default value: 256.";
    }
    leaf nBNbIot {
      type enumeration {
        enum T4;
        enum T2;
        enum T;
        enum T1_2;
        enum T1_4;
        enum T1_8;
        enum T1_16;
        enum T1_32;
        enum T1_64;
        enum T1_128;
        enum T1_256;
        enum T1_512;
        enum T1_1024;
      }
    }
    leaf numRepetitionsPagingNbIot {
      type int32 {
        range "1..2 | 4 | 8 | 16 | 32 | 64 | 128 | 256 | 512 | 1024 | 2048";
      }
    }
    leaf pagingDiscardTimerNb {
      type eytypes:int32_range_1-60;
      units "s";
      description "range 1..60.";
    }
    leaf maxNoOfPagingRecordsNb {
      type eytypes:int32_range_1-16;
      default "3";
      description "range 1..16; Default value: 3.";
    }
    leaf pagingDiscardTimerDrx {
      type eytypes:int32_range_1-15;
      default "3";
      units "s";
      description "range 1..15; Default value: 3.";
    }
    leaf pagingDiscardTimerDrxNb {
      type eytypes:int32_range_1-30;
      default "6";
      units "s";
      description "range 1..30; Default value: 6.";
    }
    leaf pagingDiscardTimerEdrxNb {
      type int32 {
        range "1..52";
      }
      default "31";
      units "s";
      description "range 1..52; Default value: 31.";
    }
    leaf pagingDiscardTimerEdrx {
      type int32 {
        range "1..31";
      }
      default "13";
      units "s";
      description "range 1..31; Default value: 13.";
    }
    leaf cssRmaxForPagingNb {
      type int32 {
        range "1..2 | 4 | 8 | 16 | 32 | 64 | 128 | 256 | 512 | 1024 | 2048";
      }
      config false;
    }
    leaf pagingAssistDataNbEnabled {
      type boolean;
      default "true";
      description "Default value: true.";
    }
    leaf pagingAssistDataSupportBr {
      type ietfinet:port-number;
    }
  }
  grouping ParameterChangeRequests-attributes {
    list parameterChangeRequestList {
      config false;
      container attributes {
      leaf seqNo {
        type string;
      }
      leaf objectRef {
        type string;
      }
      leaf attributeName {
        type string {
          length "0..32";
        }
        description "length 0..32.";
      }
      leaf originalValue {
        type string {
          length "0..32";
        }
        description "length 0..32.";
      }
      leaf requestedValue {
        type string {
          length "0..32";
        }
        description "length 0..32.";
      }
      leaf causeCode {
        type enumeration {
          enum INITIAL;
          enum MRO;
          enum MLB;
          enum RACH;
        }
      }
      leaf causeString {
        type string {
          length "0..100";
        }
        description "length 0..100.";
      }
      leaf state {
        type enumeration {
          enum INITIAL;
          enum PENDING;
          enum APPROVED;
          enum REJECTED;
          enum CANCELLED;
        }
      }
      leaf timeOfCreation {
        type string {
          length "0..19";
        }
        description "length 0..19.";
      }
      leaf timeOfChange {
        type string {
          length "0..19";
        }
        description "length 0..19.";
      }
      }
    }
    list latestUpdate {
      config false;
      container attributes {
      leaf seqNo {
        type string;
      }
      leaf objectRef {
        type string;
      }
      leaf attributeName {
        type string {
          length "0..32";
        }
        description "length 0..32.";
      }
      leaf originalValue {
        type string {
          length "0..32";
        }
        description "length 0..32.";
      }
      leaf requestedValue {
        type string {
          length "0..32";
        }
        description "length 0..32.";
      }
      leaf causeCode {
        type enumeration {
          enum INITIAL;
          enum MRO;
          enum MLB;
          enum RACH;
        }
      }
      leaf causeString {
        type string {
          length "0..100";
        }
        description "length 0..100.";
      }
      leaf state {
        type enumeration {
          enum INITIAL;
          enum PENDING;
          enum APPROVED;
          enum REJECTED;
          enum CANCELLED;
        }
      }
      leaf timeOfCreation {
        type string {
          length "0..19";
        }
        description "length 0..19.";
      }
      leaf timeOfChange {
        type string {
          length "0..19";
        }
        description "length 0..19.";
      }
      }
    }
    leaf parameterChangeRequestsId {
      type string;
      mandatory true;
    }
  }
  grouping PimCancellationConfig-attributes {
    leaf pimCancellationConfigId {
      type string;
      mandatory true;
    }
    leaf pimCancellationFunctionRef {
      type string;
    }
    leaf ulPimCancellationMode {
      type enumeration {
        enum EXCLUDED;
        enum DEACTIVATED;
        enum ACTIVATED;
      }
    }
    leaf dlPimCandidate {
      type boolean;
      default "false";
      description "Default value: false.";
    }
    leaf createdBy {
      type enumeration {
        enum SYSTEM;
        enum OPERATOR;
      }
      config false;
    }
  }
  grouping PlmnAbConfProfile-attributes {
    leaf plmnAbConfProfileId {
      type string;
      mandatory true;
    }
    list acBarringPlmnId {
      key "id";
      leaf id {
        type uint32;
        description "Synthetic key for struct entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf acBarringPerPlmnPriority {
      type enumeration {
        enum PRIORITY0;
        enum PRIORITY1;
        enum PRIORITY2;
      }
    }
    leaf acBarringForEmergency {
      type boolean;
      default "false";
      description "Default value: false.";
    }
    list acBarringForMoData {
      key "id";
      leaf id {
        type uint32;
        description "Synthetic key for struct entry.";
      }
      container attributes {
      leaf acBarringFactor {
        type int32;
        default "95";
        units "percent";
        description "Default value: 95.";
      }
      leaf acBarringTime {
        type int32;
        default "64";
        units "s";
        description "Default value: 64.";
      }
      leaf acBarringForSpecialAC {
        type string;
      }
      }
    }
    list acBarringForMoSignalling {
      key "id";
      leaf id {
        type uint32;
        description "Synthetic key for struct entry.";
      }
      container attributes {
      leaf acBarringFactor {
        type int32;
        default "95";
        units "percent";
        description "Default value: 95.";
      }
      leaf acBarringTime {
        type int32;
        default "64";
        units "s";
        description "Default value: 64.";
      }
      leaf acBarringForSpecialAC {
        type string;
      }
      }
    }
    list acBarringForCsfb {
      key "id";
      leaf id {
        type uint32;
        description "Synthetic key for struct entry.";
      }
      container attributes {
      leaf acBarringFactor {
        type int32;
        default "95";
        units "percent";
        description "Default value: 95.";
      }
      leaf acBarringTime {
        type int32;
        default "64";
        units "s";
        description "Default value: 64.";
      }
      leaf acBarringForSpecialAC {
        type string;
      }
      }
    }
    list ssacBarringForMmtelVideo {
      key "id";
      leaf id {
        type uint32;
        description "Synthetic key for struct entry.";
      }
      container attributes {
      leaf acBarringFactor {
        type int32;
        default "95";
        units "percent";
        description "Default value: 95.";
      }
      leaf acBarringTime {
        type int32;
        default "64";
        units "s";
        description "Default value: 64.";
      }
      leaf acBarringForSpecialAC {
        type string;
      }
      }
    }
    list ssacBarringForMmtelVoice {
      key "id";
      leaf id {
        type uint32;
        description "Synthetic key for struct entry.";
      }
      container attributes {
      leaf acBarringFactor {
        type int32;
        default "95";
        units "percent";
        description "Default value: 95.";
      }
      leaf acBarringTime {
        type int32;
        default "64";
        units "s";
        description "Default value: 64.";
      }
      leaf acBarringForSpecialAC {
        type string;
      }
      }
    }
    leaf acBarringSkipForMmtelVideo {
      type ietfinet:ip-address;
      description "Default value: false.";
    }
    leaf acBarringSkipForMmtelVoice {
      type ietfinet:ip-address;
      description "Default value: false.";
    }
    leaf acBarringSkipForSms {
      type ietfinet:ip-address;
      description "Default value: false.";
    }
    leaf acBarringForCsfbPresence {
      type enumeration {
        enum OFF;
        enum MANUAL;
        enum AUTO;
      }
    }
    leaf acBarringForMmtelVidPres {
      type enumeration {
        enum OFF;
        enum MANUAL;
        enum AUTO;
      }
    }
    leaf acBarringForMmtelVoicePres {
      type enumeration {
        enum OFF;
        enum MANUAL;
        enum AUTO;
      }
    }
    leaf acBarringForMoDataPresence {
      type enumeration {
        enum OFF;
        enum MANUAL;
        enum AUTO;
      }
    }
    leaf acBarringForMoSignalPresence {
      type enumeration {
        enum OFF;
        enum MANUAL;
        enum AUTO;
      }
    }
    leaf-list reservedBy {
      type string;
    }
    leaf acBarringForEmergencySpecAcPres {
      type enumeration {
        enum MANUAL;
        enum AUTO;
      }
    }
  }
  grouping PlmnInfo-attributes {
    leaf plmnInfoId {
      type string;
      mandatory true;
    }
    list plmnWhiteList {
      key "id";
      leaf id {
        type uint32;
        description "Synthetic key for struct sequence entry.";
      }
      container attributes {
      leaf mcc {
        type int32 {
          range "-1..999";
        }
        default "1";
        description "range -1..999; Default value: 1.";
      }
      leaf mnc {
        type int32 {
          range "-1..999";
        }
        default "1";
        description "range -1..999; Default value: 1.";
      }
      leaf mncLength {
        type eytypes:int32_range_2-3;
        default "2";
        description "range 2..3; Default value: 2.";
      }
      }
    }
    list actualPlmn {
      key "id";
      leaf id {
        type uint32;
        description "Synthetic key for struct entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf csfbTargetRat {
      type enumeration {
        enum GERAN_UTRAN;
        enum CDMA_1XRTT;
      }
    }
  }
  grouping PmchMch-attributes {
    leaf pmchMchId {
      type string;
      mandatory true;
    }
    leaf userLabel {
      type string {
        length "1..128";
      }
      description "length 1..128.";
    }
    leaf sfAllocEnd {
      type int32 {
        range "-1..1535";
      }
      default "-1";
      description "range -1..1535; Default value: -1.";
    }
    leaf dataMcs {
      type eytypes:int32_range_0-28;
      mandatory true;
      description "range 0..28.";
    }
    leaf mchSchedulingPeriod {
      type int32 {
        range "8 | 16 | 32 | 64 | 128 | 256 | 512 | 1024";
      }
      default "32";
      description "Default value: 32.";
    }
    leaf-list qci {
      type eytypes:int32_range_0-255;
    }
    leaf syncSequenceLength {
      type int32 {
        range "8 | 16 | 32 | 64 | 128 | 256 | 512 | 1024";
      }
      default "8";
      units "ms";
      description "Default value: 8.";
    }
  }
  grouping PmEventService-attributes {
    leaf cellTraceHighPrioReserve {
      type int32 {
        range "0..80";
      }
      units "percent";
      description "range 0..80.";
    }
    leaf totalCellTraceStorageSize {
      type int32 {
        range "100..250000";
      }
      units "kilobyte (kb)";
      description "range 100..250000.";
    }
    leaf cellTraceFileSize {
      type int32 {
        range "100..30000";
      }
      units "kilobyte (kb)";
      description "range 100..30000.";
    }
    leaf totalEventStorageSize {
      type int32 {
        range "0..266000";
      }
      units "kilobyte (kb)";
      description "range 0..266000.";
    }
    leaf ueTraceFileSize {
      type int32 {
        range "100..1000";
      }
      default "1000";
      units "kilobyte (kb)";
      description "range 100..1000; Default value: 1000.";
    }
    leaf pmEventServiceId {
      type string;
      mandatory true;
    }
    leaf totalUeTraceStorageSize {
      type int32 {
        range "100..20000";
      }
      units "kilobyte (kb)";
      description "range 100..20000.";
    }
    leaf streamPortPmUeTrace {
      type ietfinet:port-number;
      default "51543";
      description "range 0..65535; Default value: 51543.";
    }
    list streamStatusPmCellTrace {
      config false;
      container attributes {
      leaf traceReference {
        type string;
      }
      leaf scannerId {
        type string;
      }
      leaf ipAddress {
        type ietfinet:ip-address;
        description "length 2..46.";
      }
      leaf portNumber {
        type ietfinet:port-number;
        description "range 0..65535.";
      }
      leaf fileStatus {
        type enumeration {
          enum INACTIVE;
          enum ACTIVE;
          enum FILECLOSED;
          enum LOAD_INHIBITED;
        }
      }
      leaf streamStatus {
        type enumeration {
          enum INACTIVE;
          enum ACTIVE;
          enum CONNECTING;
          enum RECONNECTING;
          enum ERROR;
          enum NOT_LICENSED;
          enum LOAD_INHIBITED;
          enum STREAM_REPORT_OFF;
        }
      }
      }
    }
    list streamStatusPmUeTrace {
      config false;
      container attributes {
      leaf traceReference {
        type string;
      }
      leaf scannerId {
        type string;
      }
      leaf ipAddress {
        type ietfinet:ip-address;
        description "length 2..46.";
      }
      leaf portNumber {
        type ietfinet:port-number;
        description "range 0..65535.";
      }
      leaf fileStatus {
        type enumeration {
          enum INACTIVE;
          enum ACTIVE;
          enum FILECLOSED;
          enum LOAD_INHIBITED;
        }
      }
      leaf streamStatus {
        type enumeration {
          enum INACTIVE;
          enum ACTIVE;
          enum CONNECTING;
          enum RECONNECTING;
          enum ERROR;
          enum NOT_LICENSED;
          enum LOAD_INHIBITED;
          enum STREAM_REPORT_OFF;
        }
      }
      }
    }
    leaf cellTracePeriodicReport {
      type ietfinet:port-number;
      description "Default value: false.";
    }
    leaf streamStatusNotification {
      type boolean;
      default "true";
      description "Default value: true.";
    }
    leaf-list eventsExcludedFromUeTrace {
      type enumeration {
        enum S1_PAGING;
      }
      description "Takes effect: New connection; Status info: Since 20.Q3. Planned to be removed..";
    }
    leaf thpFilterThresholdDl {
      type enumeration {
        enum FILTER_THRESH_0;
        enum FILTER_THRESH_1;
        enum FILTER_THRESH_10;
        enum FILTER_THRESH_15;
        enum FILTER_THRESH_22;
        enum FILTER_THRESH_45;
        enum FILTER_THRESH_70;
        enum FILTER_THRESH_100;
        enum FILTER_THRESH_150;
        enum FILTER_THRESH_220;
        enum FILTER_THRESH_450;
        enum FILTER_THRESH_700;
        enum FILTER_THRESH_1000;
        enum FILTER_THRESH_1500;
        enum FILTER_THRESH_2200;
        enum FILTER_THRESH_4500;
        enum FILTER_THRESH_7000;
        enum FILTER_THRESH_10000;
        enum FILTER_THRESH_15000;
        enum FILTER_THRESH_22000;
        enum FILTER_THRESH_45000;
        enum FILTER_THRESH_70000;
        enum FILTER_THRESH_100000;
        enum FILTER_THRESH_150000;
        enum FILTER_THRESH_220000;
        enum FILTER_THRESH_450000;
      }
      status deprecated;
      default "FILTER_THRESH_70000";
      description "Default value: FILTER_THRESH_70000; Status info: Since 18.Q3. Has no functional behavior. Planned to be removed..";
    }
    leaf ueTrExcludeNonRacUeRefEvents {
      type boolean;
      default "true";
      description "Default value: true.";
    }
    leaf ueTraceSyncF1AndE1WithX2 {
      type boolean;
      default "false";
      description "Default value: false.";
    }
  }
  grouping PmFlexCounterFilter-attributes {
    leaf pmFlexCounterFilterId {
      type string;
      mandatory true;
    }
    leaf counterNameSuffix {
      type string;
      config false;
    }
    leaf plmnFilterEnabled {
      type boolean;
      default "false";
      description "Default value: false.";
    }
    leaf plmnFilterMin {
      type eytypes:int32_range_0-5;
      default "0";
      description "range 0..5; Default value: 0.";
    }
    leaf plmnFilterMax {
      type eytypes:int32_range_0-5;
      default "0";
      description "range 0..5; Default value: 0.";
    }
    leaf ueCatFilterEnabled {
      type boolean;
      default "false";
      description "Default value: false.";
    }
    leaf ueCatFilterMin {
      type enumeration {
        enum UE_CATEGORY_DL_M1_UL_M1;
        enum UE_CATEGORY_DL_0_UL_0;
        enum UE_CATEGORY_1;
        enum UE_CATEGORY_2;
        enum UE_CATEGORY_3;
        enum UE_CATEGORY_4;
        enum UE_CATEGORY_5;
        enum UE_CATEGORY_6;
        enum UE_CATEGORY_7;
        enum UE_CATEGORY_8;
        enum UE_CATEGORY_9;
        enum UE_CATEGORY_10;
        enum UE_CATEGORY_11;
        enum UE_CATEGORY_12;
        enum UE_CATEGORY_DL_6_UL_5;
        enum UE_CATEGORY_DL_7_UL_13;
        enum UE_CATEGORY_DL_9_UL_5;
        enum UE_CATEGORY_DL_10_UL_13;
        enum UE_CATEGORY_DL_11_UL_5;
        enum UE_CATEGORY_DL_12_UL_13;
        enum UE_CATEGORY_DL_13_UL_3;
        enum UE_CATEGORY_DL_13_UL_5;
        enum UE_CATEGORY_DL_13_UL_7;
        enum UE_CATEGORY_DL_13_UL_13;
        enum UE_CATEGORY_DL_14_UL_8;
        enum UE_CATEGORY_DL_15_UL_3;
        enum UE_CATEGORY_DL_15_UL_5;
        enum UE_CATEGORY_DL_15_UL_7;
        enum UE_CATEGORY_DL_15_UL_13;
        enum UE_CATEGORY_DL_16_UL_3;
        enum UE_CATEGORY_DL_16_UL_5;
        enum UE_CATEGORY_DL_16_UL_7;
        enum UE_CATEGORY_DL_16_UL_13;
        enum UE_CATEGORY_DL_17_UL_14;
        enum UE_CATEGORY_DL_18_UL_3;
        enum UE_CATEGORY_DL_18_UL_5;
        enum UE_CATEGORY_DL_18_UL_7;
        enum UE_CATEGORY_DL_18_UL_13;
        enum UE_CATEGORY_DL_19_UL_3;
        enum UE_CATEGORY_DL_19_UL_5;
        enum UE_CATEGORY_DL_19_UL_7;
        enum UE_CATEGORY_DL_19_UL_13;
        enum UE_CATEGORY_DL_20_UL_3;
        enum UE_CATEGORY_DL_20_UL_5;
        enum UE_CATEGORY_DL_20_UL_7;
        enum UE_CATEGORY_DL_20_UL_13;
        enum UE_CATEGORY_DL_4_UL_5;
        enum UE_CATEGORY_DL_6_UL_16;
        enum UE_CATEGORY_DL_7_UL_18;
        enum UE_CATEGORY_DL_9_UL_16;
        enum UE_CATEGORY_DL_10_UL_18;
        enum UE_CATEGORY_DL_11_UL_16;
        enum UE_CATEGORY_DL_12_UL_18;
        enum UE_CATEGORY_DL_13_UL_16;
        enum UE_CATEGORY_DL_13_UL_18;
        enum UE_CATEGORY_DL_15_UL_16;
        enum UE_CATEGORY_DL_15_UL_18;
        enum UE_CATEGORY_DL_16_UL_16;
        enum UE_CATEGORY_DL_16_UL_18;
        enum UE_CATEGORY_DL_18_UL_16;
        enum UE_CATEGORY_DL_18_UL_18;
        enum UE_CATEGORY_DL_19_UL_16;
        enum UE_CATEGORY_DL_19_UL_18;
        enum UE_CATEGORY_DL_20_UL_16;
        enum UE_CATEGORY_DL_20_UL_18;
        enum UE_CATEGORY_DL_12_UL_20;
        enum UE_CATEGORY_DL_16_UL_20;
        enum UE_CATEGORY_DL_18_UL_20;
        enum UE_CATEGORY_DL_19_UL_20;
        enum UE_CATEGORY_DL_20_UL_20;
        enum UE_CATEGORY_DL_22_UL_20;
      }
    }
    leaf ueCatFilterMax {
      type enumeration {
        enum UE_CATEGORY_DL_M1_UL_M1;
        enum UE_CATEGORY_DL_0_UL_0;
        enum UE_CATEGORY_1;
        enum UE_CATEGORY_2;
        enum UE_CATEGORY_3;
        enum UE_CATEGORY_4;
        enum UE_CATEGORY_5;
        enum UE_CATEGORY_6;
        enum UE_CATEGORY_7;
        enum UE_CATEGORY_8;
        enum UE_CATEGORY_9;
        enum UE_CATEGORY_10;
        enum UE_CATEGORY_11;
        enum UE_CATEGORY_12;
        enum UE_CATEGORY_DL_6_UL_5;
        enum UE_CATEGORY_DL_7_UL_13;
        enum UE_CATEGORY_DL_9_UL_5;
        enum UE_CATEGORY_DL_10_UL_13;
        enum UE_CATEGORY_DL_11_UL_5;
        enum UE_CATEGORY_DL_12_UL_13;
        enum UE_CATEGORY_DL_13_UL_3;
        enum UE_CATEGORY_DL_13_UL_5;
        enum UE_CATEGORY_DL_13_UL_7;
        enum UE_CATEGORY_DL_13_UL_13;
        enum UE_CATEGORY_DL_14_UL_8;
        enum UE_CATEGORY_DL_15_UL_3;
        enum UE_CATEGORY_DL_15_UL_5;
        enum UE_CATEGORY_DL_15_UL_7;
        enum UE_CATEGORY_DL_15_UL_13;
        enum UE_CATEGORY_DL_16_UL_3;
        enum UE_CATEGORY_DL_16_UL_5;
        enum UE_CATEGORY_DL_16_UL_7;
        enum UE_CATEGORY_DL_16_UL_13;
        enum UE_CATEGORY_DL_17_UL_14;
        enum UE_CATEGORY_DL_18_UL_3;
        enum UE_CATEGORY_DL_18_UL_5;
        enum UE_CATEGORY_DL_18_UL_7;
        enum UE_CATEGORY_DL_18_UL_13;
        enum UE_CATEGORY_DL_19_UL_3;
        enum UE_CATEGORY_DL_19_UL_5;
        enum UE_CATEGORY_DL_19_UL_7;
        enum UE_CATEGORY_DL_19_UL_13;
        enum UE_CATEGORY_DL_20_UL_3;
        enum UE_CATEGORY_DL_20_UL_5;
        enum UE_CATEGORY_DL_20_UL_7;
        enum UE_CATEGORY_DL_20_UL_13;
        enum UE_CATEGORY_DL_4_UL_5;
        enum UE_CATEGORY_DL_6_UL_16;
        enum UE_CATEGORY_DL_7_UL_18;
        enum UE_CATEGORY_DL_9_UL_16;
        enum UE_CATEGORY_DL_10_UL_18;
        enum UE_CATEGORY_DL_11_UL_16;
        enum UE_CATEGORY_DL_12_UL_18;
        enum UE_CATEGORY_DL_13_UL_16;
        enum UE_CATEGORY_DL_13_UL_18;
        enum UE_CATEGORY_DL_15_UL_16;
        enum UE_CATEGORY_DL_15_UL_18;
        enum UE_CATEGORY_DL_16_UL_16;
        enum UE_CATEGORY_DL_16_UL_18;
        enum UE_CATEGORY_DL_18_UL_16;
        enum UE_CATEGORY_DL_18_UL_18;
        enum UE_CATEGORY_DL_19_UL_16;
        enum UE_CATEGORY_DL_19_UL_18;
        enum UE_CATEGORY_DL_20_UL_16;
        enum UE_CATEGORY_DL_20_UL_18;
        enum UE_CATEGORY_DL_12_UL_20;
        enum UE_CATEGORY_DL_16_UL_20;
        enum UE_CATEGORY_DL_18_UL_20;
        enum UE_CATEGORY_DL_19_UL_20;
        enum UE_CATEGORY_DL_20_UL_20;
        enum UE_CATEGORY_DL_22_UL_20;
      }
    }
    leaf spidFilterEnabled {
      type boolean;
      default "false";
      description "Default value: false.";
    }
    leaf spidFilterMin {
      type eytypes:int32_range_1-256;
      default "1";
      description "range 1..256; Default value: 1.";
    }
    leaf spidFilterMax {
      type eytypes:int32_range_1-256;
      default "1";
      description "range 1..256; Default value: 1.";
    }
    leaf qciFilterEnabled {
      type boolean;
      default "false";
      description "Default value: false.";
    }
    leaf qciFilterMin {
      type eytypes:int32_range_0-255;
      default "0";
      description "range 0..255; Default value: 0.";
    }
    leaf qciFilterMax {
      type eytypes:int32_range_0-255;
      default "0";
      description "range 0..255; Default value: 0.";
    }
    leaf arpFilterEnabled {
      type boolean;
      default "false";
      description "Default value: false.";
    }
    leaf arpFilterMin {
      type eytypes:int32_range_0-15;
      default "0";
      description "range 0..15; Default value: 0.";
    }
    leaf arpFilterMax {
      type eytypes:int32_range_0-15;
      default "0";
      description "range 0..15; Default value: 0.";
    }
    leaf lcgFilterEnabled {
      type boolean;
      default "false";
      description "Default value: false.";
    }
    leaf lcgFilterMin {
      type eytypes:int32_range_0-3;
      default "0";
      description "range 0..3; Default value: 0.";
    }
    leaf lcgFilterMax {
      type eytypes:int32_range_0-3;
      default "0";
      description "range 0..3; Default value: 0.";
    }
    leaf uePowerClassFilterEnabled {
      type boolean;
      default "false";
      description "Default value: false.";
    }
    leaf uePowerClassFilterMin {
      type eytypes:int32_range_1-5-21;
      default "1";
      description "range 1..5; Default value: 1.";
    }
    leaf uePowerClassFilterMax {
      type eytypes:int32_range_1-5-21;
      default "1";
      description "range 1..5; Default value: 1.";
    }
    leaf ceLevelEnabled {
      type boolean;
    }
    leaf ceLevelFilterMax {
      type enumeration {
        enum CE_LEVEL_0;
        enum CE_LEVEL_1;
        enum CE_LEVEL_2;
        enum CE_LEVEL_3;
      }
    }
    leaf ceLevelFilterMin {
      type enumeration {
        enum CE_LEVEL_0;
        enum CE_LEVEL_1;
        enum CE_LEVEL_2;
        enum CE_LEVEL_3;
      }
    }
    leaf ceLevelFilterEnabled {
      type boolean;
      default "false";
      description "Default value: false.";
    }
    leaf subscriberGroupFilterEnabled {
      type boolean;
      default "false";
      description "Default value: false.";
    }
    leaf subscriberGroupFilterMin {
      type eytypes:int32_range_0-9;
      default "0";
      description "range 0..9; Default value: 0.";
    }
    leaf subscriberGroupFilterMax {
      type eytypes:int32_range_0-9;
      default "0";
      description "range 0..9; Default value: 0.";
    }
    leaf endcFilterEnabled {
      type boolean;
      default "false";
      description "Default value: false.";
    }
    leaf endcFilterMin {
      type enumeration {
        enum ENDC_NR_CAPABLE;
        enum ENDC_NR_MATCHED;
        enum ENDC_NR_ACTIVE;
        enum ENDC_UE_RELEASED;
      }
    }
    leaf endcFilterMax {
      type enumeration {
        enum ENDC_NR_CAPABLE;
        enum ENDC_NR_MATCHED;
        enum ENDC_NR_ACTIVE;
        enum ENDC_UE_RELEASED;
      }
      config false;
    }
    leaf pciFilterEnabled {
      type boolean;
      default "false";
      description "Default value: false.";
    }
    leaf pciFilterMin {
      type enumeration {
        enum SHALL_NOT_TRIGGER_PREEMPTION;
        enum MAY_TRIGGER_PREEMPTION;
      }
    }
    leaf pciFilterMax {
      type enumeration {
        enum SHALL_NOT_TRIGGER_PREEMPTION;
        enum MAY_TRIGGER_PREEMPTION;
      }
    }
    leaf pviFilterEnabled {
      type boolean;
      default "false";
      description "Default value: false.";
    }
    leaf pviFilterMin {
      type enumeration {
        enum NOT_PREEMPTABLE;
        enum PREEMPTABLE;
      }
    }
    leaf pviFilterMax {
      type enumeration {
        enum NOT_PREEMPTABLE;
        enum PREEMPTABLE;
      }
    }
    leaf reportAppCounterOnly {
      type ietfinet:port-number;
      description "Default value: true.";
    }
  }
  grouping PmUeMeasControl-attributes {
    list ueMeasIntraFreq1 {
      key "id";
      leaf id {
        type uint32;
        description "Synthetic key for struct entry.";
      }
      container attributes {
      leaf eutranFrequencyRef {
        type string;
      }
      leaf reportConfigEUtraIntraFreqPmRef {
        type ietfinet:port-number;
      }
      }
    }
    list ueMeasIntraFreq2 {
      key "id";
      leaf id {
        type uint32;
        description "Synthetic key for struct entry.";
      }
      container attributes {
      leaf eutranFrequencyRef {
        type string;
      }
      leaf reportConfigEUtraIntraFreqPmRef {
        type ietfinet:port-number;
      }
      }
    }
    leaf pmUeMeasControlId {
      type string;
      mandatory true;
    }
    list ueMeasInterFreq1 {
      key "id";
      leaf id {
        type uint32;
        description "Synthetic key for struct entry.";
      }
      container attributes {
      leaf eutranFrequencyRef {
        type string;
      }
      leaf reportConfigEUtraInterFreqPmRef {
        type ietfinet:port-number;
      }
      }
    }
    list ueMeasInterFreq2 {
      key "id";
      leaf id {
        type uint32;
        description "Synthetic key for struct entry.";
      }
      container attributes {
      leaf eutranFrequencyRef {
        type string;
      }
      leaf reportConfigEUtraInterFreqPmRef {
        type ietfinet:port-number;
      }
      }
    }
    list ueMeasInterRat1 {
      key "id";
      leaf id {
        type uint32;
        description "Synthetic key for struct entry.";
      }
      container attributes {
      leaf geranFrequencyRef {
        type string;
      }
      leaf utranFrequencyRef {
        type string;
      }
      leaf reportConfigInterRatPmRef {
        type ietfinet:port-number;
      }
      }
    }
    list ueMeasInterRat2 {
      key "id";
      leaf id {
        type uint32;
        description "Synthetic key for struct entry.";
      }
      container attributes {
      leaf geranFrequencyRef {
        type string;
      }
      leaf utranFrequencyRef {
        type string;
      }
      leaf reportConfigInterRatPmRef {
        type ietfinet:port-number;
      }
      }
    }
    leaf measGapAllowedPm {
      type boolean;
      default "false";
      description "Default value: false.";
    }
    leaf-list pmZtemporary44 {
      type uint32;
    }
    leaf-list pmUeMeasRsrpDeltaIntraFreq1 {
      type uint32;
    }
    leaf-list pmUeMeasRsrqInterFreq1 {
      type uint32;
    }
    leaf-list pmUeMeasRsrqServIntraFreq1 {
      type uint32;
    }
    leaf-list pmUeMeasRsrqDeltaInterFreq1 {
      type uint32;
    }
    leaf-list pmUeMeasRsrpDeltaInterFreq1 {
      type uint32;
    }
    leaf-list pmUeMeasRsrpInterFreq1 {
      type uint32;
    }
    leaf-list pmUeMeasRscpUtran1 {
      type uint32;
    }
    leaf-list pmUeMeasRsrpServIntraFreq1 {
      type uint32;
    }
    leaf-list pmUeMeasRsrqDeltaIntraFreq1 {
      type uint32;
    }
    leaf-list pmUeMeasEcNoUtran1 {
      type uint32;
    }
    leaf-list pmUeMeasRssiGeran1 {
      type uint32;
    }
  }
  grouping PmUlInterferenceReport-attributes {
    leaf pmUlInterferenceReportId {
      type ietfinet:port-number;
      mandatory true;
    }
    leaf rfBranchRxRef {
      type string;
      config false;
    }
    leaf pmRadioRecInterferencePwrBrPrb92 {
      type uint32;
      config false;
    }
    leaf pmRadioRecInterferencePwrBrPrb32 {
      type uint32;
      config false;
    }
    leaf pmRadioRecInterferencePwrBrPrb64 {
      type uint32;
      config false;
    }
    leaf pmRadioRecInterferencePwrBrPrb11 {
      type uint32;
      config false;
    }
    leaf pmRadioRecInterferencePwrBrPrb79 {
      type uint32;
      config false;
    }
    leaf pmRadioRecInterferencePwrBrPrb18 {
      type uint32;
      config false;
    }
    leaf pmRadioRecInterferencePwrBrPrb15 {
      type uint32;
      config false;
    }
    leaf pmRadioRecInterferencePwrBrPrb40 {
      type uint32;
      config false;
    }
    leaf pmRadioRecInterferencePwrBrPrb88 {
      type uint32;
      config false;
    }
    leaf pmRadioRecInterferencePwrBrPrb4 {
      type uint32;
      config false;
    }
    leaf pmRadioRecInterferencePwrBrPrb30 {
      type uint32;
      config false;
    }
    leaf pmRadioRecInterferencePwrBrPrb76 {
      type uint32;
      config false;
    }
    leaf pmRadioRecInterferencePwrBrPrb2 {
      type uint32;
      config false;
    }
    leaf pmRadioRecInterferencePwrBrPrb21 {
      type uint32;
      config false;
    }
    leaf pmRadioRecInterferencePwrBrPrb77 {
      type uint32;
      config false;
    }
    leaf pmRadioRecInterferencePwrBrPrb71 {
      type uint32;
      config false;
    }
    leaf pmRadioRecInterferencePwrBrPrb85 {
      type uint32;
      config false;
    }
    leaf pmRadioRecInterferencePwrBrPrb93 {
      type uint32;
      config false;
    }
    leaf pmRadioRecInterferencePwrBrPrb70 {
      type uint32;
      config false;
    }
    leaf pmRadioRecInterferencePwrBrPrb59 {
      type uint32;
      config false;
    }
    leaf pmRadioRecInterferencePwrBrPrb61 {
      type uint32;
      config false;
    }
    leaf pmRadioRecInterferencePwrBrPrb82 {
      type uint32;
      config false;
    }
    leaf pmRadioRecInterferencePwrBrPrb8 {
      type uint32;
      config false;
    }
    leaf pmRadioRecInterferencePwrBrPrb97 {
      type uint32;
      config false;
    }
    leaf pmRadioRecInterferencePwrBrPrb10 {
      type uint32;
      config false;
    }
    leaf pmRadioRecInterferencePwrBrPrb34 {
      type uint32;
      config false;
    }
    leaf pmRadioRecInterferencePwrBrPrb25 {
      type uint32;
      config false;
    }
    leaf pmRadioRecInterferencePwrBrPrb68 {
      type uint32;
      config false;
    }
    leaf pmRadioRecInterferencePwrBrPrb1 {
      type uint32;
      config false;
    }
    leaf pmRadioRecInterferencePwrBrPrb38 {
      type uint32;
      config false;
    }
    leaf pmRadioRecInterferencePwrBrPrb33 {
      type uint32;
      config false;
    }
    leaf pmRadioRecInterferencePwrBrPrb23 {
      type uint32;
      config false;
    }
    leaf pmRadioRecInterferencePwrBrPrb55 {
      type uint32;
      config false;
    }
    leaf pmRadioRecInterferencePwrBrPrb28 {
      type uint32;
      config false;
    }
    leaf pmRadioRecInterferencePwrBrPrb24 {
      type uint32;
      config false;
    }
    leaf pmRadioRecInterferencePwrBrPrb73 {
      type uint32;
      config false;
    }
    leaf pmRadioRecInterferencePwrBrPrb89 {
      type uint32;
      config false;
    }
    leaf pmRadioRecInterferencePwrBrPrb63 {
      type uint32;
      config false;
    }
    leaf pmRadioRecInterferencePwrBrPrb83 {
      type uint32;
      config false;
    }
    leaf pmRadioRecInterferencePwrBrPrb81 {
      type uint32;
      config false;
    }
    leaf pmRadioRecInterferencePwrBrPrb69 {
      type uint32;
      config false;
    }
    leaf pmRadioRecInterferencePwrBrPrb86 {
      type uint32;
      config false;
    }
    leaf pmRadioRecInterferencePwrBrPrb57 {
      type uint32;
      config false;
    }
    leaf pmRadioRecInterferencePwrBrPrb29 {
      type uint32;
      config false;
    }
    leaf pmRadioRecInterferencePwrBrPrb67 {
      type uint32;
      config false;
    }
    leaf pmRadioRecInterferencePwrBrPrb95 {
      type uint32;
      config false;
    }
    leaf pmRadioRecInterferencePwrBrPrb41 {
      type uint32;
      config false;
    }
    leaf pmRadioRecInterferencePwrBrPrb49 {
      type uint32;
      config false;
    }
    leaf pmRadioRecInterferencePwrBrPrb80 {
      type uint32;
      config false;
    }
    leaf pmRadioRecInterferencePwrBrPrb90 {
      type uint32;
      config false;
    }
    leaf pmRadioRecInterferencePwrBrPrb3 {
      type uint32;
      config false;
    }
    leaf pmRadioRecInterferencePwrBrPrb100 {
      type uint32;
      config false;
    }
    leaf pmRadioRecInterferencePwrBrPrb42 {
      type uint32;
      config false;
    }
    leaf pmRadioRecInterferencePwrBrPrb99 {
      type uint32;
      config false;
    }
    leaf pmRadioRecInterferencePwrBrPrb98 {
      type uint32;
      config false;
    }
    leaf pmRadioRecInterferencePwrBrPrb48 {
      type uint32;
      config false;
    }
    leaf pmRadioRecInterferencePwrBrPrb91 {
      type uint32;
      config false;
    }
    leaf pmRadioRecInterferencePwrBrPrb66 {
      type uint32;
      config false;
    }
    leaf pmRadioRecInterferencePwrBrPrb14 {
      type uint32;
      config false;
    }
    leaf pmRadioRecInterferencePwrBrPrb84 {
      type uint32;
      config false;
    }
    leaf pmRadioRecInterferencePwrBrPrb43 {
      type uint32;
      config false;
    }
    leaf pmRadioRecInterferencePwrBrPrb56 {
      type uint32;
      config false;
    }
    leaf pmRadioRecInterferencePwrBrPrb75 {
      type uint32;
      config false;
    }
    leaf pmRadioRecInterferencePwrBrPrb44 {
      type uint32;
      config false;
    }
    leaf pmRadioRecInterferencePwrBrPrb7 {
      type uint32;
      config false;
    }
    leaf pmRadioRecInterferencePwrBrPrb9 {
      type uint32;
      config false;
    }
    leaf pmRadioRecInterferencePwrBrPrb36 {
      type uint32;
      config false;
    }
    leaf pmRadioRecInterferencePwrBrPrb6 {
      type uint32;
      config false;
    }
    leaf pmRadioRecInterferencePwrBrPrb52 {
      type uint32;
      config false;
    }
    leaf pmRadioRecInterferencePwrBrPrb96 {
      type uint32;
      config false;
    }
    leaf pmZtemporary105 {
      type uint32;
      config false;
    }
    leaf pmRadioRecInterferencePwrBrPrb78 {
      type uint32;
      config false;
    }
    leaf pmRadioRecInterferencePwrBrPrb62 {
      type uint32;
      config false;
    }
    leaf pmRadioRecInterferencePwrBrPrb46 {
      type uint32;
      config false;
    }
    leaf pmRadioRecInterferencePwrBrPrb87 {
      type uint32;
      config false;
    }
    leaf pmRadioRecInterferencePwrBrPrb13 {
      type uint32;
      config false;
    }
    leaf pmRadioRecInterferencePwrBrPrb54 {
      type uint32;
      config false;
    }
    leaf pmRadioRecInterferencePwrBrPrb94 {
      type uint32;
      config false;
    }
    leaf pmRadioRecInterferencePwrBrPrb60 {
      type uint32;
      config false;
    }
    leaf pmRadioRecInterferencePwrBrPrb35 {
      type uint32;
      config false;
    }
    leaf pmRadioRecInterferencePwrBrPrb17 {
      type uint32;
      config false;
    }
    leaf pmRadioRecInterferencePwrBrPrb26 {
      type uint32;
      config false;
    }
    leaf pmRadioRecInterferencePwrBrPrb53 {
      type uint32;
      config false;
    }
    leaf pmRadioRecInterferencePwrBrPrb27 {
      type uint32;
      config false;
    }
    leaf pmRadioRecInterferencePwrBrPrb47 {
      type uint32;
      config false;
    }
    leaf pmRadioRecInterferencePwrBrPrb37 {
      type uint32;
      config false;
    }
    leaf pmRadioRecInterferencePwrBrPrb20 {
      type uint32;
      config false;
    }
    leaf pmRadioRecInterferencePwrBrPrb22 {
      type uint32;
      config false;
    }
    leaf pmRadioRecInterferencePwrBrPrb5 {
      type uint32;
      config false;
    }
    leaf pmRadioRecInterferencePwrBrPrb12 {
      type uint32;
      config false;
    }
    leaf pmRadioRecInterferencePwrBrPrb31 {
      type uint32;
      config false;
    }
    leaf pmZtemporary104 {
      type uint32;
      config false;
    }
    leaf pmRadioRecInterferencePwrBrPrb16 {
      type uint32;
      config false;
    }
    leaf pmRadioRecInterferencePwrBrPrb74 {
      type uint32;
      config false;
    }
    leaf pmRadioRecInterferencePwrBrPrb58 {
      type uint32;
      config false;
    }
    leaf pmRadioRecInterferencePwrBrPrb51 {
      type uint32;
      config false;
    }
    leaf pmRadioRecInterferencePwrBrPrb39 {
      type uint32;
      config false;
    }
    leaf pmRadioRecInterferencePwrBrPrb19 {
      type uint32;
      config false;
    }
    leaf pmRadioRecInterferencePwrBrPrb50 {
      type uint32;
      config false;
    }
    leaf pmRadioRecInterferencePwrBrPrb45 {
      type uint32;
      config false;
    }
    leaf pmRadioRecInterferencePwrBrPrb72 {
      type uint32;
      config false;
    }
    leaf pmRadioRecInterferencePwrBrPrb65 {
      type uint32;
      config false;
    }
  }
  grouping PowerBackoff-attributes {
    leaf powerBackoffId {
      type string;
      mandatory true;
    }
    leaf powerBackoffEnabled {
      type boolean;
      mandatory true;
    }
    leaf powerBackoffAvgTime {
      type eytypes:int32_range_30-1800;
      mandatory true;
      units "s";
      description "range 30..1800.";
    }
    leaf powerBackoffThresh {
      type eytypes:int32_range_0-1000-2;
      mandatory true;
      description "range 0..1000.";
    }
    leaf ipecPrbCycles {
      type ietfinet:ip-address;
      description "range 25..100.";
    }
  }
  grouping PrefTrafficMgmt-attributes {
    leaf-list inhibitSpidList {
      type eytypes:int32_range_1-256;
      description "Status info: Since 19.Q2. Planned to be removed..";
    }
    leaf prefTrafficMgmtId {
      type string;
      mandatory true;
      status deprecated;
      description "MOM flags: restricted, noNotification; Status info: Since 19.Q2. Planned to be removed..";
    }
    leaf inhibitIMPrioritizationInterval {
      type int32 {
        range "0..60";
      }
      status deprecated;
      default "10";
      units "minutes";
      description "range 0..60; Default value: 10; Status info: Since 19.Q2. Planned to be removed..";
    }
    leaf inhibitIMPrioritizationEnabled {
      type boolean;
      status deprecated;
      default "false";
      description "Default value: false; Status info: Since 19.Q2. Planned to be removed..";
    }
    leaf sendInhibitIMPrioritizationEnabled {
      type boolean;
      status deprecated;
      default "false";
      description "Default value: false; Status info: Since 19.Q2. Planned to be removed..";
    }
    leaf lbStopIncomingIflbThreshold {
      type eytypes:int32_range_0-1600;
      status deprecated;
      default "60";
      units ".";
      description "range 0..1600; Default value: 60; Status info: Since 19.Q2. Planned to be removed..";
    }
    leaf sendStopIncomingIflbEnabled {
      type boolean;
      status deprecated;
      default "false";
      description "Default value: false; Status info: Since 19.Q2. Planned to be removed..";
    }
    leaf stopOutgoingIflbEnabled {
      type boolean;
      status deprecated;
      default "false";
      description "Default value: false; Status info: Since 19.Q2. Planned to be removed..";
    }
    list plmnsToReserveAtHighLoad {
      key "id";
      leaf id {
        type uint32;
        description "Synthetic key for struct sequence entry.";
      }
      description "Status info: Since 19.Q2. Planned to be removed..";
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf plmnResOpUseSRatioThreshold {
      type eytypes:int32_range_0-1600;
      status deprecated;
      default "70";
      units ".";
      description "range 0..1600; Default value: 70; Status info: Since 19.Q2. Planned to be removed..";
    }
    leaf plmnUnresOpUseSRatioThreshold {
      type eytypes:int32_range_0-1600;
      status deprecated;
      default "55";
      units ".";
      description "range 0..1600; Default value: 55; Status info: Since 19.Q2. Planned to be removed..";
    }
    leaf plmnResOpUseMsrUsageThreshold {
      type eytypes:int32_range_0-100-3;
      status deprecated;
      default "70";
      description "range 0..100; Default value: 70; Status info: Since 19.Q2. Planned to be removed..";
    }
    leaf plmnUnresOpUseMsrUsageThreshold {
      type eytypes:int32_range_0-100-3;
      status deprecated;
      default "40";
      description "range 0..100; Default value: 40; Status info: Since 19.Q2. Planned to be removed..";
    }
    leaf-list spidBlacklistHo {
      type int32 {
        range "-1 | 1..256";
      }
      description "Status info: Since 19.Q2. Planned to be removed..";
    }
    leaf highLoadPlmnReservedEnabled {
      type boolean;
      status deprecated;
      default "false";
      description "Default value: false; Status info: Since 19.Q2. Planned to be removed..";
    }
    leaf atoAllowedFrom {
      type boolean;
      status deprecated;
      default "true";
      description "Default value: true; Status info: Since 19.Q2. Planned to be removed..";
    }
  }
  grouping PreschedProfile-attributes {
    leaf preschedProfileId {
      type string;
      mandatory true;
    }
    leaf preschedulingDataSize {
      type eytypes:int32_range_1-5000;
      default "86";
      units "byte";
      description "range 1..5000; Default value: 86.";
    }
    leaf preschedulingPeriod {
      type eytypes:int32_range_1-20-15;
      default "5";
      units "ms";
      description "range 1..20; Default value: 5.";
    }
    leaf preschedulingDuration {
      type int32 {
        range "5..30000";
      }
      default "200";
      units "ms";
      description "range 5..30000; Default value: 200.";
    }
    leaf-list reservedBy {
      type string;
    }
    leaf preschedulingSinrThreshold {
      type int32 {
        range "-10..40";
      }
      default "20";
      units "dB";
      description "range -10..40; Default value: 20.";
    }
  }
  grouping PreschedulingProfile-attributes {
    leaf preschedulingProfileId {
      type string;
      mandatory true;
    }
    leaf preschedulingPeriod {
      type eytypes:int32_range_1-20-15;
      default "5";
      units "ms";
      description "range 1..20; Default value: 5.";
    }
    leaf preschedulingDataSize {
      type eytypes:int32_range_1-5000;
      default "86";
      units "byte";
      description "range 1..5000; Default value: 86.";
    }
    leaf preschedulingDuration {
      type int32 {
        range "5..30000";
      }
      default "200";
      units "ms";
      description "range 5..30000; Default value: 200.";
    }
    leaf initPreschedulingDataSize {
      type eytypes:int32_range_1-5000;
      status deprecated;
      default "26";
      units "byte";
      description "range 1..5000; Default value: 26; Status info: Since 20.Q1. Has no functional behavior. Planned to be removed..";
    }
    leaf initPreschedulingDuration {
      type int32 {
        range "1..30000";
      }
      default "25";
      units "ms";
      description "range 1..30000; Default value: 25.";
    }
    leaf initPreschedulingPeriod {
      type eytypes:int32_range_1-20-15;
      default "1";
      units "ms";
      description "range 1..20; Default value: 1.";
    }
    leaf initPreschedulingControl {
      type enumeration {
        enum NO_CONTROL;
        enum SINR;
        enum PATHLOSS;
      }
    }
    leaf initPreschedulingSinrThr {
      type int32 {
        range "-10..40";
      }
      default "5";
      units "dB";
      description "range -10..40; Default value: 5.";
    }
    leaf initPreschedulingPathlossThr {
      type int32 {
        range "50..150";
      }
      default "135";
      units "dB";
      description "range 50..150; Default value: 135.";
    }
  }
  grouping PtmAtoConfig-attributes {
    leaf minSuccRateThreshold {
      type eytypes:int32_range_0-100-3;
      default "50";
      description "range 0..100; Default value: 50.";
    }
    leaf-list ptmSubscriberGroupRef {
      type string;
    }
    leaf ptmAtoConfigId {
      type string;
      mandatory true;
    }
  }
  grouping PtmCellProfile-attributes {
    leaf cellType {
      type enumeration {
        enum PRIORITY;
        enum NON_PRIORITY;
      }
    }
    list iflbConfig {
      key "id";
      leaf id {
        type uint32;
        description "Synthetic key for struct entry.";
      }
      description "Status info: Since 18.Q4. Has no functional behavior. Planned to be removed..";
      container attributes {
      leaf stopIncomingIflbThreshold {
        type eytypes:int32_range_0-1600-44;
        default "60";
        units "Subscription Ratio";
        description "range 0..1600; Default value: 60.";
      }
      leaf stopOutgoingIflbEnabled {
        type boolean;
        default "false";
        description "Default value: false.";
      }
      }
    }
    list ifoConfig {
      key "id";
      leaf id {
        type uint32;
        description "Synthetic key for struct entry.";
      }
      description "Status info: Since 18.Q4. Has no functional behavior. Planned to be removed..";
      container attributes {
      leaf subscriberGroupRefList {
        type string;
      }
      }
    }
    list atoConfig {
      key "id";
      leaf id {
        type uint32;
        description "Synthetic key for struct entry.";
      }
      description "Status info: Since 18.Q4. Has no functional behavior. Planned to be removed..";
      container attributes {
      leaf minSuccRateThreshold {
        type eytypes:int32_range_0-100-3;
        default "50";
        description "range 0..100; Default value: 50.";
      }
      leaf subscriberGroupRefList {
        type string;
      }
      }
    }
    list resOpUseConfig {
      key "id";
      leaf id {
        type uint32;
        description "Synthetic key for struct entry.";
      }
      description "Status info: Since 18.Q4. Has no functional behavior. Planned to be removed..";
      container attributes {
      leaf resSRatioThreshold {
        type eytypes:int32_range_0-1600-44;
        default "70";
        units "Subscription Ratio";
        description "range 0..1600; Default value: 70.";
      }
      leaf unresSRatioThreshold {
        type eytypes:int32_range_0-1600-44;
        default "55";
        units "Subscription Ratio";
        description "range 0..1600; Default value: 55.";
      }
      leaf resMsrUsageThreshold {
        type eytypes:int32_range_0-100-45;
        default "70";
        units "Monitored System Resources";
        description "range 0..100; Default value: 70.";
      }
      leaf unresMsrUsageThreshold {
        type eytypes:int32_range_0-100-45;
        default "40";
        units "Monitored System Resources";
        description "range 0..100; Default value: 40.";
      }
      leaf subscriberGroupRefList {
        type string;
      }
      }
    }
    list stmConfig {
      key "id";
      leaf id {
        type uint32;
        description "Synthetic key for struct entry.";
      }
      description "Status info: Since 18.Q4. Has no functional behavior. Planned to be removed..";
      container attributes {
      leaf sendInhibitImpEnabled {
        type boolean;
        default "false";
        description "Default value: false.";
      }
      leaf subscriberGroupRefList {
        type string;
      }
      }
    }
    leaf ptmCellProfileId {
      type string;
      mandatory true;
    }
    leaf-list reservedBy {
      type string;
    }
  }
  grouping PtmFunction-attributes {
    leaf ptmEnabled {
      type boolean;
      default "false";
      description "Default value: false.";
    }
    leaf ptmFunctionId {
      type string;
      mandatory true;
    }
  }
  grouping PtmIflbConfig-attributes {
    leaf stopOutgoingIflbEnabled {
      type boolean;
      default "false";
      description "Default value: false.";
    }
    leaf stopIncomingIflbThreshold {
      type eytypes:int32_range_0-1600-44;
      default "60";
      units "Subscription Ratio";
      description "range 0..1600; Default value: 60.";
    }
    leaf ptmIflbConfigId {
      type string;
      mandatory true;
    }
  }
  grouping PtmIfoConfig-attributes {
    leaf-list ptmSubscriberGroupRef {
      type string;
    }
    leaf ptmIfoConfigId {
      type string;
      mandatory true;
    }
  }
  grouping PtmResOpUseConfig-attributes {
    leaf resSRatioThreshold {
      type eytypes:int32_range_0-1600-44;
      default "70";
      units "Subscription Ratio";
      description "range 0..1600; Default value: 70.";
    }
    leaf unresSRatioThreshold {
      type eytypes:int32_range_0-1600-44;
      default "55";
      units "Subscription Ratio";
      description "range 0..1600; Default value: 55.";
    }
    leaf resMsrUsageThreshold {
      type eytypes:int32_range_0-100-45;
      default "70";
      units "Monitored System Resources";
      description "range 0..100; Default value: 70.";
    }
    leaf unresMsrUsageThreshold {
      type eytypes:int32_range_0-100-45;
      default "40";
      units "Monitored System Resources";
      description "range 0..100; Default value: 40.";
    }
    leaf-list ptmSubscriberGroupRef {
      type string;
    }
    leaf ptmResOpUseConfigId {
      type string;
      mandatory true;
    }
    list suspResOpUsePlmnList {
      key "id";
      leaf id {
        type uint32;
        description "Synthetic key for struct sequence entry.";
      }
      ordered-by user;
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
  }
  grouping PtmStmConfig-attributes {
    leaf inhibitImpInterval {
      type int32 {
        range "15..3600";
      }
      default "60";
      units "s";
      description "range 15..3600; Default value: 60.";
    }
    leaf-list ptmSubscriberGroupRef {
      type string;
    }
    leaf ptmStmConfigId {
      type string;
      mandatory true;
    }
  }
  grouping PtmSubscriberGroup-attributes {
    list plmn {
      key "id";
      leaf id {
        type uint32;
        description "Synthetic key for struct entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf-list spidList {
      type int32 {
        range "-1..256";
      }
      min-elements 1;
    }
    leaf ptmSubscriberGroupId {
      type string;
      mandatory true;
    }
    leaf-list reservedBy {
      type string;
    }
  }
  grouping PwsCmas-attributes {
    leaf pwsCmasId {
      type string;
      mandatory true;
    }
  }
  grouping QciProfileOperatorDefined-attributes {
    leaf absPrioOverride {
      type enumeration {
        enum NO_OVERRIDE;
        enum HI_PRIO_OVERRIDE;
      }
    }
    leaf aqmMode {
      type enumeration {
        enum OFF;
        enum MODE1;
        enum MODE2;
      }
    }
    leaf dataFwdPerQciEnabled {
      type boolean;
      default "false";
      description "Default value: false.";
    }
    leaf dlMinBitRate {
      type int32 {
        range "0..150000";
      }
      default "0";
      units "kbps";
      description "range 0..150000; Default value: 0.";
    }
    leaf dscp {
      type eytypes:int32_range_0-63;
      mandatory true;
      description "range 0..63.";
    }
    leaf logicalChannelGroupRef {
      type string;
      mandatory true;
    }
    list measReportConfigParams {
      key "id";
      leaf id {
        type uint32;
        description "Synthetic key for struct entry.";
      }
      container attributes {
      leaf a1ThresholdRsrpPrimOffset {
        type eytypes:int32_range_-100-100;
        default "0";
        units "dB";
        description "range -100..100; Default value: 0.";
      }
      leaf a1ThresholdRsrpSecOffset {
        type eytypes:int32_range_-100-100;
        default "0";
        units "dB";
        description "range -100..100; Default value: 0.";
      }
      leaf a1ThresholdRsrqPrimOffset {
        type eytypes:int32_range_-240-240;
        default "0";
        units "dB";
        description "range -240..240; Default value: 0.";
      }
      leaf a1ThresholdRsrqSecOffset {
        type eytypes:int32_range_-240-240;
        default "0";
        units "dB";
        description "range -240..240; Default value: 0.";
      }
      leaf a2ThresholdRsrpPrimOffset {
        type eytypes:int32_range_-100-100;
        default "0";
        units "dB";
        description "range -100..100; Default value: 0.";
      }
      leaf a2ThresholdRsrpSecOffset {
        type eytypes:int32_range_-100-100;
        default "0";
        units "dB";
        description "range -100..100; Default value: 0.";
      }
      leaf a2ThresholdRsrqPrimOffset {
        type eytypes:int32_range_-240-240;
        default "0";
        units "dB";
        description "range -240..240; Default value: 0.";
      }
      leaf a2ThresholdRsrqSecOffset {
        type eytypes:int32_range_-240-240;
        default "0";
        units "dB";
        description "range -240..240; Default value: 0.";
      }
      leaf a5Threshold1RsrpOffset {
        type eytypes:int32_range_-100-100;
        default "0";
        units "dB";
        description "range -100..100; Default value: 0.";
      }
      leaf a5Threshold1RsrqOffset {
        type eytypes:int32_range_-240-240;
        default "0";
        units "dB";
        description "range -240..240; Default value: 0.";
      }
      leaf a5Threshold2RsrpOffset {
        type eytypes:int32_range_-100-100;
        default "0";
        units "dB";
        description "range -100..100; Default value: 0.";
      }
      leaf a5Threshold2RsrqOffset {
        type eytypes:int32_range_-240-240;
        default "0";
        units "dB";
        description "range -240..240; Default value: 0.";
      }
      leaf b2Threshold1RsrpCdma2000Offset {
        type eytypes:int32_range_-100-100;
        default "0";
        units "dB";
        description "range -100..100; Default value: 0.";
      }
      leaf b2Threshold1RsrqCdma2000Offset {
        type eytypes:int32_range_-240-240;
        default "0";
        units "dB";
        description "range -240..240; Default value: 0.";
      }
      leaf b2Threshold2Cdma2000Offset {
        type eytypes:int32_range_-50-50;
        default "0";
        units "dB";
        description "range -50..50; Default value: 0.";
      }
      leaf b2Threshold1RsrpGeranOffset {
        type eytypes:int32_range_-100-100;
        default "0";
        units "dB";
        description "range -100..100; Default value: 0.";
      }
      leaf b2Threshold1RsrqGeranOffset {
        type eytypes:int32_range_-240-240;
        default "0";
        units "dB";
        description "range -240..240; Default value: 0.";
      }
      leaf b2Threshold2GeranOffset {
        type eytypes:int32_range_-24-24;
        default "0";
        units "dB";
        description "range -24..24; Default value: 0.";
      }
      leaf b2Threshold1RsrpUtraOffset {
        type eytypes:int32_range_-100-100;
        default "0";
        units "dB";
        description "range -100..100; Default value: 0.";
      }
      leaf b2Threshold1RsrqUtraOffset {
        type eytypes:int32_range_-240-240;
        default "0";
        units "dB";
        description "range -240..240; Default value: 0.";
      }
      leaf b2Threshold2EcNoUtraOffset {
        type eytypes:int32_range_-50-50;
        default "0";
        units "dB";
        description "range -50..50; Default value: 0.";
      }
      leaf b2Threshold2RscpUtraOffset {
        type eytypes:int32_range_-24-24;
        default "0";
        units "dB";
        description "range -24..24; Default value: 0.";
      }
      leaf a3IntraOffsetAdjustmentRsrp {
        type eytypes:int32_range_-150-150;
        default "0";
        units "dB";
        description "range -150..150; Default value: 0.";
      }
      leaf a3IntraOffsetAdjustmentRsrq {
        type eytypes:int32_range_-150-150;
        default "0";
        units "dB";
        description "range -150..150; Default value: 0.";
      }
      leaf a3InterOffsetAdjustmentRsrp {
        type eytypes:int32_range_-150-150;
        default "0";
        units "dB";
        description "range -150..150; Default value: 0.";
      }
      leaf a3InterOffsetAdjustmentRsrq {
        type eytypes:int32_range_-150-150;
        default "0";
        units "dB";
        description "range -150..150; Default value: 0.";
      }
      leaf timeToTriggerInterA3 {
        type int32;
        default "-1";
        units "ms";
        description "Default value: -1.";
      }
      leaf timeToTriggerIntraA3 {
        type int32;
        default "-1";
        units "ms";
        description "Default value: -1.";
      }
      leaf offsetPerQciPrio {
        type ietfinet:ip-address;
        description "range -1..7; Default value: 0.";
      }
      leaf timeToTriggerInterA3Rsrq {
        type int32;
        default "-1";
        units "ms";
        description "Default value: -1.";
      }
      }
    }
    leaf pdb {
      type eytypes:int32_range_0-500;
      default "80";
      units "ms";
      description "range 0..500; Default value: 80.";
    }
    leaf pdbOffset {
      type int32 {
        range "-500..1000";
      }
      default "0";
      units "ms";
      description "range -500..1000; Default value: 0.";
    }
    leaf pdcpSNLength {
      type int32 {
        range "7 | 12 | 15";
      }
      default "12";
      description "Default value: 12.";
    }
    leaf priority {
      type eytypes:int32_range_0-14;
      mandatory true;
      description "range 0..14.";
    }
    leaf qci {
      type int32 {
        range "10..255";
      }
      mandatory true;
      description "range 10..255.";
    }
    leaf qciACTuning {
      type int32 {
        range "1..1999";
      }
      default "1000";
      units ".";
      description "range 1..1999; Default value: 1000.";
    }
    leaf qciProfileOperatorDefinedId {
      type ietfinet:ip-address;
      mandatory true;
    }
    leaf qciSubscriptionQuanta {
      type ietfinet:ip-address;
      description "range 0..50000; Default value: 1.";
    }
    leaf resourceAllocationStrategy {
      type enumeration {
        enum RESOURCE_FAIR;
        enum FREQUENCY_SELECTIVE;
      }
    }
    leaf resourceType {
      type enumeration {
        enum NON_GBR;
        enum GBR;
      }
      mandatory true;
    }
    leaf rlcMode {
      type enumeration {
        enum AM;
        enum UM;
        enum TM;
      }
    }
    leaf rlcSNLength {
      type int32 {
        range "5 | 10 | 16";
      }
      default "10";
      description "Default value: 10.";
    }
    leaf schedulingAlgorithm {
      type enumeration {
        enum RESOURCE_FAIR;
        enum EQUAL_RATE;
        enum PROPORTIONAL_FAIR_HIGH;
        enum PROPORTIONAL_FAIR_MEDIUM;
        enum PROPORTIONAL_FAIR_LOW;
        enum MAXIMUM_C_OVER_I;
        enum DELAY_BASED;
      }
    }
    leaf srsAllocationStrategy {
      type enumeration {
        enum DEACTIVATED;
        enum ACTIVATED;
      }
    }
    leaf tReorderingDl {
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200";
      }
      default "35";
      description "Default value: 35.";
    }
    leaf tReorderingUl {
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200";
      }
      default "35";
      units "ms";
      description "Default value: 35.";
    }
    leaf ulMinBitRate {
      type eytypes:int32_range_0-75000;
      default "0";
      units "kbps";
      description "range 0..75000; Default value: 0.";
    }
    leaf userLabel {
      type string {
        length "1..128";
      }
      description "length 1..128.";
    }
    leaf relativePriority {
      type eytypes:int32_range_1-65535;
      default "1";
      description "range 1..65535; Default value: 1.";
    }
    leaf serviceType {
      type enumeration {
        enum UNDEFINED;
        enum VOIP;
        enum IMS_SIGNALING;
        enum PTT;
        enum MC_SIGNALING;
      }
    }
    leaf drxProfileRef {
      type string;
    }
    leaf drxPriority {
      type eytypes:int32_range_0-100-3;
      default "0";
      description "range 0..100; Default value: 0.";
    }
    leaf counterActiveMode {
      type boolean;
      default "false";
      description "Default value: false.";
    }
    leaf rohcEnabled {
      type boolean;
      default "false";
      description "Default value: false.";
    }
    leaf dlResourceAllocationStrategy {
      type enumeration {
        enum RESOURCE_FAIR;
        enum FREQUENCY_SELECTIVE;
      }
    }
    leaf-list reservedBy {
      type string;
    }
    leaf rlfProfileRef {
      type string;
    }
    leaf rlfPriority {
      type eytypes:int32_range_0-100-3;
      default "0";
      description "range 0..100; Default value: 0.";
    }
    leaf inactivityTimerOffset {
      type int32 {
        range "0..65535";
      }
      default "0";
      units "s";
      description "range 0..65535; Default value: 0.";
    }
    leaf dlMaxWaitingTime {
      type eytypes:int32_range_0-500;
      default "0";
      units "ms";
      description "range 0..500; Default value: 0.";
    }
    leaf ulMaxWaitingTime {
      type eytypes:int32_range_0-500;
      default "0";
      units "ms";
      description "range 0..500; Default value: 0.";
    }
    leaf timerProfileRef {
      type string;
    }
    leaf timerPriority {
      type eytypes:int32_range_0-100-3;
      default "0";
      description "range 0..100; Default value: 0.";
    }
    leaf dlMaxHARQTxQci {
      type int32 {
        range "1..8 | 10 | 12 | 16 | 20 | 24 | 28";
      }
      default "5";
      description "Default value: 5.";
    }
    leaf ulMaxHARQTxQci {
      type eytypes:int32_range_1-7;
      default "5";
      description "range 1..7; Default value: 5.";
    }
    leaf harqPriority {
      type eytypes:int32_range_0-99;
      default "0";
      description "range 0..99; Default value: 0.";
    }
    leaf lessMaxDelayThreshold {
      type eytypes:int32_range_0-20-20;
      default "0";
      units "ms";
      description "range 0..20; Default value: 0.";
    }
    leaf endcProfileRef {
      type string;
    }
    leaf priorityFraction {
      type eytypes:int32_range_0-9;
      default "0";
      description "range 0..9; Default value: 0.";
    }
    leaf bitRateRecommendationEnabled {
      type boolean;
      default "false";
      description "Default value: false.";
    }
    leaf rohcForUlDataEnabled {
      type boolean;
      default "false";
      description "Default value: false.";
    }
    list dscpArpMap {
      key "id";
      leaf id {
        type uint32;
        description "Synthetic key for struct entry.";
      }
      container attributes {
      leaf dscpArp1 {
        type eytypes:int32_range_-1-63;
        default "-1";
        description "range -1..63; Default value: -1.";
      }
      leaf dscpArp2 {
        type eytypes:int32_range_-1-63;
        default "-1";
        description "range -1..63; Default value: -1.";
      }
      leaf dscpArp3 {
        type eytypes:int32_range_-1-63;
        default "-1";
        description "range -1..63; Default value: -1.";
      }
      leaf dscpArp4 {
        type eytypes:int32_range_-1-63;
        default "-1";
        description "range -1..63; Default value: -1.";
      }
      leaf dscpArp5 {
        type eytypes:int32_range_-1-63;
        default "-1";
        description "range -1..63; Default value: -1.";
      }
      leaf dscpArp6 {
        type eytypes:int32_range_-1-63;
        default "-1";
        description "range -1..63; Default value: -1.";
      }
      leaf dscpArp7 {
        type eytypes:int32_range_-1-63;
        default "-1";
        description "range -1..63; Default value: -1.";
      }
      leaf dscpArp8 {
        type eytypes:int32_range_-1-63;
        default "-1";
        description "range -1..63; Default value: -1.";
      }
      leaf dscpArp9 {
        type eytypes:int32_range_-1-63;
        default "-1";
        description "range -1..63; Default value: -1.";
      }
      leaf dscpArp10 {
        type eytypes:int32_range_-1-63;
        default "-1";
        description "range -1..63; Default value: -1.";
      }
      leaf dscpArp11 {
        type eytypes:int32_range_-1-63;
        default "-1";
        description "range -1..63; Default value: -1.";
      }
      leaf dscpArp12 {
        type eytypes:int32_range_-1-63;
        default "-1";
        description "range -1..63; Default value: -1.";
      }
      leaf dscpArp13 {
        type eytypes:int32_range_-1-63;
        default "-1";
        description "range -1..63; Default value: -1.";
      }
      leaf dscpArp14 {
        type eytypes:int32_range_-1-63;
        default "-1";
        description "range -1..63; Default value: -1.";
      }
      leaf dscpArp15 {
        type eytypes:int32_range_-1-63;
        default "-1";
        description "range -1..63; Default value: -1.";
      }
      }
    }
    leaf zzzTemporary1 {
      type string;
    }
    leaf zzzTemporary2 {
      type string;
    }
    leaf zzzTemporary3 {
      type int32;
      default "-2000000000";
      description "Default value: -2000000000.";
    }
    leaf zzzTemporary4 {
      type int32;
      default "-2000000000";
      description "Default value: -2000000000.";
    }
    leaf zzzTemporary5 {
      type int32;
      default "-2000000000";
      description "Default value: -2000000000.";
    }
    leaf paPartitionOverride {
      type boolean;
      default "false";
      description "Default value: false.";
    }
    leaf laaSupported {
      type ietfinet:port-number;
      description "Default value: false.";
    }
    leaf caOffloadingEnabled {
      type boolean;
      default "false";
      description "Default value: false.";
    }
    leaf essResourceAllocationMode {
      type enumeration {
        enum SCHED_POLICY;
        enum DEMAND_WEIGHTED_RP;
      }
    }
    leaf relativePriorityBr {
      type eytypes:int32_range_1-32767;
      default "4";
      description "range 1..32767; Default value: 4.";
    }
    leaf lessMaxDelayThresholdWindow2 {
      type eytypes:int32_range_0-20-20;
      default "0";
      units "ms";
      description "range 0..20; Default value: 0.";
    }
  }
  grouping QciProfilePredefined-attributes {
    leaf schedulingAlgorithm {
      type enumeration {
        enum RESOURCE_FAIR;
        enum EQUAL_RATE;
        enum PROPORTIONAL_FAIR_HIGH;
        enum PROPORTIONAL_FAIR_MEDIUM;
        enum PROPORTIONAL_FAIR_LOW;
        enum MAXIMUM_C_OVER_I;
        enum DELAY_BASED;
      }
    }
    leaf qciProfilePredefinedId {
      type ietfinet:ip-address;
      mandatory true;
    }
    leaf userLabel {
      type string {
        length "1..128";
      }
      description "length 1..128.";
    }
    leaf qci {
      type int32 {
        range "0..9 | 65..66 | 69..70";
      }
      mandatory true;
    }
    leaf priority {
      type eytypes:int32_range_0-14;
      mandatory true;
      description "range 0..14.";
    }
    leaf pdb {
      type eytypes:int32_range_0-500;
      default "0";
      units "ms";
      description "range 0..500; Default value: 0.";
    }
    leaf dscp {
      type eytypes:int32_range_0-63;
      mandatory true;
      description "range 0..63.";
    }
    leaf logicalChannelGroupRef {
      type string;
      mandatory true;
    }
    leaf aqmMode {
      type enumeration {
        enum OFF;
        enum MODE1;
        enum MODE2;
      }
    }
    leaf pdbOffset {
      type int32 {
        range "-500..1000";
      }
      default "0";
      description "range -500..1000; Default value: 0.";
    }
    leaf dlMinBitRate {
      type int32 {
        range "0..150000";
      }
      default "0";
      units "kbps";
      description "range 0..150000; Default value: 0.";
    }
    leaf rlcSNLength {
      type int32 {
        range "5 | 10 | 16";
      }
      default "10";
      description "Default value: 10.";
    }
    leaf pdcpSNLength {
      type int32 {
        range "7 | 12 | 15";
      }
      default "12";
      description "Default value: 12.";
    }
    leaf tReorderingDl {
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200";
      }
      default "35";
      units "ms";
      description "Default value: 35.";
    }
    leaf tReorderingUl {
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200";
      }
      default "35";
      units "ms";
      description "Default value: 35.";
    }
    leaf rlcMode {
      type enumeration {
        enum AM;
        enum UM;
        enum TM;
      }
    }
    leaf resourceType {
      type enumeration {
        enum NON_GBR;
        enum GBR;
      }
      mandatory true;
    }
    leaf dataFwdPerQciEnabled {
      type boolean;
      default "false";
      description "Default value: false.";
    }
    leaf ulMinBitRate {
      type eytypes:int32_range_0-75000;
      default "0";
      units "kbps";
      description "range 0..75000; Default value: 0.";
    }
    leaf absPrioOverride {
      type enumeration {
        enum NO_OVERRIDE;
        enum HI_PRIO_OVERRIDE;
      }
    }
    leaf resourceAllocationStrategy {
      type enumeration {
        enum RESOURCE_FAIR;
        enum FREQUENCY_SELECTIVE;
      }
    }
    leaf srsAllocationStrategy {
      type enumeration {
        enum DEACTIVATED;
        enum ACTIVATED;
      }
    }
    list measReportConfigParams {
      key "id";
      leaf id {
        type uint32;
        description "Synthetic key for struct entry.";
      }
      container attributes {
      leaf a1ThresholdRsrpPrimOffset {
        type eytypes:int32_range_-100-100;
        default "0";
        units "dB";
        description "range -100..100; Default value: 0.";
      }
      leaf a1ThresholdRsrpSecOffset {
        type eytypes:int32_range_-100-100;
        default "0";
        units "dB";
        description "range -100..100; Default value: 0.";
      }
      leaf a1ThresholdRsrqPrimOffset {
        type eytypes:int32_range_-240-240;
        default "0";
        units "dB";
        description "range -240..240; Default value: 0.";
      }
      leaf a1ThresholdRsrqSecOffset {
        type eytypes:int32_range_-240-240;
        default "0";
        units "dB";
        description "range -240..240; Default value: 0.";
      }
      leaf a2ThresholdRsrpPrimOffset {
        type eytypes:int32_range_-100-100;
        default "0";
        units "dB";
        description "range -100..100; Default value: 0.";
      }
      leaf a2ThresholdRsrpSecOffset {
        type eytypes:int32_range_-100-100;
        default "0";
        units "dB";
        description "range -100..100; Default value: 0.";
      }
      leaf a2ThresholdRsrqPrimOffset {
        type eytypes:int32_range_-240-240;
        default "0";
        units "dB";
        description "range -240..240; Default value: 0.";
      }
      leaf a2ThresholdRsrqSecOffset {
        type eytypes:int32_range_-240-240;
        default "0";
        units "dB";
        description "range -240..240; Default value: 0.";
      }
      leaf a5Threshold1RsrpOffset {
        type eytypes:int32_range_-100-100;
        default "0";
        units "dB";
        description "range -100..100; Default value: 0.";
      }
      leaf a5Threshold1RsrqOffset {
        type eytypes:int32_range_-240-240;
        default "0";
        units "dB";
        description "range -240..240; Default value: 0.";
      }
      leaf a5Threshold2RsrpOffset {
        type eytypes:int32_range_-100-100;
        default "0";
        units "dB";
        description "range -100..100; Default value: 0.";
      }
      leaf a5Threshold2RsrqOffset {
        type eytypes:int32_range_-240-240;
        default "0";
        units "dB";
        description "range -240..240; Default value: 0.";
      }
      leaf b2Threshold1RsrpCdma2000Offset {
        type eytypes:int32_range_-100-100;
        default "0";
        units "dB";
        description "range -100..100; Default value: 0.";
      }
      leaf b2Threshold1RsrqCdma2000Offset {
        type eytypes:int32_range_-240-240;
        default "0";
        units "dB";
        description "range -240..240; Default value: 0.";
      }
      leaf b2Threshold2Cdma2000Offset {
        type eytypes:int32_range_-50-50;
        default "0";
        units "dB";
        description "range -50..50; Default value: 0.";
      }
      leaf b2Threshold1RsrpGeranOffset {
        type eytypes:int32_range_-100-100;
        default "0";
        units "dB";
        description "range -100..100; Default value: 0.";
      }
      leaf b2Threshold1RsrqGeranOffset {
        type eytypes:int32_range_-240-240;
        default "0";
        units "dB";
        description "range -240..240; Default value: 0.";
      }
      leaf b2Threshold2GeranOffset {
        type eytypes:int32_range_-24-24;
        default "0";
        units "dB";
        description "range -24..24; Default value: 0.";
      }
      leaf b2Threshold1RsrpUtraOffset {
        type eytypes:int32_range_-100-100;
        default "0";
        units "dB";
        description "range -100..100; Default value: 0.";
      }
      leaf b2Threshold1RsrqUtraOffset {
        type eytypes:int32_range_-240-240;
        default "0";
        units "dB";
        description "range -240..240; Default value: 0.";
      }
      leaf b2Threshold2EcNoUtraOffset {
        type eytypes:int32_range_-50-50;
        default "0";
        units "dB";
        description "range -50..50; Default value: 0.";
      }
      leaf b2Threshold2RscpUtraOffset {
        type eytypes:int32_range_-24-24;
        default "0";
        units "dB";
        description "range -24..24; Default value: 0.";
      }
      leaf a3IntraOffsetAdjustmentRsrp {
        type eytypes:int32_range_-150-150;
        default "0";
        units "dB";
        description "range -150..150; Default value: 0.";
      }
      leaf a3IntraOffsetAdjustmentRsrq {
        type eytypes:int32_range_-150-150;
        default "0";
        units "dB";
        description "range -150..150; Default value: 0.";
      }
      leaf a3InterOffsetAdjustmentRsrp {
        type eytypes:int32_range_-150-150;
        default "0";
        units "dB";
        description "range -150..150; Default value: 0.";
      }
      leaf a3InterOffsetAdjustmentRsrq {
        type eytypes:int32_range_-150-150;
        default "0";
        units "dB";
        description "range -150..150; Default value: 0.";
      }
      leaf timeToTriggerInterA3 {
        type int32;
        default "-1";
        units "ms";
        description "Default value: -1.";
      }
      leaf timeToTriggerIntraA3 {
        type int32;
        default "-1";
        units "ms";
        description "Default value: -1.";
      }
      leaf offsetPerQciPrio {
        type ietfinet:ip-address;
        description "range -1..7; Default value: 0.";
      }
      leaf timeToTriggerInterA3Rsrq {
        type int32;
        default "-1";
        units "ms";
        description "Default value: -1.";
      }
      }
    }
    leaf qciSubscriptionQuanta {
      type ietfinet:ip-address;
      description "range 0..50000; Default value: 1.";
    }
    leaf qciACTuning {
      type int32 {
        range "1..1999";
      }
      default "1000";
      units ".";
      description "range 1..1999; Default value: 1000.";
    }
    leaf dlResourceAllocationStrategy {
      type enumeration {
        enum RESOURCE_FAIR;
        enum FREQUENCY_SELECTIVE;
      }
    }
    leaf relativePriority {
      type eytypes:int32_range_1-65535;
      default "1";
      description "range 1..65535; Default value: 1.";
    }
    leaf rohcEnabled {
      type boolean;
      default "false";
      description "Default value: false.";
    }
    leaf serviceType {
      type enumeration {
        enum UNDEFINED;
        enum VOIP;
        enum IMS_SIGNALING;
        enum PTT;
        enum MC_SIGNALING;
      }
    }
    leaf drxProfileRef {
      type string;
    }
    leaf drxPriority {
      type eytypes:int32_range_0-100-3;
      default "0";
      description "range 0..100; Default value: 0.";
    }
    leaf counterActiveMode {
      type boolean;
      default "false";
      description "Default value: false.";
    }
    leaf-list reservedBy {
      type string;
    }
    leaf rlfProfileRef {
      type string;
    }
    leaf rlfPriority {
      type eytypes:int32_range_0-100-3;
      default "0";
      description "range 0..100; Default value: 0.";
    }
    leaf inactivityTimerOffset {
      type int32 {
        range "0..65535";
      }
      default "0";
      units "s";
      description "range 0..65535; Default value: 0.";
    }
    leaf dlMaxWaitingTime {
      type eytypes:int32_range_0-500;
      default "0";
      units "ms";
      description "range 0..500; Default value: 0.";
    }
    leaf ulMaxWaitingTime {
      type eytypes:int32_range_0-500;
      default "0";
      units "ms";
      description "range 0..500; Default value: 0.";
    }
    leaf timerProfileRef {
      type string;
    }
    leaf timerPriority {
      type eytypes:int32_range_0-100-3;
      default "0";
      description "range 0..100; Default value: 0.";
    }
    leaf dlMaxHARQTxQci {
      type int32 {
        range "1..8 | 10 | 12 | 16 | 20 | 24 | 28";
      }
      default "5";
      description "Default value: 5.";
    }
    leaf ulMaxHARQTxQci {
      type eytypes:int32_range_1-7;
      default "5";
      description "range 1..7; Default value: 5.";
    }
    leaf harqPriority {
      type eytypes:int32_range_0-99;
      default "0";
      description "range 0..99; Default value: 0.";
    }
    leaf lessMaxDelayThreshold {
      type eytypes:int32_range_0-20-20;
      default "0";
      units "ms";
      description "range 0..20; Default value: 0.";
    }
    leaf endcProfileRef {
      type string;
    }
    leaf pdbMeasurementDelta {
      type int32 {
        range "-80..100";
      }
      status deprecated;
      default "0";
      units "ms";
      description "range -80..100; Default value: 0; Takes effect: New connection; Status info: Since 19.Q1. Has no functional behavior. Planned to be removed..";
      reference "Takes effect: New connection.";
    }
    leaf priorityFraction {
      type eytypes:int32_range_0-9;
      default "0";
      description "range 0..9; Default value: 0.";
    }
    leaf bitRateRecommendationEnabled {
      type boolean;
      default "false";
      description "Default value: false.";
    }
    leaf rohcForUlDataEnabled {
      type boolean;
      default "false";
      description "Default value: false.";
    }
    list dscpArpMap {
      key "id";
      leaf id {
        type uint32;
        description "Synthetic key for struct entry.";
      }
      container attributes {
      leaf dscpArp1 {
        type eytypes:int32_range_-1-63;
        default "-1";
        description "range -1..63; Default value: -1.";
      }
      leaf dscpArp2 {
        type eytypes:int32_range_-1-63;
        default "-1";
        description "range -1..63; Default value: -1.";
      }
      leaf dscpArp3 {
        type eytypes:int32_range_-1-63;
        default "-1";
        description "range -1..63; Default value: -1.";
      }
      leaf dscpArp4 {
        type eytypes:int32_range_-1-63;
        default "-1";
        description "range -1..63; Default value: -1.";
      }
      leaf dscpArp5 {
        type eytypes:int32_range_-1-63;
        default "-1";
        description "range -1..63; Default value: -1.";
      }
      leaf dscpArp6 {
        type eytypes:int32_range_-1-63;
        default "-1";
        description "range -1..63; Default value: -1.";
      }
      leaf dscpArp7 {
        type eytypes:int32_range_-1-63;
        default "-1";
        description "range -1..63; Default value: -1.";
      }
      leaf dscpArp8 {
        type eytypes:int32_range_-1-63;
        default "-1";
        description "range -1..63; Default value: -1.";
      }
      leaf dscpArp9 {
        type eytypes:int32_range_-1-63;
        default "-1";
        description "range -1..63; Default value: -1.";
      }
      leaf dscpArp10 {
        type eytypes:int32_range_-1-63;
        default "-1";
        description "range -1..63; Default value: -1.";
      }
      leaf dscpArp11 {
        type eytypes:int32_range_-1-63;
        default "-1";
        description "range -1..63; Default value: -1.";
      }
      leaf dscpArp12 {
        type eytypes:int32_range_-1-63;
        default "-1";
        description "range -1..63; Default value: -1.";
      }
      leaf dscpArp13 {
        type eytypes:int32_range_-1-63;
        default "-1";
        description "range -1..63; Default value: -1.";
      }
      leaf dscpArp14 {
        type eytypes:int32_range_-1-63;
        default "-1";
        description "range -1..63; Default value: -1.";
      }
      leaf dscpArp15 {
        type eytypes:int32_range_-1-63;
        default "-1";
        description "range -1..63; Default value: -1.";
      }
      }
    }
    leaf zzzTemporary1 {
      type string;
    }
    leaf zzzTemporary2 {
      type string;
    }
    leaf zzzTemporary3 {
      type int32;
      default "-2000000000";
      description "Default value: -2000000000.";
    }
    leaf zzzTemporary4 {
      type int32;
      default "-2000000000";
      description "Default value: -2000000000.";
    }
    leaf zzzTemporary5 {
      type int32;
      default "-2000000000";
      description "Default value: -2000000000.";
    }
    leaf paPartitionOverride {
      type boolean;
      default "false";
      description "Default value: false.";
    }
    leaf laaSupported {
      type ietfinet:port-number;
      description "Default value: false.";
    }
    leaf caOffloadingEnabled {
      type boolean;
      default "false";
      description "Default value: false.";
    }
    leaf essResourceAllocationMode {
      type enumeration {
        enum SCHED_POLICY;
        enum DEMAND_WEIGHTED_RP;
      }
    }
    leaf relativePriorityBr {
      type eytypes:int32_range_1-32767;
      default "4";
      description "range 1..32767; Default value: 4.";
    }
    leaf lessMaxDelayThresholdWindow2 {
      type eytypes:int32_range_0-20-20;
      default "0";
      units "ms";
      description "range 0..20; Default value: 0.";
    }
  }
  grouping QciTable-attributes {
    leaf qciTableId {
      type string;
      mandatory true;
    }
    leaf-list reservedBy {
      type string;
    }
  }
  grouping RadioBearerTable-attributes {
    leaf radioBearerTableId {
      type string;
      mandatory true;
    }
    leaf tReorderingCatmCeLev0 {
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200 | 1600";
      }
      default "190";
      units "ms";
      description "Default value: 190.";
    }
    leaf tReorderingCatmCeLev1 {
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200 | 1600";
      }
      default "200";
      units "ms";
      description "Default value: 200.";
    }
  }
  grouping RATFreqPrio-attributes {
    leaf rATFreqPrioId {
      type string;
      mandatory true;
    }
    leaf-list spidList {
      type int32 {
        range "-1000 | 1..256";
      }
    }
    leaf t320 {
      type int32 {
        range "5 | 10 | 20 | 30 | 60 | 120 | 180";
      }
      default "30";
      units "min";
      description "Default value: 30.";
    }
    list freqPrioListEUTRA {
      key "id";
      leaf id {
        type uint32;
        description "Synthetic key for struct sequence entry.";
      }
      container attributes {
      leaf cellReselectionPriority {
        type int32;
        default "-1000";
        description "Default value: -1000.";
      }
      leaf connectedModeMobilityPrio {
        type int32;
        default "-1000";
        description "Default value: -1000.";
      }
      leaf arfcnValueEUtranDl {
        type int32;
        default "-1000";
        description "Default value: -1000.";
      }
      leaf voicePrio {
        type int32;
        default "-1000";
        description "Default value: -1000.";
      }
      leaf arpPrio {
        type eytypes:int32_range_-1-7;
        default "0";
        description "range -1..7; Default value: 0.";
      }
      leaf loadBalancingAllowed {
        type boolean;
        default "true";
        description "Default value: true.";
      }
      leaf atoAllowed {
        type boolean;
        default "false";
        description "Default value: false.";
      }
      leaf offloadAllowed {
        type boolean;
        default "false";
        description "Default value: false.";
      }
      }
    }
    list freqGroupPrioListGERAN {
      key "id";
      leaf id {
        type uint32;
        description "Synthetic key for struct sequence entry.";
      }
      container attributes {
      leaf cellReselectionPriority {
        type int32;
        default "-1000";
        description "Default value: -1000.";
      }
      leaf connectedModeMobilityPrio {
        type int32;
        default "-1000";
        description "Default value: -1000.";
      }
      leaf csFallbackPrio {
        type int32;
        default "-1000";
        description "Default value: -1000.";
      }
      leaf csFallbackPrioEC {
        type int32;
        default "-1000";
        description "Default value: -1000.";
      }
      leaf bandIndicatorGERAN {
        type enumeration {
          enum DCS_1800;
          enum PCS_1900;
        }
      }
      leaf frequencyGroupId {
        type int32;
        default "-1000";
        description "Default value: -1000.";
      }
      leaf voicePrio {
        type int32;
        default "-1000";
        description "Default value: -1000.";
      }
      leaf altCsfbTargetPrio {
        type int32;
        default "-1000";
        description "Default value: -1000.";
      }
      leaf altCsfbTargetPrioEc {
        type int32;
        default "-1000";
        description "Default value: -1000.";
      }
      }
    }
    list freqPrioListUTRA {
      key "id";
      leaf id {
        type uint32;
        description "Synthetic key for struct sequence entry.";
      }
      container attributes {
      leaf cellReselectionPriority {
        type int32;
        default "-1000";
        description "Default value: -1000.";
      }
      leaf connectedModeMobilityPrio {
        type int32;
        default "-1000";
        description "Default value: -1000.";
      }
      leaf arfcnValueUtranDl {
        type int32;
        default "-1000";
        description "Default value: -1000.";
      }
      leaf csFallbackPrio {
        type int32;
        default "-1000";
        description "Default value: -1000.";
      }
      leaf csFallbackPrioEC {
        type int32;
        default "-1000";
        description "Default value: -1000.";
      }
      leaf voicePrio {
        type int32;
        default "-1000";
        description "Default value: -1000.";
      }
      leaf altCsfbTargetPrio {
        type int32;
        default "-1000";
        description "Default value: -1000.";
      }
      leaf altCsfbTargetPrioEc {
        type int32;
        default "-1000";
        description "Default value: -1000.";
      }
      leaf loadBalancingAllowed {
        type boolean;
        default "true";
        description "Default value: true.";
      }
      leaf atoAllowed {
        type boolean;
        default "false";
        description "Default value: false.";
      }
      }
    }
    list bandClassPrioListCDMA2000 {
      key "id";
      leaf id {
        type uint32;
        description "Synthetic key for struct sequence entry.";
      }
      container attributes {
      leaf cellReselectionPriority {
        type int32;
        default "-1000";
        description "Default value: -1000.";
      }
      leaf connectedModeMobilityPrio {
        type int32;
        default "-1000";
        description "Default value: -1000.";
      }
      leaf freqCdma {
        type int32;
        default "-1000";
        description "Default value: -1000.";
      }
      leaf hrpdBandClass {
        type enumeration {
          enum BAND_CLASS_0;
          enum BAND_CLASS_1;
          enum BAND_CLASS_2;
          enum BAND_CLASS_3;
          enum BAND_CLASS_4;
          enum BAND_CLASS_5;
          enum BAND_CLASS_6;
          enum BAND_CLASS_7;
          enum BAND_CLASS_8;
          enum BAND_CLASS_9;
          enum BAND_CLASS_10;
          enum BAND_CLASS_11;
          enum BAND_CLASS_12;
          enum BAND_CLASS_13;
          enum BAND_CLASS_14;
          enum BAND_CLASS_15;
          enum BAND_CLASS_16;
          enum BAND_CLASS_17;
          enum BAND_CLASS_18;
          enum BAND_CLASS_19;
          enum BAND_CLASS_20;
          enum BAND_CLASS_21;
          enum UNDEFINED_VALUE;
        }
      }
      }
    }
    leaf userLabel {
      type string {
        length "1..128";
      }
      description "length 1..128.";
    }
    list bandClassPrioListCDMA1xRtt {
      key "id";
      leaf id {
        type uint32;
        description "Synthetic key for struct sequence entry.";
      }
      container attributes {
      leaf freqCdma {
        type int32;
        default "-1000";
        description "Default value: -1000.";
      }
      leaf cdma1xRttBandClass {
        type enumeration {
          enum BAND_CLASS_0;
          enum BAND_CLASS_1;
          enum BAND_CLASS_2;
          enum BAND_CLASS_3;
          enum BAND_CLASS_4;
          enum BAND_CLASS_5;
          enum BAND_CLASS_6;
          enum BAND_CLASS_7;
          enum BAND_CLASS_8;
          enum BAND_CLASS_9;
          enum BAND_CLASS_10;
          enum BAND_CLASS_11;
          enum BAND_CLASS_12;
          enum BAND_CLASS_13;
          enum BAND_CLASS_14;
          enum BAND_CLASS_15;
          enum BAND_CLASS_16;
          enum BAND_CLASS_17;
          enum BAND_CLASS_18;
          enum BAND_CLASS_19;
          enum BAND_CLASS_20;
          enum BAND_CLASS_21;
          enum UNDEFINED_VALUE;
        }
      }
      leaf cellReselectionPriority {
        type int32;
        default "-1000";
        description "Default value: -1000.";
      }
      leaf csFallbackPrio {
        type int32;
        default "-1000";
        description "Default value: -1000.";
      }
      leaf csFallbackPrioEC {
        type int32;
        default "-1000";
        description "Default value: -1000.";
      }
      leaf voicePrio {
        type eytypes:int32_range_-1-7;
        default "0";
        description "range -1..7; Default value: 0.";
      }
      }
    }
    leaf ueCapPrioAllowed {
      type boolean;
      default "false";
      description "Default value: false.";
    }
    leaf mobBackToNrFreqDisabled {
      type enumeration {
        enum NO_RESTRICTION;
        enum CONNECTED_MODE_MOBILITY;
        enum CONNECTED_IDLE_MODE_MOBILITY;
      }
    }
    leaf mobBackToNrFreqDisabledTime {
      type eytypes:int32_range_5-300;
      default "15";
      units "s";
      description "range 5..300; Default value: 15.";
    }
    leaf nrMobilityTrigQciAllAllowed {
      type boolean;
      default "false";
      description "Default value: false.";
    }
    leaf spidUeEnhLoadMgmtIncl {
      type boolean;
      default "false";
      description "Default value: false.";
    }
  }
  grouping Rcs-attributes {
    leaf rcsId {
      type string;
      mandatory true;
    }
    leaf tInactivityTimer {
      type int32 {
        range "0 | 4..86400";
      }
      default "10";
      units "s";
      description "Default value: 10.";
    }
    leaf rlcDlDeliveryFailureAction {
      type enumeration {
        enum UE_CONTEXT_RELEASE;
        enum RETAIN_CONNECTION_IF_OTHER_DRB_WITH_HIGHER_ARP;
        enum RETAIN_CONNECTION_IF_OTHER_DRB_WITH_HIGHER_OR_EQUAL_ARP;
      }
    }
    leaf tInactivityTimerBr {
      type eytypes:int32_range_0-86400;
      default "10";
      units "s";
      description "range 0..86400; Default value: 10.";
    }
    leaf bufferInactivityTimerBr {
      type int32 {
        range "0..400";
      }
      default "0";
      units "s";
      description "range 0..400; Default value: 0.";
    }
    leaf raiReleaseDelayTimerBr {
      type int32 {
        range "0..200";
      }
      default "0";
      units "s";
      description "range 0..200; Default value: 0.";
    }
    leaf tInactivityTimerMin {
      type int32 {
        range "2..86400";
      }
      status deprecated;
      default "4";
      units "s";
      description "range 2..86400; Default value: 4; Takes effect: New connection; Status info: Since 20.Q2. Has no functional behavior. Planned to be removed..";
      reference "Takes effect: New connection.";
    }
    leaf extendInactAfterVolteRel {
      type eytypes:int32_range_0-3600;
      default "0";
      units "s";
      description "range 0..3600; Default value: 0.";
    }
    leaf extendInactEmergency {
      type int32 {
        range "1..3600";
      }
      default "300";
      units "s";
      description "range 1..3600; Default value: 300.";
    }
    leaf extendInactEmMode {
      type enumeration {
        enum INACTIVE;
        enum QCI1_EM;
        enum QCI1_QCI5_EM;
        enum QCI5_EM;
      }
    }
    leaf tNasInactivityTimer {
      type int32 {
        range "0..20";
      }
      default "4";
      units "s";
      description "range 0..20; Default value: 4.";
    }
    leaf hoProhibitInactUeVsTInact {
      type eytypes:int32_range_0-32767;
      default "0";
      description "range 0..32767; Default value: 0.";
    }
  }
  grouping ReportConfigA1A2Br-attributes {
    leaf reportConfigA1A2BrId {
      type ietfinet:port-number;
      mandatory true;
    }
    leaf a1a2UlIntraSearchIntraFThr {
      type eytypes:int32_range_-150-450;
      default "340";
      units "dB";
      description "range -150..450; Default value: 340.";
    }
    leaf hysteresisA1A2UlIntraFSearch {
      type eytypes:int32_range_0-150;
      default "20";
      units "dB";
      description "range 0..150; Default value: 20.";
    }
    leaf timeToTriggerA1UlIntraFSearch {
      type int32 {
        range "0 | 40 | 64 | 80 | 100 | 128 | 160 | 256 | 320 | 480 | 512 | 640 | 1024 | 1280 | 2560 | 5120";
      }
      default "40";
      units "ms";
      description "Default value: 40.";
    }
    leaf timeToTriggerA2UlIntraFSearch {
      type int32 {
        range "0 | 40 | 64 | 80 | 100 | 128 | 160 | 256 | 320 | 480 | 512 | 640 | 1024 | 1280 | 2560 | 5120";
      }
      default "40";
      units "ms";
      description "Default value: 40.";
    }
  }
  grouping ReportConfigA1A2Endc-attributes {
    leaf reportConfigA1A2EndcId {
      type ietfinet:port-number;
      mandatory true;
    }
    list qciA1A2ThrOffsetsEndc {
      key "id";
      leaf id {
        type uint32;
        description "Synthetic key for struct sequence entry.";
      }
      container attributes {
      leaf qciProfileRef {
        type ietfinet:ip-address;
      }
      leaf a1a2ThrRsrpQciOffsetEndc {
        type eytypes:int32_range_-100-0;
        default "0";
        units "dB";
        description "range -100..0; Default value: 0.";
      }
      leaf a1a2ThrRsrqQciOffsetEndc {
        type eytypes:int32_range_-240-0;
        default "0";
        units "dB";
        description "range -240..0; Default value: 0.";
      }
      }
    }
    leaf a2OuterSearchThrRsrpOffsetEndc {
      type eytypes:int32_range_-100-0;
      default "0";
      units "dB";
      description "range -100..0; Default value: 0.";
    }
    leaf a2OuterSearchThrRsrqOffsetEndc {
      type eytypes:int32_range_-240-0;
      default "0";
      units "dB";
      description "range -240..0; Default value: 0.";
    }
  }
  grouping ReportConfigA1A2HigherPrio-attributes {
    leaf thresholdRsrp {
      type eytypes:int32_range_-140--44;
      default "-126";
      units "dBm";
      description "range -140..-44; Default value: -126.";
    }
    leaf thresholdRsrq {
      type eytypes:int32_range_-195--30;
      default "-140";
      units "dB";
      description "range -195..-30; Default value: -140.";
    }
    leaf hysteresis {
      type eytypes:int32_range_0-150;
      default "10";
      units "dB";
      description "range 0..150; Default value: 10.";
    }
    leaf timeToTrigger {
      type int32 {
        range "0 | 40 | 64 | 80 | 100 | 128 | 160 | 256 | 320 | 480 | 512 | 640 | 1024 | 1280 | 2560 | 5120";
      }
      default "40";
      units "ms";
      description "Default value: 40.";
    }
    leaf reportConfigA1A2HigherPrioId {
      type ietfinet:port-number;
      mandatory true;
    }
    leaf triggerQuantity {
      type enumeration {
        enum RSRP;
        enum RSRQ;
      }
    }
    leaf hysteresisRsrq {
      type eytypes:int32_range_0-150;
      default "10";
      units "dB";
      description "range 0..150; Default value: 10.";
    }
  }
  grouping ReportConfigA1Prim-attributes {
    leaf reportConfigA1PrimId {
      type ietfinet:port-number;
      mandatory true;
    }
    leaf a1ThresholdRsrpPrim {
      type eytypes:int32_range_-140--44;
      default "-136";
      units "dBm";
      description "range -140..-44; Default value: -136.";
    }
    leaf a1ThresholdRsrqPrim {
      type eytypes:int32_range_-195--30;
      default "-195";
      units "dB";
      description "range -195..-30; Default value: -195.";
    }
    leaf hysteresisA1Prim {
      type eytypes:int32_range_0-150;
      default "10";
      units "dB";
      description "range 0..150; Default value: 10.";
    }
    leaf timeToTriggerA1Prim {
      type int32 {
        range "0 | 40 | 64 | 80 | 100 | 128 | 160 | 256 | 320 | 480 | 512 | 640 | 1024 | 1280 | 2560 | 5120";
      }
      default "640";
      units "ms";
      description "Default value: 640.";
    }
    leaf a1ThrRsrpPrimOffsetCeABr {
      type eytypes:int32_range_-100-100;
      default "0";
      units "dB";
      description "range -100..100; Default value: 0.";
    }
  }
  grouping ReportConfigA1Sec-attributes {
    leaf reportConfigA1SecId {
      type ietfinet:port-number;
      mandatory true;
    }
    leaf a1ThresholdRsrpSec {
      type eytypes:int32_range_-140--44;
      default "-136";
      units "dBm";
      description "range -140..-44; Default value: -136.";
    }
    leaf a1ThresholdRsrqSec {
      type eytypes:int32_range_-195--30;
      default "-195";
      units "dB";
      description "range -195..-30; Default value: -195.";
    }
    leaf hysteresisA1Sec {
      type eytypes:int32_range_0-150;
      default "10";
      units "dB";
      description "range 0..150; Default value: 10.";
    }
    leaf timeToTriggerA1Sec {
      type int32 {
        range "0 | 40 | 64 | 80 | 100 | 128 | 160 | 256 | 320 | 480 | 512 | 640 | 1024 | 1280 | 2560 | 5120";
      }
      default "640";
      units "ms";
      description "Default value: 640.";
    }
    leaf a1ThrRsrpSecOffsetCeABr {
      type eytypes:int32_range_-100-100;
      default "0";
      units "dB";
      description "range -100..100; Default value: 0.";
    }
  }
  grouping ReportConfigA4-attributes {
    leaf reportConfigA4Id {
      type ietfinet:port-number;
      mandatory true;
    }
    leaf a4ThresholdRsrp {
      type eytypes:int32_range_-140--44;
      default "-140";
      units "dBm";
      description "range -140..-44; Default value: -140.";
    }
    leaf a4ThresholdRsrq {
      type eytypes:int32_range_-195--30;
      default "-195";
      units "dB";
      description "range -195..-30; Default value: -195.";
    }
    leaf hysteresisA4 {
      type eytypes:int32_range_0-150;
      default "10";
      units "dB";
      description "range 0..150; Default value: 10.";
    }
    leaf timeToTriggerA4 {
      type int32 {
        range "0 | 40 | 64 | 80 | 100 | 128 | 160 | 256 | 320 | 480 | 512 | 640 | 1024 | 1280 | 2560 | 5120";
      }
      default "640";
      units "ms";
      description "Default value: 640.";
    }
    leaf triggerQuantityA4 {
      type enumeration {
        enum RSRP;
        enum RSRQ;
      }
    }
  }
  grouping ReportConfigA5-attributes {
    leaf reportConfigA5Id {
      type ietfinet:port-number;
      mandatory true;
    }
    leaf a5Threshold1Rsrp {
      type eytypes:int32_range_-140--44;
      default "-140";
      units "dBm";
      description "range -140..-44; Default value: -140.";
    }
    leaf a5Threshold2Rsrp {
      type eytypes:int32_range_-140--44;
      default "-136";
      units "dBm";
      description "range -140..-44; Default value: -136.";
    }
    leaf a5Threshold1Rsrq {
      type eytypes:int32_range_-195--30;
      default "-195";
      units "dB";
      description "range -195..-30; Default value: -195.";
    }
    leaf a5Threshold2Rsrq {
      type eytypes:int32_range_-195--30;
      default "-195";
      units "dB";
      description "range -195..-30; Default value: -195.";
    }
    leaf hysteresisA5 {
      type eytypes:int32_range_0-150;
      default "10";
      units "dB";
      description "range 0..150; Default value: 10.";
    }
    leaf timeToTriggerA5 {
      type int32 {
        range "0 | 40 | 64 | 80 | 100 | 128 | 160 | 256 | 320 | 480 | 512 | 640 | 1024 | 1280 | 2560 | 5120";
      }
      default "640";
      units "ms";
      description "Default value: 640.";
    }
    leaf triggerQuantityA5 {
      type enumeration {
        enum RSRP;
        enum RSRQ;
      }
    }
    leaf maxReportCellsA5 {
      type ietfinet:port-number;
      default "4";
      description "range 1..8; Default value: 4.";
    }
    leaf hysteresisA5RsrqOffset {
      type eytypes:int32_range_-150-150;
      default "0";
      units "dB";
      description "range -150..150; Default value: 0.";
    }
    leaf timeToTriggerA5Rsrq {
      type int32 {
        range "-1..0 | 40 | 64 | 80 | 100 | 128 | 160 | 256 | 320 | 480 | 512 | 640 | 1024 | 1280 | 2560 | 5120";
      }
      default "-1";
      units "ms";
      description "Default value: -1.";
    }
  }
  grouping ReportConfigA5Anr-attributes {
    leaf reportConfigA5AnrId {
      type ietfinet:port-number;
      mandatory true;
    }
    leaf a5Threshold1RsrpAnrDelta {
      type eytypes:int32_range_-10-10;
      default "1";
      units "dB";
      description "range -10..10; Default value: 1.";
    }
    leaf a5Threshold2RsrpAnrDelta {
      type eytypes:int32_range_-10-10;
      default "1";
      units "dB";
      description "range -10..10; Default value: 1.";
    }
    leaf a5Threshold1RsrqAnrDelta {
      type eytypes:int32_range_-10-10;
      default "10";
      units "dB";
      description "range -10..10; Default value: 10.";
    }
    leaf a5Threshold2RsrqAnrDelta {
      type eytypes:int32_range_-10-10;
      default "10";
      units "dB";
      description "range -10..10; Default value: 10.";
    }
    leaf timeToTriggerA5 {
      type int32 {
        range "0 | 40 | 64 | 80 | 100 | 128 | 160 | 256 | 320 | 480 | 512 | 640 | 1024 | 1280 | 2560 | 5120";
      }
      default "640";
      units "ms";
      description "Default value: 640.";
    }
    leaf hysteresisA5 {
      type eytypes:int32_range_0-150;
      default "10";
      units "dB";
      description "range 0..150; Default value: 10.";
    }
  }
  grouping ReportConfigA5DlComp-attributes {
    leaf a5Threshold1Rsrq {
      type eytypes:int32_range_-195--30;
      default "-115";
      units "dB";
      description "range -195..-30; Default value: -115.";
    }
    leaf a5Threshold2Rsrq {
      type eytypes:int32_range_-195--30;
      default "-185";
      units "dB";
      description "range -195..-30; Default value: -185.";
    }
    leaf reportConfigA5DlCompId {
      type ietfinet:port-number;
      mandatory true;
    }
  }
  grouping ReportConfigA5EndcHo-attributes {
    leaf reportConfigA5EndcHoId {
      type ietfinet:port-number;
      mandatory true;
    }
    leaf a5Threshold1Rsrp {
      type eytypes:int32_range_-140--44;
      default "-44";
      units "dBm";
      description "range -140..-44; Default value: -44.";
    }
    leaf a5Threshold2Rsrp {
      type eytypes:int32_range_-140--44;
      default "-112";
      units "dBm";
      description "range -140..-44; Default value: -112.";
    }
    leaf a5Threshold1Rsrq {
      type eytypes:int32_range_-195--30;
      default "-30";
      units "dB";
      description "range -195..-30; Default value: -30.";
    }
    leaf a5Threshold2Rsrq {
      type eytypes:int32_range_-195--30;
      default "-150";
      units "dB";
      description "range -195..-30; Default value: -150.";
    }
    leaf reportAmountA5 {
      type ietfinet:port-number;
      default "0";
      description "Default value: 0.";
    }
    leaf reportIntervalA5 {
      type ietfinet:port-number;
    }
    leaf triggerQuantityA5 {
      type enumeration {
        enum RSRP;
        enum RSRQ;
      }
    }
    leaf timeToTriggerA5 {
      type int32 {
        range "0 | 40 | 64 | 80 | 100 | 128 | 160 | 256 | 320 | 480 | 512 | 640 | 1024 | 1280 | 2560 | 5120";
      }
      default "100";
      units "ms";
      description "Default value: 100.";
    }
    leaf hysteresisA5 {
      type eytypes:int32_range_0-150;
      default "10";
      units "dB";
      description "range 0..150; Default value: 10.";
    }
    leaf reportQuantityA5 {
      type ietfinet:port-number;
    }
    leaf maxReportCellsA5 {
      type ietfinet:port-number;
      default "4";
      description "range 1..8; Default value: 4.";
    }
  }
  grouping ReportConfigA5InterFreqHigherPrio-attributes {
    leaf a5Threshold1Rsrp {
      type eytypes:int32_range_-140--44;
      default "-44";
      units "dBm";
      description "range -140..-44; Default value: -44.";
    }
    leaf a5Threshold1Rsrq {
      type eytypes:int32_range_-195--30;
      default "-30";
      units "dB";
      description "range -195..-30; Default value: -30.";
    }
    leaf a5Threshold2Rsrp {
      type eytypes:int32_range_-140--44;
      default "-140";
      units "dBm";
      description "range -140..-44; Default value: -140.";
    }
    leaf a5Threshold2Rsrq {
      type eytypes:int32_range_-195--30;
      default "-195";
      units "dB";
      description "range -195..-30; Default value: -195.";
    }
    leaf hysterisisA5 {
      type eytypes:int32_range_0-150;
      status deprecated;
      default "10";
      units "dB";
      description "range 0..150; Default value: 10; Takes effect: Next usage; Status info: Since 24.Q2. Replaced by hysteresisA5. Planned to be removed..";
      reference "Takes effect: Next usage.";
    }
    leaf timeToTriggerA5 {
      type int32 {
        range "0 | 40 | 64 | 80 | 100 | 128 | 160 | 256 | 320 | 480 | 512 | 640 | 1024 | 1280 | 2560 | 5120";
      }
      default "40";
      units "ms";
      description "Default value: 40.";
    }
    leaf triggerQuantityA5 {
      type enumeration {
        enum RSRP;
        enum RSRQ;
      }
    }
    leaf reportConfigA5InterFreqHigherPrioId {
      type ietfinet:port-number;
      mandatory true;
    }
    leaf hysteresisA5 {
      type eytypes:int32_range_0-150;
      default "10";
      units "dB";
      description "range 0..150; Default value: 10.";
    }
  }
  grouping ReportConfigA5SoftLock-attributes {
    leaf reportConfigA5SoftLockId {
      type ietfinet:port-number;
      mandatory true;
    }
    leaf a5Threshold2Rsrp {
      type eytypes:int32_range_-140--44;
      default "-140";
      units "dBm";
      description "range -140..-44; Default value: -140.";
    }
  }
  grouping ReportConfigA5Spifho-attributes {
    leaf a5Threshold1Rsrp {
      type eytypes:int32_range_-140--44;
      default "-44";
      units "dBm";
      description "range -140..-44; Default value: -44.";
    }
    leaf a5Threshold1Rsrq {
      type eytypes:int32_range_-195--30;
      default "-30";
      units "dB";
      description "range -195..-30; Default value: -30.";
    }
    leaf a5Threshold2Rsrp {
      type eytypes:int32_range_-140--44;
      default "-110";
      units "dBm";
      description "range -140..-44; Default value: -110.";
    }
    leaf a5Threshold2Rsrq {
      type eytypes:int32_range_-195--30;
      default "-150";
      units "dB";
      description "range -195..-30; Default value: -150.";
    }
    leaf hysteresisA5 {
      type eytypes:int32_range_0-150;
      default "10";
      units "dB";
      description "range 0..150; Default value: 10.";
    }
    leaf reportConfigA5SpifhoId {
      type ietfinet:port-number;
      mandatory true;
    }
    leaf timeToTriggerA5 {
      type int32 {
        range "0 | 40 | 64 | 80 | 100 | 128 | 160 | 256 | 320 | 480 | 512 | 640 | 1024 | 1280 | 2560 | 5120";
      }
      default "80";
      units "ms";
      description "Default value: 80.";
    }
    leaf triggerQuantityA5 {
      type enumeration {
        enum RSRP;
        enum RSRQ;
      }
    }
  }
  grouping ReportConfigA5UlTraffic-attributes {
    leaf reportConfigA5UlTrafficId {
      type ietfinet:port-number;
      mandatory true;
    }
    leaf a5Threshold2Rsrp {
      type eytypes:int32_range_-140--44;
      default "-140";
      units "dBm";
      description "range -140..-44; Default value: -140.";
    }
    leaf hysteresisA5 {
      type eytypes:int32_range_0-150;
      default "10";
      units "dB";
      description "range 0..150; Default value: 10.";
    }
    leaf timeToTriggerA5 {
      type int32 {
        range "0 | 40 | 64 | 80 | 100 | 128 | 160 | 256 | 320 | 480 | 512 | 640 | 1024 | 1280 | 2560 | 5120";
      }
      default "640";
      units "ms";
      description "Default value: 640.";
    }
    leaf a5Threshold1Rsrp {
      type eytypes:int32_range_-140--44;
      default "-44";
      units "dBm";
      description "range -140..-44; Default value: -44.";
    }
    leaf a5Threshold1Rsrq {
      type eytypes:int32_range_-195--30;
      default "-30";
      units "dB";
      description "range -195..-30; Default value: -30.";
    }
    leaf a5Threshold2Rsrq {
      type int32 {
        range "-195..-31";
      }
      default "-195";
      units "dB";
      description "range -195..-31; Default value: -195.";
    }
    leaf triggerQuantityA5 {
      type enumeration {
        enum RSRP;
        enum RSRQ;
      }
    }
  }
  grouping ReportConfigA5UlTrig-attributes {
    leaf reportConfigA5UlTrigId {
      type ietfinet:port-number;
      mandatory true;
    }
    leaf a5Threshold2Rsrp {
      type eytypes:int32_range_-140--44;
      default "-140";
      units "dBm";
      description "range -140..-44; Default value: -140.";
    }
    leaf hysteresisA5 {
      type eytypes:int32_range_0-150;
      default "10";
      units "dB";
      description "range 0..150; Default value: 10.";
    }
    leaf reportIntervalA5 {
      type ietfinet:port-number;
    }
    leaf timeToTriggerA5 {
      type int32 {
        range "0 | 40 | 64 | 80 | 100 | 128 | 160 | 256 | 320 | 480 | 512 | 640 | 1024 | 1280 | 2560 | 5120";
      }
      default "640";
      units "ms";
      description "Default value: 640.";
    }
    leaf a5Threshold1Rsrp {
      type eytypes:int32_range_-140--44;
      default "-44";
      units "dBm";
      description "range -140..-44; Default value: -44.";
    }
    leaf a5Threshold1Rsrq {
      type eytypes:int32_range_-195--30;
      default "-30";
      units "dB";
      description "range -195..-30; Default value: -30.";
    }
    leaf a5Threshold2Rsrq {
      type int32 {
        range "-195..-31";
      }
      default "-195";
      units "dB";
      description "range -195..-31; Default value: -195.";
    }
  }
  grouping ReportConfigA5UlVolte-attributes {
    leaf a5Threshold1Rsrp {
      type eytypes:int32_range_-140--44;
      default "-44";
      units "dBm";
      description "range -140..-44; Default value: -44.";
    }
    leaf a5Threshold1Rsrq {
      type eytypes:int32_range_-195--30;
      default "-30";
      units "dB";
      description "range -195..-30; Default value: -30.";
    }
    leaf a5Threshold2Rsrp {
      type eytypes:int32_range_-140--44;
      default "-140";
      units "dBm";
      description "range -140..-44; Default value: -140.";
    }
    leaf a5Threshold2Rsrq {
      type eytypes:int32_range_-195--30;
      default "-195";
      units "dB";
      description "range -195..-30; Default value: -195.";
    }
    leaf hysteresisA5 {
      type eytypes:int32_range_0-150;
      default "10";
      units "dB";
      description "range 0..150; Default value: 10.";
    }
    leaf timeToTriggerA5 {
      type int32 {
        range "0 | 40 | 64 | 80 | 100 | 128 | 160 | 256 | 320 | 480 | 512 | 640 | 1024 | 1280 | 2560 | 5120";
      }
      default "40";
      units "ms";
      description "Default value: 40.";
    }
    leaf triggerQuantityA5 {
      type enumeration {
        enum RSRP;
        enum RSRQ;
      }
    }
    leaf reportConfigA5UlVolteId {
      type ietfinet:port-number;
      mandatory true;
    }
  }
  grouping ReportConfigB1Geran-attributes {
    leaf reportConfigB1GeranId {
      type ietfinet:port-number;
      mandatory true;
    }
    leaf b1ThresholdGeran {
      type eytypes:int32_range_-110--47;
      default "-110";
      units "dBm";
      description "range -110..-47; Default value: -110.";
    }
    leaf hysteresisB1 {
      type eytypes:int32_range_0-150;
      default "10";
      units "dB";
      description "range 0..150; Default value: 10.";
    }
    leaf timeToTriggerB1 {
      type int32 {
        range "0 | 40 | 64 | 80 | 100 | 128 | 160 | 256 | 320 | 480 | 512 | 640 | 1024 | 1280 | 2560 | 5120";
      }
      default "640";
      units "ms";
      description "Default value: 640.";
    }
  }
  grouping ReportConfigB1GUtra-attributes {
    leaf reportConfigB1GUtraId {
      type ietfinet:port-number;
      mandatory true;
    }
    leaf b1Threshold {
      type eytypes:int32_range_0-127;
      status deprecated;
      default "0";
      description "range 0..127; Default value: 0; Takes effect: New connection; Status info: Since 19.Q3. Replaced by b1ThresholdRsrp and b1ThresholdRsrq. Planned to be removed.; Specification: 3GPP TS 38.133.";
      reference "Takes effect: New connection.";
    }
    leaf hysteresisB1 {
      type eytypes:int32_range_0-30;
      default "0";
      units "dB";
      description "range 0..30; Default value: 0.";
    }
    leaf timeToTriggerB1 {
      type int32 {
        range "0 | 40 | 64 | 80 | 100 | 128 | 160 | 256 | 320 | 480 | 512 | 640 | 1024 | 1280 | 2560 | 5120";
      }
      default "0";
      units "ms";
      description "Default value: 0.";
    }
    leaf maxReportCellsB1 {
      type ietfinet:port-number;
      default "4";
      description "range 1..8; Default value: 4.";
    }
    leaf reportIntervalB1 {
      type ietfinet:port-number;
    }
    leaf triggerQuantityB1 {
      type enumeration {
        enum SS_RSRP;
        enum SS_RSRQ;
      }
    }
    leaf b1ThresholdRsrp {
      type eytypes:int32_range_-156--29;
      default "-140";
      units "dBm";
      description "range -156..-29; Default value: -140.";
    }
    leaf b1ThresholdRsrq {
      type eytypes:int32_range_-435-200;
      default "-430";
      units "dB";
      description "range -435..200; Default value: -430.";
    }
  }
  grouping ReportConfigB1NR-attributes {
    leaf reportConfigB1NRId {
      type ietfinet:port-number;
      mandatory true;
    }
    leaf b1Threshold {
      type eytypes:int32_range_0-127;
      status deprecated;
      default "0";
      description "range 0..127; Default value: 0; Takes effect: New connection; Status info: Since 19.Q3. Replaced by b1ThresholdRsrp and b1ThresholdRsrq. Planned to be removed.; Specification: 3GPP TS 38.331.";
      reference "Takes effect: New connection.";
    }
    leaf hysteresisB1 {
      type eytypes:int32_range_0-30;
      default "2";
      units "dB";
      description "range 0..30; Default value: 2.";
    }
    leaf timeToTriggerB1 {
      type int32 {
        range "0 | 40 | 64 | 80 | 100 | 128 | 160 | 256 | 320 | 480 | 512 | 640 | 1024 | 1280 | 2560 | 5120";
      }
      default "640";
      units "ms";
      description "Default value: 640.";
    }
    leaf triggerQuantityB1NR {
      type enumeration {
        enum SS_RSRP;
        enum SS_RSRQ;
      }
    }
    leaf b1ThresholdRsrp {
      type eytypes:int32_range_-156--29;
      default "-140";
      units "dBm";
      description "range -156..-29; Default value: -140.";
    }
    leaf b1ThresholdRsrq {
      type eytypes:int32_range_-435-200;
      default "-435";
      units "dB";
      description "range -435..200; Default value: -435.";
    }
  }
  grouping ReportConfigB1NRCommon-attributes {
    leaf reportConfigB1NRCommonId {
      type ietfinet:port-number;
      mandatory true;
      status deprecated;
      description "MOM flags: restricted, noNotification; Status info: Since 19.Q4. Has no functional behavior. Planned to be removed..";
    }
    leaf b1ThresholdRsrp {
      type eytypes:int32_range_-156--29;
      status deprecated;
      default "-140";
      units "dBm";
      description "range -156..-29; Default value: -140; Takes effect: New connection; Status info: Since 19.Q4. Has no functional behavior. Planned to be removed.; Specification: 3GPP TS 38.133.";
      reference "Takes effect: New connection.";
    }
    leaf b1ThresholdRsrq {
      type int32 {
        range "-430..200";
      }
      status deprecated;
      default "-430";
      units "dB";
      description "range -430..200; Default value: -430; Takes effect: New connection; Status info: Since 19.Q4. Has no functional behavior. Planned to be removed.; Specification: 3GPP TS 38.133.";
      reference "Takes effect: New connection.";
    }
    leaf hysteresisB1 {
      type eytypes:int32_range_0-30;
      status deprecated;
      default "0";
      units "dB";
      description "range 0..30; Default value: 0; Takes effect: New connection; Status info: Since 19.Q4. Has no functional behavior. Planned to be removed..";
      reference "Takes effect: New connection.";
    }
    leaf timeToTriggerB1 {
      type int32 {
        range "0 | 40 | 64 | 80 | 100 | 128 | 160 | 256 | 320 | 480 | 512 | 640 | 1024 | 1280 | 2560 | 5120";
      }
      status deprecated;
      default "640";
      units "ms";
      description "Default value: 640; Takes effect: New connection; Status info: Since 19.Q4. Has no functional behavior. Planned to be removed..";
      reference "Takes effect: New connection.";
    }
    leaf triggerQuantityB1NR {
      type enumeration {
        enum SS_RSRP;
        enum SS_RSRQ;
      }
      status deprecated;
      default "SS_RSRP";
      description "Default value: SS_RSRP; Takes effect: New connection; Status info: Since 19.Q4. Has no functional behavior. Planned to be removed..";
      reference "Takes effect: New connection.";
    }
    leaf-list reservedBy {
      type string;
      description "Status info: Since 19.Q4. Has no functional behavior. Planned to be removed..";
    }
  }
  grouping ReportConfigB1Utra-attributes {
    leaf reportConfigB1UtraId {
      type ietfinet:port-number;
      mandatory true;
    }
    leaf b1ThresholdEcNoUtra {
      type eytypes:int32_range_-245-0;
      default "-240";
      units "dB";
      description "range -245..0; Default value: -240.";
    }
    leaf hysteresisB1 {
      type eytypes:int32_range_0-150;
      default "10";
      units "dB";
      description "range 0..150; Default value: 10.";
    }
    leaf timeToTriggerB1 {
      type int32 {
        range "0 | 40 | 64 | 80 | 100 | 128 | 160 | 256 | 320 | 480 | 512 | 640 | 1024 | 1280 | 2560 | 5120";
      }
      default "640";
      units "ms";
      description "Default value: 640.";
    }
    leaf b1ThresholdRscpUtra {
      type eytypes:int32_range_-120--24;
      default "-115";
      units "dBm";
      description "range -120..-24; Default value: -115.";
    }
  }
  grouping ReportConfigB2Cdma2000-attributes {
    leaf reportConfigB2Cdma2000Id {
      type ietfinet:port-number;
      mandatory true;
    }
    leaf b2Threshold1Rsrp {
      type eytypes:int32_range_-140--44;
      default "-140";
      units "dBm";
      description "range -140..-44; Default value: -140.";
    }
    leaf b2Threshold1Rsrq {
      type eytypes:int32_range_-195--30;
      default "-195";
      units "dB";
      description "range -195..-30; Default value: -195.";
    }
    leaf b2Threshold2Cdma2000 {
      type eytypes:int32_range_-315-0;
      default "-75";
      units "dB";
      description "range -315..0; Default value: -75.";
    }
    leaf hysteresisB2 {
      type eytypes:int32_range_0-150;
      default "10";
      units "dB";
      description "range 0..150; Default value: 10.";
    }
    leaf timeToTriggerB2 {
      type int32 {
        range "0 | 40 | 64 | 80 | 100 | 128 | 160 | 256 | 320 | 480 | 512 | 640 | 1024 | 1280 | 2560 | 5120";
      }
      default "640";
      units "ms";
      description "Default value: 640.";
    }
    leaf triggerQuantityB2 {
      type enumeration {
        enum RSRP;
        enum RSRQ;
      }
    }
    leaf timeToTriggerB2Rsrq {
      type int32 {
        range "-1..0 | 40 | 64 | 80 | 100 | 128 | 160 | 256 | 320 | 480 | 512 | 640 | 1024 | 1280 | 2560 | 5120";
      }
      default "-1";
      units "ms";
      description "Default value: -1.";
    }
    leaf hysteresisB2RsrqOffset {
      type eytypes:int32_range_-150-150;
      default "0";
      units "dB";
      description "range -150..150; Default value: 0.";
    }
  }
  grouping ReportConfigB2Cdma20001xRtt-attributes {
    leaf reportConfigB2Cdma20001xRttId {
      type ietfinet:port-number;
      mandatory true;
    }
    leaf b2Threshold1Rsrp {
      type eytypes:int32_range_-140--44;
      default "-140";
      units "dBm";
      description "range -140..-44; Default value: -140.";
    }
    leaf b2Threshold1Rsrq {
      type eytypes:int32_range_-195--30;
      default "-195";
      units "dB";
      description "range -195..-30; Default value: -195.";
    }
    leaf b2Threshold2Cdma20001xRtt {
      type eytypes:int32_range_-315-0;
      default "-75";
      units "dB";
      description "range -315..0; Default value: -75.";
    }
    leaf hysteresisB2 {
      type eytypes:int32_range_0-150;
      default "10";
      units "dB";
      description "range 0..150; Default value: 10.";
    }
    leaf timeToTriggerB2 {
      type int32 {
        range "0 | 40 | 64 | 80 | 100 | 128 | 160 | 256 | 320 | 480 | 512 | 640 | 1024 | 1280 | 2560 | 5120";
      }
      default "640";
      units "ms";
      description "Default value: 640.";
    }
    leaf triggerQuantityB2 {
      type enumeration {
        enum RSRP;
        enum RSRQ;
      }
    }
    leaf timeToTriggerB2Rsrq {
      type int32 {
        range "-1..0 | 40 | 64 | 80 | 100 | 128 | 160 | 256 | 320 | 480 | 512 | 640 | 1024 | 1280 | 2560 | 5120";
      }
      default "-1";
      units "ms";
      description "Default value: -1.";
    }
    leaf hysteresisB2RsrqOffset {
      type eytypes:int32_range_-150-150;
      default "0";
      units "dB";
      description "range -150..150; Default value: 0.";
    }
  }
  grouping ReportConfigB2CdmaRttUlTrig-attributes {
    leaf reportConfigB2CdmaRttUlTrigId {
      type ietfinet:port-number;
      mandatory true;
      status deprecated;
      description "MOM flags: restricted, noNotification; Status info: Since 17.Q4. Has no functional behavior. Planned to be removed..";
    }
    leaf b2Threshold2Cdma20001xRtt {
      type eytypes:int32_range_-315-0;
      status deprecated;
      default "-75";
      units "dB";
      description "range -315..0; Default value: -75; Takes effect: New connection; Status info: Since 17.Q4. Has no functional behavior. Planned to be removed..";
      reference "Takes effect: New connection.";
    }
    leaf hysteresisB2 {
      type eytypes:int32_range_0-150;
      status deprecated;
      default "10";
      units "dB";
      description "range 0..150; Default value: 10; Takes effect: New connection; Status info: Since 17.Q4. Has no functional behavior. Planned to be removed..";
      reference "Takes effect: New connection.";
    }
    leaf reportIntervalB2 {
      type ietfinet:port-number;
      status deprecated;
      description "Default value: MS_2048; Takes effect: New connection; Status info: Since 17.Q4. Has no functional behavior. Planned to be removed..";
      reference "Takes effect: New connection.";
    }
    leaf timeToTriggerB2 {
      type int32 {
        range "0 | 40 | 64 | 80 | 100 | 128 | 160 | 256 | 320 | 480 | 512 | 640 | 1024 | 1280 | 2560 | 5120";
      }
      status deprecated;
      default "640";
      units "ms";
      description "Default value: 640; Takes effect: New connection; Status info: Since 17.Q4. Has no functional behavior. Planned to be removed..";
      reference "Takes effect: New connection.";
    }
  }
  grouping ReportConfigB2CdmaUlTrig-attributes {
    leaf reportConfigB2CdmaUlTrigId {
      type ietfinet:port-number;
      mandatory true;
      status deprecated;
      description "MOM flags: restricted, noNotification; Status info: Since 17.Q4. Has no functional behavior. Planned to be removed..";
    }
    leaf b2Threshold2Cdma2000 {
      type eytypes:int32_range_-315-0;
      status deprecated;
      default "-75";
      units "dB";
      description "range -315..0; Default value: -75; Takes effect: New connection; Status info: Since 17.Q4. Has no functional behavior. Planned to be removed..";
      reference "Takes effect: New connection.";
    }
    leaf hysteresisB2 {
      type eytypes:int32_range_0-150;
      status deprecated;
      default "10";
      units "dB";
      description "range 0..150; Default value: 10; Takes effect: New connection; Status info: Since 17.Q4. Has no functional behavior. Planned to be removed..";
      reference "Takes effect: New connection.";
    }
    leaf reportIntervalB2 {
      type ietfinet:port-number;
      status deprecated;
      description "Default value: MS_2048; Takes effect: New connection; Status info: Since 17.Q4. Has no functional behavior. Planned to be removed..";
      reference "Takes effect: New connection.";
    }
    leaf timeToTriggerB2 {
      type int32 {
        range "0 | 40 | 64 | 80 | 100 | 128 | 160 | 256 | 320 | 480 | 512 | 640 | 1024 | 1280 | 2560 | 5120";
      }
      status deprecated;
      default "640";
      units "ms";
      description "Default value: 640; Takes effect: New connection; Status info: Since 17.Q4. Has no functional behavior. Planned to be removed..";
      reference "Takes effect: New connection.";
    }
  }
  grouping ReportConfigB2Geran-attributes {
    leaf reportConfigB2GeranId {
      type ietfinet:port-number;
      mandatory true;
    }
    leaf b2Threshold1Rsrp {
      type eytypes:int32_range_-140--44;
      default "-140";
      units "dBm";
      description "range -140..-44; Default value: -140.";
    }
    leaf b2Threshold1Rsrq {
      type eytypes:int32_range_-195--30;
      default "-195";
      units "dB";
      description "range -195..-30; Default value: -195.";
    }
    leaf b2Threshold2Geran {
      type eytypes:int32_range_-110--47;
      default "-110";
      units "dBm";
      description "range -110..-47; Default value: -110.";
    }
    leaf hysteresisB2 {
      type eytypes:int32_range_0-150;
      default "10";
      units "dB";
      description "range 0..150; Default value: 10.";
    }
    leaf timeToTriggerB2 {
      type int32 {
        range "0 | 40 | 64 | 80 | 100 | 128 | 160 | 256 | 320 | 480 | 512 | 640 | 1024 | 1280 | 2560 | 5120";
      }
      default "640";
      units "ms";
      description "Default value: 640.";
    }
    leaf triggerQuantityB2 {
      type enumeration {
        enum RSRP;
        enum RSRQ;
      }
    }
    leaf timeToTriggerB2Rsrq {
      type int32 {
        range "-1..0 | 40 | 64 | 80 | 100 | 128 | 160 | 256 | 320 | 480 | 512 | 640 | 1024 | 1280 | 2560 | 5120";
      }
      default "-1";
      units "ms";
      description "Default value: -1.";
    }
    leaf hysteresisB2RsrqOffset {
      type eytypes:int32_range_-150-150;
      default "0";
      units "dB";
      description "range -150..150; Default value: 0.";
    }
  }
  grouping ReportConfigB2GeranUlTrig-attributes {
    leaf reportConfigB2GeranUlTrigId {
      type ietfinet:port-number;
      mandatory true;
    }
    leaf b2Threshold2Geran {
      type eytypes:int32_range_-110--47;
      default "-110";
      units "dBm";
      description "range -110..-47; Default value: -110.";
    }
    leaf hysteresisB2 {
      type eytypes:int32_range_0-150;
      default "10";
      units "dB";
      description "range 0..150; Default value: 10.";
    }
    leaf reportIntervalB2 {
      type ietfinet:port-number;
    }
    leaf timeToTriggerB2 {
      type int32 {
        range "0 | 40 | 64 | 80 | 100 | 128 | 160 | 256 | 320 | 480 | 512 | 640 | 1024 | 1280 | 2560 | 5120";
      }
      default "640";
      units "ms";
      description "Default value: 640.";
    }
  }
  grouping ReportConfigB2NR-attributes {
    leaf b2Threshold1Rsrp {
      type eytypes:int32_range_-140--44;
      default "-120";
      units "dBm";
      description "range -140..-44; Default value: -120.";
    }
    leaf b2Threshold1Rsrq {
      type eytypes:int32_range_-195--30;
      default "-170";
      units "dB";
      description "range -195..-30; Default value: -170.";
    }
    leaf b2Threshold2Rsrp {
      type eytypes:int32_range_-156--29;
      default "-110";
      units "dBm";
      description "range -156..-29; Default value: -110.";
    }
    leaf b2Threshold2Rsrq {
      type eytypes:int32_range_-435-200;
      default "-300";
      units "dB";
      description "range -435..200; Default value: -300.";
    }
    leaf hysteresisB2 {
      type eytypes:int32_range_0-30;
      default "2";
      units "dB";
      description "range 0..30; Default value: 2.";
    }
    leaf hysteresisB2RsrqOffset {
      type eytypes:int32_range_-30-30;
      default "0";
      units "dB";
      description "range -30..30; Default value: 0.";
    }
    leaf reportConfigB2NRId {
      type ietfinet:port-number;
      mandatory true;
    }
    leaf timeToTriggerB2 {
      type int32 {
        range "0 | 40 | 64 | 80 | 100 | 128 | 160 | 256 | 320 | 480 | 512 | 640 | 1024 | 1280 | 2560 | 5120";
      }
      default "640";
      units "ms";
      description "Default value: 640.";
    }
    leaf timeToTriggerB2Rsrq {
      type int32 {
        range "-1..0 | 40 | 64 | 80 | 100 | 128 | 160 | 256 | 320 | 480 | 512 | 640 | 1024 | 1280 | 2560 | 5120";
      }
      default "-1";
      units "ms";
      description "Default value: -1.";
    }
    leaf triggerQuantityB2NR {
      type enumeration {
        enum SS_RSRP;
        enum SS_RSRQ;
      }
    }
    leaf triggerQuantityB2 {
      type enumeration {
        enum RSRP;
        enum RSRQ;
      }
    }
    leaf mbmsB2ThresholdRsrpOffset {
      type int32 {
        range "-100..0";
      }
      default "-5";
      units "dBm";
      description "range -100..0; Default value: -5.";
    }
    leaf mbmsB2ThresholdRsrqOffset {
      type eytypes:int32_range_-100-0;
      default "-10";
      units "dB";
      description "range -100..0; Default value: -10.";
    }
  }
  grouping ReportConfigB2Utra-attributes {
    leaf reportConfigB2UtraId {
      type ietfinet:port-number;
      mandatory true;
    }
    leaf b2Threshold1Rsrp {
      type eytypes:int32_range_-140--44;
      default "-140";
      units "dBm";
      description "range -140..-44; Default value: -140.";
    }
    leaf b2Threshold1Rsrq {
      type eytypes:int32_range_-195--30;
      default "-195";
      units "dB";
      description "range -195..-30; Default value: -195.";
    }
    leaf b2Threshold2RscpUtra {
      type eytypes:int32_range_-120--24;
      default "-115";
      units "dBm";
      description "range -120..-24; Default value: -115.";
    }
    leaf b2Threshold2EcNoUtra {
      type eytypes:int32_range_-245-0;
      default "-240";
      units "dB";
      description "range -245..0; Default value: -240.";
    }
    leaf hysteresisB2 {
      type eytypes:int32_range_0-150;
      default "10";
      units "dB";
      description "range 0..150; Default value: 10.";
    }
    leaf timeToTriggerB2 {
      type int32 {
        range "0 | 40 | 64 | 80 | 100 | 128 | 160 | 256 | 320 | 480 | 512 | 640 | 1024 | 1280 | 2560 | 5120";
      }
      default "640";
      units "ms";
      description "Default value: 640.";
    }
    leaf triggerQuantityB2 {
      type enumeration {
        enum RSRP;
        enum RSRQ;
      }
    }
    leaf timeToTriggerB2Rsrq {
      type int32 {
        range "-1..0 | 40 | 64 | 80 | 100 | 128 | 160 | 256 | 320 | 480 | 512 | 640 | 1024 | 1280 | 2560 | 5120";
      }
      default "-1";
      units "ms";
      description "Default value: -1.";
    }
    leaf hysteresisB2RsrqOffset {
      type eytypes:int32_range_-150-150;
      default "0";
      units "dB";
      description "range -150..150; Default value: 0.";
    }
  }
  grouping ReportConfigB2UtraUlTrig-attributes {
    leaf reportConfigB2UtraUlTrigId {
      type ietfinet:port-number;
      mandatory true;
    }
    leaf b2Threshold2EcNoUtra {
      type eytypes:int32_range_-240-0;
      default "-240";
      units "dB";
      description "range -240..0; Default value: -240.";
    }
    leaf b2Threshold2RscpUtra {
      type eytypes:int32_range_-120--24;
      default "-115";
      units "dBm";
      description "range -120..-24; Default value: -115.";
    }
    leaf hysteresisB2 {
      type eytypes:int32_range_0-150;
      default "10";
      units "dB";
      description "range 0..150; Default value: 10.";
    }
    leaf reportIntervalB2 {
      type ietfinet:port-number;
    }
    leaf timeToTriggerB2 {
      type int32 {
        range "0 | 40 | 64 | 80 | 100 | 128 | 160 | 256 | 320 | 480 | 512 | 640 | 1024 | 1280 | 2560 | 5120";
      }
      default "640";
      units "ms";
      description "Default value: 640.";
    }
  }
  grouping ReportConfigCsfbCdma2000-attributes {
    leaf thresholdCdma20001xRtt {
      type eytypes:int32_range_-315-0;
      default "-75";
      units "dB";
      description "range -315..0; Default value: -75.";
    }
    leaf hysteresis {
      type eytypes:int32_range_0-150;
      default "10";
      units "dB";
      description "range 0..150; Default value: 10.";
    }
    leaf reportConfigCsfbCdma2000Id {
      type ietfinet:port-number;
      mandatory true;
    }
    leaf timeToTrigger {
      type int32 {
        range "0 | 40 | 64 | 80 | 100 | 128 | 160 | 256 | 320 | 480 | 640 | 1024 | 1280 | 2560 | 5120";
      }
      default "40";
      units "ms";
      description "Default value: 40.";
    }
  }
  grouping ReportConfigCsfbGeran-attributes {
    leaf reportConfigCsfbGeranId {
      type ietfinet:port-number;
      mandatory true;
    }
    leaf thresholdGeran {
      type eytypes:int32_range_-110--47;
      default "-110";
      units "dBm";
      description "range -110..-47; Default value: -110.";
    }
    leaf hysteresis {
      type eytypes:int32_range_0-150;
      default "10";
      units "dB";
      description "range 0..150; Default value: 10.";
    }
    leaf timeToTrigger {
      type int32 {
        range "0 | 40 | 64 | 80 | 100 | 128 | 160 | 256 | 320 | 480 | 512 | 640 | 1024 | 1280 | 2560 | 5120";
      }
      default "40";
      units "ms";
      description "Default value: 40.";
    }
  }
  grouping ReportConfigCsfbUtra-attributes {
    leaf reportConfigCsfbUtraId {
      type ietfinet:port-number;
      mandatory true;
    }
    leaf thresholdEcNo {
      type eytypes:int32_range_-245-0;
      default "-240";
      units "dB";
      description "range -245..0; Default value: -240.";
    }
    leaf thresholdRscp {
      type eytypes:int32_range_-120--24;
      default "-115";
      units "dBm";
      description "range -120..-24; Default value: -115.";
    }
    leaf hysteresis {
      type eytypes:int32_range_0-150;
      default "10";
      units "dB";
      description "range 0..150; Default value: 10.";
    }
    leaf timeToTrigger {
      type int32 {
        range "0 | 40 | 64 | 80 | 100 | 128 | 160 | 256 | 320 | 480 | 512 | 640 | 1024 | 1280 | 2560 | 5120";
      }
      default "40";
      units "ms";
      description "Default value: 40.";
    }
  }
  grouping ReportConfigCsg-attributes {
    leaf reportConfigCsgId {
      type ietfinet:port-number;
      mandatory true;
    }
    leaf a5Thr1RsrpAltCsgOffset {
      type eytypes:int32_range_-100-100;
      default "0";
      units "dB";
      description "range -100..100; Default value: 0.";
    }
    leaf a5Thr2RsrpAltCsgOffset {
      type eytypes:int32_range_-100-100;
      default "0";
      units "dB";
      description "range -100..100; Default value: 0.";
    }
    leaf hysteresisA5AltCsg {
      type eytypes:int32_range_0-150;
      default "10";
      units "dB";
      description "range 0..150; Default value: 10.";
    }
    leaf timeToTriggerA5AltCsg {
      type int32 {
        range "0 | 40 | 64 | 80 | 100 | 128 | 160 | 256 | 320 | 480 | 512 | 640 | 1024 | 1280 | 2560 | 5120";
      }
      default "0";
      units "ms";
      description "Default value: 0.";
    }
  }
  grouping ReportConfigElcA1A2-attributes {
    leaf reportConfigElcA1A2Id {
      type ietfinet:port-number;
      mandatory true;
    }
    leaf a1a2ThresholdRsrp {
      type eytypes:int32_range_-140--44;
      default "-134";
      units "dBm";
      description "range -140..-44; Default value: -134.";
    }
    leaf hysteresisA1A2Rsrp {
      type eytypes:int32_range_0-150;
      default "10";
      units "dB";
      description "range 0..150; Default value: 10.";
    }
    leaf timeToTriggerA1 {
      type int32 {
        range "0 | 40 | 64 | 80 | 100 | 128 | 160 | 256 | 320 | 480 | 512 | 640 | 1024 | 1280 | 2560 | 5120";
      }
      default "40";
      units "ms";
      description "Default value: 40.";
    }
    leaf timeToTriggerA2 {
      type int32 {
        range "0 | 40 | 64 | 80 | 100 | 128 | 160 | 256 | 320 | 480 | 512 | 640 | 1024 | 1280 | 2560 | 5120";
      }
      default "40";
      units "ms";
      description "Default value: 40.";
    }
  }
  grouping ReportConfigErabSetup-attributes {
    leaf filterCoeffUlSinrMax {
      type int32 {
        range "0..9 | 11 | 13 | 15 | 17 | 19";
      }
      default "8";
      description "Default value: 8.";
    }
    leaf a1a2UlSinrThr {
      type int32 {
        range "0..250";
      }
      default "100";
      units "dB";
      description "range 0..250; Default value: 100.";
    }
    leaf hysteresisA1A2UlSinr {
      type eytypes:int32_range_0-150;
      default "20";
      units "dB";
      description "range 0..150; Default value: 20.";
    }
    leaf timeToTriggerA1A2UlSinr {
      type int32 {
        range "0 | 40 | 64 | 80 | 100 | 128 | 160 | 256 | 320 | 480 | 512 | 640 | 1024 | 1280 | 2560 | 5120";
      }
      default "40";
      units "ms";
      description "Default value: 40.";
    }
    leaf a1a2UlPlThr {
      type int32 {
        range "70..140";
      }
      default "130";
      units "dB";
      description "range 70..140; Default value: 130.";
    }
    leaf hysteresisA1A2UlPl {
      type eytypes:int32_range_0-150;
      default "20";
      units "dB";
      description "range 0..150; Default value: 20.";
    }
    leaf timeToTriggerA1A2UlPl {
      type int32 {
        range "0 | 40 | 64 | 80 | 100 | 128 | 160 | 256 | 320 | 480 | 512 | 640 | 1024 | 1280 | 2560 | 5120";
      }
      default "40";
      units "ms";
      description "Default value: 40.";
    }
    leaf reportConfigErabSetupId {
      type ietfinet:port-number;
      mandatory true;
    }
  }
  grouping ReportConfigEUtraBadCovPrim-attributes {
    leaf a2ThresholdRsrpPrim {
      type eytypes:int32_range_-140--44;
      default "-140";
      units "dBm";
      description "range -140..-44; Default value: -140.";
    }
    leaf a2ThresholdRsrqPrim {
      type eytypes:int32_range_-195--30;
      default "-195";
      units "dB";
      description "range -195..-30; Default value: -195.";
    }
    leaf hysteresisA2Prim {
      type eytypes:int32_range_0-150;
      default "10";
      units "dB";
      description "range 0..150; Default value: 10.";
    }
    leaf timeToTriggerA2Prim {
      type int32 {
        range "0 | 40 | 64 | 80 | 100 | 128 | 160 | 256 | 320 | 480 | 512 | 640 | 1024 | 1280 | 2560 | 5120";
      }
      default "640";
      units "ms";
      description "Default value: 640.";
    }
    leaf triggerQuantityA2Prim {
      type enumeration {
        enum RSRP;
        enum RSRQ;
      }
    }
    leaf reportConfigEUtraBadCovPrimId {
      type ietfinet:port-number;
      mandatory true;
    }
    leaf a2ThrRsrpPrimOffsetCeABr {
      type eytypes:int32_range_-100-100;
      default "0";
      units "dB";
      description "range -100..100; Default value: 0.";
    }
  }
  grouping ReportConfigEUtraBadCovSec-attributes {
    leaf a2ThresholdRsrpSec {
      type eytypes:int32_range_-140--44;
      default "-140";
      units "dBm";
      description "range -140..-44; Default value: -140.";
    }
    leaf a2ThresholdRsrqSec {
      type eytypes:int32_range_-195--30;
      default "-195";
      units "dB";
      description "range -195..-30; Default value: -195.";
    }
    leaf hysteresisA2Sec {
      type eytypes:int32_range_0-150;
      default "10";
      units "dB";
      description "range 0..150; Default value: 10.";
    }
    leaf timeToTriggerA2Sec {
      type int32 {
        range "0 | 40 | 64 | 80 | 100 | 128 | 160 | 256 | 320 | 480 | 512 | 640 | 1024 | 1280 | 2560 | 5120";
      }
      default "640";
      units "ms";
      description "Default value: 640.";
    }
    leaf triggerQuantityA2Sec {
      type enumeration {
        enum RSRP;
        enum RSRQ;
      }
    }
    leaf reportConfigEUtraBadCovSecId {
      type ietfinet:port-number;
      mandatory true;
    }
    leaf a2ThrRsrpSecOffsetCeABr {
      type eytypes:int32_range_-100-100;
      default "0";
      units "dB";
      description "range -100..100; Default value: 0.";
    }
  }
  grouping ReportConfigEUtraBestCell-attributes {
    leaf a3offset {
      type eytypes:int32_range_-150-150;
      default "30";
      units "dB";
      description "range -150..150; Default value: 30.";
    }
    leaf hysteresisA3 {
      type eytypes:int32_range_0-150;
      default "10";
      units "dB";
      description "range 0..150; Default value: 10.";
    }
    leaf maxReportCellsA3 {
      type ietfinet:port-number;
      default "4";
      description "range 1..8; Default value: 4.";
    }
    leaf timeToTriggerA3 {
      type int32 {
        range "0 | 40 | 64 | 80 | 100 | 128 | 160 | 256 | 320 | 480 | 512 | 640 | 1024 | 1280 | 2560 | 5120";
      }
      default "40";
      units "ms";
      description "Default value: 40.";
    }
    leaf triggerQuantityA3 {
      type enumeration {
        enum RSRP;
        enum RSRQ;
      }
    }
    leaf reportConfigEUtraBestCellId {
      type ietfinet:port-number;
      mandatory true;
    }
  }
  grouping ReportConfigEUtraBestCellAnr-attributes {
    leaf a3offsetAnrDelta {
      type eytypes:int32_range_-10-10;
      default "3";
      units "dB";
      description "range -10..10; Default value: 3.";
    }
    leaf hysteresisA3 {
      type eytypes:int32_range_0-150;
      default "10";
      units "dB";
      description "range 0..150; Default value: 10.";
    }
    leaf reportConfigEUtraBestCellAnrId {
      type ietfinet:port-number;
      mandatory true;
    }
    leaf timeToTriggerA3 {
      type int32 {
        range "0 | 40 | 64 | 80 | 100 | 128 | 160 | 256 | 320 | 480 | 512 | 640 | 1024 | 1280 | 2560 | 5120";
      }
      default "640";
      units "ms";
      description "Default value: 640.";
    }
  }
  grouping ReportConfigEUtraIFA3UlTrig-attributes {
    leaf reportConfigEUtraIFA3UlTrigId {
      type ietfinet:port-number;
      mandatory true;
    }
    leaf a3Offset {
      type eytypes:int32_range_-150-150;
      default "0";
      units "dB";
      description "range -150..150; Default value: 0.";
    }
    leaf hysteresisA3 {
      type eytypes:int32_range_0-150;
      default "10";
      units "dB";
      description "range 0..150; Default value: 10.";
    }
    leaf timeToTriggerA3 {
      type int32 {
        range "0 | 40 | 64 | 80 | 100 | 128 | 160 | 256 | 320 | 480 | 512 | 640 | 1024 | 1280 | 2560 | 5120";
      }
      default "40";
      units "ms";
      description "Default value: 40.";
    }
    leaf reportIntervalA3 {
      type ietfinet:port-number;
    }
  }
  grouping ReportConfigEUtraIFBestCell-attributes {
    leaf reportConfigEUtraIFBestCellId {
      type ietfinet:port-number;
      mandatory true;
    }
    leaf a3offset {
      type eytypes:int32_range_-150-150;
      default "30";
      units "dB";
      description "range -150..150; Default value: 30.";
    }
    leaf hysteresisA3 {
      type eytypes:int32_range_0-150;
      default "10";
      units "dB";
      description "range 0..150; Default value: 10.";
    }
    leaf triggerQuantityA3 {
      type enumeration {
        enum RSRP;
        enum RSRQ;
      }
    }
    leaf timeToTriggerA3 {
      type int32 {
        range "0 | 40 | 64 | 80 | 100 | 128 | 160 | 256 | 320 | 480 | 512 | 640 | 1024 | 1280 | 2560 | 5120";
      }
      default "40";
      units "ms";
      description "Default value: 40.";
    }
    leaf timeToTriggerA3Rsrq {
      type int32 {
        range "-1..0 | 40 | 64 | 80 | 100 | 128 | 160 | 256 | 320 | 480 | 512 | 640 | 1024 | 1280 | 2560 | 5120";
      }
      default "-1";
      units "ms";
      description "Default value: -1.";
    }
    leaf a3RsrqOffset {
      type eytypes:int32_range_-150-150;
      default "0";
      units "dB";
      description "range -150..150; Default value: 0.";
    }
    leaf hysteresisA3RsrqOffset {
      type eytypes:int32_range_-150-150;
      default "0";
      units "dB";
      description "range -150..150; Default value: 0.";
    }
  }
  grouping ReportConfigEUtraInterFreqLb-attributes {
    leaf reportConfigEUtraInterFreqLbId {
      type ietfinet:port-number;
      mandatory true;
    }
    leaf a5Threshold2Rsrp {
      type int32 {
        range "-140..44";
      }
      default "-44";
      units "dBm";
      description "range -140..44; Default value: -44.";
    }
    leaf hysteresisA5 {
      type eytypes:int32_range_0-150;
      default "10";
      units "dB";
      description "range 0..150; Default value: 10.";
    }
    leaf a5Threshold1Rsrp {
      type eytypes:int32_range_-140--44;
      default "-44";
      units "dBm";
      description "range -140..-44; Default value: -44.";
    }
    leaf a5Threshold2Rsrq {
      type eytypes:int32_range_-195--30;
      default "-195";
      units "dB";
      description "range -195..-30; Default value: -195.";
    }
  }
  grouping ReportConfigEUtraInterFreqMbms-attributes {
    leaf reportConfigEUtraInterFreqMbmsId {
      type ietfinet:port-number;
      mandatory true;
    }
    leaf a5ThresholdRsrp {
      type int32 {
        range "-140..-44";
      }
      default "-44";
      units "dB";
      description "range -140..-44; Default value: -44.";
    }
    leaf hysteresisA5 {
      type eytypes:int32_range_0-150;
      default "10";
      units "dB";
      description "range 0..150; Default value: 10.";
    }
  }
  grouping ReportConfigEUtraInterFreqPm-attributes {
    leaf reportConfigEUtraInterFreqPmId {
      type ietfinet:port-number;
      mandatory true;
    }
    leaf a1ThresholdRsrpPm {
      type eytypes:int32_range_-140--44;
      default "-140";
      units "dBm";
      description "range -140..-44; Default value: -140.";
    }
    leaf a1ThresholdRsrqPm {
      type eytypes:int32_range_-195--30;
      default "-195";
      units "dB";
      description "range -195..-30; Default value: -195.";
    }
    leaf a2ThresholdRsrpPm {
      type eytypes:int32_range_-140--44;
      default "-140";
      units "dBm";
      description "range -140..-44; Default value: -140.";
    }
    leaf a2ThresholdRsrqPm {
      type eytypes:int32_range_-195--30;
      default "-195";
      units "dB";
      description "range -195..-30; Default value: -195.";
    }
    leaf a3OffsetPm {
      type eytypes:int32_range_-150-150;
      default "5";
      units "dB";
      description "range -150..150; Default value: 5.";
    }
    leaf a3ReportOnLeavePm {
      type ietfinet:port-number;
      description "Default value: false.";
    }
    leaf a4ThresholdRsrpPm {
      type eytypes:int32_range_-140--44;
      default "-140";
      units "dBm";
      description "range -140..-44; Default value: -140.";
    }
    leaf a4ThresholdRsrqPm {
      type eytypes:int32_range_-195--30;
      default "-195";
      units "dB";
      description "range -195..-30; Default value: -195.";
    }
    leaf a5Threshold1RsrpPm {
      type eytypes:int32_range_-140--44;
      default "-140";
      units "dBm";
      description "range -140..-44; Default value: -140.";
    }
    leaf a5Threshold2RsrpPm {
      type eytypes:int32_range_-140--44;
      default "-140";
      units "dBm";
      description "range -140..-44; Default value: -140.";
    }
    leaf a5Threshold1RsrqPm {
      type eytypes:int32_range_-195--30;
      default "-195";
      units "dB";
      description "range -195..-30; Default value: -195.";
    }
    leaf a5Threshold2RsrqPm {
      type eytypes:int32_range_-195--30;
      default "-195";
      units "dB";
      description "range -195..-30; Default value: -195.";
    }
    leaf a6OffsetPm {
      type eytypes:int32_range_-150-150;
      default "30";
      units "dB";
      description "range -150..150; Default value: 30.";
    }
    leaf hysteresisPm {
      type eytypes:int32_range_0-150;
      default "10";
      units "dB";
      description "range 0..150; Default value: 10.";
    }
    leaf maxReportCellsPm {
      type ietfinet:port-number;
      default "4";
      description "range 1..8; Default value: 4.";
    }
    leaf measSelectionEUtraPm {
      type enumeration {
        enum PERIODICAL;
        enum EVENT_A1;
        enum EVENT_A2;
        enum EVENT_A3;
        enum EVENT_A4;
        enum EVENT_A5;
        enum EVENT_A6;
      }
    }
    leaf reportAmountPm {
      type ietfinet:port-number;
      default "0";
      description "Default value: 0.";
    }
    leaf reportIntervalPm {
      type ietfinet:port-number;
    }
    leaf reportQuantityPm {
      type ietfinet:port-number;
    }
    leaf-list reservedBy {
      type string;
    }
    leaf timeToTriggerPm {
      type int32 {
        range "0 | 40 | 64 | 80 | 100 | 128 | 160 | 256 | 320 | 480 | 512 | 640 | 1024 | 1280 | 2560 | 5120";
      }
      default "640";
      units "ms";
      description "Default value: 640.";
    }
    leaf triggerQuantityPm {
      type enumeration {
        enum RSRP;
        enum RSRQ;
      }
    }
  }
  grouping ReportConfigEUtraInterFreqSec-attributes {
    leaf reportConfigEUtraInterFreqSecId {
      type ietfinet:port-number;
      mandatory true;
    }
    leaf a1ThresholdRsrpSec {
      type eytypes:int32_range_-140--44;
      default "-140";
      units "dBm";
      description "range -140..-44; Default value: -140.";
    }
    leaf a2ThresholdRsrpSec {
      type eytypes:int32_range_-140--44;
      default "-140";
      units "dBm";
      description "range -140..-44; Default value: -140.";
    }
    leaf a3OffsetSec {
      type eytypes:int32_range_-150-150;
      default "5";
      units "dB";
      description "range -150..150; Default value: 5.";
    }
    leaf a3ReportOnLeaveSec {
      type ietfinet:port-number;
      description "Default value: false.";
    }
    leaf a4ThresholdRsrpSec {
      type eytypes:int32_range_-140--44;
      default "-140";
      units "dBm";
      description "range -140..-44; Default value: -140.";
    }
    leaf a5Threshold1RsrpSec {
      type eytypes:int32_range_-140--44;
      default "-140";
      units "dBm";
      description "range -140..-44; Default value: -140.";
    }
    leaf a5Threshold2RsrpSec {
      type eytypes:int32_range_-140--44;
      default "-140";
      units "dBm";
      description "range -140..-44; Default value: -140.";
    }
    leaf a6OffsetSec {
      type eytypes:int32_range_-150-150;
      default "30";
      units "dB";
      description "range -150..150; Default value: 30.";
    }
    leaf hysteresisSec {
      type eytypes:int32_range_0-150;
      default "10";
      units "dB";
      description "range 0..150; Default value: 10.";
    }
    leaf maxReportCellsSec {
      type ietfinet:port-number;
      default "4";
      description "range 1..8; Default value: 4.";
    }
    leaf measSelectionEUtraSec {
      type enumeration {
        enum PERIODICAL;
        enum EVENT_A1;
        enum EVENT_A2;
        enum EVENT_A3;
        enum EVENT_A4;
        enum EVENT_A5;
        enum EVENT_A6;
      }
    }
    leaf reportAmountSec {
      type ietfinet:port-number;
    }
    leaf reportIntervalSec {
      type ietfinet:port-number;
    }
    leaf-list reservedBy {
      type string;
    }
    leaf timeToTriggerSec {
      type int32 {
        range "0 | 40 | 64 | 80 | 100 | 128 | 160 | 256 | 320 | 480 | 512 | 640 | 1024 | 1280 | 2560 | 5120";
      }
      default "640";
      units "ms";
      description "Default value: 640.";
    }
  }
  grouping ReportConfigEUtraIntraFreqPm-attributes {
    leaf measSelectionEUtraPm {
      type enumeration {
        enum PERIODICAL;
        enum EVENT_A1;
        enum EVENT_A2;
        enum EVENT_A3;
        enum EVENT_A4;
        enum EVENT_A5;
        enum EVENT_A6;
      }
    }
    leaf a1ThresholdRsrpPm {
      type eytypes:int32_range_-140--44;
      default "-140";
      units "dBm";
      description "range -140..-44; Default value: -140.";
    }
    leaf a1ThresholdRsrqPm {
      type eytypes:int32_range_-195--30;
      default "-195";
      units "dB";
      description "range -195..-30; Default value: -195.";
    }
    leaf a2ThresholdRsrpPm {
      type eytypes:int32_range_-140--44;
      default "-140";
      units "dBm";
      description "range -140..-44; Default value: -140.";
    }
    leaf a2ThresholdRsrqPm {
      type eytypes:int32_range_-195--30;
      default "-195";
      units "dB";
      description "range -195..-30; Default value: -195.";
    }
    leaf a3OffsetPm {
      type eytypes:int32_range_-150-150;
      default "5";
      units "dB";
      description "range -150..150; Default value: 5.";
    }
    leaf a3ReportOnLeavePm {
      type ietfinet:port-number;
      description "Default value: false.";
    }
    leaf a4ThresholdRsrpPm {
      type eytypes:int32_range_-140--44;
      default "-140";
      units "dBm";
      description "range -140..-44; Default value: -140.";
    }
    leaf a4ThresholdRsrqPm {
      type eytypes:int32_range_-195--30;
      default "-195";
      units "dB";
      description "range -195..-30; Default value: -195.";
    }
    leaf a5ThresholdRsrpPm1 {
      type eytypes:int32_range_-140--44;
      default "-140";
      units "dBm";
      description "range -140..-44; Default value: -140.";
    }
    leaf a5ThresholdRsrqPm1 {
      type eytypes:int32_range_-195--30;
      default "-195";
      units "dB";
      description "range -195..-30; Default value: -195.";
    }
    leaf a5ThresholdRsrpPm2 {
      type eytypes:int32_range_-140--44;
      default "-140";
      units "dBm";
      description "range -140..-44; Default value: -140.";
    }
    leaf a5ThresholdRsrqPm2 {
      type eytypes:int32_range_-195--30;
      default "-195";
      units "dB";
      description "range -195..-30; Default value: -195.";
    }
    leaf triggerQuantityPm {
      type enumeration {
        enum RSRP;
        enum RSRQ;
      }
    }
    leaf hysteresisPm {
      type eytypes:int32_range_0-150;
      default "10";
      units "dB";
      description "range 0..150; Default value: 10.";
    }
    leaf timeToTriggerPm {
      type int32 {
        range "0 | 40 | 64 | 80 | 100 | 128 | 160 | 256 | 320 | 480 | 512 | 640 | 1024 | 1280 | 2560 | 5120";
      }
      default "640";
      units "ms";
      description "Default value: 640.";
    }
    leaf reportQuantityPm {
      type ietfinet:port-number;
    }
    leaf maxReportCellsPm {
      type ietfinet:port-number;
      default "4";
      description "range 1..8; Default value: 4.";
    }
    leaf reportIntervalPm {
      type ietfinet:port-number;
    }
    leaf reportAmountPm {
      type ietfinet:port-number;
      default "0";
      description "Default value: 0.";
    }
    leaf-list reservedBy {
      type string;
    }
    leaf reportConfigEUtraIntraFreqPmId {
      type ietfinet:port-number;
      mandatory true;
    }
  }
  grouping ReportConfigEUtraIntraFreqSec-attributes {
    leaf reportConfigEUtraIntraFreqSecId {
      type ietfinet:port-number;
      mandatory true;
    }
    leaf a1ThresholdRsrpSec {
      type eytypes:int32_range_-140--44;
      default "-140";
      units "dBm";
      description "range -140..-44; Default value: -140.";
    }
    leaf a2ThresholdRsrpSec {
      type eytypes:int32_range_-140--44;
      default "-140";
      units "dBm";
      description "range -140..-44; Default value: -140.";
    }
    leaf a3OffsetSec {
      type eytypes:int32_range_-150-150;
      default "5";
      units "dB";
      description "range -150..150; Default value: 5.";
    }
    leaf a3ReportOnLeaveSec {
      type ietfinet:port-number;
      description "Default value: false.";
    }
    leaf a4ThresholdRsrpSec {
      type eytypes:int32_range_-140--44;
      default "-140";
      units "dBm";
      description "range -140..-44; Default value: -140.";
    }
    leaf a5Threshold1RsrpSec {
      type eytypes:int32_range_-140--44;
      default "-140";
      units "dBm";
      description "range -140..-44; Default value: -140.";
    }
    leaf a5Threshold2RsrpSec {
      type eytypes:int32_range_-140--44;
      default "-140";
      units "dBm";
      description "range -140..-44; Default value: -140.";
    }
    leaf hysteresisSec {
      type eytypes:int32_range_0-150;
      default "10";
      units "dB";
      description "range 0..150; Default value: 10.";
    }
    leaf maxReportCellsSec {
      type ietfinet:port-number;
      default "4";
      description "range 1..8; Default value: 4.";
    }
    leaf measSelectionEUtraSec {
      type enumeration {
        enum PERIODICAL;
        enum EVENT_A1;
        enum EVENT_A2;
        enum EVENT_A3;
        enum EVENT_A4;
        enum EVENT_A5;
        enum EVENT_A6;
      }
    }
    leaf reportAmountSec {
      type ietfinet:port-number;
    }
    leaf reportIntervalSec {
      type ietfinet:port-number;
    }
    leaf-list reservedBy {
      type string;
    }
    leaf timeToTriggerSec {
      type int32 {
        range "0 | 40 | 64 | 80 | 100 | 128 | 160 | 256 | 320 | 480 | 512 | 640 | 1024 | 1280 | 2560 | 5120";
      }
      default "640";
      units "ms";
      description "Default value: 640.";
    }
  }
  grouping ReportConfigInterEnbUlComp-attributes {
    leaf reportConfigInterEnbUlCompId {
      type ietfinet:port-number;
      mandatory true;
    }
    leaf a3Offset {
      type eytypes:int32_range_-150-150;
      default "-20";
      units "dB";
      description "range -150..150; Default value: -20.";
    }
    leaf hysteresisA3 {
      type eytypes:int32_range_0-150;
      default "10";
      units "dB";
      description "range 0..150; Default value: 10.";
    }
    leaf reportIntervalA3 {
      type ietfinet:port-number;
    }
    leaf timeToTriggerA3 {
      type int32 {
        range "0 | 40 | 64 | 80 | 100 | 128 | 160 | 256 | 320 | 480 | 512 | 640 | 1024 | 1280 | 2560 | 5120";
      }
      default "40";
      units "ms";
      description "Default value: 40.";
    }
  }
  grouping ReportConfigInterRatLb-attributes {
    leaf reportConfigInterRatLbId {
      type ietfinet:port-number;
      mandatory true;
    }
    leaf utranB1ThresholdRscp {
      type eytypes:int32_range_-120--24;
      default "-24";
      units "dBm";
      description "range -120..-24; Default value: -24.";
    }
    leaf utranHysteresisB1 {
      type eytypes:int32_range_0-150;
      default "10";
      units "dB";
      description "range 0..150; Default value: 10.";
    }
    leaf utranB1ThresholdEcNo {
      type eytypes:int32_range_-245-0;
      default "-240";
      units "dB";
      description "range -245..0; Default value: -240.";
    }
  }
  grouping ReportConfigInterRatPm-attributes {
    leaf reportConfigInterRatPmId {
      type ietfinet:port-number;
      mandatory true;
    }
    leaf b1ThresholdGeranPm {
      type eytypes:int32_range_-110--47;
      default "-110";
      units "dBm";
      description "range -110..-47; Default value: -110.";
    }
    leaf b1ThresholdEcNoUtraPm {
      type eytypes:int32_range_-245-0;
      default "-240";
      units "dB";
      description "range -245..0; Default value: -240.";
    }
    leaf b1ThresholdRscpUtraPm {
      type eytypes:int32_range_-120--24;
      default "-115";
      units "dBm";
      description "range -120..-24; Default value: -115.";
    }
    leaf b2Threshold1RsrpPm {
      type eytypes:int32_range_-140--44;
      default "-140";
      units "dBm";
      description "range -140..-44; Default value: -140.";
    }
    leaf b2Threshold1RsrqPm {
      type eytypes:int32_range_-195--30;
      default "-195";
      units "dB";
      description "range -195..-30; Default value: -195.";
    }
    leaf b2Threshold2GeranPm {
      type eytypes:int32_range_-110--47;
      default "-110";
      units "dBm";
      description "range -110..-47; Default value: -110.";
    }
    leaf b2Threshold2EcNoUtraPm {
      type eytypes:int32_range_-245-0;
      default "-240";
      units "dB";
      description "range -245..0; Default value: -240.";
    }
    leaf b2Threshold2RscpUtraPm {
      type eytypes:int32_range_-120--24;
      default "-115";
      units "dBm";
      description "range -120..-24; Default value: -115.";
    }
    leaf hysteresisPm {
      type eytypes:int32_range_0-150;
      default "10";
      units "dB";
      description "range 0..150; Default value: 10.";
    }
    leaf ratSelectionPm {
      type enumeration {
        enum UTRAN;
        enum GERAN;
      }
    }
    leaf maxReportCellsPm {
      type ietfinet:port-number;
      default "4";
      description "range 1..8; Default value: 4.";
    }
    leaf measSelectionInterRatPm {
      type enumeration {
        enum PERIODICAL;
        enum EVENT_B1;
        enum EVENT_B2;
      }
    }
    leaf reportAmountPm {
      type ietfinet:port-number;
      default "0";
      description "Default value: 0.";
    }
    leaf reportIntervalPm {
      type ietfinet:port-number;
    }
    leaf-list reservedBy {
      type string;
    }
    leaf timeToTriggerPm {
      type int32 {
        range "0 | 40 | 64 | 80 | 100 | 128 | 160 | 256 | 320 | 480 | 512 | 640 | 1024 | 1280 | 2560 | 5120";
      }
      default "640";
      units "ms";
      description "Default value: 640.";
    }
    leaf triggerQuantityPm {
      type enumeration {
        enum RSRP;
        enum RSRQ;
      }
    }
  }
  grouping ReportConfigInterRatSec-attributes {
    leaf reportConfigInterRatSecId {
      type ietfinet:port-number;
      mandatory true;
    }
    leaf b1ThresholdGeranSec {
      type eytypes:int32_range_-110--47;
      default "-110";
      units "dBm";
      description "range -110..-47; Default value: -110.";
    }
    leaf b1ThresholdRscpUtraSec {
      type eytypes:int32_range_-120--24;
      default "-115";
      units "dBm";
      description "range -120..-24; Default value: -115.";
    }
    leaf b2Threshold1RsrpSec {
      type eytypes:int32_range_-140--44;
      default "-140";
      units "dBm";
      description "range -140..-44; Default value: -140.";
    }
    leaf b2Threshold2GeranSec {
      type eytypes:int32_range_-110--47;
      default "-110";
      units "dBm";
      description "range -110..-47; Default value: -110.";
    }
    leaf b2Threshold2RscpUtraSec {
      type eytypes:int32_range_-120--24;
      default "-115";
      units "dBm";
      description "range -120..-24; Default value: -115.";
    }
    leaf hysteresisSec {
      type eytypes:int32_range_0-150;
      default "10";
      units "dB";
      description "range 0..150; Default value: 10.";
    }
    leaf maxReportCellsSec {
      type ietfinet:port-number;
      default "4";
      description "range 1..8; Default value: 4.";
    }
    leaf measSelectionInterRatSec {
      type enumeration {
        enum PERIODICAL;
        enum EVENT_B1;
        enum EVENT_B2;
      }
    }
    leaf ratSelectionSec {
      type enumeration {
        enum UTRAN;
        enum GERAN;
      }
    }
    leaf reportAmountSec {
      type ietfinet:port-number;
    }
    leaf reportIntervalSec {
      type ietfinet:port-number;
    }
    leaf-list reservedBy {
      type string;
    }
    leaf timeToTriggerSec {
      type int32 {
        range "0 | 40 | 64 | 80 | 100 | 128 | 160 | 256 | 320 | 480 | 512 | 640 | 1024 | 1280 | 2560 | 5120";
      }
      default "640";
      units "ms";
      description "Default value: 640.";
    }
  }
  grouping ReportConfigSCellA1A2-attributes {
    leaf a1a2ThresholdRsrp {
      type eytypes:int32_range_-140--44;
      default "-126";
      units "dBm";
      description "range -140..-44; Default value: -126.";
    }
    leaf a1a2ThresholdRsrq {
      type eytypes:int32_range_-195--30;
      default "-165";
      units "dB";
      description "range -195..-30; Default value: -165.";
    }
    leaf hysteresisA1A2Rsrp {
      type eytypes:int32_range_0-150;
      default "10";
      units "dB";
      description "range 0..150; Default value: 10.";
    }
    leaf hysteresisA1A2Rsrq {
      type eytypes:int32_range_0-150;
      default "15";
      units "dB";
      description "range 0..150; Default value: 15.";
    }
    leaf timeToTriggerA1 {
      type int32 {
        range "0 | 40 | 64 | 80 | 100 | 128 | 160 | 256 | 320 | 480 | 512 | 640 | 1024 | 1280 | 2560 | 5120";
      }
      default "40";
      units "ms";
      description "Default value: 40.";
    }
    leaf timeToTriggerA2 {
      type int32 {
        range "0 | 40 | 64 | 80 | 100 | 128 | 160 | 256 | 320 | 480 | 512 | 640 | 1024 | 1280 | 2560 | 5120";
      }
      default "40";
      units "ms";
      description "Default value: 40.";
    }
    leaf reportConfigSCellA1A2Id {
      type ietfinet:port-number;
      mandatory true;
    }
    leaf triggerQuantityA1A2 {
      type enumeration {
        enum RSRP;
        enum RSRQ;
      }
    }
    leaf hysteresisA1A2RsrpBidir {
      type eytypes:int32_range_0-150;
      status deprecated;
      default "20";
      units "dB";
      description "range 0..150; Default value: 20; Takes effect: Changed value may take effect related to the next SCell configuration during the ongoing connection.; Status info: Since 17.Q2. Planned to be removed..";
      reference "Takes effect: Changed value may take effect related to the next SCell configuration during the ongoing connection..";
    }
    leaf a1a2ThresholdRsrpBidir {
      type eytypes:int32_range_-140--44;
      default "-140";
      units "dBm";
      description "range -140..-44; Default value: -140.";
    }
    leaf hysteresisA1A2RsrpBidirectional {
      type eytypes:int32_range_0-150;
      default "20";
      units "dB";
      description "range 0..150; Default value: 20.";
    }
  }
  grouping ReportConfigSCellA4-attributes {
    leaf a4ThresholdRsrp {
      type eytypes:int32_range_-140--44;
      default "-140";
      units "dBm";
      description "range -140..-44; Default value: -140.";
    }
    leaf a4ThresholdRsrq {
      type eytypes:int32_range_-195--30;
      default "-195";
      units "dB";
      description "range -195..-30; Default value: -195.";
    }
    leaf reportConfigSCellA4Id {
      type ietfinet:port-number;
      mandatory true;
    }
    leaf timeToTriggerA4 {
      type int32 {
        range "0 | 40 | 64 | 80 | 100 | 128 | 160 | 256 | 320 | 480 | 512 | 640 | 1024 | 1280 | 2560 | 5120";
      }
      default "640";
      units "ms";
      description "Default value: 640.";
    }
    leaf triggerQuantityA4 {
      type enumeration {
        enum RSRP;
        enum RSRQ;
      }
    }
    leaf hysteresisA4 {
      type eytypes:int32_range_0-150;
      default "10";
      units "dB";
      description "range 0..150; Default value: 10.";
    }
  }
  grouping ReportConfigSCellA6-attributes {
    leaf a6offset {
      type eytypes:int32_range_-150-150;
      default "30";
      units "dB";
      description "range -150..150; Default value: 30.";
    }
    leaf hysteresisA6 {
      type eytypes:int32_range_0-150;
      default "10";
      units "dB";
      description "range 0..150; Default value: 10.";
    }
    leaf reportConfigSCellA6Id {
      type ietfinet:port-number;
      mandatory true;
    }
    leaf timeToTriggerA6 {
      type int32 {
        range "0 | 40 | 64 | 80 | 100 | 128 | 160 | 256 | 320 | 480 | 512 | 640 | 1024 | 1280 | 2560 | 5120";
      }
      default "40";
      units "ms";
      description "Default value: 40.";
    }
    leaf triggerQuantityA6 {
      type enumeration {
        enum RSRP;
        enum RSRQ;
      }
    }
  }
  grouping ReportConfigSearch-attributes {
    leaf reportConfigSearchId {
      type ietfinet:port-number;
      mandatory true;
    }
    leaf a1a2SearchThresholdRsrp {
      type eytypes:int32_range_-140--44;
      default "-134";
      units "dBm";
      description "range -140..-44; Default value: -134.";
    }
    leaf a1a2SearchThresholdRsrq {
      type eytypes:int32_range_-195--30;
      default "-165";
      units "dB";
      description "range -195..-30; Default value: -165.";
    }
    leaf hysteresisA1A2SearchRsrp {
      type eytypes:int32_range_0-150;
      default "20";
      units "dB";
      description "range 0..150; Default value: 20.";
    }
    leaf hysteresisA1A2SearchRsrq {
      type eytypes:int32_range_0-150;
      default "15";
      units "dB";
      description "range 0..150; Default value: 15.";
    }
    leaf timeToTriggerA1Search {
      type int32 {
        range "0 | 40 | 64 | 80 | 100 | 128 | 160 | 256 | 320 | 480 | 512 | 640 | 1024 | 1280 | 2560 | 5120";
      }
      default "640";
      units "ms";
      description "Default value: 640.";
    }
    leaf timeToTriggerA2Search {
      type int32 {
        range "0 | 40 | 64 | 80 | 100 | 128 | 160 | 256 | 320 | 480 | 512 | 640 | 1024 | 1280 | 2560 | 5120";
      }
      default "40";
      units "ms";
      description "Default value: 40.";
    }
    leaf a2CriticalThresholdRsrp {
      type eytypes:int32_range_-140--44;
      default "-140";
      units "dBm";
      description "range -140..-44; Default value: -140.";
    }
    leaf a2CriticalThresholdRsrq {
      type eytypes:int32_range_-195--30;
      default "-195";
      units "dB";
      description "range -195..-30; Default value: -195.";
    }
    leaf hysteresisA2CriticalRsrp {
      type eytypes:int32_range_0-150;
      default "10";
      units "dB";
      description "range 0..150; Default value: 10.";
    }
    leaf hysteresisA2CriticalRsrq {
      type eytypes:int32_range_0-150;
      default "10";
      units "dB";
      description "range 0..150; Default value: 10.";
    }
    leaf timeToTriggerA2Critical {
      type int32 {
        range "0 | 40 | 64 | 80 | 100 | 128 | 160 | 256 | 320 | 480 | 512 | 640 | 1024 | 1280 | 2560 | 5120";
      }
      default "40";
      units "ms";
      description "Default value: 40.";
    }
    list qciA1A2ThrOffsets {
      key "id";
      leaf id {
        type uint32;
        description "Synthetic key for struct sequence entry.";
      }
      container attributes {
      leaf qciProfileRef {
        type ietfinet:ip-address;
      }
      leaf a1a2ThrRsrpQciOffset {
        type eytypes:int32_range_-100-100;
        default "0";
        units "dB";
        description "range -100..100; Default value: 0.";
      }
      leaf a1a2ThrRsrqQciOffset {
        type eytypes:int32_range_-240-240;
        default "0";
        units "dB";
        description "range -240..240; Default value: 0.";
      }
      }
    }
    leaf a2OuterSearchThrRsrpOffset {
      type eytypes:int32_range_-100-0;
      default "0";
      units "dB";
      description "range -100..0; Default value: 0.";
    }
    leaf a2OuterSearchThrRsrqOffset {
      type eytypes:int32_range_-240-0;
      default "0";
      units "dB";
      description "range -240..0; Default value: 0.";
    }
    leaf timeToTriggerA1SearchRsrq {
      type int32 {
        range "-1..0 | 40 | 64 | 80 | 100 | 128 | 160 | 256 | 320 | 480 | 512 | 640 | 1024 | 1280 | 2560 | 5120";
      }
      default "-1";
      units "ms";
      description "Default value: -1.";
    }
    leaf timeToTriggerA2CriticalRsrq {
      type int32 {
        range "-1..0 | 40 | 64 | 80 | 100 | 128 | 160 | 256 | 320 | 480 | 512 | 640 | 1024 | 1280 | 2560 | 5120";
      }
      default "-1";
      units "ms";
      description "Default value: -1.";
    }
    leaf timeToTriggerA2SearchRsrq {
      type int32 {
        range "-1..0 | 40 | 64 | 80 | 100 | 128 | 160 | 256 | 320 | 480 | 512 | 640 | 1024 | 1280 | 2560 | 5120";
      }
      default "-1";
      units "ms";
      description "Default value: -1.";
    }
    leaf timeToTriggerA2OutSearch {
      type int32 {
        range "0 | 40 | 64 | 80 | 100 | 128 | 160 | 256 | 320 | 480 | 512 | 640 | 1024 | 1280 | 2560 | 5120";
      }
      default "40";
      units "ms";
      description "Default value: 40.";
    }
    leaf timeToTriggerA2OutSearchRsrq {
      type int32 {
        range "-1..0 | 40 | 64 | 80 | 100 | 128 | 160 | 256 | 320 | 480 | 512 | 640 | 1024 | 1280 | 2560 | 5120";
      }
      default "-1";
      units "ms";
      description "Default value: -1.";
    }
    leaf hysteresisA2OuterSearchRsrp {
      type eytypes:int32_range_0-150;
      default "20";
      units "dB";
      description "range 0..150; Default value: 20.";
    }
    leaf hysteresisA2OuterSearchRsrq {
      type eytypes:int32_range_0-150;
      default "15";
      units "dB";
      description "range 0..150; Default value: 15.";
    }
    leaf a2CriticalThrQci1RsrpOffset {
      type eytypes:int32_range_-100-100;
      default "0";
      units "dB";
      description "range -100..100; Default value: 0.";
    }
    leaf a2CriticalThrQci1RsrqOffset {
      type eytypes:int32_range_-240-240;
      default "0";
      units "dB";
      description "range -240..240; Default value: 0.";
    }
    leaf inhibitA2SearchConfig {
      type enumeration {
        enum NOT_INHIBIT;
        enum INHIBIT_A2SEARCH_RSRQ;
        enum INHIBIT_A2SEARCH_RSRP;
      }
    }
    leaf a1a2UlSearchThreshold {
      type eytypes:int32_range_-150-450;
      default "-150";
      units "dB";
      description "range -150..450; Default value: -150.";
    }
    leaf hysteresisA1A2UlSearch {
      type eytypes:int32_range_0-150;
      default "20";
      units "dB";
      description "range 0..150; Default value: 20.";
    }
    leaf a2UlCriticalThreshold {
      type eytypes:int32_range_-150-450;
      default "-150";
      units "dB";
      description "range -150..450; Default value: -150.";
    }
    leaf hysteresisA2UlCritical {
      type eytypes:int32_range_0-150;
      default "20";
      units "dB";
      description "range 0..150; Default value: 20.";
    }
    leaf timeToTriggerA1UlSearch {
      type int32 {
        range "0 | 40 | 64 | 80 | 100 | 128 | 160 | 256 | 320 | 480 | 512 | 640 | 1024 | 1280 | 2560 | 5120";
      }
      default "40";
      units "ms";
      description "Default value: 40.";
    }
    leaf timeToTriggerA2UlSearch {
      type int32 {
        range "0 | 40 | 64 | 80 | 100 | 128 | 160 | 256 | 320 | 480 | 512 | 640 | 1024 | 1280 | 2560 | 5120";
      }
      default "40";
      units "ms";
      description "Default value: 40.";
    }
    leaf timeToTriggerA2UlCritical {
      type int32 {
        range "0 | 40 | 64 | 80 | 100 | 128 | 160 | 256 | 320 | 480 | 512 | 640 | 1024 | 1280 | 2560 | 5120";
      }
      default "40";
      units "ms";
      description "Default value: 40.";
    }
    list qciA1A2UlThrOffsets {
      key "id";
      leaf id {
        type uint32;
        description "Synthetic key for struct sequence entry.";
      }
      container attributes {
      leaf a1a2UlThrQciOffset {
        type eytypes:int32_range_-100-100;
        default "0";
        units "dB";
        description "range -100..100; Default value: 0.";
      }
      leaf qciProfileRef {
        type ietfinet:ip-address;
      }
      }
    }
    list a2CriticalOffsetPerPC {
      key "id";
      leaf id {
        type uint32;
        description "Synthetic key for struct sequence entry.";
      }
      container attributes {
      leaf powerClass {
        type enumeration {
          enum PC_1;
          enum PC_2;
        }
      }
      leaf a2CriticalThrRsrpPCOffset {
        type eytypes:int32_range_-100-100;
        default "0";
        units "dB";
        description "range -100..100; Default value: 0.";
      }
      leaf a2CriticalThrRsrqPCOffset {
        type eytypes:int32_range_-240-240;
        default "0";
        units "dB";
        description "range -240..240; Default value: 0.";
      }
      }
    }
    leaf a1a2UlSinrCsfbThr {
      type int32 {
        range "0..250";
      }
      status deprecated;
      default "100";
      units "dB";
      description "range 0..250; Default value: 100; Status info: Since 20.Q1. Has no functional behavior. Planned to be removed..";
    }
    leaf hysteresisA1A2UlSinrCsfb {
      type eytypes:int32_range_0-150;
      status deprecated;
      default "20";
      units "dB";
      description "range 0..150; Default value: 20; Status info: Since 20.Q1. Has no functional behavior. Planned to be removed..";
    }
    leaf timeToTriggerA1A2UlSinrCsfb {
      type int32 {
        range "0 | 40 | 64 | 80 | 100 | 128 | 160 | 256 | 320 | 480 | 512 | 640 | 1024 | 1280 | 2560 | 5120";
      }
      status deprecated;
      default "40";
      units "ms";
      description "Default value: 40; Status info: Since 20.Q1. Has no functional behavior. Planned to be removed..";
    }
    leaf a1a2UlPlCsfbThr {
      type int32 {
        range "70..140";
      }
      status deprecated;
      default "130";
      units "dB";
      description "range 70..140; Default value: 130; Status info: Since 20.Q1. Has no functional behavior. Planned to be removed..";
    }
    leaf hysteresisA1A2UlPlCsfb {
      type eytypes:int32_range_0-150;
      status deprecated;
      default "20";
      units "dB";
      description "range 0..150; Default value: 20; Status info: Since 20.Q1. Has no functional behavior. Planned to be removed..";
    }
    leaf timeToTriggerA1A2UlPlCsfb {
      type int32 {
        range "0 | 40 | 64 | 80 | 100 | 128 | 160 | 256 | 320 | 480 | 512 | 640 | 1024 | 1280 | 2560 | 5120";
      }
      status deprecated;
      default "40";
      units "ms";
      description "Default value: 40; Status info: Since 20.Q1. Has no functional behavior. Planned to be removed..";
    }
  }
  grouping ResourcePartition-attributes {
    leaf resourcePartitionId {
      type string;
      mandatory true;
    }
    list plmnList {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf-list spidList {
      type eytypes:int32_range_0-256;
    }
    leaf-list reservedBy {
      type string;
    }
    leaf partitionId {
      type eytypes:int32_range_0-24;
      default "0";
      description "range 0..24; Default value: 0.";
    }
    leaf zzzTemporary1 {
      type string;
    }
    leaf zzzTemporary2 {
      type int32;
      default "-2000000000";
      description "Default value: -2000000000.";
    }
    leaf zzzTemporary3 {
      type int32;
      default "-2000000000";
      description "Default value: -2000000000.";
    }
    leaf zzzTemporary4 {
      type int32;
      default "-2000000000";
      description "Default value: -2000000000.";
    }
  }
  grouping ResourcePartitionGroup-attributes {
    leaf resourcePartitionGroupId {
      type string;
      mandatory true;
    }
    leaf-list reservedBy {
      type string;
    }
    leaf resourceSharingType {
      type enumeration {
        enum DYNAMIC;
        enum STATIC;
      }
      status deprecated;
      default "DYNAMIC";
      description "Default value: DYNAMIC; Takes effect: Next cell unlock; Status info: Since 20.Q4. Planned to be removed. Since 21.Q1. Has no functional behavior..";
      reference "Takes effect: Next cell unlock.";
    }
    leaf zzzTemporary1 {
      type string;
    }
    leaf zzzTemporary2 {
      type int32;
      default "-2000000000";
      description "Default value: -2000000000.";
    }
    leaf zzzTemporary3 {
      type int32;
      default "-2000000000";
      description "Default value: -2000000000.";
    }
    leaf zzzTemporary4 {
      type int32;
      default "-2000000000";
      description "Default value: -2000000000.";
    }
  }
  grouping ResourcePartitionGroupMember-attributes {
    leaf resourcePartitionGroupMemberId {
      type string;
      mandatory true;
    }
    leaf resourcePartitionRef {
      type string;
      mandatory true;
    }
    leaf resourcePartitionShare {
      type eytypes:int32_range_0-100;
      mandatory true;
      units "percent";
      description "range 0..100.";
    }
    leaf zzzTemporary1 {
      type string;
    }
    leaf zzzTemporary2 {
      type int32;
      default "-2000000000";
      description "Default value: -2000000000.";
    }
    leaf zzzTemporary3 {
      type int32;
      default "-2000000000";
      description "Default value: -2000000000.";
    }
    leaf zzzTemporary4 {
      type int32;
      default "-2000000000";
      description "Default value: -2000000000.";
    }
    leaf resourcePartitionMaxShare {
      type eytypes:int32_range_0-100;
      default "100";
      units "percent";
      description "range 0..100; Default value: 100.";
    }
  }
  grouping ResourcePartitions-attributes {
    leaf resourcePartitionsId {
      type string;
      mandatory true;
    }
    leaf zzzTemporary1 {
      type string;
    }
    leaf zzzTemporary2 {
      type string;
    }
    leaf zzzTemporary3 {
      type int32;
      default "-2000000000";
      description "Default value: -2000000000.";
    }
    leaf zzzTemporary4 {
      type int32;
      default "-2000000000";
      description "Default value: -2000000000.";
    }
    leaf zzzTemporary5 {
      type int32;
      default "-2000000000";
      description "Default value: -2000000000.";
    }
    leaf gbrPartitioning {
      type boolean;
      default "false";
      description "Default value: false.";
    }
    leaf gbrAdmCtrlPerPartition {
      type boolean;
      default "false";
      description "Default value: false.";
    }
    leaf rrpAdmCtrlRejPaReqOvlGbr {
      type boolean;
      default "true";
      description "Default value: true.";
    }
  }
  grouping RlcConfiguration-attributes {
    leaf ulRlcStalledRbqLenThr {
      type int32 {
        range "25..200";
      }
      default "50";
      description "range 25..200; Default value: 50.";
    }
    leaf ulRlcStalledWinAdvTimeThr {
      type int32 {
        range "200..2000";
      }
      default "500";
      units "ms";
      description "range 200..2000; Default value: 500.";
    }
    leaf rlcConfigurationId {
      type string;
      mandatory true;
    }
    leaf ulRlcBufferCellThresUlMaxRetx {
      type eytypes:int32_range_1-100;
      default "25";
      units "percent";
      description "range 1..100; Default value: 25.";
    }
    leaf ulRlcBufferMaxRetxThresHigh {
      type eytypes:int32_range_1-100;
      default "90";
      units "percent";
      description "range 1..100; Default value: 90.";
    }
    leaf ulRlcBufferMaxRetxThresLow {
      type eytypes:int32_range_1-100;
      default "80";
      units "percent";
      description "range 1..100; Default value: 80.";
    }
    leaf-list pmRlcUlMaxRetxThrAdapt {
      type uint32;
    }
  }
  grouping RlfProfile-attributes {
    leaf n310 {
      type int32 {
        range "1..4 | 6 | 8 | 10 | 20";
      }
      default "20";
      description "Default value: 20.";
    }
    leaf n311 {
      type int32 {
        range "1..6 | 8 | 10";
      }
      default "1";
      description "Default value: 1.";
    }
    leaf t301 {
      type int32 {
        range "100 | 200 | 300 | 400 | 600 | 1000 | 1500 | 2000";
      }
      default "400";
      units "ms";
      description "Default value: 400.";
    }
    leaf t310 {
      type int32 {
        range "0 | 50 | 100 | 200 | 500 | 1000 | 2000";
      }
      default "2000";
      units "ms";
      description "Default value: 2000.";
    }
    leaf t311 {
      type int32 {
        range "1000 | 3000 | 5000 | 10000 | 15000 | 20000 | 30000";
      }
      default "3000";
      units "ms";
      description "Default value: 3000.";
    }
    leaf rlfProfileId {
      type string;
      mandatory true;
    }
    leaf-list reservedBy {
      type string;
    }
  }
  grouping RobustCallSetup-attributes {
    leaf imsSignalingDetectionEnabled {
      type boolean;
      default "false";
      description "Default value: false.";
    }
    leaf moVoiceDetectionEnabled {
      type boolean;
      default "false";
      description "Default value: false.";
    }
    leaf poorCoverageEnhEnabled {
      type boolean;
      default "true";
      description "Default value: true.";
    }
    leaf nrMobilityDelayEnabled {
      type boolean;
      default "true";
      description "Default value: true.";
    }
    leaf geranUtranMobilityDelayEnabled {
      type boolean;
      default "true";
      description "Default value: true.";
    }
    leaf intraLteMobilityDelayEnabled {
      type boolean;
      default "true";
      description "Default value: true.";
    }
    leaf guardTimer {
      type int32 {
        range "10..100";
      }
      default "25";
      units "s";
      description "range 10..100; Default value: 25.";
    }
    leaf robustCallSetupId {
      type string;
      mandatory true;
    }
    leaf endcSetupDelayEnabled {
      type boolean;
      default "true";
      description "Default value: true.";
    }
  }
  grouping Rrc-attributes {
    leaf rrcId {
      type string;
      mandatory true;
    }
    leaf t300 {
      type int32 {
        range "100 | 200 | 300 | 400 | 600 | 1000 | 1500 | 2000";
      }
      default "1000";
      units "ms";
      description "Default value: 1000.";
    }
    leaf t301 {
      type int32 {
        range "100 | 200 | 300 | 400 | 600 | 1000 | 1500 | 2000";
      }
      default "400";
      units "ms";
      description "Default value: 400.";
    }
    leaf t302 {
      type int32 {
        range "0..16";
      }
      default "0";
      units "s";
      description "range 0..16; Default value: 0.";
    }
    leaf t304 {
      type int32 {
        range "50 | 100 | 150 | 200 | 500 | 1000 | 2000";
      }
      default "1000";
      units "ms";
      description "Default value: 1000.";
    }
    leaf t311 {
      type int32 {
        range "1000 | 3000 | 5000 | 10000 | 15000 | 20000 | 30000";
      }
      default "3000";
      units "ms";
      description "Default value: 3000.";
    }
    leaf t320 {
      type int32 {
        range "5 | 10 | 20 | 30 | 60 | 120 | 180";
      }
      default "30";
      units "min";
      description "Default value: 30.";
    }
    leaf tRrcConnectionSetup {
      type eytypes:int32_range_1-20;
      default "3";
      units "s";
      description "range 1..20; Default value: 3.";
    }
    leaf tRrcConnectionReconfiguration {
      type eytypes:int32_range_1-20;
      default "6";
      units "s";
      description "range 1..20; Default value: 6.";
    }
    leaf tRrcConnReest {
      type eytypes:int32_range_1-20;
      default "1";
      units "s";
      description "range 1..20; Default value: 1.";
    }
    leaf tWaitForRrcConnReest {
      type eytypes:int32_range_1-20;
      default "6";
      units "s";
      description "range 1..20; Default value: 6.";
    }
    leaf t300Br {
      type int32 {
        range "0 | 2500 | 3000 | 3500 | 4000 | 5000 | 6000 | 8000 | 10000";
      }
      default "0";
      units "ms";
      description "Default value: 0.";
    }
    leaf t301Br {
      type int32 {
        range "0 | 2500 | 3000 | 3500 | 4000 | 5000 | 6000 | 8000 | 10000";
      }
      default "0";
      units "ms";
      description "Default value: 0.";
    }
    leaf t300NbIot {
      type int32 {
        range "2500 | 4000 | 6000 | 10000 | 15000 | 25000 | 40000 | 60000";
      }
      default "40000";
      units "ms";
      description "Default value: 40000.";
    }
    leaf t301NbIot {
      type int32 {
        range "2500 | 4000 | 6000 | 10000 | 15000 | 25000 | 40000 | 60000";
      }
      status deprecated;
      default "10000";
      units "ms";
      description "Default value: 10000; Takes effect: Next cell unlock; Status info: Since 17.Q3. Planned to be removed.; Specification: 3GPP TS 36.331 Rel-13.";
      reference "Takes effect: Next cell unlock.";
    }
    leaf t311NbIot {
      type int32 {
        range "1000 | 3000 | 5000 | 10000 | 15000 | 20000 | 30000";
      }
      status deprecated;
      default "5000";
      units "ms";
      description "Default value: 5000; Takes effect: Next cell unlock; Status info: Since 17.Q3. Planned to be removed.; Specification: 3GPP TS 36.331 Rel-13.";
      reference "Takes effect: Next cell unlock.";
    }
    leaf t304Br {
      type int32 {
        range "50 | 100 | 150 | 200 | 500 | 1000 | 2000 | 10000";
      }
      default "1000";
      units "ms";
      description "Default value: 1000.";
    }
    leaf t301Nb {
      type int32 {
        range "2500 | 4000 | 6000 | 10000 | 15000 | 25000 | 40000 | 60000";
      }
      default "10000";
      units "ms";
      description "Default value: 10000.";
    }
    leaf t311Nb {
      type int32 {
        range "1000 | 3000 | 5000 | 10000 | 15000 | 20000 | 30000";
      }
      default "5000";
      units "ms";
      description "Default value: 5000.";
    }
    leaf tRrcConnectionResume {
      type eytypes:int32_range_1-20;
      default "1";
      units "s";
      description "range 1..20; Default value: 1.";
    }
    leaf tRetrieveUeInformationNb {
      type int32 {
        range "10..1000";
      }
      default "40";
      units "ms";
      description "range 10..1000; Default value: 40.";
    }
    leaf tRrcUeCapabilityInfo {
      type eytypes:int32_range_1-30;
      default "5";
      units "s";
      description "range 1..30; Default value: 5.";
    }
    leaf t300Ce0Br {
      type enumeration {
        enum T300_100MS;
        enum T300_200MS;
        enum T300_300MS;
        enum T300_400MS;
        enum T300_600MS;
        enum T300_1000MS;
        enum T300_1500MS;
        enum T300_2000MS;
      }
    }
    leaf t300Ce1Br {
      type enumeration {
        enum T300_100MS;
        enum T300_200MS;
        enum T300_300MS;
        enum T300_400MS;
        enum T300_600MS;
        enum T300_1000MS;
        enum T300_1500MS;
        enum T300_2000MS;
      }
    }
    leaf tSiChangeNotifyCellSetupInt {
      type int32 {
        range "0..999";
      }
      default "0";
      units "s";
      description "range 0..999; Default value: 0.";
    }
    leaf ulPowerControlCommonV1020Enabled {
      type boolean;
      default "true";
      description "Default value: true.";
    }
  }
  grouping SciProfile-attributes {
    leaf absPrioOverride {
      type enumeration {
        enum NO_OVERRIDE;
        enum HI_PRIO_OVERRIDE;
      }
    }
    leaf dlMaxWaitingTime {
      type eytypes:int32_range_0-500;
      default "0";
      units "ms";
      description "range 0..500; Default value: 0.";
    }
    leaf dlMinBitRate {
      type int32 {
        range "0..15000";
      }
      default "0";
      units "kbps";
      description "range 0..15000; Default value: 0.";
    }
    leaf dlResourceAllocationStrategy {
      type enumeration {
        enum RESOURCE_FAIR;
        enum FREQUENCY_SELECTIVE;
      }
    }
    leaf logicalChannelGroupRef {
      type string;
      mandatory true;
    }
    leaf pdb {
      type eytypes:int32_range_0-500;
      default "0";
      units "ms";
      description "range 0..500; Default value: 0.";
    }
    leaf priority {
      type int32 {
        range "1..14";
      }
      default "9";
      description "range 1..14; Default value: 9.";
    }
    leaf sci {
      type int32 {
        range "0..18";
      }
      mandatory true;
      description "range 0..18.";
    }
    leaf sciProfileId {
      type ietfinet:ip-address;
      mandatory true;
    }
    leaf dlRelativePriority {
      type eytypes:int32_range_1-65535;
      default "1";
      description "range 1..65535; Default value: 1.";
    }
    leaf-list reservedBy {
      type string;
    }
    leaf ulResourceAllocationStrategy {
      type enumeration {
        enum RESOURCE_FAIR;
        enum FREQUENCY_SELECTIVE;
      }
    }
    leaf schedulingAlgorithm {
      type enumeration {
        enum RESOURCE_FAIR;
        enum EQUAL_RATE;
        enum PROPORTIONAL_FAIR_HIGH;
        enum PROPORTIONAL_FAIR_MEDIUM;
        enum PROPORTIONAL_FAIR_LOW;
        enum MAXIMUM_C_OVER_I;
        enum DELAY_BASED;
      }
    }
    leaf srsAllocationStrategy {
      type enumeration {
        enum DEACTIVATED;
        enum ACTIVATED;
      }
    }
    leaf ulMaxWaitingTime {
      type eytypes:int32_range_0-500;
      default "0";
      units "ms";
      description "range 0..500; Default value: 0.";
    }
    leaf ulMinBitRate {
      type eytypes:int32_range_0-75000;
      default "0";
      units "kbps";
      description "range 0..75000; Default value: 0.";
    }
    leaf ulRelativePriority {
      type eytypes:int32_range_1-65535;
      default "1";
      description "range 1..65535; Default value: 1.";
    }
    leaf lessMaxDelayThreshold {
      type eytypes:int32_range_0-20-20;
      default "0";
      units "ms";
      description "range 0..20; Default value: 0.";
    }
    leaf lessMaxDelayThresholdWindow2 {
      type eytypes:int32_range_0-20-20;
      default "0";
      units "ms";
      description "range 0..20; Default value: 0.";
    }
  }
  grouping SecPmUeMeasControl-attributes {
    leaf secPmUeMeasControlId {
      type string;
      mandatory true;
    }
    list ueMeasInterFreq {
      key "id";
      leaf id {
        type uint32;
        description "Synthetic key for struct entry.";
      }
      container attributes {
      leaf eutranFrequencyRef {
        type string;
      }
      leaf reportConfigEUtraInterFreqSecRef {
        type ietfinet:port-number;
      }
      }
    }
    list ueMeasIntraFreq {
      key "id";
      leaf id {
        type uint32;
        description "Synthetic key for struct entry.";
      }
      container attributes {
      leaf eutranFrequencyRef {
        type string;
      }
      leaf reportConfigEUtraIntraFreqSecRef {
        type ietfinet:port-number;
      }
      }
    }
    list ueMeasInterRat {
      key "id";
      leaf id {
        type uint32;
        description "Synthetic key for struct entry.";
      }
      container attributes {
      leaf geranFrequencyRef {
        type string;
      }
      leaf utranFrequencyRef {
        type string;
      }
      leaf reportConfigInterRatSecRef {
        type ietfinet:port-number;
      }
      }
    }
    leaf measGapAllowedPm {
      type boolean;
      default "false";
      description "Default value: false.";
    }
    leaf secUeFraction {
      type eytypes:int32_range_0-100;
      units "percent";
      description "range 0..100.";
    }
    leaf-list pmUeMeasSecRssiGeranDistr {
      type uint32;
      description "MOM flags: noNotification.";
    }
    leaf-list pmUeMeasSecRscpUtranDistr {
      type uint32;
      description "MOM flags: noNotification.";
    }
    leaf-list pmUeMeasSecRsrpServIntraFreqDistr {
      type uint32;
      description "MOM flags: noNotification.";
    }
    leaf-list pmUeMeasSecRsrpInterFreqDistr {
      type uint32;
      description "MOM flags: noNotification.";
    }
    leaf-list pmUeMeasSecRsrpDeltaIntraFreqDistr {
      type uint32;
      description "MOM flags: noNotification.";
    }
    leaf-list pmUeMeasSecRsrpDeltaInterFreqDistr {
      type uint32;
      description "MOM flags: noNotification.";
    }
  }
  grouping SectorCarrier-attributes {
    leaf sectorCarrierId {
      type string;
      mandatory true;
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf operationalState {
      type enumeration {
        enum DISABLED;
        enum ENABLED;
      }
      config false;
    }
    leaf sectorFunctionRef {
      type string;
      mandatory true;
    }
    leaf-list reservedBy {
      type string;
    }
    leaf noOfRxAntennas {
      type int32 {
        range "0..2 | 4 | 8";
      }
      default "0";
      description "Default value: 0.";
    }
    leaf noOfTxAntennas {
      type int32 {
        range "0..2 | 4 | 8 | 16";
      }
      default "0";
      description "Default value: 0.";
    }
    leaf noOfUsedRxAntennas {
      type int32;
      config false;
    }
    leaf noOfUsedTxAntennas {
      type int32;
      config false;
    }
    leaf maximumTransmissionPower {
      type int32 {
        range "-1..1200";
      }
      config false;
      units "dBm";
      description "range -1..1200.";
    }
    leaf prsEnabled {
      type boolean;
      default "true";
      description "Default value: true.";
    }
    leaf-list rfBranchRxRef {
      type string;
    }
    leaf-list rfBranchTxRef {
      type string;
    }
    leaf ulForcedTimingAdvanceCommand {
      type int32 {
        range "0..10";
      }
      default "0";
      units "microsecond";
      description "range 0..10; Default value: 0.";
    }
    leaf noOfMutedTxAntennas {
      type eytypes:int32_range_0-7;
      config false;
      description "range 0..7.";
    }
    leaf radioTransmitPerformanceMode {
      type enumeration {
        enum DEFAULT;
        enum QAM_64_BOOST;
        enum QAM_256_BOOST;
        enum MAX_POWER_CLASS;
      }
      status deprecated;
      default "DEFAULT";
      description "Default value: DEFAULT; Takes effect: Cell lock/unlock; Status info: Since 20.Q1. Replaced by radioTransmitPerfMode. Planned to be removed..";
      reference "Takes effect: Cell lock/unlock.";
    }
    leaf configuredMaxTxPower {
      type eytypes:int32_range_0-10000000;
      default "20000";
      units "mW";
      description "range 0..10000000; Default value: 20000.";
    }
    leaf txPowerPersistentLock {
      type boolean;
      default "false";
      description "Default value: false.";
    }
    list dlCalibrationData {
      config false;
      container attributes {
      leaf dlCalibrationSupportedMethods {
        type ietfinet:port-number;
      }
      leaf dlCalibrationActiveMethod {
        type enumeration {
          enum NONE;
          enum INTERNAL;
        }
      }
      leaf dlCalibrationStatus {
        type enumeration {
          enum INACTIVE;
          enum CONVERGING;
          enum CALIBRATED;
          enum FAILED;
        }
      }
      }
    }
    leaf pimcFunctionReference {
      type string;
      status deprecated;
      description "Status info: Since 17.Q2. Replaced by PimCancellationConfig::pimCancellationFunctionRef. Planned to be removed..";
    }
    leaf ulPimCancellationMode {
      type enumeration {
        enum EXCLUDED;
        enum DEACTIVATED;
        enum ACTIVATED;
      }
      status deprecated;
      default "EXCLUDED";
      description "Default value: EXCLUDED; Status info: Since 17.Q2. Replaced by PimCancellationConfig::ulPimCancellationMode. Planned to be removed..";
    }
    leaf dlPimCandidate {
      type boolean;
      status deprecated;
      default "false";
      description "Default value: false; Status info: Since 17.Q2. Replaced by PimCancellationConfig::dlPimCandidate. Planned to be removed..";
    }
    leaf zzzTemporary1 {
      type string;
    }
    leaf zzzTemporary2 {
      type string;
    }
    leaf zzzTemporary3 {
      type int32;
      status deprecated;
      default "-2000000000";
      description "Default value: -2000000000; Status info: Since 18.Q2. Replaced by antCalModeTddAasDl. Planned to be removed..";
    }
    leaf zzzTemporary4 {
      type int32;
      default "-2000000000";
      description "Default value: -2000000000.";
    }
    leaf zzzTemporary5 {
      type int32;
      default "-2000000000";
      description "Default value: -2000000000.";
    }
    leaf zzzTemporary6 {
      type int32;
      default "-2000000000";
      description "Default value: -2000000000.";
    }
    leaf microSleepTxActivation {
      type boolean;
      config false;
      status deprecated;
      description "Status info: Since 21.Q3. Planned to be removed..";
    }
    leaf virtualSector {
      type boolean;
      default "false";
      description "Default value: false.";
    }
    leaf-list virtualComChBeamfrmWtsAmplitude {
      type eytypes:int32_range_0-100-3;
    }
    leaf-list virtualComChBeamfrmWtsPhase {
      type int32 {
        range "0..359";
      }
    }
    leaf digitalTilt {
      type int32 {
        range "-300..300";
      }
      default "30";
      units "degrees";
      description "range -300..300; Default value: 30.";
    }
    leaf sectorShape {
      type enumeration {
        enum MACRO;
        enum HIGHRISE;
        enum HOTSPOT;
        enum MACRO_NARROW;
        enum MACRO_WIDE;
        enum MACRO_2LOBE;
        enum MACRO_NARROW_H33;
      }
    }
    list ulCalibrationData {
      config false;
      container attributes {
      leaf ulCalibrationSupportedMethods {
        type ietfinet:port-number;
      }
      leaf ulCalibrationActiveMethod {
        type enumeration {
          enum NONE;
          enum INTERNAL;
        }
      }
      leaf ulCalibrationStatus {
        type enumeration {
          enum INACTIVE;
          enum CONVERGING;
          enum CALIBRATED;
          enum FAILED;
        }
      }
      }
    }
    leaf zzzTemporary7 {
      type int32;
      status deprecated;
      default "-2000000000";
      description "Default value: -2000000000; Status info: Since 20.Q4. Planned to be removed..";
    }
    leaf antCalModeTddAasDl {
      type eytypes:int32_range_0-1;
      default "0";
      description "range 0..1; Default value: 0.";
    }
    leaf pimMitigLevelThresh {
      type int32 {
        range "-180..-125 | 0";
      }
      status deprecated;
      default "-145";
      units "dB";
      description "Default value: -145; Status info: Since 24.Q1. Planned to be removed..";
    }
    leaf pimMitigAggressiveness {
      type enumeration {
        enum LOW;
        enum MEDIUM;
        enum HIGH;
      }
      status deprecated;
      default "MEDIUM";
      description "Default value: MEDIUM; Status info: Since 22.Q2. Replaced by pimMitigLevel. Planned to be removed..";
    }
    leaf pimMitigDlMutingPeriod {
      type int32 {
        range "4..15";
      }
      default "8";
      units "ms";
      description "range 4..15; Default value: 8.";
    }
    leaf pimMitigDlMutingPerc {
      type eytypes:int32_range_0-100;
      default "40";
      units "percent";
      description "range 0..100; Default value: 40.";
    }
    leaf pimMitigDlMutingFixed {
      type boolean;
      default "false";
      description "Default value: false.";
    }
    leaf pimMitigStatus {
      type enumeration {
        enum PIM_MITIG_STATUS_UNKNOWN;
        enum PIM_MITIG_STATUS_ACTIVE;
        enum PIM_MITIG_STATUS_FAILED;
        enum PIM_MITIG_STATUS_FINISHED;
      }
      config false;
    }
    leaf usedSectorShape {
      type enumeration {
        enum MACRO;
        enum HIGHRISE;
        enum HOTSPOT;
        enum MACRO_NARROW;
        enum MACRO_WIDE;
        enum MACRO_2LOBE;
        enum MACRO_NARROW_H33;
      }
      config false;
    }
    leaf essScLocalId {
      type int32 {
        range "0..99999";
      }
      default "0";
      description "range 0..99999; Default value: 0.";
    }
    leaf verticalTaperType {
      type enumeration {
        enum NO_TAPERING;
        enum TYPE1;
        enum TYPE2;
        enum TYPE3;
        enum TYPE4;
        enum TYPE5;
      }
    }
    leaf sectorCarrierType {
      type enumeration {
        enum NORMAL_SECTOR;
        enum LEFT_DIGITAL_SECTOR;
        enum RIGHT_DIGITAL_SECTOR;
        enum LEFT_DIGITAL_SECTOR_3DS;
        enum RIGHT_DIGITAL_SECTOR_3DS;
        enum MIDDLE_DIGITAL_SECTOR_3DS;
        enum A1_DIGITAL_SECTOR_4DS;
        enum B1_DIGITAL_SECTOR_4DS;
        enum C1_DIGITAL_SECTOR_4DS;
        enum D1_DIGITAL_SECTOR_4DS;
        enum A2_DIGITAL_SECTOR_4DS;
        enum B2_DIGITAL_SECTOR_4DS;
        enum C2_DIGITAL_SECTOR_4DS;
        enum D2_DIGITAL_SECTOR_4DS;
      }
    }
    leaf essScPairId {
      type int64 {
        range "0..9223372036854775807";
      }
      default "0";
      description "range 0..9223372036854775807; Default value: 0.";
    }
    leaf radioTransmitPerfMode {
      type enumeration {
        enum COVERAGE;
        enum CAPACITY;
        enum COVERAGE_GREEN;
        enum CAPACITY_GREEN;
      }
    }
    leaf maxAllowedEirpPsd {
      type int32 {
        range "-1 | 1..10000";
      }
      default "-1";
      units "dBm";
      description "Default value: -1.";
    }
    leaf zzzTemporary8 {
      type int32;
      default "-2000000000";
      description "Default value: -2000000000.";
    }
    leaf microSleepTxEnabled {
      type boolean;
      default "true";
      description "Default value: true.";
    }
    leaf pimMitigMinIntPwrAutoConfig {
      type int32 {
        range "-112..-92 | 0";
      }
      default "0";
      units "dBm/PRB";
      description "Default value: 0.";
    }
    leaf beamOverlapEirpControl {
      type boolean;
      default "false";
      description "Default value: false.";
    }
    leaf pimMitigLevel {
      type enumeration {
        enum LOW;
        enum MEDIUM;
        enum HIGH;
      }
    }
    leaf-list supportedVerticalTaperTypes {
      type ietfinet:port-number;
    }
    leaf-list supportedSectorShapes {
      type ietfinet:port-number;
    }
    leaf supportedTiltRange {
      type ietfinet:port-number;
      config false;
    }
    leaf usedVerticalTaperType {
      type enumeration {
        enum NO_TAPERING;
        enum TYPE1;
        enum TYPE2;
        enum TYPE3;
        enum TYPE4;
        enum TYPE5;
      }
      config false;
    }
    leaf usedDigitalTilt {
      type int32 {
        range "-300..300";
      }
      config false;
      units "degrees";
      description "range -300..300.";
    }
    leaf evmPowerBackoffAllowed {
      type boolean;
      status deprecated;
      default "true";
      description "Default value: true; Status info: Since 24.Q4. Replaced by SectorCarrier::ltePowerBackoffMode. Planned to be removed..";
    }
    leaf lteBbOnlyBackoffAllowed {
      type boolean;
      status deprecated;
      default "false";
      description "Default value: false; Takes effect: Next cell unlock; Status info: Since 24.Q4. Replaced by SectorCarrier::ltePowerBackoffMode. Planned to be removed..";
      reference "Takes effect: Next cell unlock.";
    }
    leaf ulGainScalingEnabled {
      type boolean;
      default "false";
      description "Default value: false.";
    }
    leaf ulGainScalingDelta {
      type eytypes:int32_range_-30-30;
      default "0";
      units "dB";
      description "range -30..30; Default value: 0.";
    }
    leaf ltePowerBackoffMode {
      type enumeration {
        enum AUTO;
        enum OFF;
        enum STATIC;
      }
    }
    leaf-list pmEmfPwrBackoffStepPwrDistr {
      type uint32;
    }
    leaf-list pmEmfPwrBackoffOnPwrDistr {
      type uint32;
    }
    leaf-list pmBranchDeltaSinrDistr0 {
      type uint32;
    }
    leaf pmActiveUeUlSumSectorCarrierNb {
      type ietfyang:mac-address;
      config false;
    }
    leaf pmEmfPwrBackoffSumOn {
      type uint32;
      config false;
    }
    leaf-list pmEmfPwrBackoffPwrDistr {
      type uint32;
    }
    leaf-list pmBranchDeltaSinrDistr2 {
      type uint32;
    }
    leaf-list pmBranchDeltaSinrDistr3 {
      type uint32;
    }
    leaf pmActiveUeDlSumSectorCarrierNb {
      type ietfyang:mac-address;
      config false;
    }
    leaf pmActiveUeUlSumSectorCarrier {
      type ietfyang:mac-address;
      config false;
    }
    leaf-list pmRadioRecInterferencePwr {
      type uint32;
      description "MOM flags: noNotification.";
    }
    leaf pmMicroTxSleepTime {
      type uint32;
      config false;
    }
    leaf pmActiveNbUeDlSumSectorCarrier {
      type ietfyang:mac-address;
      config false;
      status deprecated;
      description "MOM flags: noNotification.";
    }
    leaf-list pmSinrPuschSectorCarrierDistr {
      type uint32;
      description "MOM flags: noNotification.";
    }
    leaf pmZtemporary56 {
      type uint32;
      config false;
    }
    leaf-list pmBranchDeltaSinrDistr4 {
      type uint32;
    }
    leaf pmActiveNbUeUlSumSectorCarrier {
      type ietfyang:mac-address;
      config false;
      status deprecated;
      description "MOM flags: noNotification.";
    }
    leaf pmActiveUeDlSumSectorCarrier {
      type ietfyang:mac-address;
      config false;
    }
    leaf pmEmfPwrBackoffSamp {
      type uint32;
      config false;
    }
    leaf-list pmCompUlToADiffDistr {
      type uint32;
    }
    leaf-list pmBranchDeltaSinrDistr1 {
      type uint32;
    }
    leaf-list pmBranchDeltaSinrDistr6 {
      type uint32;
    }
    leaf-list pmConnectedNbUeSectorCarrierCe {
      type uint32;
      description "MOM flags: noNotification.";
    }
    leaf pmEmfPwrBackoffHardLimit {
      type uint32;
      config false;
    }
    leaf-list pmEmfPwrBackoffDynResThrDistr {
      type uint32;
    }
    leaf pmEmfPwrBackoffSum {
      type uint32;
      config false;
    }
    leaf-list pmBranchDeltaSinrDistr5 {
      type uint32;
    }
    leaf-list pmSinrPucchSectorCarrierDistr {
      type uint32;
      description "MOM flags: noNotification.";
    }
    leaf pmRadioTxPowerMaxConfigured {
      type int32;
      config false;
    }
  }
  grouping SecurityHandling-attributes {
    leaf securityHandlingId {
      type string;
      mandatory true;
    }
    leaf countWrapSupervisionActive {
      type boolean;
      default "true";
      description "Default value: true.";
    }
    leaf rbIdSupervisionActive {
      type boolean;
      default "true";
      description "Default value: true.";
    }
    leaf-list cipheringAlgoPrio {
      type ietfinet:ip-address;
    }
    leaf-list integrityProtectAlgoPrio {
      type enumeration {
        enum EIA1;
        enum EIA2;
        enum EIA3;
      }
    }
    leaf personalDataProtectionEnabled {
      type boolean;
      default "true";
      description "Default value: true.";
    }
    leaf pmRrcSecFailMsgContent {
      type uint32;
      config false;
    }
    leaf pmS1X2SecFailInUnexpectedMsg {
      type uint32;
      config false;
    }
    leaf pmZtemporary45 {
      type uint32;
      config false;
    }
    leaf pmRrcSecFailUnexpectedMsg {
      type uint32;
      config false;
    }
    leaf pmRrcSecFailIntegrity {
      type uint32;
      config false;
    }
  }
  grouping SharingGroup-attributes {
    leaf eUtranCellRef {
      type string;
      mandatory true;
    }
    leaf gUtranCellRelationRef {
      type string;
      mandatory true;
    }
    leaf userLabel {
      type string {
        length "1..128";
      }
      description "length 1..128.";
    }
    leaf schedPolicy {
      type enumeration {
        enum FAIR;
        enum LTE_BIASED;
        enum NR_BIASED;
      }
    }
    leaf sharingGroupId {
      type string;
      mandatory true;
    }
    leaf pmSubframeAllocDlShared {
      type uint32;
      config false;
    }
    leaf pmPrbUsedPuschNr {
      type uint32;
      config false;
    }
    leaf pmPrbUsedPdschNrMbsfn {
      type uint32;
      config false;
    }
    leaf pmPrbCatmNr {
      type uint32;
      config false;
    }
    leaf pmPrbAvailDlHighUtilizationBr {
      type uint32;
      config false;
    }
    leaf pmPuschSchedActivity {
      type uint32;
      config false;
    }
    leaf pmPrbPdcchPdschNr {
      type uint32;
      config false;
    }
    leaf pmPrbAllocPuschLte {
      type uint32;
      config false;
    }
    leaf pmPrbAvailPdschNr {
      type uint32;
      config false;
    }
    leaf pmSubframeAllocUlNr {
      type uint32;
      config false;
    }
    leaf pmPrbAllocPdschLte {
      type uint32;
      config false;
    }
    leaf pmPdschSchedActivity {
      type uint32;
      config false;
    }
    leaf pmSubframeAllocUlShared {
      type uint32;
      config false;
    }
    leaf pmPrbAvailDl {
      type uint32;
      config false;
    }
    leaf pmPrbAvailUl {
      type uint32;
      config false;
    }
    leaf-list pmPrbUsedPdschNrMbsfnDistr {
      type uint32;
    }
    leaf pmPrbUsedPdschNr {
      type uint32;
      config false;
    }
    leaf pmSubframeAllocDlNr {
      type uint32;
      config false;
    }
    leaf pmPrbAllocPuschNr {
      type uint32;
      config false;
    }
  }
  grouping SignalingRadioBearer-attributes {
    leaf signalingRadioBearerId {
      type string;
      mandatory true;
    }
    leaf tReorderingUl {
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200";
      }
      default "35";
      units "ms";
      description "Default value: 35.";
    }
    leaf tPollRetransmitDl {
      type int32 {
        range "5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500";
      }
      default "80";
      units "ms";
      description "Default value: 80.";
    }
    leaf dlPollPDU {
      type int32 {
        range "0 | 4 | 8 | 16 | 32 | 64 | 128 | 256";
      }
      default "0";
      description "Default value: 0.";
    }
    leaf dlMaxRetxThreshold {
      type int32 {
        range "1..4 | 6 | 8 | 16 | 32";
      }
      default "8";
      description "Default value: 8.";
    }
    leaf tPollRetransmitUl {
      type int32 {
        range "5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500";
      }
      default "80";
      units "ms";
      description "Default value: 80.";
    }
    leaf ulPollPDU {
      type int32 {
        range "0 | 4 | 8 | 16 | 32 | 64 | 128 | 256";
      }
      default "0";
      description "Default value: 0.";
    }
    leaf tReorderingDl {
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200";
      }
      default "35";
      units "ms";
      description "Default value: 35.";
    }
    leaf ulMaxRetxThreshold {
      type int32 {
        range "1..4 | 6 | 8 | 16 | 32";
      }
      default "8";
      description "Default value: 8.";
    }
    leaf tReorderingDlNb {
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200";
      }
      default "130";
      units "ms";
      description "Default value: 130.";
    }
    leaf tReorderingUlNb {
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200";
      }
      default "100";
      units "ms";
      description "Default value: 100.";
    }
    list tPollRetransmitNbDl {
      key "id";
      leaf id {
        type uint32;
        description "Synthetic key for struct entry.";
      }
      container attributes {
      leaf tPollRetransmitNbDlCe0 {
        type int32;
        default "2000";
        units "ms";
        description "Default value: 2000.";
      }
      leaf tPollRetransmitNbDlCe1 {
        type int32;
        default "3000";
        units "ms";
        description "Default value: 3000.";
      }
      leaf tPollRetransmitNbDlCe2 {
        type int32;
        default "10000";
        units "ms";
        description "Default value: 10000.";
      }
      }
    }
    list tPollRetransmitNbUl {
      key "id";
      leaf id {
        type uint32;
        description "Synthetic key for struct entry.";
      }
      container attributes {
      leaf tPollRetransmitNbUlCe0 {
        type int32;
        default "2000";
        units "ms";
        description "Default value: 2000.";
      }
      leaf tPollRetransmitNbUlCe1 {
        type int32;
        default "3000";
        units "ms";
        description "Default value: 3000.";
      }
      leaf tPollRetransmitNbUlCe2 {
        type int32;
        default "10000";
        units "ms";
        description "Default value: 10000.";
      }
      }
    }
    leaf tPollRetransmitSrbUlCatmCeLev0 {
      type int32 {
        range "5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 2000 | 4000";
      }
      default "400";
      units "ms";
      description "Default value: 400.";
    }
    leaf tPollRetransmitSrbDlCatmCeLev0 {
      type int32 {
        range "5 | 10 | 15 | 20 | 25 | 30 | 35 | 40 | 45 | 50 | 55 | 60 | 65 | 70 | 75 | 80 | 85 | 90 | 95 | 100 | 105 | 110 | 115 | 120 | 125 | 130 | 135 | 140 | 145 | 150 | 155 | 160 | 165 | 170 | 175 | 180 | 185 | 190 | 195 | 200 | 205 | 210 | 215 | 220 | 225 | 230 | 235 | 240 | 245 | 250 | 300 | 350 | 400 | 450 | 500 | 800 | 1000 | 2000 | 4000";
      }
      default "500";
      units "ms";
      description "Default value: 500.";
    }
    leaf tReorderingCatmCeLev0 {
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200 | 1600";
      }
      units "ms";
    }
    leaf tReorderingCatmCeLev1 {
      type int32 {
        range "0 | 5 | 10 | 15 | 20 | 25 | 30 | 35 | 40 | 45 | 50 | 55 | 60 | 65 | 70 | 75 | 80 | 85 | 90 | 95 | 100 | 110 | 120 | 130 | 140 | 150 | 160 | 170 | 180 | 190 | 200 | 1600";
      }
      units "ms";
    }
    leaf mpdcchNumRepetitionCeLev0 {
      type int32 {
        range "1..2 | 4 | 8 | 16 | 32 | 64 | 128 | 256";
      }
    }
    leaf ulMaxRetxThresholdNb {
      type int32 {
        range "1..4 | 6 | 8 | 16 | 32";
      }
      default "2";
      description "Default value: 2.";
    }
    leaf dlMaxRetxThresholdNb {
      type int32 {
        range "1..4 | 6 | 8 | 16 | 32";
      }
      default "2";
      description "Default value: 2.";
    }
  }
  grouping SleepModeCovProfile-attributes {
    leaf sleepModeCovProfileId {
      type string;
      mandatory true;
    }
    leaf-list reservedBy {
      type string;
    }
  }
  grouping SpectrumSharingFunction-attributes {
    leaf spectrumSharingFunctionId {
      type string;
      mandatory true;
    }
  }
  grouping SubscriberGroupProfile-attributes {
    leaf userLabel {
      type string {
        length "1..128";
      }
      description "length 1..128.";
    }
    leaf subscriberGroupProfileId {
      type string;
      mandatory true;
    }
    leaf-list spidTriggerList {
      type eytypes:int32_range_0-256;
    }
    list bearerTriggerList {
      key "id";
      leaf id {
        type uint32;
        description "Synthetic key for struct sequence entry.";
      }
      container attributes {
      leaf qci {
        type int32;
        default "0";
        description "Default value: 0.";
      }
      leaf arp {
        type eytypes:int32_range_0-15;
        default "0";
        description "range 0..15; Default value: 0.";
      }
      }
    }
    leaf customTriggerType {
      type enumeration {
        enum TRIGGER_NOT_USED;
        enum TRIGGER_TYPE_1;
        enum TRIGGER_TYPE_2;
        enum TRIGGER_TYPE_3;
        enum TRIGGER_TYPE_4;
        enum TRIGGER_TYPE_5;
        enum TRIGGER_TYPE_6;
        enum TRIGGER_TYPE_7;
        enum TRIGGER_TYPE_8;
        enum TRIGGER_TYPE_9;
        enum TRIGGER_TYPE_10;
      }
    }
    leaf-list customTriggerList {
      type eytypes:int32_range_0-65535-10;
    }
    leaf pZeroNominalPuschOffset {
      type eytypes:int32_range_-10-20;
      default "0";
      units "dB";
      description "range -10..20; Default value: 0.";
    }
    leaf pZeroNominalPucchOffset {
      type eytypes:int32_range_-10-20;
      default "0";
      units "dB";
      description "range -10..20; Default value: 0.";
    }
    leaf qciOffsetForQCI6 {
      type int32 {
        range "0 | 4..250";
      }
      default "0";
      description "Default value: 0.";
    }
    leaf qciOffsetForQCI7 {
      type int32 {
        range "0 | 3..249";
      }
      default "0";
      description "Default value: 0.";
    }
    leaf qciOffsetForQCI8 {
      type int32 {
        range "0 | 2..248";
      }
      default "0";
      description "Default value: 0.";
    }
    leaf qciOffsetForQCI9 {
      type int32 {
        range "0..247";
      }
      default "0";
      description "range 0..247; Default value: 0.";
    }
    leaf-list subGroupConfiguration1 {
      type eytypes:int32_range_0-65535-10;
    }
    leaf-list subGroupConfiguration2 {
      type eytypes:int32_range_0-65535-10;
    }
    leaf-list subGroupConfiguration3 {
      type eytypes:int32_range_0-65535-10;
    }
    leaf-list subGroupConfiguration4 {
      type eytypes:int32_range_0-65535-10;
    }
    leaf-list subGroupConfiguration5 {
      type eytypes:int32_range_0-65535-10;
    }
    leaf-list subGroupConfiguration6 {
      type eytypes:int32_range_0-65535-10;
    }
    leaf-list subGroupConfiguration7 {
      type int32 {
        range "-200..2147483647";
      }
    }
    leaf drxMode {
      type enumeration {
        enum NO_OVERRIDE;
        enum DISABLE_DRX;
        enum RESERVED_FOR_FUTURE_USE;
      }
    }
    leaf preschedulingMode {
      type enumeration {
        enum NO_OVERRIDE;
        enum DISABLE_PRESCHEDULING;
        enum USE_SPECIFIC_PRESCHEDULING;
      }
    }
    leaf caRateAdjustCoeff {
      type int32 {
        range "-1..10";
      }
      default "-1";
      description "range -1..10; Default value: -1.";
    }
    leaf profileIndex {
      type eytypes:int32_range_0-9;
      config false;
      description "range 0..9.";
    }
    leaf profilePriority {
      type eytypes:int32_range_1-65535;
      default "1";
      description "range 1..65535; Default value: 1.";
    }
    leaf preschedProfileRef {
      type string;
    }
    leaf iuaMode {
      type enumeration {
        enum NO_OVERRIDE;
        enum DISABLE_IUA;
        enum USE_SPECIFIC_IUA;
      }
    }
    leaf iuaProfileRef {
      type string;
    }
    leaf selectionProbability {
      type eytypes:int32_range_0-100;
      default "100";
      units "percent";
      description "range 0..100; Default value: 100.";
    }
    leaf-list cellTriggerList {
      type eytypes:int32_range_0-255;
    }
    leaf ulMcsUpperLimit {
      type int32 {
        range "-1 | 1..28";
      }
      default "-1";
      description "Default value: -1.";
    }
    leaf ulMcsLowerLimit {
      type int32 {
        range "-1 | 1..28";
      }
      default "-1";
      description "Default value: -1.";
    }
    leaf ulHarqBlerTarget {
      type eytypes:int32_range_1-100-4;
      default "10";
      description "range 1..100; Default value: 10.";
    }
    leaf dlHarqBlerTarget {
      type eytypes:int32_range_1-100-4;
      default "10";
      description "range 1..100; Default value: 10.";
    }
    leaf groupExtendInactAfterVolteRel {
      type eytypes:int32_range_0-3600;
      default "0";
      units "s";
      description "range 0..3600; Default value: 0.";
    }
    leaf dlDynBlerTargetMax {
      type int32 {
        range "-1 | 1..100";
      }
      default "-1";
      units "percent";
      description "Default value: -1.";
    }
    leaf dlDynBlerTargetAlg {
      type eytypes:int32_range_0-3;
      default "0";
      description "range 0..3; Default value: 0.";
    }
    leaf ulCandidateToRegion {
      type boolean;
      default "false";
      description "Default value: false.";
    }
    leaf ulPlThresToRegion {
      type int32 {
        range "0..2000";
      }
      default "500";
      units "dB";
      description "range 0..2000; Default value: 500.";
    }
    leaf ulSinrThresToRegion {
      type int32 {
        range "-100..400";
      }
      default "400";
      units "dB";
      description "range -100..400; Default value: 400.";
    }
    leaf dlDynBlerTargetMin {
      type eytypes:int32_range_1-100;
      default "1";
      units "percent";
      description "range 1..100; Default value: 1.";
    }
    leaf sCellScheduleSinrThresOffset {
      type eytypes:int32_range_-200-200;
      default "0";
      units "dB";
      description "range -200..200; Default value: 0.";
    }
    leaf endcUserProfileRef {
      type string;
    }
    leaf fastACqiReportEnabled {
      type ietfinet:port-number;
      description "Default value: false.";
    }
    leaf lastSchedLinkAdaptMode {
      type enumeration {
        enum NO_OVERRIDE;
        enum DISABLE;
        enum ENABLE;
      }
    }
    leaf pdcchFlexibleBlerMode {
      type enumeration {
        enum NO_OVERRIDE;
        enum DISABLED;
        enum ENABLED;
      }
    }
    leaf-list featuresToDisableMeas {
      type enumeration {
        enum ANR;
        enum PM_INIT_UE_MEAS;
        enum MDT;
        enum BNR_INTRA_LTE_LM;
        enum ASM;
      }
    }
    leaf dlAiLaDeltaSinrMax {
      type int32 {
        range "0..200";
      }
      default "30";
      units "dB";
      description "range 0..200; Default value: 30.";
    }
    leaf volteCodecRateForUlSinrEst {
      type int32 {
        range "-1..0 | 475 | 515 | 590 | 660 | 670 | 720 | 740 | 795 | 800 | 885 | 960 | 1020 | 1220 | 1265 | 1320 | 1425 | 1585 | 1640 | 1825 | 1985 | 2305 | 2385 | 2440 | 3200 | 4800 | 6400 | 9600 | 12800";
      }
      default "-1";
      units "kbps";
      description "Default value: -1.";
    }
    leaf ulOuterloopStepSizeFactor {
      type int32 {
        range "10..15";
      }
      default "10";
      description "range 10..15; Default value: 10.";
    }
    leaf higherPriorityEnabled {
      type boolean;
      default "false";
      description "Default value: false.";
    }
    list plmnTriggerList {
      key "id";
      leaf id {
        type uint32;
        description "Synthetic key for struct sequence entry.";
      }
      ordered-by user;
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
  }
  grouping SubscriberProfileID-attributes {
    leaf subscriberProfileIDId {
      type string;
      mandatory true;
    }
    leaf userLabel {
      type string {
        length "1..128";
      }
      description "length 1..128.";
    }
  }
  grouping TermPointToCts-attributes {
    leaf administrativeState {
      type enumeration {
        enum LOCKED;
        enum UNLOCKED;
        enum SHUTTINGDOWN;
      }
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf operationalState {
      type enumeration {
        enum DISABLED;
        enum ENABLED;
      }
      config false;
    }
    leaf ipv4Address {
      type ietfinet:ipv4-address;
      default "0.0.0.0";
      description "length 7..15; Default value: 0.0.0.0.";
    }
    leaf ipv6Address {
      type ietfinet:ipv6-address;
      default "::";
      description "length 2..39; Default value: ::.";
    }
    leaf usedIpAddress {
      type ietfinet:ip-address;
      config false;
      description "length 2..39.";
    }
    leaf termPointToCtsId {
      type string;
      mandatory true;
    }
    leaf mlDPortNumber {
      type ietfinet:port-number;
      default "9660";
      description "range 1..65535; Default value: 9660.";
    }
    leaf mlCPortNumber {
      type ietfinet:port-number;
      default "9650";
      description "range 1..65535; Default value: 9650.";
    }
  }
  grouping TermPointToENB-attributes {
    leaf termPointToENBId {
      type string;
      mandatory true;
    }
    leaf ipAddress {
      type ietfinet:ip-address;
      default "0.0.0.0";
      description "length 7..15; Default value: 0.0.0.0.";
    }
    leaf administrativeState {
      type enumeration {
        enum LOCKED;
        enum UNLOCKED;
        enum SHUTTINGDOWN;
      }
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf operationalState {
      type enumeration {
        enum DISABLED;
        enum ENABLED;
      }
      config false;
    }
    leaf domainName {
      type ietfinet:domain-name;
      description "length 0..255.";
    }
    leaf usedIpAddress {
      type ietfinet:ip-address;
      config false;
      description "length 2..39.";
    }
    leaf ipv6Address {
      type ietfinet:ipv6-address;
      default "::";
      description "length 2..39; Default value: ::.";
    }
    leaf createdBy {
      type enumeration {
        enum ANR;
        enum X2;
        enum OPERATOR;
      }
      config false;
    }
    leaf timeOfCreation {
      type string {
        length "0..19";
      }
      config false;
      description "length 0..19.";
    }
    leaf lastModification {
      type enumeration {
        enum ANR_MODIFICATION;
        enum X2_MODIFICATION;
        enum OPERATOR_MODIFICATION;
        enum ANR_DELETE;
        enum X2_DELETE;
        enum OPERATOR_DELETE;
        enum NOT_MODIFIED;
        enum MRO_MODIFICATION;
        enum PCI_MODIFICATION;
        enum MLB_MODIFICATION;
        enum RACH_OPT_MODIFICATION;
        enum LM_MODIFICATION;
      }
      config false;
    }
    leaf timeOfLastModification {
      type string {
        length "0..19";
      }
      config false;
      description "length 0..19.";
    }
    leaf interEnbSwCompatibilityState {
      type enumeration {
        enum UNKNOWN;
        enum COMPATIBLE;
        enum INCOMPATIBLE;
        enum RELEASE_COMPATIBLE;
      }
      config false;
    }
    leaf ipsecEpAddress {
      type ietfinet:ip-address;
      config false;
    }
    leaf interEnbUlCompSwCompatibility {
      type enumeration {
        enum UNKNOWN;
        enum COMPATIBLE;
        enum INCOMPATIBLE;
        enum RELEASE_COMPATIBLE;
      }
      config false;
    }
    leaf eranUlCompSwCompatibility {
      type enumeration {
        enum UNKNOWN;
        enum COMPATIBLE;
        enum INCOMPATIBLE;
        enum RELEASE_COMPATIBLE;
      }
      config false;
    }
    leaf eRanCaProtVerActive {
      type eytypes:int32_range_-1-2147483647;
      config false;
      description "range -1..2147483647.";
    }
    leaf interEnbCaProtVerActive {
      type eytypes:int32_range_-1-2147483647;
      config false;
      description "range -1..2147483647.";
    }
    leaf eRanUlCompProtVerActive {
      type eytypes:int32_range_-1-2147483647;
      config false;
      description "range -1..2147483647.";
    }
    leaf interEnbUlCompProtVerActive {
      type eytypes:int32_range_-1-2147483647;
      config false;
      description "range -1..2147483647.";
    }
    leaf additionalCnRef {
      type string;
    }
    leaf eranCaSwCompatibility {
      type enumeration {
        enum UNKNOWN;
        enum COMPATIBLE;
        enum INCOMPATIBLE;
        enum RELEASE_COMPATIBLE;
      }
      config false;
    }
    leaf eranPimAvoidSwCompatibility {
      type enumeration {
        enum UNKNOWN;
        enum COMPATIBLE;
        enum INCOMPATIBLE;
        enum RELEASE_COMPATIBLE;
      }
      config false;
    }
  }
  grouping TermPointToGNB-attributes {
    leaf termPointToGNBId {
      type string;
      mandatory true;
    }
    leaf administrativeState {
      type enumeration {
        enum LOCKED;
        enum UNLOCKED;
        enum SHUTTINGDOWN;
      }
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf operationalState {
      type enumeration {
        enum DISABLED;
        enum ENABLED;
      }
      config false;
    }
    leaf ipAddress {
      type ietfinet:ip-address;
      default "0.0.0.0";
      description "length 7..15; Default value: 0.0.0.0.";
    }
    leaf ipv6Address {
      type ietfinet:ipv6-address;
      default "::";
      description "length 2..39; Default value: ::.";
    }
    leaf domainName {
      type ietfinet:domain-name;
      description "length 0..255.";
    }
    leaf usedIpAddress {
      type ietfinet:ip-address;
      config false;
      description "length 2..39.";
    }
    leaf ipsecEpAddress {
      type ietfinet:ip-address;
      default "::";
      description "length 2..39; Default value: ::.";
    }
    leaf upIpAddress {
      type ietfinet:ip-address;
      default "::";
      description "length 2..39; Default value: ::.";
    }
    leaf connectionPurpose {
      type enumeration {
        enum ENDC;
        enum ESS;
        enum ENDC_ESS;
      }
      status deprecated;
      default "ENDC";
      description "Default value: ENDC; Takes effect: Next MO unlock; Status info: Since 20.Q1. Has no functional behavior. Planned to removed..";
      reference "Takes effect: Next MO unlock.";
    }
    leaf createdBy {
      type enumeration {
        enum ANR;
        enum X2;
        enum OPERATOR;
      }
      config false;
    }
    leaf timeOfCreation {
      type string {
        length "0..19";
      }
      config false;
      description "length 0..19.";
    }
    leaf-list ipAddress2 {
      type ietfinet:ip-address;
      ordered-by user;
    }
    leaf-list ipv6Address2 {
      type ietfinet:ipv6-address;
      ordered-by user;
    }
    leaf additionalCnRef {
      type string;
    }
  }
  grouping TermPointToLbm-attributes {
    leaf termPointToLbmId {
      type string;
      mandatory true;
    }
    leaf operationalState {
      type enumeration {
        enum DISABLED;
        enum ENABLED;
      }
      config false;
    }
    leaf pmCompUlReqTransInterEnb {
      type uint32;
      config false;
    }
    leaf pmCompUlRspRecInterEnb {
      type uint32;
      config false;
    }
    leaf pmCompUlReqRecInterEnb {
      type uint32;
      config false;
    }
    leaf pmCompUlRspTransInterEnb {
      type uint32;
      config false;
    }
  }
  grouping TermPointToMme-attributes {
    leaf termPointToMmeId {
      type string;
      mandatory true;
    }
    leaf mmeName {
      type string {
        length "0..150";
      }
      config false;
      description "length 0..150.";
    }
    leaf domainName {
      type ietfinet:domain-name;
      description "length 0..255.";
    }
    leaf ipAddress1 {
      type ietfinet:ip-address;
      default "0.0.0.0";
      description "length 7..15; Default value: 0.0.0.0.";
    }
    leaf administrativeState {
      type enumeration {
        enum LOCKED;
        enum UNLOCKED;
        enum SHUTTINGDOWN;
      }
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf operationalState {
      type enumeration {
        enum DISABLED;
        enum ENABLED;
      }
      config false;
    }
    leaf ipAddress2 {
      type ietfinet:ip-address;
      default "0.0.0.0";
      description "length 7..15; Default value: 0.0.0.0.";
    }
    leaf usedIpAddress {
      type ietfinet:ip-address;
      config false;
      description "length 2..39.";
    }
    leaf relativeMmeCapacity {
      type eytypes:int32_range_0-255;
      config false;
      description "range 0..255.";
    }
    leaf ipv6Address1 {
      type ietfinet:ipv6-address;
      default "::";
      description "length 2..39; Default value: ::.";
    }
    leaf ipv6Address2 {
      type ietfinet:ipv6-address;
      default "::";
      description "length 2..39; Default value: ::.";
    }
    list servedPlmnListLTERelated {
      config false;
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    list servedPlmnListOtherRATs {
      config false;
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf-list mmeGIListLTERelated {
      type int32 {
        range "-1..65535";
      }
    }
    leaf-list mmeCodeListLTERelated {
      type eytypes:int32_range_-1-255;
    }
    leaf-list mmeCodeListOtherRATs {
      type eytypes:int32_range_-1-255;
    }
    leaf dcnType {
      type enumeration {
        enum DEFAULT;
        enum SPECIFIC;
      }
    }
    leaf mmeSupportLegacyLte {
      type ietfinet:port-number;
      description "Default value: true.";
    }
    leaf mmeSupportNbIoT {
      type ietfinet:port-number;
      description "Default value: false.";
    }
    leaf additionalCnRef {
      type string;
    }
    leaf pwsRestartHandling {
      type enumeration {
        enum DISABLED;
        enum ENABLED;
      }
    }
  }
  grouping TermPointToSGW-attributes {
    leaf usedIpAddress {
      type ietfinet:ip-address;
      config false;
      description "length 2..39.";
    }
    leaf timeOfCreation {
      type string {
        length "0..19";
      }
      config false;
      description "length 0..19.";
    }
    leaf termPointToSGWId {
      type string;
      mandatory true;
    }
    leaf-list pmS1uPktRecMaxBurstSampQci {
      type uint32;
      description "MOM flags: noNotification.";
    }
    leaf-list pmS1uPktLostDlQci {
      type uint32;
    }
    leaf-list pmS1uPktRecQci {
      type uint32;
    }
    leaf-list pmS1uPktRecDiscontQci {
      type uint32;
      description "MOM flags: noNotification.";
    }
    leaf-list pmS1uPktRecMaxBurstSumQci {
      type uint32;
      description "MOM flags: noNotification.";
    }
    leaf-list pmS1uPktRecOooQci {
      type uint32;
    }
  }
  grouping TimerProfile-attributes {
    leaf timerProfileId {
      type string;
      mandatory true;
    }
    leaf-list reservedBy {
      type string;
    }
    leaf tWaitForRrcConnReest {
      type eytypes:int32_range_1-20;
      mandatory true;
      units "s";
      description "range 1..20.";
    }
    leaf tRrcConnectionReconfiguration {
      type eytypes:int32_range_1-20;
      mandatory true;
      units "s";
      description "range 1..20.";
    }
    leaf tRrcConnReest {
      type eytypes:int32_range_1-20;
      mandatory true;
      units "s";
      description "range 1..20.";
    }
    leaf tRelocOverall {
      type eytypes:int32_range_1-20;
      mandatory true;
      units "s";
      description "range 1..20.";
    }
  }
  grouping UeMeasControl-attributes {
    leaf ueMeasControlId {
      type string;
      mandatory true;
    }
    leaf sMeasure {
      type int32 {
        range "-140..-44 | 0";
      }
      default "0";
      units "dBm";
      description "Default value: 0.";
    }
    leaf filterCoefficientEUtraRsrp {
      type int32 {
        range "0..9 | 11 | 13 | 15 | 17 | 19";
      }
      default "4";
      description "Default value: 4.";
    }
    leaf filterCoefficientEUtraRsrq {
      type int32 {
        range "0..9 | 11 | 13 | 15 | 17 | 19";
      }
      default "11";
      description "Default value: 11.";
    }
    leaf ueMeasurementsActive {
      type boolean;
      default "false";
      description "Default value: false.";
    }
    leaf a5B2MobilityTimer {
      type eytypes:int32_range_0-120000;
      default "0";
      units "ms";
      description "range 0..120000; Default value: 0.";
    }
    leaf maxMeasInterFreqEUtra {
      type eytypes:int32_range_1-7;
      default "7";
      description "range 1..7; Default value: 7.";
    }
    leaf maxMeasEUtraOther {
      type eytypes:int32_range_1-5-21;
      default "5";
      description "range 1..5; Default value: 5.";
    }
    leaf maxMeasGeran {
      type eytypes:int32_range_1-5-21;
      default "5";
      description "range 1..5; Default value: 5.";
    }
    leaf maxMeasUtraFdd {
      type eytypes:int32_range_1-5-21;
      default "5";
      description "range 1..5; Default value: 5.";
    }
    leaf maxMeasCdma2000eHrpd {
      type eytypes:int32_range_1-5-21;
      default "5";
      description "range 1..5; Default value: 5.";
    }
    leaf measQuantityUtraFDD {
      type enumeration {
        enum RSCP;
        enum ECNO;
      }
    }
    leaf zzzTemporary1 {
      type string;
    }
    leaf zzzTemporary2 {
      type string;
    }
    leaf zzzTemporary3 {
      type string;
    }
    leaf zzzTemporary4 {
      type string;
    }
    leaf zzzTemporary5 {
      type int32;
      default "-2000000000";
      description "Default value: -2000000000.";
    }
    leaf zzzTemporary6 {
      type int32;
      default "-2000000000";
      description "Default value: -2000000000.";
    }
    leaf zzzTemporary7 {
      type int32;
      default "-2000000000";
      description "Default value: -2000000000.";
    }
    leaf maxMeasUtraTdd {
      type eytypes:int32_range_1-5-21;
      default "5";
      description "range 1..5; Default value: 5.";
    }
    leaf maxUtranCellsToMeasure {
      type int32 {
        range "0..64";
      }
      default "32";
      description "range 0..64; Default value: 32.";
    }
    leaf csfbHoTargetSearchTimer {
      type eytypes:int32_range_1-12000;
      default "500";
      units "ms";
      description "range 1..12000; Default value: 500.";
    }
    leaf maxMeasCdma20001xRtt {
      type eytypes:int32_range_1-5-21;
      default "3";
      description "range 1..5; Default value: 3.";
    }
    leaf ueMeasurementsActiveIF {
      type boolean;
      default "true";
      description "Default value: true.";
    }
    leaf ueMeasurementsActiveUTRAN {
      type boolean;
      default "true";
      description "Default value: true.";
    }
    leaf ueMeasurementsActiveGERAN {
      type boolean;
      default "true";
      description "Default value: true.";
    }
    leaf ueMeasurementsActiveCDMA2000 {
      type boolean;
      default "true";
      description "Default value: true.";
    }
    leaf allowReleaseQci1 {
      type boolean;
      default "false";
      description "Default value: false.";
    }
    leaf searchEffortTime {
      type int32 {
        range "0..1200";
      }
      default "40";
      units "s";
      description "range 0..1200; Default value: 40.";
    }
    leaf ueMeasurementsActiveCDMA20001xRtt {
      type boolean;
      default "true";
      description "Default value: true.";
    }
    leaf servOrPrioIFHoTimer {
      type int32 {
        range "0..60000";
      }
      default "0";
      units "ms";
      description "range 0..60000; Default value: 0.";
    }
    leaf inhibitB2RsrqConfig {
      type boolean;
      default "false";
      description "Default value: false.";
    }
    leaf lowPrioMeasThresh {
      type eytypes:int32_range_0-7;
      default "0";
      description "range 0..7; Default value: 0.";
    }
    leaf excludeInterFreqAtCritical {
      type boolean;
      default "false";
      description "Default value: false.";
    }
    leaf bothA5RsrpRsrqCheck {
      type boolean;
      default "false";
      description "Default value: false.";
    }
    leaf zzzTemporary8 {
      type int32;
      default "-2000000000";
      description "Default value: -2000000000.";
    }
    leaf zzzTemporary9 {
      type int32;
      default "-2000000000";
      description "Default value: -2000000000.";
    }
    leaf zzzTemporary10 {
      type int32;
      default "-2000000000";
      description "Default value: -2000000000.";
    }
    leaf zzzTemporary11 {
      type int32;
      default "-2000000000";
      description "Default value: -2000000000.";
    }
    leaf zzzTemporary12 {
      type int32;
      default "-2000000000";
      description "Default value: -2000000000.";
    }
    leaf zzzTemporary13 {
      type int32;
      default "-2000000000";
      description "Default value: -2000000000.";
    }
    leaf zzzTemporary14 {
      type int32;
      default "-2000000000";
      description "Default value: -2000000000.";
    }
    leaf zzzTemporary15 {
      type int32;
      default "-2000000000";
      description "Default value: -2000000000.";
    }
    leaf zzzTemporary16 {
      type int32;
      default "-2000000000";
      description "Default value: -2000000000.";
    }
    leaf zzzTemporary17 {
      type int32;
      default "-2000000000";
      description "Default value: -2000000000.";
    }
    leaf zzzTemporary18 {
      type int32;
      default "-2000000000";
      description "Default value: -2000000000.";
    }
    leaf zzzTemporary20 {
      type int32;
      status deprecated;
      default "-2000000000";
      description "Default value: -2000000000; Status info: Since 17.Q1. Replaced by ReportConfigSCellA1A2::a1a2ThresholdRsrpBidir. Planned to be removed..";
    }
    leaf filterCoefficientEUtraUlSinrMax {
      type int32 {
        range "0..9 | 11 | 13 | 15 | 17 | 19";
      }
      default "11";
      description "Default value: 11.";
    }
    leaf maxNoMeasReportsInact {
      type ietfinet:port-number;
      default "1";
      description "range 0..100; Default value: 1.";
    }
    leaf filterCoefficientEUtraNI {
      type eytypes:int32_range_0-31-13;
      default "9";
      description "range 0..31; Default value: 9.";
    }
    leaf targetA2UlSearchOffset {
      type eytypes:int32_range_-150-150;
      default "20";
      units "dB";
      description "range -150..150; Default value: 20.";
    }
    leaf ulSinrOffset {
      type eytypes:int32_range_-150-150;
      default "30";
      units "dB";
      description "range -150..150; Default value: 30.";
    }
    leaf a3SuspendCsgTimer {
      type eytypes:int32_range_0-120000;
      default "0";
      units "ms";
      description "range 0..120000; Default value: 0.";
    }
    leaf zzzTemporary21 {
      type int32;
      default "-2000000000";
      description "Default value: -2000000000.";
    }
    leaf zzzTemporary22 {
      type int32;
      default "-2000000000";
      description "Default value: -2000000000.";
    }
    leaf zzzTemporary23 {
      type int32;
      default "-2000000000";
      description "Default value: -2000000000.";
    }
    leaf zzzTemporary24 {
      type int32;
      default "-2000000000";
      description "Default value: -2000000000.";
    }
    leaf zzzTemporary25 {
      type int32;
      default "-2000000000";
      description "Default value: -2000000000.";
    }
    leaf checkA2SearchLevel {
      type boolean;
      default "true";
      description "Default value: true.";
    }
    leaf zzzTemporary26 {
      type int32;
      default "-2000000000";
      description "Default value: -2000000000.";
    }
    leaf zzzTemporary27 {
      type int32;
      default "-2000000000";
      description "Default value: -2000000000.";
    }
    leaf a3MobilityTimerBr {
      type eytypes:int32_range_0-120000;
      default "0";
      units "ms";
      description "range 0..120000; Default value: 0.";
    }
    leaf intraFreqMeasModeBr {
      type enumeration {
        enum DEFAULT_MEASUREMENT;
        enum PUSCH_SINR_BASED;
      }
    }
    leaf ueMeasurementsActiveBr {
      type boolean;
      default "false";
      description "Default value: false.";
    }
    leaf a5MobilityTimerBr {
      type eytypes:int32_range_0-120000;
      default "0";
      units "ms";
      description "range 0..120000; Default value: 0.";
    }
    list prioOffsetPerQci {
      key "id";
      leaf id {
        type uint32;
        description "Synthetic key for struct sequence entry.";
      }
      container attributes {
      leaf offsetPerQciPrio {
        type ietfinet:ip-address;
        description "range -1..7; Default value: 0.";
      }
      leaf qciProfileRef {
        type ietfinet:ip-address;
      }
      }
    }
    leaf bothB1RscpEcnoCheck {
      type boolean;
      default "false";
      description "Default value: false.";
    }
    leaf bothB2RscpEcnoCheck {
      type boolean;
      default "false";
      description "Default value: false.";
    }
    leaf bothIntraA3RsrpRsrqCheck {
      type boolean;
      default "false";
      description "Default value: false.";
    }
    leaf bothInterA3RsrpRsrqCheck {
      type boolean;
      default "false";
      description "Default value: false.";
    }
    leaf filterCoefficientRscpUtra {
      type int32 {
        range "0..9 | 11 | 13 | 15 | 17 | 19";
      }
      default "4";
      description "Default value: 4.";
    }
    leaf filterCoefficientEcnoUtra {
      type int32 {
        range "0..9 | 11 | 13 | 15 | 17 | 19";
      }
      default "4";
      description "Default value: 4.";
    }
    leaf rwrToNRAllowed {
      type boolean;
      status deprecated;
      default "false";
      description "Default value: false; Status info: Since 23.Q4. Replaced by nrB1MeasEnabled. Planned to be removed..";
    }
    leaf maxMeasNR {
      type eytypes:int32_range_1-8;
      default "5";
      description "range 1..8; Default value: 5.";
    }
    leaf waitForStartNRMeas {
      type int32 {
        range "1000..240000";
      }
      default "6000";
      units "ms";
      description "range 1000..240000; Default value: 6000.";
    }
    leaf nrB1MobiltyTimerLessTtt {
      type int32 {
        range "-1 | 1..20000";
      }
      status deprecated;
      default "600";
      units "ms";
      description "Default value: 600; Takes effect: New connection; Status info: Since 19.Q3. Has no functional behavior. Planned to be removed..";
      reference "Takes effect: New connection.";
    }
    leaf waitForResumeNRMeas {
      type int32 {
        range "-1 | 1..240000";
      }
      default "6000";
      units "ms";
      description "Default value: 6000.";
    }
    leaf maxMeasInterFreqEUtraR12 {
      type eytypes:int32_range_1-32;
      default "7";
      description "range 1..32; Default value: 7.";
    }
    leaf maxMeasEUtraOtherR12 {
      type eytypes:int32_range_1-32;
      default "5";
      description "range 1..32; Default value: 5.";
    }
    leaf maxMeasInterFreqEUtraIncR12 {
      type eytypes:int32_range_1-32;
      default "20";
      description "range 1..32; Default value: 20.";
    }
    leaf nrB1MobilityTimerLessTtt {
      type int32 {
        range "-1 | 1..20000";
      }
      default "600";
      units "ms";
      description "Default value: 600.";
    }
    leaf numB1EndcMeasConfig {
      type eytypes:int32_range_0-8;
      status deprecated;
      default "1";
      description "range 0..8; Default value: 1; Takes effect: New connection; Status info: Since 19.Q4. Has no functional behavior. Planned to be removed..";
      reference "Takes effect: New connection.";
    }
    leaf measScaleFactor {
      type int32 {
        range "-1..1";
      }
      default "-1";
      description "range -1..1; Default value: -1.";
    }
    leaf maxMeasB1Endc {
      type eytypes:int32_range_0-8;
      default "3";
      description "range 0..8; Default value: 3.";
    }
    leaf endcMeasTime {
      type int32 {
        range "-1 | 40..120000";
      }
      default "2000";
      units "ms";
      description "Default value: 2000.";
    }
    leaf filterCoeffUlSinrMaxCsfb {
      type int32 {
        range "0..9 | 11 | 13 | 15 | 17 | 19";
      }
      status deprecated;
      default "8";
      description "Default value: 8; Status info: Since 20.Q1. Has no functional behavior. Planned to be removed..";
    }
    leaf endcMeasRestartTime {
      type int32 {
        range "-1..240000";
      }
      default "-1";
      units "ms";
      description "range -1..240000; Default value: -1.";
    }
    leaf endcB1MeasWindow {
      type int32 {
        range "0 | 40..2000";
      }
      default "40";
      units "ms";
      description "Default value: 40.";
    }
    leaf endcCheckForRwrToNRDisabled {
      type boolean;
      status deprecated;
      default "false";
      description "Default value: false; Status info: Since 22.Q3. Replaced by nrB1MeasAtEndcEnabled. Planned to be removed..";
    }
    leaf bothA5RsrpRsrqCheckSpifho {
      type boolean;
      default "false";
      description "Default value: false.";
    }
    leaf bothRsrpRsrqCheckUlTraffic {
      type boolean;
      default "false";
      description "Default value: false.";
    }
    leaf a5MobilityTimerUlTraffic {
      type eytypes:int32_range_0-120000;
      default "2000";
      units "ms";
      description "range 0..120000; Default value: 2000.";
    }
    leaf a5TimerUlVolteCovMob {
      type eytypes:int32_range_0-120000;
      default "2000";
      units "ms";
      description "range 0..120000; Default value: 2000.";
    }
    leaf nrB1MeasAtEndcEnabled {
      type boolean;
      default "false";
      description "Default value: false.";
    }
    leaf nrB1MeasWindow {
      type int32 {
        range "0 | 40..2000";
      }
      default "40";
      units "ms";
      description "Default value: 40.";
    }
    leaf ueMeasurementsActiveNR {
      type boolean;
      default "true";
      description "Default value: true.";
    }
    leaf b2NrMeasAllowed {
      type boolean;
    }
    leaf endcInhibitTime {
      type int32 {
        range "-1 | 100..240000";
      }
      default "-1";
      units "ms";
      description "Default value: -1.";
    }
    leaf waitStartInterFHoHigherPrio {
      type int32 {
        range "1000..24000";
      }
      default "6000";
      units "ms";
      description "range 1000..24000; Default value: 6000.";
    }
    leaf a5measInterFHoHigherPrioT {
      type int32 {
        range "1..20000";
      }
      default "600";
      units "ms";
      description "range 1..20000; Default value: 600.";
    }
    leaf nrB1MeasEnabled {
      type boolean;
      default "false";
      description "Default value: false.";
    }
  }
  grouping UeMeasControlCommon-attributes {
    leaf ueMeasControlCommonId {
      type string;
      mandatory true;
      status deprecated;
      description "MOM flags: restricted, noNotification; Status info: Since 19.Q4. Has no functional behavior. Planned to be removed..";
    }
  }
  grouping UePolicyOptimization-attributes {
    leaf-list ueCapPrioList {
      type enumeration {
        enum ENDC;
        enum TM9;
      }
    }
    leaf t320 {
      type int32 {
        range "5 | 10 | 20 | 30 | 60 | 120 | 180";
      }
      default "30";
      units "min";
      description "Default value: 30.";
    }
    leaf uePolicyOptimizationId {
      type string;
      mandatory true;
    }
    leaf miEnabledEndcIdleModeControl {
      type enumeration {
        enum DEACTIVATED;
        enum OBSERVABILITY_MODE;
        enum OPERATIONAL_MODE;
      }
      status deprecated;
      default "DEACTIVATED";
      description "Default value: DEACTIVATED; Status info: Since 21.Q1. Has no functional behavior. Planned to be removed..";
    }
    leaf minRsrpCellReselection {
      type int32 {
        range "-140..-44";
      }
      status deprecated;
      default "-116";
      units "dB";
      description "range -140..-44; Default value: -116; Status info: Since 21.Q1. Has no functional behavior. Planned to be removed..";
    }
    leaf coverageAwareImc {
      type boolean;
      default "true";
      description "Default value: true.";
    }
    leaf endcAwareImc {
      type enumeration {
        enum DEACTIVATED;
        enum MODE_1;
        enum MODE_2;
      }
    }
    leaf zzzTemporary1 {
      type int32;
      default "-2000000000";
      description "Default value: -2000000000.";
    }
    leaf zzzTemporary2 {
      type int32;
      default "-2000000000";
      description "Default value: -2000000000.";
    }
    leaf zzzTemporary3 {
      type int32;
      default "-2000000000";
      description "Default value: -2000000000.";
    }
    leaf loadAwareImc {
      type boolean;
      default "false";
      description "Default value: false.";
    }
  }
  grouping UeProfile-attributes {
    leaf ueProfileId {
      type string;
      mandatory true;
    }
  }
  grouping UeProfileFilter-attributes {
    leaf-list spidList {
      type eytypes:int32_range_1-256;
      ordered-by user;
    }
    leaf ueProfileFilterId {
      type string;
      mandatory true;
    }
    leaf-list reservedBy {
      type string;
    }
    leaf t320 {
      type int32 {
        range "5 | 10 | 20 | 30 | 60 | 120 | 180";
      }
      default "30";
      units "minute";
      description "Default value: 30.";
    }
    leaf ueCapPrioAllowed {
      type boolean;
      default "false";
      description "Default value: false.";
    }
    leaf mobBackToNrFreqDisabled {
      type enumeration {
        enum NO_RESTRICTION;
        enum CONNECTED_MODE_MOBILITY;
        enum CONNECTED_IDLE_MODE_MOBILITY;
      }
    }
    leaf mobBackToNrFreqDisabledTime {
      type eytypes:int32_range_5-300;
      default "15";
      units "s";
      description "range 5..300; Default value: 15.";
    }
    leaf nrMobilityTrigQciAllAllowed {
      type boolean;
      default "false";
      description "Default value: false.";
    }
    leaf spidUeEnhLoadMgmtIncl {
      type boolean;
      default "false";
      description "Default value: false.";
    }
  }
  grouping UlCompGroup-attributes {
    leaf ulCompGroupId {
      type string;
      mandatory true;
    }
    leaf-list sectorCarrierRef {
      type string;
      min-elements 1;
    }
    leaf administrativeState {
      type enumeration {
        enum LOCKED;
        enum UNLOCKED;
        enum SHUTTINGDOWN;
      }
    }
    leaf-list availabilityStatus {
      type enumeration {
        enum IN_TEST;
        enum FAILED;
        enum POWER_OFF;
        enum OFF_LINE;
        enum OFF_DUTY;
        enum DEPENDENCY;
        enum DEGRADED;
        enum NOT_INSTALLED;
        enum LOG_FULL;
        enum DEPENDENCY_LOCKED;
        enum DEPENDENCY_FAILED;
        enum DEPENDENCY_SHUTTINGDOWN;
        enum DEPENDENCY_RECOVERY;
        enum DEPENDENCY_HOLDING;
      }
    }
    leaf operationalState {
      type enumeration {
        enum DISABLED;
        enum ENABLED;
      }
      config false;
    }
  }
  grouping UnlicensedAccessFunction-attributes {
    leaf laaMaxOccupancy {
      type int32 {
        range "4..20";
      }
      default "8";
      units "ms";
      description "range 4..20; Default value: 8.";
    }
    leaf laaDrsPeriodicity {
      type int32 {
        range "40 | 80 | 160";
      }
      default "40";
      units "ms";
      description "Default value: 40.";
    }
    leaf laaDrsOffset {
      type eytypes:int32_range_0-159;
      default "5";
      units "ms";
      description "range 0..159; Default value: 5.";
    }
    leaf unlicensedAccessFunctionId {
      type string;
      mandatory true;
    }
    leaf laaLbtSuccessRateThreshold {
      type int32 {
        range "10..90";
      }
      default "50";
      units "percent";
      description "range 10..90; Default value: 50.";
    }
    leaf laaChannelEvaluationTimer {
      type int32 {
        range "1..1500";
      }
      default "180";
      units "minutes";
      description "range 1..1500; Default value: 180.";
    }
    leaf laaLbtCheckTimer {
      type int32 {
        range "1..1800";
      }
      default "900";
      units "seconds";
      description "range 1..1800; Default value: 900.";
    }
    leaf laaMasterCarrierTimer {
      type int32 {
        range "1..60";
      }
      default "10";
      units "seconds";
      description "range 1..60; Default value: 10.";
    }
    leaf laaChannelSelectionType {
      type enumeration {
        enum STATIC_CHANNEL_SELECTION;
        enum DYNAMIC_CHANNEL_SELECTION;
      }
    }
    leaf laaSCellActDeactDataThres {
      type eytypes:int32_range_-1-5000;
      default "100";
      units "Number of DL subframes";
      description "range -1..5000; Default value: 100.";
    }
    leaf laaSCellActDeactDataThresHyst {
      type eytypes:int32_range_-1-5000;
      default "90";
      units "Number of DL subframes";
      description "range -1..5000; Default value: 90.";
    }
    leaf laaSCellActProhibitTimer {
      type eytypes:int32_range_0-5000-5;
      default "10";
      units "ms";
      description "range 0..5000; Default value: 10.";
    }
    leaf laaSCellDeactProhibitTimer {
      type eytypes:int32_range_0-5000-5;
      default "200";
      units "ms";
      description "range 0..5000; Default value: 200.";
    }
  }
  grouping UnlicensedBandProfile-attributes {
    leaf unlicensedBandProfileId {
      type string;
      mandatory true;
    }
    list unlicensedBandProfileList {
      key "id";
      leaf id {
        type uint32;
        description "Synthetic key for struct sequence entry.";
      }
      container attributes {
      leaf unlicensedBand {
        type enumeration {
          enum NONE;
          enum BAND_46A;
          enum BAND_46B;
          enum BAND_46C;
          enum BAND_46D;
        }
      }
      leaf unlicensedEarfcn {
        type enumeration {
          enum NONE;
          enum EARFCN_46890;
          enum EARFCN_47090;
          enum EARFCN_47290;
          enum EARFCN_47490;
          enum EARFCN_47690;
          enum EARFCN_47890;
          enum EARFCN_48090;
          enum EARFCN_48290;
          enum EARFCN_48490;
          enum EARFCN_48690;
          enum EARFCN_50090;
          enum EARFCN_50290;
          enum EARFCN_50490;
          enum EARFCN_50690;
          enum EARFCN_50890;
          enum EARFCN_51090;
          enum EARFCN_51290;
          enum EARFCN_51490;
          enum EARFCN_51690;
          enum EARFCN_51890;
          enum EARFCN_52090;
          enum EARFCN_52290;
          enum EARFCN_52490;
          enum EARFCN_52740;
          enum EARFCN_52940;
          enum EARFCN_53140;
          enum EARFCN_53340;
          enum EARFCN_53540;
          enum EARFCN_53740;
          enum EARFCN_53940;
          enum EARFCN_54140;
          enum EARFCN_54340;
        }
      }
      leaf channelCharacteristic {
        type enumeration {
          enum CHANNEL_DISABLED;
          enum CHANNEL_ENABLED;
        }
      }
      leaf maxUnlicensedTxPower {
        type int32 {
          range "0..40000";
        }
        default "0";
        units "mW";
        description "range 0..40000; Default value: 0.";
      }
      }
    }
    leaf-list reservedBy {
      type string;
    }
    leaf sectorEquipmentFunctionRef {
      type ietfinet:ip-address;
    }
  }
  grouping UnsupportedFreqProfile-attributes {
    leaf unsupportedFreqProfileId {
      type ietfinet:port-number;
      mandatory true;
    }
    list unsupportedFreqList {
      key "id";
      leaf id {
        type uint32;
        description "Synthetic key for struct sequence entry.";
      }
      container attributes {
      leaf earfcnDlLow {
        type int32;
        default "-1000";
        description "Default value: -1000.";
      }
      leaf earfcnDlHigh {
        type int32;
        default "-1000";
        description "Default value: -1000.";
      }
      }
    }
    leaf-list reservedBy {
      type string;
    }
  }
  grouping UserProfile-attributes {
    leaf userProfileId {
      type string;
      mandatory true;
    }
    leaf userProfileName {
      type string;
    }
    leaf-list spidList {
      type eytypes:int32_range_1-256;
    }
    list plmnList {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf-list arpList {
      type eytypes:int32_range_1-15-8;
    }
    leaf-list reservedBy {
      type string;
    }
  }
  grouping UtranCellRelation-attributes {
    leaf utranCellRelationId {
      type string;
      mandatory true;
    }
    leaf externalUtranCellFDDRef {
      type string;
      mandatory true;
    }
    leaf createdBy {
      type enumeration {
        enum OPERATOR;
        enum ANR;
      }
      config false;
    }
    leaf timeOfCreation {
      type string {
        length "0..19";
      }
      config false;
      description "length 0..19.";
    }
    leaf coverageIndicator {
      type enumeration {
        enum NONE;
        enum COVERS;
        enum OVERLAP;
        enum CONTAINED_IN;
      }
    }
    leaf isHoAllowed {
      type boolean;
      default "true";
      description "Default value: true.";
    }
    leaf isRemoveAllowed {
      type boolean;
      default "false";
      description "Default value: false.";
    }
    leaf lastModification {
      type enumeration {
        enum ANR_MODIFICATION;
        enum OPERATOR_MODIFICATION;
        enum NOT_MODIFIED;
        enum ANR_DELETE;
        enum OPERATOR_DELETE;
        enum LM_MODIFICATION;
      }
      config false;
    }
    leaf timeOfLastModification {
      type string {
        length "0..19";
      }
      config false;
      description "length 0..19.";
    }
    leaf loadBalancing {
      type enumeration {
        enum NOT_ALLOWED;
        enum OFFLOAD;
      }
    }
    leaf lbBnrAllowed {
      type boolean;
      default "true";
      description "Default value: true.";
    }
    leaf lbCovIndicated {
      type boolean;
      default "false";
      description "Default value: false.";
    }
    list mobilityStatus {
      config false;
      container attributes {
      leaf available {
        type string;
      }
      leaf reason {
        type string;
      }
      }
    }
    leaf pmHoPrepAttNonMob {
      type uint32;
      config false;
    }
    leaf pmHoPrepSuccNonMob {
      type uint32;
      config false;
    }
    leaf pmHoPrepAttSrvccExtIat {
      type uint32;
      config false;
    }
    leaf pmZtemporary37 {
      type uint32;
      config false;
    }
    leaf pmHoPrepCancelSrvccReest {
      type uint32;
      config false;
    }
    leaf pmHoPrepSucc {
      type uint32;
      config false;
    }
    leaf pmHoExeAttLb {
      type uint32;
      config false;
    }
    leaf pmHoPrepAttSrvcc {
      type uint32;
      config false;
    }
    leaf pmHoPrepAttLb {
      type uint32;
      config false;
    }
    leaf pmHoPrepAttCsfb {
      type uint32;
      config false;
    }
    leaf pmHoExeSuccCsfbEm {
      type uint32;
      config false;
    }
    leaf pmHoPrepSuccLb {
      type uint32;
      config false;
    }
    leaf pmHoPrepAttCsfbEm {
      type uint32;
      config false;
    }
    leaf pmHoExeSucc {
      type uint32;
      config false;
    }
    leaf pmHoPrepAttSrvccLb {
      type uint32;
      config false;
    }
    leaf pmLbQualifiedUe {
      type uint32;
      config false;
    }
    leaf pmAtoMeasRepUe {
      type uint32;
      config false;
    }
    leaf pmHoPrepCancelSrvcc {
      type uint32;
      config false;
    }
    leaf pmHoExeAttSrvcc {
      type uint32;
      config false;
    }
    leaf pmHoExeAtt {
      type uint32;
      config false;
    }
    leaf pmHoPrepSuccCsfbEm {
      type uint32;
      config false;
    }
    leaf pmAtoQualifiedUe {
      type uint32;
      config false;
    }
    leaf pmHoExeSuccCsfb {
      type uint32;
      config false;
    }
    leaf pmHoPrepSuccCsfb {
      type uint32;
      config false;
    }
    leaf pmLbMeasRepUe {
      type uint32;
      config false;
    }
    leaf pmHoExeSuccLb {
      type uint32;
      config false;
    }
    leaf pmHoExeSuccNonMob {
      type uint32;
      config false;
    }
    leaf pmHoExeAttCsfbEm {
      type uint32;
      config false;
    }
    leaf pmHoPrepAtt {
      type uint32;
      config false;
    }
    leaf pmHoPrepSuccSrvccLb {
      type uint32;
      config false;
    }
    leaf pmHoExeSuccSrvccLb {
      type uint32;
      config false;
    }
    leaf pmHoExeAttSrvccLb {
      type uint32;
      config false;
    }
    leaf pmHoExeAttNonMob {
      type uint32;
      config false;
    }
    leaf pmHoExeAttCsfb {
      type uint32;
      config false;
    }
    leaf pmHoExeCancelSrvcc {
      type uint32;
      config false;
    }
    leaf pmHoExeSuccSrvcc {
      type uint32;
      config false;
    }
    leaf pmHoPrepSuccSrvcc {
      type uint32;
      config false;
    }
  }
  grouping UtraNetwork-attributes {
    leaf utraNetworkId {
      type string;
      mandatory true;
    }
    leaf userLabel {
      type string {
        length "1..128";
      }
      description "length 1..128.";
    }
  }
  grouping UtranFreqRelation-attributes {
    leaf anrMeasOn {
      type boolean;
      default "true";
      description "Default value: true.";
    }
    leaf utranFreqRelationId {
      type string;
      mandatory true;
    }
    leaf userLabel {
      type string {
        length "1..128";
      }
      description "length 1..128.";
    }
    leaf utranFrequencyRef {
      type string;
      mandatory true;
    }
    leaf threshXHigh {
      type eytypes:int32_range_0-62-22;
      default "4";
      description "range 0..62; Default value: 4.";
    }
    leaf threshXLow {
      type eytypes:int32_range_0-62-22;
      default "0";
      description "range 0..62; Default value: 0.";
    }
    leaf qRxLevMin {
      type int32 {
        range "-119..-25";
      }
      default "-119";
      units "dBm";
      description "range -119..-25; Default value: -119.";
    }
    leaf pMaxUtra {
      type int32 {
        range "-50..33";
      }
      default "33";
      units "dBm";
      description "range -50..33; Default value: 33.";
    }
    leaf qQualMin {
      type eytypes:int32_range_-24-0;
      default "-18";
      units "dB";
      description "range -24..0; Default value: -18.";
    }
    leaf cellReselectionPriority {
      type eytypes:int32_range_0-7;
      default "6";
      description "range 0..7; Default value: 6.";
    }
    list allowedPlmnList {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf csFallbackPrio {
      type eytypes:int32_range_-1-7;
      default "0";
      description "range -1..7; Default value: 0.";
    }
    leaf connectedModeMobilityPrio {
      type eytypes:int32_range_-1-7;
      default "6";
      description "range -1..7; Default value: 6.";
    }
    leaf qOffsetFreq {
      type eytypes:int32_range_-15-15;
      default "0";
      units "dB";
      description "range -15..15; Default value: 0.";
    }
    leaf csFallbackPrioEC {
      type eytypes:int32_range_-1-7;
      default "0";
      description "range -1..7; Default value: 0.";
    }
    leaf mobilityAction {
      type enumeration {
        enum RELEASE_WITH_REDIRECT;
        enum RELEASE_WITH_REDIRECT_NACC;
        enum HANDOVER;
      }
    }
    leaf mobilityActionCsfb {
      type enumeration {
        enum RELEASE_WITH_REDIRECT;
        enum RELEASE_WITH_REDIRECT_NACC;
        enum HANDOVER;
      }
    }
    leaf threshXHighQ {
      type eytypes:int32_range_0-31;
      default "0";
      units "dB";
      description "range 0..31; Default value: 0.";
    }
    leaf threshXLowQ {
      type eytypes:int32_range_0-31;
      default "0";
      units "dB";
      description "range 0..31; Default value: 0.";
    }
    leaf voicePrio {
      type eytypes:int32_range_-1-7;
      default "0";
      description "range -1..7; Default value: 0.";
    }
    list utranFreqToQciProfileRelation {
      key "id";
      leaf id {
        type uint32;
        description "Synthetic key for struct sequence entry.";
      }
      container attributes {
      leaf lbUtranB1ThresholdRscpOffset {
        type eytypes:int32_range_0-24-29;
        default "0";
        units "dB";
        description "range 0..24; Default value: 0.";
      }
      leaf lbQciProfileHandling {
        type ietfinet:ip-address;
      }
      leaf qciProfileRef {
        type ietfinet:ip-address;
      }
      leaf b2Thr1RsrpUtraFreqQciOffset {
        type eytypes:int32_range_-100-100;
        default "0";
        units "dB";
        description "range -100..100; Default value: 0.";
      }
      leaf b2Thr1RsrqUtraFreqQciOffset {
        type eytypes:int32_range_-240-240;
        default "0";
        units "dB";
        description "range -240..240; Default value: 0.";
      }
      leaf b2Thr2EcNoUtraFreqQciOffset {
        type eytypes:int32_range_-50-50;
        default "0";
        units "dB";
        description "range -50..50; Default value: 0.";
      }
      leaf b2Thr2RscpUtraFreqQciOffset {
        type eytypes:int32_range_-24-24;
        default "0";
        units "dB";
        description "range -24..24; Default value: 0.";
      }
      leaf lbUtranB1ThresholdEcNoOffset {
        type eytypes:int32_range_0-50;
        default "0";
        units "dB";
        description "range 0..50; Default value: 0.";
      }
      leaf atoThresh1QciProfileHandling {
        type ietfinet:ip-address;
      }
      leaf atoThresh2QciProfileHandling {
        type ietfinet:ip-address;
      }
      }
    }
    leaf lbBnrPolicy {
      type enumeration {
        enum NOT_ALLOWED;
        enum OFFLOAD_ONLY;
      }
    }
    leaf maxNrUtranCellRelations {
      type int32 {
        range "0..64";
      }
      config false;
      description "range 0..64.";
    }
    leaf altCsfbTargetPrio {
      type eytypes:int32_range_-1-7;
      default "0";
      description "range -1..7; Default value: 0.";
    }
    leaf altCsfbTargetPrioEc {
      type eytypes:int32_range_-1-7;
      default "0";
      description "range -1..7; Default value: 0.";
    }
    leaf b2Thr1RsrpUtraFreqOffset {
      type eytypes:int32_range_-100-100;
      default "0";
      units "dB";
      description "range -100..100; Default value: 0.";
    }
    leaf b2Thr1RsrqUtraFreqOffset {
      type eytypes:int32_range_-240-240;
      default "0";
      units "dB";
      description "range -240..240; Default value: 0.";
    }
    leaf b2Thr2EcNoUtraFreqOffset {
      type eytypes:int32_range_-50-50;
      default "0";
      units "dB";
      description "range -50..50; Default value: 0.";
    }
    leaf b2Thr2RscpUtraFreqOffset {
      type eytypes:int32_range_-24-24;
      default "0";
      units "dB";
      description "range -24..24; Default value: 0.";
    }
    leaf atoAllowed {
      type boolean;
      default "false";
      description "Default value: false.";
    }
    list b2UtranOffsetPerPC {
      key "id";
      leaf id {
        type uint32;
        description "Synthetic key for struct sequence entry.";
      }
      container attributes {
      leaf powerClass {
        type enumeration {
          enum PC_1;
          enum PC_2;
        }
      }
      leaf b2Thr1RsrpUtranPCOffset {
        type eytypes:int32_range_-100-100;
        default "0";
        units "dB";
        description "range -100..100; Default value: 0.";
      }
      leaf b2Thr1RsrqUtranPCOffset {
        type eytypes:int32_range_-240-240;
        default "0";
        units "dB";
        description "range -240..240; Default value: 0.";
      }
      }
    }
    leaf pmLbMeasuredUe {
      type uint32;
      config false;
    }
    leaf pmZtemporary106 {
      type uint32;
      config false;
    }
    leaf pmZtemporary107 {
      type uint32;
      config false;
    }
    leaf pmAtoMeasuredUe {
      type uint32;
      config false;
    }
  }
  grouping UtranFrequency-attributes {
    leaf utranFrequencyId {
      type string;
      mandatory true;
    }
    leaf-list reservedBy {
      type string;
    }
    leaf userLabel {
      type string {
        length "1..128";
      }
      description "length 1..128.";
    }
    leaf arfcnValueUtranDl {
      type eytypes:int32_range_0-16383;
      mandatory true;
      description "range 0..16383.";
    }
  }
  grouping UtranTDDFreqRelation-attributes {
    leaf utranTDDFreqRelationId {
      type string;
      mandatory true;
    }
    leaf userLabel {
      type string {
        length "1..128";
      }
      description "length 1..128.";
    }
    leaf utranFrequencyRef {
      type string;
    }
    leaf cellReselectionPriority {
      type eytypes:int32_range_0-7;
      default "6";
      description "range 0..7; Default value: 6.";
    }
    leaf threshXHigh {
      type eytypes:int32_range_0-62;
      default "4";
      units "dB";
      description "range 0..62; Default value: 4.";
    }
    leaf threshXLow {
      type eytypes:int32_range_0-62;
      default "0";
      units "dB";
      description "range 0..62; Default value: 0.";
    }
    leaf qRxLevMin {
      type int32 {
        range "-119..-25";
      }
      default "-119";
      units "dBm";
      description "range -119..-25; Default value: -119.";
    }
    leaf pMaxUtra {
      type int32 {
        range "-50..33";
      }
      default "33";
      units "dBm";
      description "range -50..33; Default value: 33.";
    }
    list allowedPlmnList {
      key "id";
      leaf id {
        type uint32;
        description "Synthetic key for struct sequence entry.";
      }
      container attributes {
      leaf mcc {
        type eytypes:int32_range_0-999;
        description "range 0..999.";
      }
      leaf mnc {
        type eytypes:int32_range_0-999;
        description "range 0..999.";
      }
      leaf mncLength {
        type eytypes:int32_range_2-3;
        description "range 2..3.";
      }
      }
    }
    leaf connectedModeMobilityPrio {
      type eytypes:int32_range_-1-7;
      default "6";
      description "range -1..7; Default value: 6.";
    }
    leaf csFallbackPrio {
      type eytypes:int32_range_-1-7;
      default "0";
      description "range -1..7; Default value: 0.";
    }
    leaf csFallbackPrioEC {
      type eytypes:int32_range_-1-7;
      default "0";
      description "range -1..7; Default value: 0.";
    }
    leaf qOffsetFreq {
      type eytypes:int32_range_-15-15;
      default "0";
      units "dB";
      description "range -15..15; Default value: 0.";
    }
    leaf mobilityAction {
      type enumeration {
        enum RELEASE_WITH_REDIRECT;
        enum RELEASE_WITH_REDIRECT_NACC;
        enum HANDOVER;
      }
    }
    leaf mobilityActionCsfb {
      type enumeration {
        enum RELEASE_WITH_REDIRECT;
        enum RELEASE_WITH_REDIRECT_NACC;
        enum HANDOVER;
      }
    }
    leaf anrMeasOn {
      type boolean;
      default "true";
      description "Default value: true.";
    }
    leaf b2Thr1RsrpUtraFreqOffset {
      type eytypes:int32_range_-100-100;
      default "0";
      units "dB";
      description "range -100..100; Default value: 0.";
    }
    leaf b2Thr1RsrqUtraFreqOffset {
      type eytypes:int32_range_-240-240;
      default "0";
      units "dB";
      description "range -240..240; Default value: 0.";
    }
    leaf b2Thr2RscpUtraFreqOffset {
      type eytypes:int32_range_-24-24;
      default "0";
      units "dB";
      description "range -24..24; Default value: 0.";
    }
    list qciB2ThrOffsets {
      key "id";
      leaf id {
        type uint32;
        description "Synthetic key for struct sequence entry.";
      }
      container attributes {
      leaf lbUtranB1ThresholdRscpOffset {
        type eytypes:int32_range_0-24-29;
        default "0";
        units "dB";
        description "range 0..24; Default value: 0.";
      }
      leaf lbQciProfileHandling {
        type ietfinet:ip-address;
      }
      leaf qciProfileRef {
        type ietfinet:ip-address;
      }
      leaf b2Thr1RsrpUtraFreqQciOffset {
        type eytypes:int32_range_-100-100;
        default "0";
        units "dB";
        description "range -100..100; Default value: 0.";
      }
      leaf b2Thr1RsrqUtraFreqQciOffset {
        type eytypes:int32_range_-240-240;
        default "0";
        units "dB";
        description "range -240..240; Default value: 0.";
      }
      leaf b2Thr2EcNoUtraFreqQciOffset {
        type eytypes:int32_range_-50-50;
        default "0";
        units "dB";
        description "range -50..50; Default value: 0.";
      }
      leaf b2Thr2RscpUtraFreqQciOffset {
        type eytypes:int32_range_-24-24;
        default "0";
        units "dB";
        description "range -24..24; Default value: 0.";
      }
      leaf lbUtranB1ThresholdEcNoOffset {
        type eytypes:int32_range_0-50;
        default "0";
        units "dB";
        description "range 0..50; Default value: 0.";
      }
      leaf atoThresh1QciProfileHandling {
        type ietfinet:ip-address;
      }
      leaf atoThresh2QciProfileHandling {
        type ietfinet:ip-address;
      }
      }
    }
  }
  grouping WakeUpFreqPriority-attributes {
    leaf wakeUpFreqPriorityId {
      type string;
      mandatory true;
    }
    leaf-list reservedBy {
      type string;
    }
    leaf eutranFrequencyRef {
      type string;
      mandatory true;
    }
    leaf wakeUpPriority {
      type eytypes:int32_range_0-7;
      default "0";
      description "range 0..7; Default value: 0.";
    }
  }
}
